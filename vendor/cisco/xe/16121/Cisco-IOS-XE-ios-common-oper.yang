module Cisco-IOS-XE-ios-common-oper {
  yang-version 1;
  namespace "http://cisco.com/ns/yang/Cisco-IOS-XE-ios-common-oper";
  prefix ios-common-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for some common IOS structures
     Copyright (c) 2018-2019 by Cisco Systems, Inc.
     All rights reserved.";

  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2018-01-04 {
    description
      "Initial revision";
    reference "1.0.0";
    cisco-semver:module-version "1.0.0";
  }

  typedef ios-snpa-type {
    type enumeration {
      enum "ios-snpa-type-illegal" {
        value 0;
        description
          "illegal address";
      }
      enum "ios-snpa-type-ieee48" {
        value 1;
        description
          "48bit IEEE 802.X address";
      }
      enum "ios-snpa-type-ieee16" {
        value 2;
        description
          "16bit IEEE 802.X address";
      }
      enum "ios-snpa-type-xerox" {
        value 3;
        description
          "Xerox 3MB experimental ether";
      }
      enum "ios-snpa-type-x121" {
        value 4;
        description
          "CCITT X.121 address";
      }
      enum "ios-snpa-type-cisco-hdlc" {
        value 5;
        description
          "cisco HDLC framing";
      }
      enum "ios-snpa-type-cisco-mlapb" {
        value 6;
        description
          "cisco multi-LAPB framing";
      }
      enum "ios-snpa-type-lapb" {
        value 7;
        description
          "ISO/CCITT LAPB framing";
      }
      enum "ios-snpa-type-smds48" {
        value 8;
        description
          "SMDS with 48 bit addresses";
      }
      enum "ios-snpa-type-cisco-msdlc" {
        value 9;
        description
          "cisco multi-SDLC framing";
      }
      enum "ios-snpa-type-fr10" {
        value 10;
        description
          "Frame Relay with 10-bit DLCI";
      }
      enum "ios-snpa-type-ultra" {
        value 11;
        description
          "CCCI defined Ultranet";
      }
      enum "ios-snpa-type-cisco-tunnel" {
        value 12;
        description
          "cisco tunnel and EON encoding";
      }
      enum "ios-snpa-type-cisco-ctunnel" {
        value 13;
        description
          "CLNP tunnel";
      }
      enum "ios-snpa-type-rrr-tunnel" {
        value 14;
        description
          "rrr tunnel";
      }
      enum "ios-snpa-type-ppp" {
        value 15;
        description
          "PPP framing";
      }
      enum "ios-snpa-type-smds64" {
        value 16;
        description
          "SMDS 64-bit addressing";
      }
      enum "ios-snpa-type-atmvc" {
        value 17;
        description
          "AIP VC no.";
      }
      enum "ios-snpa-type-atm-bundle" {
        value 18;
        description
          "ATM PVC bundle";
      }
      enum "ios-snpa-type-atm-svc-bundle" {
        value 19;
        description
          "ATM SVC bundle";
      }
      enum "ios-snpa-type-atmnsap" {
        value 20;
        description
          "ATM NSAP address";
      }
      enum "ios-snpa-type-atm-e164" {
        value 21;
        description
          "ATM E164 address";
      }
      enum "ios-snpa-type-atm-userspecified" {
        value 22;
        description
          "ATM User Specified address";
      }
      enum "ios-snpa-type-sdlc" {
        value 23;
        description
          "SDLC address";
      }
      enum "ios-snpa-type-x25pvc" {
        value 24;
        description
          "X.25 Lci fpr PVC's";
      }
      enum "ios-snpa-type-lapd" {
        value 25;
        description
          "LAPD framing";
      }
      enum "ios-snpa-type-masked-atmnsap" {
        value 26;
        description
          "masked ATM NSAP address";
      }
      enum "ios-snpa-type-atmesi" {
        value 27;
        description
          "ATM ESI address";
      }
      enum "ios-snpa-type-slip" {
        value 28;
        description
          "SLIP Framing";
      }
      enum "ios-snpa-type-routedesc" {
        value 29;
        description
          "route descriptor for TR LANE";
      }
      enum "ios-snpa-type-srp-outer" {
        value 30;
        description
          "48bit SRP address on outer ring";
      }
      enum "ios-snpa-type-srp-inner" {
        value 31;
        description
          "48bit SRP address on inner ring";
      }
    }
    description
      "SNPA Type";
  }

  typedef ios-encaps-type {
    type enumeration {
      enum "ios-encaps-type-null" {
        value 0;
        description
          "undefined -- error";
      }
      enum "ios-encaps-type-arpa" {
        value 1;
        description
          "Ethernet - DDN style";
      }
      enum "ios-encaps-type-sap" {
        value 2;
        description
          "Ethernet";
      }
      enum "ios-encaps-type-snap" {
        value 3;
        description
          "802.2 SNAP types";
      }
      enum "ios-encaps-type-1822" {
        value 4;
        description
          "DDN - 1822 (obsolete)";
      }
      enum "ios-encaps-type-hdlc" {
        value 5;
        description
          "Serial - raw HDLC";
      }
      enum "ios-encaps-type-unused2" {
        value 6;
        description
          "Unused Placeholder (3MB)";
      }
      enum "ios-encaps-type-unused1" {
        value 7;
        description
          "Unused Placeholder (HDH)";
      }
      enum "ios-encaps-type-lapb" {
        value 8;
        description
          "Serial - LAPB";
      }
      enum "ios-encaps-type-x25" {
        value 9;
        description
          "Serial - X.25";
      }
      enum "ios-encaps-type-hub" {
        value 10;
        description
          "HUB fiber optic";
      }
      enum "ios-encaps-type-novell-ether" {
        value 11;
        description
          "Novell style XNS on Ethernet";
      }
      enum "ios-encaps-type-unsupported" {
        value 12;
        description
          "Unsupported protocols";
      }
      enum "ios-encaps-type-3com-tr" {
        value 13;
        description
          "3Com XNS over TR 802.2 0x80";
      }
      enum "ios-encaps-type-ub-tr" {
        value 14;
        description
          "Ungermann-Bass XNS over TR SNAP";
      }
      enum "ios-encaps-type-apollo" {
        value 15;
        description
          "Apollo domain packets";
      }
      enum "ios-encaps-type-ppp" {
        value 16;
        description
          "Serial PPP";
      }
      enum "ios-encaps-type-unused4" {
        value 17;
        description
          "Unused Placeholder (ISO3)";
      }
      enum "ios-encaps-type-vines-tr" {
        value 18;
        description
          "ISO1 with Vines demux byte";
      }
      enum "ios-encaps-type-ethertalk" {
        value 19;
        description
          "AppleTalk phase 1 on ethernet";
      }
      enum "ios-encaps-type-frame-relay" {
        value 20;
        description
          "Frame Relay";
      }
      enum "ios-encaps-type-smds" {
        value 21;
        description
          "Switched Multimegabit Data Service (SMDS)";
      }
      enum "ios-encaps-type-mac" {
        value 22;
        description
          "MAC level packets";
      }
      enum "ios-encaps-type-ultra-iso2" {
        value 23;
        description
          "Ultranet";
      }
      enum "ios-encaps-type-ultra-iso1" {
        value 24;
        description
          "Ultranet-Hello";
      }
      enum "ios-encaps-type-stun" {
        value 25;
        description
          "Serial - serial tunnelling";
      }
      enum "ios-encaps-type-bridge" {
        value 26;
        description
          "Packet in bridge encapsulation";
      }
      enum "ios-encaps-type-llc2" {
        value 27;
        description
          "LLC 2";
      }
      enum "ios-encaps-type-sdlcp" {
        value 28;
        description
          "Serial - SDLC (primary)";
      }
      enum "ios-encaps-type-sdlcs" {
        value 29;
        description
          "Serial - SDLC (secondary)";
      }
      enum "ios-encaps-type-slip" {
        value 30;
        description
          "Async SLIP encapsulation";
      }
      enum "ios-encaps-type-tunnel" {
        value 31;
        description
          "Standard Tunnel Interface";
      }
      enum "ios-encaps-type-bridge-encaps" {
        value 32;
        description
          "Bridge encapsulation";
      }
      enum "ios-encaps-type-atm" {
        value 33;
        description
          "ATM interface encapsulation";
      }
      enum "ios-encaps-type-atm-dxi" {
        value 34;
        description
          "ATM DXI implementation";
      }
      enum "ios-encaps-type-fr-ietf" {
        value 35;
        description
          "Frame Relay with IETF encapsulation";
      }
      enum "ios-encaps-type-smds-dxi" {
        value 36;
        description
          "SMDS DXI implementation";
      }
      enum "ios-encaps-type-atm-dxi-ietf" {
        value 37;
        description
          "atm-dxi with IETF encapsulation";
      }
      enum "ios-encaps-type-channel" {
        value 38;
        description
          "IBM Channel";
      }
      enum "ios-encaps-type-sdlc" {
        value 39;
        description
          "CLSI compliant SDLC";
      }
      enum "ios-encaps-type-sde" {
        value 40;
        description
          "802.10 Secure Data Exchange";
      }
      enum "ios-encaps-type-bstun" {
        value 41;
        description
          "block serial tunnel";
      }
      enum "ios-encaps-type-dialer" {
        value 42;
        description
          "Dialer encapsulation";
      }
      enum "ios-encaps-type-novell-fddi" {
        value 43;
        description
          "Novell style XNS on FDDI";
      }
      enum "ios-encaps-type-v120" {
        value 44;
        description
          "V120 ISDN->ASYNC encapsulation";
      }
      enum "ios-encaps-type-isl" {
        value 45;
        description
          "Inter Switch Link - vLANs on FEIP";
      }
      enum "ios-encaps-type-loop" {
        value 46;
        description
          "loopback interface";
      }
      enum "ios-encaps-type-channel-ilan" {
        value 47;
        description
          "IBM Channel internal LAN";
      }
      enum "ios-encaps-type-serial-autodetect" {
        value 48;
        description
          "Autodetected for Serials";
      }
      enum "ios-encaps-type-cpp" {
        value 49;
        description
          "Combinet proprietary protocol";
      }
      enum "ios-encaps-type-ndlc" {
        value 50;
        description
          "NCIA DLC";
      }
      enum "ios-encaps-type-lapd" {
        value 51;
        description
          "ISDN Q.921";
      }
      enum "ios-encaps-type-ftc-trunk" {
        value 52;
        description
          "StrataCom IPX/Fastpad protocol";
      }
      enum "ios-encaps-type-atmces-t1" {
        value 53;
        description
          "ATM T1 Circuit Emulation.";
      }
      enum "ios-encaps-type-atmces-e1" {
        value 54;
        description
          "ATM E1 Circuit Emulation.";
      }
      enum "ios-encaps-type-voice" {
        value 55;
        description
          "Packetized Voice";
      }
      enum "ios-encaps-type-alc" {
        value 56;
        description
          "ALC (P1024B) sync protocol";
      }
      enum "ios-encaps-type-uts" {
        value 57;
        description
          "UTS (P1024C) sync protocol";
      }
      enum "ios-encaps-type-trisl" {
        value 58;
        description
          "Token Ring Inter-Switch Link (TRISL)";
      }
      enum "ios-encaps-type-mcns" {
        value 59;
        description
          "Cable - MCNS";
      }
      enum "ios-encaps-type-atmces" {
        value 60;
        description
          "ATM circuit emulation service";
      }
      enum "ios-encaps-type-trans" {
        value 61;
        description
          "for transparent mode";
      }
      enum "ios-encaps-type-clear-channel" {
        value 62;
        description
          "TDM clear channel";
      }
      enum "ios-encaps-type-tc-atm" {
        value 63;
        description
          "Tag Controlled ATM interface";
      }
      enum "ios-encaps-type-fr-ppp" {
        value 64;
        description
          "PPP over Frame Relay";
      }
      enum "ios-encaps-type-dot1q" {
        value 65;
        description
          "IEEE 802.1Q";
      }
      enum "ios-encaps-type-funi" {
        value 66;
        description
          "Frame based user network interface";
      }
      enum "ios-encaps-type-lapbta" {
        value 67;
        description
          "LAPB terminal adapter";
      }
      enum "ios-encaps-type-docsis" {
        value 68;
        description
          "Cable Modem";
      }
      enum "ios-encaps-type-np-inband" {
        value 69;
        description
          "NextPort DSP modem in-band message";
      }
      enum "ios-encaps-type-ss7-mtp2" {
        value 70;
        description
          "SS7 MTP-2 over serial/TDM interface";
      }
      enum "ios-encaps-type-gtp" {
        value 71;
        description
          "General Packet Radio Service (GPRS)";
      }
      enum "ios-encaps-type-isl-switchport" {
        value 72;
        description
          "ISL SW encapsulation packet sent on switch port";
      }
      enum "ios-encaps-type-srp" {
        value 73;
        description
          "Spatial Reuse Protocol";
      }
      enum "ios-encaps-type-ppp-etype" {
        value 74;
        description
          "PPP hdr with Ethertype protocol type";
      }
      enum "ios-encaps-type-atm-ppp" {
        value 75;
        description
          "PPP over ATM";
      }
      enum "ios-encaps-type-mfr" {
        value 76;
        description
          "Multilink Frame Relay";
      }
      enum "ios-encaps-type-srp2" {
        value 77;
        description
          "SRP version 2";
      }
      enum "ios-encaps-type-fr-extended" {
        value 78;
        description
          "Frame Relay extended addressing";
      }
      enum "ios-encaps-type-pppoe" {
        value 79;
        description
          "PPP Over Ethernet";
      }
      enum "ios-encaps-type-ouni-sdcc" {
        value 80;
        description
          "OIF UNI SDCC per OIF2000.125";
      }
      enum "ios-encaps-type-multiservice" {
        value 81;
        description
          "encapsulation type for multiservice interface";
      }
      enum "ios-encaps-type-container" {
        value 82;
        description
          "Container";
      }
      enum "ios-encaps-type-dot1ad" {
        value 83;
        description
          "Dot1ad ether type";
      }
      enum "ios-encaps-type-cem" {
        value 84;
        description
          "Circuit Emulation Type";
      }
      enum "ios-encaps-type-dot1ah" {
        value 85;
        description
          "IEEE 802.1ah Ether type";
      }
      enum "ios-encaps-type-ptp" {
        value 86;
        description
          "PTP type";
      }
      enum "ios-encaps-type-ssl" {
        value 87;
        description
          "For SSLVPN";
      }
      enum "ios-encaps-type-lisp" {
        value 88;
        description
          "Locator/ID Separation Protocol (LISP)";
      }
      enum "ios-encaps-type-dsp-spa" {
        value 89;
        description
          "DSP-based SPA";
      }
      enum "ios-encaps-type-t101" {
        value 90;
        description
          "IEC-60870-5-101 for Async Serial interface";
      }
      enum "ios-encaps-type-crypto" {
        value 91;
        description
          "Crypto";
      }
      enum "ios-encaps-type-rawtcp" {
        value 92;
        description
          "Raw socket TCP for Async line interface";
      }
      enum "ios-encaps-type-async" {
        value 93;
        description
          "Async line raw data";
      }
      enum "ios-encaps-type-cmd" {
        value 94;
        description
          "Cisco Meta Data (CMD) EtherType=0x8909 encapsulation";
      }
      enum "ios-encaps-type-scada" {
        value 95;
        description
          "SCADA for Async Serial Interface";
      }
      enum "ios-encaps-type-rawudp" {
        value 96;
        description
          "Raw socket UDP for Async line interface";
      }
      enum "ios-encaps-type-relay-line" {
        value 97;
        description
          "Line relay for Async line interface";
      }
      enum "ios-encaps-type-rawmpls" {
        value 98;
        description
          "Raw socket over MPLS for Async line interface
           Market want to call it trans. It's a little conflict
           TRANSPARENT";
      }
      enum "ios-encaps-type-arpa-nid" {
        value 99;
        description
          "if NID added after ARPA we add a new type";
      }
    }
    description
      "Encapsulation Type";
  }

  typedef ios-linktype {
    type enumeration {
      enum "ios-linktype-illegal" {
        value 0;
        description
          "invalid link type";
      }
      enum "ios-linktype-arp" {
        value 1;
        description
          "IP ARP";
      }
      enum "ios-linktype-rarp" {
        value 2;
        description
          "Reverse ARP";
      }
      enum "ios-linktype-xarp" {
        value 3;
        description
          "Xerox ARP";
      }
      enum "ios-linktype-probe" {
        value 4;
        description
          "HP's 802 version of ARP";
      }
      enum "ios-linktype-loop" {
        value 5;
        description
          "Ethernet loopback";
      }
      enum "ios-linktype-address" {
        value 6;
        description
          "cisco Systems Serial ARP";
      }
      enum "ios-linktype-ip" {
        value 7;
        description
          "Internet Protocol (IP)";
      }
      enum "ios-linktype-pup" {
        value 8;
        description
          "Xerox PARC Universal Protocol (PUP)";
      }
      enum "ios-linktype-9-unused" {
        value 9;
        description
          "Available Unused Slot";
      }
      enum "ios-linktype-xns" {
        value 10;
        description
          "XNS protocol (Xerox original)";
      }
      enum "ios-linktype-novell" {
        value 11;
        description
          "Novell IPX";
      }
      enum "ios-linktype-apollo" {
        value 12;
        description
          "Apollo Domain";
      }
      enum "ios-linktype-vines" {
        value 13;
        description
          "Banyan Vines IP";
      }
      enum "ios-linktype-pad" {
        value 14;
        description
          "X.2[89] PAD protocol";
      }
      enum "ios-linktype-x25" {
        value 15;
        description
          "X.25 for purists";
      }
      enum "ios-linktype-appletalk" {
        value 16;
        description
          "AppleTalk - Extended DDP";
      }
      enum "ios-linktype-aarp" {
        value 17;
        description
          "Appletalk ARP";
      }
      enum "ios-linktype-dec-spanning" {
        value 18;
        description
          "DEC spanning tree";
      }
      enum "ios-linktype-ieee-spanning" {
        value 19;
        description
          "IEEE spanning tree BPDU";
      }
      enum "ios-linktype-nbf" {
        value 20;
        description
          "NBF NetBios Frames";
      }
      enum "ios-linktype-21-unused" {
        value 21;
        description
          "Unused Link Type";
      }
      enum "ios-linktype-decnet" {
        value 22;
        description
          "DECnet Phase IV node unicast";
      }
      enum "ios-linktype-decnet-router-l1" {
        value 23;
        description
          "(Old) DECnet PhaseIV router multicast";
      }
      enum "ios-linktype-decnet-node" {
        value 24;
        description
          "DECnet Phase IV node multicast";
      }
      enum "ios-linktype-clns" {
        value 25;
        description
          "OSI 8473 ES-IS 9542, etc.";
      }
      enum "ios-linktype-clns-all-es" {
        value 26;
        description
          "ES-IS Multicast - all end systems";
      }
      enum "ios-linktype-clns-all-is" {
        value 27;
        description
          "ES-IS Multicast - all intermed.";
      }
      enum "ios-linktype-clns-bcast" {
        value 28;
        description
          "CLNS & ES-IS Broadcasts";
      }
      enum "ios-linktype-xot" {
        value 29;
        description
          "X.25 over TCP";
      }
      enum "ios-linktype-ppp" {
        value 30;
        description
          "Protocol PPP";
      }
      enum "ios-linktype-lat" {
        value 31;
        description
          "DEC LAT terminal protocol";
      }
      enum "ios-linktype-vines-echo" {
        value 32;
        description
          "Banyan Vines Echo Protocol";
      }
      enum "ios-linktype-vines-loop" {
        value 33;
        description
          "Banyan Vines Loopback Protocol";
      }
      enum "ios-linktype-atalk-short" {
        value 34;
        description
          "AppleTalk short DDP";
      }
      enum "ios-linktype-mop-boot" {
        value 35;
        description
          "DEC MOP booting protocol";
      }
      enum "ios-linktype-mop-console" {
        value 36;
        description
          "DEC MOP console protocol";
      }
      enum "ios-linktype-rsrb" {
        value 37;
        description
          "RSRB raw";
      }
      enum "ios-linktype-bridge" {
        value 38;
        description
          "transparent bridge traffic";
      }
      enum "ios-linktype-stun" {
        value 39;
        description
          "Stunnel";
      }
      enum "ios-linktype-fr-arp" {
        value 40;
        description
          "Frame Relay";
      }
      enum "ios-linktype-smds-arp" {
        value 41;
        description
          "SMDS own ARP";
      }
      enum "ios-linktype-mac" {
        value 42;
        description
          "MAC packets";
      }
      enum "ios-linktype-ibmnm" {
        value 43;
        description
          "IBM Network Management packets";
      }
      enum "ios-linktype-uarp" {
        value 44;
        description
          "Ultranet";
      }
      enum "ios-linktype-ultra-hello" {
        value 45;
        description
          "Ultranet";
      }
      enum "ios-linktype-x25service" {
        value 46;
        description
          "X.25 services";
      }
      enum "ios-linktype-uncompressed-tcp" {
        value 47;
        description
          "Uncompressed TCP/IP";
      }
      enum "ios-linktype-compressed-tcp" {
        value 48;
        description
          "Compressed TCP/IP";
      }
      enum "ios-linktype-llc2" {
        value 49;
        description
          "LLC type II";
      }
      enum "ios-linktype-cmns" {
        value 50;
        description
          "CMNS--X.25 over non-serial media";
      }
      enum "ios-linktype-isis-all-l1-is" {
        value 51;
        description
          "ISIS - All Level 1 ISes";
      }
      enum "ios-linktype-isis-all-l2-is" {
        value 52;
        description
          "ISIS - All Level 2 ISes";
      }
      enum "ios-linktype-fr-switch" {
        value 53;
        description
          "FR switching over IP tunnel";
      }
      enum "ios-linktype-decnet-prime-router" {
        value 54;
        description
          "Ph-IV Prime all routers";
      }
      enum "ios-linktype-srb" {
        value 55;
        description
          "source route bridge traffic";
      }
      enum "ios-linktype-qllc" {
        value 56;
        description
          "qllc (SNA over X.25)";
      }
      enum "ios-linktype-x25-multi-enc" {
        value 57;
        description
          "X.25 multiprotocol encapsulation";
      }
      enum "ios-linktype-lex" {
        value 58;
        description
          "Lan Extension Protocol";
      }
      enum "ios-linktype-lex-rcmd" {
        value 59;
        description
          "Lex-NCP + LEX Remote commands";
      }
      enum "ios-linktype-decnet-router-l2" {
        value 60;
        description
          "DECnet PhaseIV L2 router multcast";
      }
      enum "ios-linktype-cls" {
        value 61;
        description
          "Frames from RSRB vring->CLS vring";
      }
      enum "ios-linktype-snapshot" {
        value 62;
        description
          "Start dialing, don't send frame";
      }
      enum "ios-linktype-dlsw" {
        value 63;
        description
          "Data Link Switching traffic";
      }
      enum "ios-linktype-sde" {
        value 64;
        description
          "802.10 Secure Data Exchange";
      }
      enum "ios-linktype-cdp" {
        value 65;
        description
          "Cisco Discovery Protocol";
      }
      enum "ios-linktype-ppp-compression" {
        value 66;
        description
          "Compression Control Protocol PPP";
      }
      enum "ios-linktype-nmp" {
        value 67;
        description
          "Local LNM packet traffic";
      }
      enum "ios-linktype-bstun" {
        value 68;
        description
          "block serial tunnel";
      }
      enum "ios-linktype-ipc" {
        value 69;
        description
          "Out-of-band IPC";
      }
      enum "ios-linktype-love" {
        value 70;
        description
          "CIP statistics";
      }
      enum "ios-linktype-cfgack" {
        value 71;
        description
          "CIP asynchronous cfg acks";
      }
      enum "ios-linktype-appn-anr" {
        value 72;
        description
          "APPN HPR ANR traffic";
      }
      enum "ios-linktype-multilink" {
        value 73;
        description
          "Multilink protocol";
      }
      enum "ios-linktype-nhrp" {
        value 74;
        description
          "Next Hop Resolution Protocol (NHRP)";
      }
      enum "ios-linktype-mac-exp" {
        value 75;
        description
          "MAC frames are express buffered";
      }
      enum "ios-linktype-cgmp" {
        value 76;
        description
          "Cisco Group Management Protocol";
      }
      enum "ios-linktype-vtp" {
        value 77;
        description
          "Cisco VLAN Transport Protocol";
      }
      enum "ios-linktype-cpp" {
        value 78;
        description
          "Combinet proprietary encapsulation";
      }
      enum "ios-linktype-ipv6" {
        value 79;
        description
          "IP version 6";
      }
      enum "ios-linktype-atm" {
        value 80;
        description
          "Asynchronous Transfer Mode (ATM)";
      }
      enum "ios-linktype-isl" {
        value 81;
        description
          "Cisco Inter Switch Link";
      }
      enum "ios-linktype-bap" {
        value 82;
        description
          "Bandwidth Allocation Protocol";
      }
      enum "ios-linktype-compressed-rtp" {
        value 83;
        description
          "Compressed RTP-UDP-IP";
      }
      enum "ios-linktype-compressed-udp" {
        value 84;
        description
          "Compressed UDP-IP";
      }
      enum "ios-linktype-uncompressed-udp" {
        value 85;
        description
          "Uncompressed RTP-UDP-IP";
      }
      enum "ios-linktype-context-status" {
        value 86;
        description
          "RTP context error";
      }
      enum "ios-linktype-fr-switch-serial" {
        value 87;
        description
          "FR switching over serial line
           internal packet identification only";
      }
      enum "ios-linktype-c5-ibipc" {
        value 88;
        description
          "Cat5k inband ipc";
      }
      enum "ios-linktype-nlsp-multicast" {
        value 89;
        description
          "NLSP multicast hello/update";
      }
      enum "ios-linktype-tag" {
        value 90;
        description
          "Tag switched packet";
      }
      enum "ios-linktype-mtag" {
        value 91;
        description
          "Multicast TAG (MTAG)";
      }
      enum "ios-linktype-alps" {
        value 92;
        description
          "Airline Protocol Support";
      }
      enum "ios-linktype-drip" {
        value 93;
        description
          "Cisco DRIP";
      }
      enum "ios-linktype-voice" {
        value 94;
        description
          "Voice over ATM";
      }
      enum "ios-linktype-fr-atm" {
        value 95;
        description
          "FR-ATM network interworking";
      }
      enum "ios-linktype-fcp" {
        value 96;
        description
          "layer3 switching on earl2";
      }
      enum "ios-linktype-voice-no-rt" {
        value 97;
        description
          "Non real time voice";
      }
      enum "ios-linktype-vlan-br-spanning" {
        value 98;
        description
          "VLAN Bridge spanning tree BPDU";
      }
      enum "ios-linktype-dot1q" {
        value 99;
        description
          "IEEE 802.1Q";
      }
      enum "ios-linktype-cisco-ipc" {
        value 100;
        description
          "cisco ipc msg.";
      }
      enum "ios-linktype-vsi" {
        value 101;
        description
          "Cisco VSI Protocol";
      }
      enum "ios-linktype-isdn-manual-call" {
        value 102;
        description
          "for manual ISDN call";
      }
      enum "ios-linktype-comp-non-tcp" {
        value 103;
        description
          "IPHC compression";
      }
      enum "ios-linktype-comp-tcp-nodelta" {
        value 104;
        description
          "IPHC compression";
      }
      enum "ios-linktype-fr-atm-srv" {
        value 105;
        description
          "FR-ATM service interworking";
      }
      enum "ios-linktype-fr-eek" {
        value 106;
        description
          "FR end-to-end keepalive";
      }
      enum "ios-linktype-ehsa" {
        value 107;
        description
          "Test type for EHSA";
      }
      enum "ios-linktype-mscp" {
        value 108;
        description
          "Multicast Shortcut PDU";
      }
      enum "ios-linktype-scp" {
        value 109;
        description
          "Cat6k - linecard control";
      }
      enum "ios-linktype-pppoe-discovery" {
        value 110;
        description
          "PPP over Ethernet Discovery";
      }
      enum "ios-linktype-pppoe-session" {
        value 111;
        description
          "PPP over Ethernet Session";
      }
      enum "ios-linktype-l2rly" {
        value 112;
        description
          "GPRS l2rly";
      }
      enum "ios-linktype-gtp" {
        value 113;
        description
          "GPRS GTP";
      }
      enum "ios-linktype-comp-rtp-16" {
        value 114;
        description
          "Compressed RTP-UDP-IP 16 bit CID";
      }
      enum "ios-linktype-comp-udp-16" {
        value 115;
        description
          "Compressed RTP-UDP-IP 16 bit CID";
      }
      enum "ios-linktype-atm-switch" {
        value 116;
        description
          "ATM PDU switching";
      }
      enum "ios-linktype-pagp" {
        value 117;
        description
          "Port Aggregation Protocol";
      }
      enum "ios-linktype-sstp" {
        value 118;
        description
          "Shared Spanning Tree BPDU";
      }
      enum "ios-linktype-rlq-req" {
        value 119;
        description
          "STP Root Link Query Request";
      }
      enum "ios-linktype-rlq-resp" {
        value 120;
        description
          "STP Root Link Query Response";
      }
      enum "ios-linktype-dyntrk" {
        value 121;
        description
          "Dynamic Trunk Protocol (DTP) PDU";
      }
      enum "ios-linktype-mls-ip" {
        value 122;
        description
          "layer3 switching internal flush";
      }
      enum "ios-linktype-dyntrk-encap" {
        value 123;
        description
          "DTP PDUs sent with SW ISL encapsulation";
      }
      enum "ios-linktype-udld" {
        value 124;
        description
          "UniDirectional Link Protocol";
      }
      enum "ios-linktype-srp" {
        value 125;
        description
          "Spatial Reuse Protocol (SRP)";
      }
      enum "ios-linktype-rgmp" {
        value 126;
        description
          "Router-port Group Management Protocol (RGMP)";
      }
      enum "ios-linktype-mistp" {
        value 127;
        description
          "Multi Instance Spanning Tree";
      }
      enum "ios-linktype-compressed-fr" {
        value 128;
        description
          "Compressed Frame Relay";
      }
      enum "ios-linktype-vito-scp" {
        value 129;
        description
          "Vito SCP protocol";
      }
      enum "ios-linktype-const-ftep" {
        value 130;
        description
          "Constellation Forwarding Table Edit Protocol";
      }
      enum "ios-linktype-vlan-switch" {
        value 131;
        description
          "VLAN PDU switching";
      }
      enum "ios-linktype-atom" {
        value 132;
        description
          "ATOM (Process) switching";
      }
      enum "ios-linktype-raw" {
        value 133;
        description
          "Raw switching";
      }
      enum "ios-linktype-oscp" {
        value 134;
        description
          "Optical Supervisory Channel Protocol";
      }
      enum "ios-linktype-diag" {
        value 135;
        description
          "For Diagnostic loop back via Ethernet chip";
      }
      enum "ios-linktype-stack-disc" {
        value 136;
        description
          "STP DUF STACK discovery";
      }
      enum "ios-linktype-fast-trans" {
        value 137;
        description
          "STP DUF Fast Transition";
      }
      enum "ios-linktype-dot1x" {
        value 138;
        description
          "802.1X Port Access Entity Type";
      }
      enum "ios-linktype-fr-frag" {
        value 139;
        description
          "FR fragmentation";
      }
      enum "ios-linktype-slow-proto" {
        value 140;
        description
          "802.3AD Slow Protocol";
      }
      enum "ios-linktype-eompls" {
        value 141;
        description
          "sync damage please name me";
      }
      enum "ios-linktype-ieee-dot1q" {
        value 142;
        description
          "sync damage please name me";
      }
      enum "ios-linktype-voice-nrt" {
        value 143;
        description
          "sync damage please name me";
      }
      enum "ios-linktype-uti-raw" {
        value 144;
        description
          "sync damage please name me";
      }
      enum "ios-linktype-hdlc-hapi" {
        value 145;
        description
          "ACE IPsec accelerator control";
      }
      enum "ios-linktype-cwan-ipsec" {
        value 146;
        description
          "IPSec acceleration for CWAN";
      }
      enum "ios-linktype-sstp-spanning" {
        value 147;
        description
          "Shared Spanning Tree BPDU";
      }
      enum "ios-linktype-fr-saa" {
        value 148;
        description
          "FR SAA round trip measurement";
      }
      enum "ios-linktype-froe" {
        value 149;
        description
          "Frame Relay over Ethernet";
      }
      enum "ios-linktype-vpdn" {
        value 150;
        description
          "Forwarded VPDN packets";
      }
      enum "ios-linktype-slm-saa" {
        value 151;
        description
          "SAA SLM Link Type";
      }
      enum "ios-linktype-rf-kpa" {
        value 152;
        description
          "Redundancy Facility keepalives";
      }
      enum "ios-linktype-rbcp" {
        value 153;
        description
          "Router blade control protocol";
      }
      enum "ios-linktype-p2ipc" {
        value 154;
        description
          "P2IPC LinkType";
      }
      enum "ios-linktype-p2ipc-mpls" {
        value 155;
        description
          "P2IPC LinkType for MPLS controller";
      }
      enum "ios-linktype-xconnect" {
        value 156;
        description
          "Xconnect (Process switching)";
      }
      enum "ios-linktype-slm-fr-saa" {
        value 157;
        description
          "FR SLM Link Type";
      }
      enum "ios-linktype-cdma-rp" {
        value 158;
        description
          "CDMA RP";
      }
      enum "ios-linktype-pw-ip-deprecated" {
        value 159;
        description
          "Deprecated
           do not reuse due to potential ISSU conflict";
      }
      enum "ios-linktype-vj-uncomp-tcp" {
        value 160;
        description
          "VJ Uncompressed TCP/IP";
      }
      enum "ios-linktype-vj-comp-tcp" {
        value 161;
        description
          "VJ Compressed TCP/IP";
      }
      enum "ios-linktype-online-diags" {
        value 162;
        description
          "Online Diagnostics";
      }
      enum "ios-linktype-vrf-ipsec" {
        value 163;
        description
          "VRF Aware Ipsec Crypto";
      }
      enum "ios-linktype-broadcom" {
        value 164;
        description
          "Link Broadcom";
      }
      enum "ios-linktype-http" {
        value 165;
        description
          "HyperText Transfer Protocol (HTTP)";
      }
      enum "ios-linktype-lfp" {
        value 166;
        description
          "Link Fault Propagation";
      }
      enum "ios-linktype-drprip" {
        value 167;
        description
          "Dual RPR Interconnect Protocol";
      }
      enum "ios-linktype-ether-cfm" {
        value 168;
        description
          "Ethernet Connectivity Fault Management
           (Version D1)";
      }
      enum "ios-linktype-ether-oam" {
        value 169;
        description
          "Ethernet OAM (802.3ah) ";
      }
      enum "ios-linktype-mmu" {
        value 170;
        description
          "Mac Move Update";
      }
      enum "ios-linktype-vslp" {
        value 171;
        description
          "Virtual Switch Link Protocol";
      }
      enum "ios-linktype-ether-lmi" {
        value 172;
        description
          "Ethernet Local Management Interface";
      }
      enum "ios-linktype-lldp" {
        value 173;
        description
          "Link Layer Discovery Protocol(IEEE 802.1AB)";
      }
      enum "ios-linktype-gvrp" {
        value 174;
        description
          "GARP VLAN Registration Protocol (802.1Q GVRP)";
      }
      enum "ios-linktype-gmrp" {
        value 175;
        description
          "GARP Multicast Registration Protocol (802.1Q GMRP)";
      }
      enum "ios-linktype-ancp" {
        value 176;
        description
          "Access Node Control Protocol";
      }
      enum "ios-linktype-rep" {
        value 177;
        description
          "Resilient Ethernet Protocol";
      }
      enum "ios-linktype-rep-hfl" {
        value 178;
        description
          "Resilient Ethernet Protocol Hardware Flood Layer";
      }
      enum "ios-linktype-ipe" {
        value 179;
        description
          "IPe Bootstrap";
      }
      enum "ios-linktype-mvrp" {
        value 180;
        description
          "Multiple VLAN Registration Protocol
           MVRP (802.1ak)";
      }
      enum "ios-linktype-vsda" {
        value 181;
        description
          "Virtual Switch Dual Active Protocol";
      }
      enum "ios-linktype-ecfm" {
        value 182;
        description
          "Ethernet Connectivity Fault Management
           (IEEE Version)";
      }
      enum "ios-linktype-dot1ah" {
        value 183;
        description
          "Ethernet Mac tunnelling Protocol
           (802.1ah I-TAG Version)";
      }
      enum "ios-linktype-sdp" {
        value 184;
        description
          "Satellite Discovery And Control protocol";
      }
      enum "ios-linktype-cdpfwd" {
        value 185;
        description
          "CDP Forwarding (CDPFWD)";
      }
      enum "ios-linktype-t101" {
        value 186;
        description
          "IEC 60870-5 101 Async Link";
      }
      enum "ios-linktype-rsvp" {
        value 187;
        description
          "RSVP Protocol ";
      }
      enum "ios-linktype-isisl2-otv-all-l1-is" {
        value 188;
        description
          "ISIS L2 OTV - All Level 1 ISes";
      }
      enum "ios-linktype-isisl2-otv-all-l2-is" {
        value 189;
        description
          "ISIS L2 OTV - All Level 2 ISes";
      }
      enum "ios-linktype-g8032" {
        value 190;
        description
          "G.8032";
      }
      enum "ios-linktype-sdac" {
        value 191;
        description
          "Satellite Discovery And Control protocol";
      }
      enum "ios-linktype-ptppd" {
        value 192;
        description
          "PTP Peer Delay protocol";
      }
      enum "ios-linktype-rawtcp" {
        value 193;
        description
          "RAWTCP";
      }
      enum "ios-linktype-an-ch" {
        value 194;
        description
          "Autonomic Networking";
      }
      enum "ios-linktype-fex-sdp" {
        value 195;
        description
          "FEX SDP/SRP Satellite Discovery Protocol
           Satellite Registration Protocols";
      }
      enum "ios-linktype-esmc" {
        value 196;
        description
          "Ethernet Synchronous Messaging Channel (ESCM)";
      }
      enum "ios-linktype-cisp" {
        value 197;
        description
          "Client Information Signaling Protocol (CISP)";
      }
      enum "ios-linktype-async" {
        value 198;
        description
          "punt/inject path Async Packet";
      }
      enum "ios-linktype-msrp" {
        value 199;
        description
          "Multiple Stream Reservation Protocol";
      }
      enum "ios-linktype-macsec-post-exp" {
        value 200;
        description
          "Online Diagnostics";
      }
      enum "ios-linktype-macsec-sectag" {
        value 201;
        description
          "Online Diagnostics";
      }
    }
    description
      "Link Type";
  }
}
