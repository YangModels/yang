submodule Cisco-IOS-XE-platform-rpc {
  belongs-to Cisco-IOS-XE-rpc {
    prefix ios-xe-rpc;
  }

  import cisco-semver {
    prefix cisco-semver;
  }

  include Cisco-IOS-XE-crypto-rpc;

  organization "Cisco Systems";

  contact
    <mailto:cs-yang@cisco.com>;

  description
    "NED Platform RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2018-12-06 {
    description
      "created for NED RPC modularisation";
  }

  grouping clear-choice-platform-case-grouping {
    container platform {
      description
        "Clear platform information";
      container hardware {
        description
          "Clear platform hardware information";
        container qfp {
          description
            "Quantum Flow Processor";
          container active {
            description
              "Active instance";
            container feature {
              description
                "Clear features";
              choice feature-choice {
              }
            }
          }
        }
      }
    }
  }

  grouping debug-choice-platform-case-grouping {
      container platform {
        description "Debug platform information";
        container condition {
          choice condition-choice {
            case start-case {
              leaf start {
                description "Start conditional debug";
                type empty;
              }
            }
            case stop-case {
              leaf stop {
                description "Stop conditional debug";
                type empty;
              }
            }
            case feature-case {
              container feature {
                description "For a specific feature";
                uses debug-platform-condition-feature-ipsec-grouping;
              }
            }
          }
        }
      }
    }
}
