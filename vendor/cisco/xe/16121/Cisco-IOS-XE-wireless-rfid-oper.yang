module Cisco-IOS-XE-wireless-rfid-oper {
  yang-version 1;
  namespace "http://cisco.com/ns/yang/Cisco-IOS-XE-wireless-rfid-oper";
  prefix wireless-rfid-ios-oper;

  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless rfid Operational Data
     Copyright (c) 2016-2019 by Cisco Systems, Inc.
     All rights reserved.";

  revision 2019-05-01 {
    description
      "- Removed data, renamed various leafs and changed types.
       - Added semantic version";
    reference "3.1.0";
    cisco-semver:module-version "3.1.0";
  }
  revision 2018-12-14 {
    description
      "- Removal of unused leaves
       - Cleaned up spelling errors in descriptions.";
    reference "3.0.0";
    cisco-semver:module-version "3.0.0";
  }
  revision 2018-01-24 {
    description
      "Changes done in ptl code for time format";
    reference "2.0.0";
    cisco-semver:module-version "2.0.0";
  }
  revision 2017-12-22 {
    description
      "Initial revision";
    reference "1.0.0";
    cisco-semver:module-version "1.0.0";
  }

  typedef enm-rfid-data-type {
    type enumeration {
      enum "bluesoft-rfid-data" {
        value 0;
        description
          "This enum value represents type of bluesoft rfid tag.";
      }
      enum "cisco-rfid-data" {
        value 1;
        description
          "This enum value represents type of cisco rfid tag.";
      }
    }
    description
      "This enum has all the RFID
       tags supported types.";
  }

  grouping st-apf-seq-control {
    description
      "sequence control represents sequence and fragmentation number.";
    leaf seq-num {
      type uint16;
      description
        "seq_num represents sequence number of rfid tag packet.";
    }
    leaf frag-num {
      type uint16;
      description
        "frag_num represents fragmentation number of rfid tag packet.";
    }
  }

  grouping st-rfid-cisco-cont-hdr {
    description
      "CTX content header contains attributes of ctx header of rfid.";
    leaf ccx-version {
      type uint8;
      description
        "ccx_version represents ccx version of rfid.";
    }
    leaf tx-power {
      type int8;
      description
        "tx_power represents tx power of rfid.";
    }
    leaf channel {
      type uint8;
      description
        "channel represents channel id of rfid.";
    }
    leaf reg-class {
      type uint8;
      description
        "reg_class represents reg_class of rfid.";
    }
    leaf burst-len {
      type uint8;
      description
        "burst_len represents burst length of rfid.";
    }
  }

  grouping st-bluesoft-rfid-data {
    description
      "Bluesoft rfid data represents data of bluesoft rfid tag.";
    leaf last-seq-num {
      type uint8;
      description
        "last_seq_num represents last sequence number of rfid tag.";
    }
    leaf tag-type {
      type uint8;
      description
        "tag_type represents type of bluesoft rfid tag.";
    }
  }

  grouping st-ccx-payload-list {
    description
      "ccx payload contains ccx payload data of rfid.";
    leaf-list data {
      type uint8;
      max-elements "500";
      ordered-by user;
      description
        "Data contains one byte of ccx payload data.";
    }
  }

  grouping st-cisco-rfid-data {
    description
      "cisco rfid data represents data of cisco rfid tag.";
    container rfid-cisco-hdr {
      description
        "cisco header represents cisco tag header.";
      uses wireless-rfid-ios-oper:st-rfid-cisco-cont-hdr;
    }
    container seq-control {
      description
        "sequence control represents sequence control number of rfid tag.";
      uses wireless-rfid-ios-oper:st-apf-seq-control;
    }
    leaf payload-len {
      type uint16;
      description
        "payload_len represents payload length of rfid packet.";
    }
    container ccx-payload {
      description
        "ccx_payload represents ccx payload length of rfid packet.";
      uses wireless-rfid-ios-oper:st-ccx-payload-list;
    }
  }

  grouping st-vendor-spec-data {
    description
      "vendor specific data of rfid packet.";
    choice type-choice {
      description
        "type choice represents type of rfid tag supported.";
      case bluesoft-rfid-data {
        container bluesoft {
          description
            "bluesoft represents update of bluesoft rfid information.";
          uses wireless-rfid-ios-oper:st-bluesoft-rfid-data;
        }
      }
      case cisco-rfid-data {
        container cisco {
          description
            "cisco represents cisco rfid tag information.";
          uses wireless-rfid-ios-oper:st-cisco-rfid-data;
        }
      }
    }
  }

  grouping st-rfid-avg-rssi {
    description
      "rfid average rssi represents AP rssi information.";
    leaf num {
      type int16;
      description
        "num represents rssi num.";
    }
    leaf denom {
      type uint16;
      description
        "denom represents rssi denom.";
    }
    leaf value {
      type int8;
      description
        "value represents value of rssi.";
    }
    leaf last-sent {
      type int8;
      description
        "last_sent represents last sent rssi.";
    }
  }

  grouping st-rfid-avg-snr {
    description
      "rfid average snr represents snr of AP.";
    leaf num {
      type int16;
      description
        "num of snr.";
    }
    leaf denom {
      type uint16;
      description
        "denom of snr.";
    }
    leaf value {
      type int8;
      description
        "value of snr.";
    }
  }

  grouping rfid-ap-entry-list {
    description
      "ap entry list is list of ap data, max count of list is 16.";
    container rssi {
      description
        "rssi represents rssi parameters of rfid.";
      uses wireless-rfid-ios-oper:st-rfid-avg-rssi;
    }
    leaf slot {
      type uint8;
      description
        "slot represents AP slot.";
    }
    leaf band {
      type uint8;
      description
        "band represents radio band of AP.";
    }
    container snr {
      description
        "snr represents value of snr.";
      uses wireless-rfid-ios-oper:st-rfid-avg-snr;
    }
    leaf time-stamp {
      type yang:date-and-time;
      description
        "time stamp represents time stamp of rfid packet received by the AP.";
    }
    leaf expired {
      type boolean;
      description
        "expired represents stale node in the list, true if time stamp time expired.";
    }
    leaf ap-mac-addr {
      type yang:mac-address;
      description
        "ap_mac_addr represents ap mac address of AP.";
    }
  }

  grouping st-rfid-ap-highest-rssi {
    description
      "ap highest rssi represents stores mac address of highest AP address.";
    leaf ap-mac-addr {
      type yang:mac-address;
      description
        "ap mac address represents ap mac address of highest rssi AP.";
    }
    container rssi {
      description
        "rssi represents rssi value of highest rssi AP.";
      uses wireless-rfid-ios-oper:st-rfid-avg-rssi;
    }
  }

  grouping st-rfid-data {
    description
      "rfid data represents rfid parameters.";
    leaf rfid-mac-addr {
      type yang:mac-address;
      description
        "rfid mac address represents mac address of the rfid device.";
    }
    leaf rfid-type {
      type wireless-rfid-ios-oper:enm-rfid-data-type;
      description
        "rfid type represents type of rfid tag.";
    }
    leaf rfid-auto-interval {
      type uint16;
      description
        "rfid auto interval represents rfid packet interval.";
    }
    leaf rfid-bytes-rx {
      type uint32;
      description
        "rfid bytes rx represents number of bytes received in rfid packet.";
    }
    leaf rfid-packets-rx {
      type uint32;
      description
        "rfid packets rx represents number of rfid packets received for same rfid.";
    }
    leaf rfid-last-heard-second {
      type yang:date-and-time;
      description
        "last heard represents time stamp of last rfid packet received.";
    }
    container rfid-vendor {
      description
        "rfid vendor represents vendor type of rfid received like cisco tag or bluesoft.";
      uses wireless-rfid-ios-oper:st-vendor-spec-data;
    }
    container ap-high-rssi {
      description
        "ap high rssi represents parameters of highest rssi AP";
      uses wireless-rfid-ios-oper:st-rfid-ap-highest-rssi;
    }
    list ap-data {
      description
        "ap data represents ap information of rfid packet received.";
      uses wireless-rfid-ios-oper:rfid-ap-entry-list;
    }
    leaf tx-power {
      type int8;
      description
        "tx_power represents tx power of AP which send rfid packet.";
    }
    leaf timer-handle {
      type uint64;
      description
        "timer_handle represents timer handle of the record.";
    }
  }

  container rfid-oper-data {
    config false;
    description
      "wireless rfid oper data contains all rfid operational data information";
    list rfid-data {
      key "rfid-mac-addr";
      description
        "rfid data represents parameter of rfid packet.";
      uses wireless-rfid-ios-oper:st-rfid-data;
    }
  }
}
