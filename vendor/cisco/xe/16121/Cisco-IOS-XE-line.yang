submodule Cisco-IOS-XE-line {
  belongs-to Cisco-IOS-XE-native {
    prefix ios;
  }

  import cisco-semver {
    prefix cisco-semver;
  }
 

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Line, configure a terminal line Yang Model.
     Copyright (c) 2016 - 2019 by Cisco Systems, Inc.
     All rights reserved.";

  // =========================================================================
  // REVISION
  // =========================================================================
  revision 2019-07-01 {
    description 
      "- Establish semantic version baseline
       - Add session-disconnect-warning";
    cisco-semver:module-version "1.0.0";
  }
  revision 2018-11-07 {                                                      
    description                                                              
      "Renamed command to commands under line-group authorization inline with ios";
  }

  revision 2018-10-10 {
    description
      "Enabled configuration of multiple transport input/output protocol for single line console ";
  }

  revision 2018-08-10 {
    description
      "Enabled multiple authorization command for single line console ";
  }

  revision 2018-03-01 {
    description
      "Added line console authorization exec list commands ";
  }

  revision 2017-09-06 {
    description
      "Added line console/vty history ";
  }
 
  revision 2017-07-24 {
    description
      "Add session-limit";
  }

  revision 2017-06-02 {
     description
       "Add alt-name for console line";
   }

  revision 2017-05-29 {
    description
      "Added /line/vty/session-limit";
  }
  revision 2017-03-24 {
    description
      "Remove refuse-message and vacant-message";
  }
  revision 2017-02-07 {
    description
      "Initial revision";
  }

  grouping password-07-grouping {
    leaf level {
      description
        "Set exec level password";
      type uint8;
    }
    leaf type {
      type enumeration {
        enum "0";
        enum "7";
      }
    }
    leaf secret {
      type string {
        pattern '.*';
      }
    }
  }

  grouping line-grouping {
    // line * / authorization
    container authorization {
      description
        "Authorization parameters";
      list commands {
        description
          "For exec (shell) commands";
        key "enable-level auth-name";
        leaf enable-level {
          type uint8 {
            range "0..15";
          }
        }
        leaf auth-name {
          type string;
        }
      }
      container exec {
        description
          "For starting an exec (shell)";
        leaf authorization-name {
          description
            "Use an authorization list with this name";
          type string;
        }
        leaf default {
          description
            "Use the default authorization list";
          type empty;
        }
      }
    }

    // line * / access-class
    container access-class {
      description
        "Filter connections based on an IP access list";
      list acccess-list {
        key "direction";
        leaf direction {
          type enumeration {
            enum "in";
            enum "out";
          }
        }
        leaf access-list {
          type ios-types:exp-acl-type;
          mandatory true;
        }
        leaf vrf-also {
          description
            "Same access list is applied for all VRFs";
          type empty;
        }
      }
    }
    // line * / activation-character
    leaf no-activation-character {
      type boolean;
    }
    leaf activation-character {
      description
        "Define the activation character";
      type union {
        type string;
        type uint8 {
          range "0..127";
        }
      }
    }
    // line * / autocommand
    container autocommand {
      description
        "Automatically execute an EXEC command";
      leaf line {
        description
          "Appropriate EXEC command";
        type string;
      }
      container no-suppress-linenumber {
        description
          "Display service linenumber message";
        presence "true";
        leaf line {
          description
            "Appropriate EXEC command";
          type string;
        }
      }
    }
    // line * / autocommand-options
    container autocommand-options {
      description
        "Autocommand options";
      presence "true";
      container abort-character {
        description
          "Autocommand abort character";
        presence "true";
        leaf character {
          type union {
            type uint8;
            type string;
          }
        }
      }
      container delay {
        description
          "Delay autocommand execution";
        presence "true";
        leaf time {
          description
            "Time in seconds";
          type uint8 {
            range "0..120";
          }
        }
      }
      container nohangup {
        description
          "No hangup after autocommand completion";
        presence "true";
        leaf abort-character {
          description
            "Autocommand abort character";
          type empty;
        }
        leaf delay {
          description
            "Delay autocommand execution";
          type empty;
        }
      }
    }
    // line * / data-character-bits
    leaf data-character-bits {
      description
        "Bits per character";
      type uint8 {
        range "7..8";
      }
    }
    // line * / databits
    container databits {
      description
        "Set number of data bits per character";
      leaf set-to-5 {
        description
          "Number of data bits";
        type empty;
      }
      leaf set-to-6 {
        description
          "Number of data bits";
        type empty;
      }
      leaf set-to-7 {
        description
          "Number of data bits";
        type empty;
      }
      leaf set-to-8 {
        description
          "Number of data bits";
        type empty;
      }
    }
    //line * / domain-lookup
    leaf domain-lookup {
      description
        "Enable domain lookups in show commands";
      type empty;
    }
    //line * /editing
    leaf editing {
      description
        "Enable command line editing";
      type empty;
    }
    // line * / escape-character
    container escape-character {
      description
        "Change the current line's escape character";
      leaf char {
        type union {
          type uint8;
          type enumeration {
            enum "BREAK";
            enum "DEFAULT";
            enum "NONE";
          }
          type string;
        }
      }
      leaf soft {
        type empty;
      }
    }
    // line * / exec
    choice exec-choice {
      container no-exec {
        leaf exec {
          description
            "Configure EXEC";
          type boolean;
        }
      }
      container exec {
        container prompt {
          leaf timestamp {
            type empty;
          }
        }
      }
    }
    // line * / exec-banner
    leaf exec-banner {
      description
        "Enable the display of the EXEC banner";
      type empty;
    }
    // line * /exec-character-bits
    leaf exec-character-bits {
      description
        "Bits per character";
      type uint8 {
        range "7..8";
      }
    }
    // line * / exec-timeout
    container exec-timeout {
      description
        "Set the EXEC timeout";
      leaf minutes {
        description
          "<0-35791>;;Timeout in minutes";
        type uint32;
      }
      leaf seconds {
        description
          "<0-2147483>;;Timeout in seconds";
        type uint32;
      }
    }
    // line * / flowcontrol
    container flowcontrol {
      description
        "Set the flow control";
      leaf NONE {
        description
          "Set no flow control";
        type empty;
      }
      leaf hardware {
        description
          "Set hardware flow control";
        type empty;
      }
      leaf software {
        description
          "Set software flow control";
        type empty;
      }
    }
    // line * / full-help
    leaf full-help {
      description
        "Provide help to unprivileged user";
      type empty;
    }
    // line * / history
    container history {
      description
        "Enable and control the command history function";
      presence "true";
      leaf size {
        description
          "Set history buffer size";
        type uint16 {
          range "0..256";
        }
      }
    }
    // line * / international
    leaf international {
      description
        "Enable international 8-bit character support";
      type empty;
    }
    // line * / ip
    container ip {
      description
        "IP options";
      container netmask-format {
        description
          "Change display of netmasks";
        presence "true";
        leaf format {
          type enumeration {
            enum "bit-count";
            enum "decimal";
            enum "hexadecimal";
          }
        }
      }
      leaf tcp {
        type empty;
      }
    }
    // line * / ipv6
    container ipv6 {
      container access-class {
        list access-class {
          key "access-class-name";
          leaf access-class-name {
            type string;
          }
          leaf enumeration-in-out {
            type enumeration {
              enum "in";
              enum "out";
            }
          }
        }
      }
    }
    // line * / length
    leaf length {
      description
        "Set number of lines on a screen";
      type uint16 {
        range "0..512";
      }
    }
    // line * / line
    leaf line {
      type uint8;
    }
    // line * / location
    leaf location {
      description
        "One text line describing the terminal's location";
      type string;
    }
    // line * / logging
    container logging {
      description
        "Modify message logging facilities";
      container synchronous {
        description
          "Synchronized message output";
        presence "true";
      }
    }
    // line * / login
    container login {
      description
        "Enable password checking";
      presence "true";
      leaf local {
        type empty;
      }
      leaf authentication {
        type string;
      }
    }
    // line * / media-type
    container media-type {
      description
        "Console connection media type";
      leaf rj45 {
        description
          "Console connection set to RJ45";
        type empty;
      }
    }
    // line * / modem
    container modem {
      description
        "Configure the Modem Control Lines";
      leaf CTS-Alarm {
        description
          "Alarm device which only uses CTS for call control";
        type empty;
      }
      leaf DTR-active {
        description
          "Leave DTR low unless line has an active incoming connection or EXEC";
        type empty;
      }
      leaf Dialin {
        description
          "Configure line for a modern dial-in modem";
        type empty;
      }
      leaf Host {
        description
          "Devices that expect an incoming modem call";
        type empty;
      }
      leaf InOut {
        description
          "Configure line for incoming AND outgoing use of modem";
        type empty;
      }
      leaf Printer {
        description
          "Devices that require DSR/CD active";
        type empty;
      }
      leaf answer-timeout {
        description
          "Set interval between raising DTR and CTS response";
        type empty;
      }
      container autoconfigure {
        description
        "Automatically configure modem on line";
        leaf discovery {
          description
            "Attempt to determine modem type automatically";
          type empty;
        } 
        leaf type {
          description
            "Modem Type";
          type string;
        }
      }
      leaf dtr-delay {
        description
          "Set interval during which DTR is held low";
        type empty;
      }
    }
    // line * / monitor
    leaf monitor {
      description
        "Copy debug output to the current terminal line";
      type empty;
    }
    // line * / motd-banner
    leaf motd-banner {
      description
        "Enable the display of the MOTD banner";
      type empty;
    }
    // line * / notify
    leaf notify {
      description
        "Inform users of output from concurrent sessions";
      type empty;
    }
    // line * / padding
    container padding {
      description
        "Set padding for a specified output character";
      leaf character {
        description
          "Character to be padded";
        type union {
          type uint8 {
            range "0..127";
          }
          type string;
        }
      }
      leaf null {
        type uint8;
      }
    }
    // line * / parity
    container parity {
      description
        "Set terminal parity";
      leaf even {
        description
          "Even parity";
        type empty;
      }
      leaf mark {
        description
          "Mark parity";
        type empty;
      }
      leaf none {
        description
          "No parity";
        type empty;
      }
      leaf odd {
        description
          "Odd parity";
        type empty;
      }
      leaf space {
        description
          "Space parity";
        type empty;
      }
    }
    // line * / password
    container password {
      description
        "Set a password";
      uses password-07-grouping;
    }
    // line * / prc
    container prc {
      description
        "PRC commands";
      leaf expose {
        description
          "Expose PRC data";
        type empty;
      }
      leaf hide {
        description
          "Hide PRC data";
        type empty;
      }
    }
    // line * / privilege
    container privilege {
      description
        "Change privilege level for line";
      container level {
        description
          "Assign default privilege level for line";
        presence "true";
        leaf number {
          type uint8 {
            range "0..15";
          }
        }
      }
    }
    // line * / rotary
    leaf rotary {
      description
        "Rotary group to add line to";
      type uint8 {
        range "1..99";
      }
    }
    // line * / rxspeed
    leaf rxspeed {
      description
        "Receive speed";
      type uint32 {
        range "0..4294967295";
      }
    }
    // line * / session-disconnect-warning
    container session-disconnect-warning {
      description
        "Set the session disconnect warning";
      leaf seconds {
        description
          "Session timeout warning in seconds";
        type uint32 {
          range "0..4294967295";
        }
      }
      leaf message {
        description
          "Optional warning message";
        type string;
      }  
    }
    // line * / session-limit
    leaf session-limit {
       description
        "Set maximum number of sessions";
       type uint32; 
    }
    // line * / session-timeout
    container session-timeout {
      description
        "Set interval for closing connection when there is no input traffic";
      leaf session-timeout-value {
        type uint16 {
          range "0..35791";
        }
      }
      leaf output {
        description
          "Include output traffic as well as input traffic";
        type empty;
      }
    }
    // line * / special-character-bits
    leaf special-character-bits {
      description
        "Bits per character";
      type uint8 {
        range "7..8";
      }
    }
    // line * / speed
    leaf speed {
      description
        "Transmit and receive speeds";
      type uint32 {
        range "0..4294967295";
      }
    }
    // line * / start-character
    leaf start-character {
      description
        "Define the start character";
      type union {
        type uint8;
        type string;
      }
    }
    // line * / stop-character
    leaf stop-character {
      description
        "Define the stop character";
      type union {
        type uint8;
        type string;
      }
    }
    // line * / stopbits
    leaf stopbits {
      description
        "Set async line stop bits";
      type enumeration {
        enum "1";
        enum "1.5";
        enum "2";
      }
    }
    // line * / terminal-type
    leaf terminal-type {
      description
        "Terminal type";
      type string;
    }
    // line * / timeout
    container timeout {
      description
        "Timeouts for the line";
      leaf login {
        description
          "Timeouts related to the login sequence";
        type empty;
      }
    }
    // line * / telnet
    container telnet {
      description
        "Telnet protocol-specific configuration";
      leaf transparent {
        description
          "Send a CR as a CR followed by a NULL instead of a CR followed by a LF";
        type empty;
      }
    }
    // line * / transport
    container transport {
      description
        "Define transport protocols for line";
      // line * / transport input
      container input {
        choice input-protocol {
          case all-protocol {
            leaf all {
              description
                "All protocols";
              type empty;
            }
          }
          case no-protocol {
            leaf none {
              description
                "Define no transport protocols for line";
              type empty;
            }
          }
          case other-protocol {
            leaf-list input {
              description
                "Define which protocols to use when connecting to the terminal server";
              ordered-by user;
              
              type enumeration {
                enum "acercon";
                enum "lapb-ta";
                enum "lat";
                enum "mop";
                enum "nasi";
                enum "pad";
                enum "rlogin";
                enum "ssh";
                enum "telnet";
                enum "udptn";
                enum "v120";
              }
            }
          }
        }
      }
      // line * / transport output
      container output {
        choice output-protocol {
          case all-protocol {
            leaf all {
              description
                "All protocols";
              type empty;
            }
          }
          case no-protocol {
            leaf none {
              description
                "Define no transport protocols for line";
              type empty;
            }
          }
          case other-protocol {
            leaf-list output {
              description
                "Define which protocols to use for outgoing connections";
              ordered-by user;
              
              type enumeration {
                enum "acercon";
                enum "lapb-ta";
                enum "lat";
                enum "mop";
                enum "nasi";
                enum "pad";
                enum "rlogin";
                enum "ssh";
                enum "telnet";
                enum "udptn";
                enum "v120";
              }
            }
          }
        }
      }
      // line * / transport preferred
      container preferred {
        description
          "Specify the preferred protocol to use";
        presence "true";
        leaf protocol {
          type enumeration {
            enum "acercon";
            enum "lat";
            enum "mop";
            enum "nasi";
            enum "none";
            enum "pad";
            enum "rlogin";
            enum "ssh";
            enum "telnet";
            enum "udptn";
          }
        }
      }
    }
    // line * / txspeed
    leaf txspeed {
      description
        "Transmit speed";
      type uint32;
    }
    // line * / usb-inactivity-timeout
    container usb-inactivity-timeout {
      description
        "Inactivity timeout for USB media type";
      leaf switch {
        description
          "Switch Number";
        type empty;
      }
    }
    // line * / width
    leaf width {
      description
        "Number of characters on a screen line";
      type uint16 {
        range "0..512";
      }
    }
  }
  /////////////////////////////////////////////////////////
  // native / line *
  /////////////////////////////////////////////////////////
  grouping config-line-grouping {
    container line { 
      description
        "Configure a terminal line";
      /// line  0-17 >
      list line-list {
        key "first-number";
        leaf first-number {
          description
            "First Line number";
          type uint8 {
            range "0..17";
          }
        }
        leaf last-number {
          type uint16 {
            range "1..17";
          }
        }
        uses line-grouping;
      }
      list aux {
        description
          "Auxiliary line";
        key "first";
        max-elements "1";
        leaf first {
          type enumeration {
            enum "0";
          }
        }
        uses line-grouping;
      }
      list console {
        description
          "Primary terminal line";
        key "first";
        max-elements "1";
        leaf first {
          type enumeration {
            enum "0";
          }
        }
        uses line-grouping;
      }
      list vty {
        description
          "Virtual terminal";
        key "first";
        leaf first {
          type uint16 {
            range "0..1869";
          }
        }
        leaf last {
          type uint16 {
            range "1..1869";
          }
        }
        uses line-grouping;
      }
    }
  }
}
