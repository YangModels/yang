submodule Cisco-IOS-XE-eigrp-obsolete {
  belongs-to Cisco-IOS-XE-eigrp {
    prefix ios-eigrp;
  }

  import ietf-inet-types {
    prefix inet;
  }


  import Cisco-IOS-XE-types {
    prefix ios-types;
  }

  import Cisco-IOS-XE-interface-common {
    prefix ios-ifc;
  }

  import Cisco-IOS-XE-native {
    prefix ios;
  }

  import Cisco-IOS-XE-features {
    prefix ios-features;
  }

  grouping eigrp-af-topo-redist-grouping {
    container route-map {
      status deprecated;
      description
        "Filter prefixes based on the route-map";
      list rmap-name {
        status deprecated;
        key "rmap-name";
        leaf rmap-name {
          status deprecated;
          description
            "route-map name";
          type string;
        }
      }
    }
    container metric {
      status obsolete;
      description
        "Metric for redistributed routes";
      leaf bandwith {
        status obsolete;
        description
          "Bandwidth metric in Kbits per second";
        type uint32 {
          range "1..4294967295";
        }
      }
      leaf delay {
        status obsolete;
        description
          "EIGRP delay metric, in 10 microsecond units";
        type uint32 {
          range "0..4294967295";
        }
      }
      leaf reliability {
        status obsolete;
        description
          "EIGRP reliability metric where 255 is 100% reliable";
        type uint8 {
          range "0..255";
        }
      }
      leaf Effective {
        status obsolete;
        description
          "EIGRP Effective bandwidth metric (Loading) where 255 is 100% loaded";
        type uint8 {
          range "1..255";
        }
      }
      leaf mtu {
        status obsolete;
        description
          "MTU of the path";
        type uint16 {
          range "1..65535";
        }
      }
    }
  }

  grouping ipv6-router-distribute-list-grouping {
    container distribute-list {
      description
        "Filter networks in routing updates";
      list prefix-list {
        description
          "Filter connections based on an IPv6 prefix-list";
        key "name";
        leaf name {
          type string;
        }
        leaf in {
          description
            "Filter incoming routing updates";
          type empty;
        }
        leaf out {
          description
            "Filter outgoing routing updates";
          type empty;
        }
      }
    }
  }

  grouping config-interface-ipv6-eigrp-grouping {
    status obsolete;
    container eigrp {
      status obsolete;
      description
        "Interface command for IPv6 EIGRP. (DEPRECATED, use router-eigrp)";
      leaf as-number {
        status obsolete;
        type uint16;
      }
    }
  }

  // Router eigrp topology base grouping
  grouping eigrp-topology-base-grouping {
    container topology {
      status deprecated;
      description
        "Topology configuration mode";
      container base {
        status deprecated;
        description
          "Base Topology";
        presence true;
        container distance {
          status obsolete;
          description
            "Define an administrative distance";
          container eigrp {
            status obsolete;
            description
              "EIGRP-IPV6 distance";
            list distance-list {
              status obsolete;
              key "internal-route";
              leaf internal-route {
                status obsolete;
                description
                  "Distance for internal routes";
                type uint8 {
                  range "1..255";
                }
              }
              leaf external-route {
                status obsolete;
                description
                  "Distance for external routes";
                type uint8 {
                  range "1..255";
                }
              }
            }
          }
        }
        container table-map {
          status deprecated;
          description
            "Define Table-Map for setting OMP-TAG into routing table";
          leaf name {
            status deprecated;
            description
              "WORD;;route-map name";
            type string;
          }
          leaf filter {
            status deprecated;
            description "Selective route download";
            type empty;
          }
        }
        container distribute-list {
          status obsolete;
          description
            "Filter entries in eigrp updates";
          list prefix-list {
            status obsolete;
            description
              "Filter prefixes in address updates";
            key "prefix-list";
            leaf prefix-list {
            status obsolete;
            description
              "Name of an IP prefix-list";
              type string;
            }
            leaf gateway {
              status obsolete;
              description
                "Filtering incoming address updates based on gateway";
              type empty;
            }
            leaf in {
              status obsolete;
              description
                "Filter incoming service updates";
              type empty;
            }
            leaf out {
              status obsolete;
              description
                "Filter outgoing service updates";
              type empty;
            }
          }
          list route-map {
            status obsolete;
            description
              "Filter prefixes based on the route-map";
            key "name";
            leaf name {
              status obsolete;
              type string;
            }
            leaf in {
              status obsolete;
              description
                "Filter incoming service updates";
              type string;
            }
            leaf out {
              status obsolete;
              description
                "Filter outgoing service updates";
              type string;
            }
          }
        }
        container redistribute {
          status deprecated;
          description
            "Redistribute IPv6 prefixes from another routing protocol";
          container eigrp {
            status obsolete;
            description
              "Enhanced Interior Gateway Routing Protocol (EIGRP)";
            list as-list {
              status obsolete;
              key "autonomous-system";
              leaf autonomous-system {
                status obsolete;
                description
                  "Autonomous system number";
                type uint16 {
                  range "1..65535";
                }
              }
              uses eigrp-af-topo-redist-grouping;
            }
          }
          container omp {
            status deprecated;
            if-feature ios-features:omp;
            description
              "Overlay Management Protocol (OMP)";
            presence true;
            uses eigrp-af-topo-redist-grouping;
          }
          container nat-route {
            status deprecated;
            if-feature ios-features:sdwan;
            description
              "NAT Route";
            leaf dia {
              status deprecated;
              description
                "Redistribute NAT Direct Internet Access routes";
              type empty;
            }
            leaf outside {
              status deprecated;
              description
                "Redistribute NAT Outside routes";
              type empty;
            }
            uses eigrp-af-topo-redist-grouping;
          }
          container ospf {
            status deprecated;
            description
              "Open Shortest Path First (OSPFv3)";
            leaf process-id {
              status deprecated;
              description
                "Process ID";
              type uint16 {
                range "1..65535";
              }
            }
            uses eigrp-af-topo-redist-grouping;
          }
          container connected {
            status deprecated;
            description
              "Connected Routes";
            presence true;
            uses eigrp-af-topo-redist-grouping;
          }
          container static {
            status deprecated;
            description
              "Static Routes";
            presence true;
            uses eigrp-af-topo-redist-grouping;
          }
          container bgp {
            status deprecated;
            description
              "Border Gateway Protocol (BGP)";
            
            leaf as-number {
              status deprecated;
              type ios-types:bgp-as-number-type;
            }
            uses eigrp-af-topo-redist-grouping;
          }
        }
        list summary-metric {
          status obsolete;
          description
            "Specify summary to apply metric/filtering";
          key "ipv4-addr-slash-prefix-len";
          leaf ipv4-addr-slash-prefix-len {
            status obsolete;
            description
              "Summary <network>/<length>, e.g., 192.168.0.0/16";
            type inet:ipv4-prefix;
          }
          container metric {
            status obsolete;
            leaf bandwidth-metric {
              status obsolete;
              description
                "Bandwidth metric in Kbits per second";
              type uint32 {
                range "1..4294967295";
              }
            }
            leaf delay-metric {
              status obsolete;
              description
                "delay metric in 10 microsecond units";
              type uint32 {
                range "1..4294967295";
              }
            }
            leaf reliability-metric {
              status obsolete;
              description
                "reliability metric where 255 is 100% reliable";
              type uint8 {
                range "0..255";
              }
            }
            leaf effective-bandwidth-metric {
              status obsolete;
              description
                "Effective bandwidth metric (Loading) where 255 is 100% loaded";
              type uint8 {
                range "0..255";
              }
            }
            leaf mtu {
              status obsolete;
              description
                "MTU of the path";
              type uint16 {
                range "1..65535";
              }
            }
          }
          leaf distance {
            status obsolete;
            description
              "Set administrative distance for summary route";
            type uint8 {
              range "1..255";
            }
          }
        }
      }
    }
  }

  // router eigrp address-family
  grouping eigrp-address-family-grouping {
    list af-interface {
      status deprecated;
      description
        "Enter Address Family interface configuration";
      key "name";
      leaf name {
        status deprecated;
        type string;
      }
      leaf bandwidth-percent {
        status obsolete;
        description
          "Set percentage of bandwidth percentage limit";
        type uint32 {
          range "1..999999";
        }
      }
      leaf shutdown {
        status deprecated;
        description
          "Shutdown this interface of EIGRP";
        type empty;
      }
      leaf bfd {
        status deprecated;
        description
          "set peer monitoring method to bfd";
        type empty;
      }
      leaf hello-interval {
        status deprecated;
        description
          "Configures hello interval";
        type uint16;
      }
      leaf hold-time {
        status deprecated;
        description
          "Configures hold time";
        type uint16;
      }
      leaf passive-interface {
        status deprecated;
        description
          "Suppress address updates on an interface";
        type boolean;
      }
      leaf split-horizon {
        status deprecated;
        description
          "Perform split horizon";
        type boolean;
      }
      container stub-site {
        status obsolete;
        description
          "Stub-Site";
          leaf wan-interface {
            status obsolete;
            description
              "Wan Interface";
            type empty;
          }
      }
      container authentication {
        status deprecated;
        description
          "authentication subcommands";
        container mode {
          status deprecated;
          description
            "authentication mode";
          leaf md5 {
            status deprecated;
            description
              "Keyed message digest";
            type empty;
          }
          container hmac-sha-256 {
            status deprecated;
            description
              "HMAC-SHA-256 Authentication";
            leaf auth-type {
              status deprecated;
              type uint8;
            }
            leaf auth-key {
              status deprecated;
              type string;
            }
          }
        }
        leaf key-chain {
          status deprecated;
          description
            "key-chain";
          type string;
        }
      }
      list summary-address {
        status deprecated;
        key "prefix";
        leaf prefix {
          status deprecated;
          type union {
            type inet:ipv4-prefix;
            type ios-types:ipv6-prefix;
          }
        }
      }
    }
    container set-as-in-submode {
      status obsolete;
      leaf autonomous-system {
        status obsolete;
        description
        "Specify Address-Family Autonomous System Number?";
          type uint16;
      }
    }
    leaf auto-summary {
      status deprecated;
      description
        "Enable automatic network number summarization";
        type empty;
    }
    container bfd {
      status obsolete;
      description
        "BFD configuration commands";
      leaf all-interfaces {
        status obsolete;
        description
          "Enable BFD on all interfaces";
          type empty;
      }
      container interface {
        status obsolete;
        description
          "Enable BFD on specific interface";
        uses ios-ifc:interface-grouping;
      }
    }
    container default-information {
      status obsolete;
      description
        "Control distribution of default information";
      container in {
        status obsolete;
        description
          "Accept input default routing information";
        presence "true";
        leaf sa-num {
          status obsolete;
          description
            "A standard expanded IP access list number";
          type uint16 {
            range "1300..1999";
          }
        }
        leaf sa-name {
          status obsolete;
          description
            "Standard Access-list name";
          type string;
        }
      }
      container out {
        status obsolete;
        description
          "Accept output default routing information";
        presence "true";
        leaf sa-out-num {
          status obsolete;
          description
            "A standard expanded IP access list number";
          type uint16 {
            range "1300..1999";
          }
        }
        leaf sa-out-name {
          status obsolete;
          description
            "Standard Access-list name";
          type string;
        }
      }
    }
    container default-metric {
      status obsolete;
      description
        "Set metric of redistributed routes";
      list dm-rdr {
        status obsolete;
        key "dm-rdr";
        leaf dm-rdr {
          status obsolete;
          description
            "Bandwidth in Kbits per second";
          type uint32 {
            range "1..4294967295";
          }
        }
        list dm-rdr0 {
          status obsolete;
          key "dm-rdr0";
          leaf dm-rdr0 {
            status obsolete;
            description
              "delay metric in 10 microsecond units";
            type uint32 {
              range "0..4294967295";
            }
          }
          leaf dm-rdr-pct {
            status obsolete;
            description
              "Reliability metric where 255 is 100% reliable";
            type uint8 {
              range "0..255";
            }
          }
        }
      }
    }
    container distance {
      status obsolete;
      description
        "Define an administrative distance";
      list rad-dis {
        status obsolete;
        key "rad-dis";
        leaf rad-dis {
          status obsolete;
          description
            "Set route administrative distance";
          type uint8 {
            range "1..255";
          }
        }
        list ipv4 {
          status obsolete;
          key "ipv4";
          leaf ipv4 {
            status obsolete;
            description
              "IP Source address";
            type inet:ipv4-address;
          }
          leaf ipv40 {
            status obsolete;
            description
              "Wildcard bits";
            type inet:ipv4-address;
          }
        }
      }
      container eigrp {
        status obsolete;
        description
          "Set distance for internal and external routes";
        list di-rt {
          status obsolete;
          key "di-rt";
          leaf di-rt {
            status obsolete;
            description
              "Distance for internal routes";
            type uint8 {
              range "1..255";
            }
          }
          leaf di-rt0 {
            status obsolete;
            description
              "Distance for external routes";
            type uint8 {
              range "1..255";
            }
          }
        }
      }
    }
    container distribute-list {
      status obsolete;
      description
        "Filter entries in eigrp updates";
      list eig-filt {
        status obsolete;
        key "eig-filt";
        leaf eig-filt {
          status obsolete;
          description
            "IP expanded access list number";
          type ios-types:exp-acl-type;
        }
        container in {
          status obsolete;
          description
            "Filter incoming service updates";
          presence "true";
          leaf-list interface_name {
            status obsolete;
            description
              "Interface name";
            type string;
          }
        }
        container out {
          status obsolete;
          description
            "Filter outgoing service updates";
          presence "true";
          leaf-list interface_name {
            status obsolete;
            description
              "Interface name";
            type string;
          }
        }
      }
      container gateway {
        status obsolete;
        description
          "Filtering incoming address updates based on gateway";
        list gw-list {
          status obsolete;
          key "gw-list";
          leaf gw-list {
            status obsolete;
            description
              "Name of an IP prefix-list";
            type string;
          }
          leaf in {
            status obsolete;
            description
              "Filter incoming service updates";
            type empty;
          }
          leaf out {
            status obsolete;
            description
              "Filter outgoing service updates";
            type empty;
          }
        }
      }
      container prefix {
        status obsolete;
        description
          "Filter prefixes in address updates";
        list pl-name {
          status obsolete;
          key "pl-name";
          leaf pl-name {
            status obsolete;
            description
              "Name of an IP prefix-list";
            type string;
          }
          leaf gateway {
            status obsolete;
            description
              "Filtering incoming address updates based on gateway";
            type empty;
          }
          leaf in {
            status obsolete;
            description
              "Filter incoming service updates";
            type empty;
          }
          leaf out {
            status obsolete;
            description
              "Filter outgoing service updates";
            type empty;
          }
        }
      }
      container route-map {
        status obsolete;
        description
          "Filter prefixes based on the route-map";
        list rmap-name {
          status obsolete;
          key "rmap-name";
          leaf rmap-name {
            status obsolete;
            description
              "route-map name";
            type string;
          }
          leaf in {
            status obsolete;
            description
              "Filter incoming service updates";
            type empty;
          }
          leaf out {
            status obsolete;
            description
              "Filter outgoing service updates";
            type empty;
          }
        }
      }
    }
    container eigrp {
      status deprecated;
      description
        "EIGRP Address Family specific commands";
      leaf router-id {
        status deprecated;
        description
          "router id for this EIGRP process";
        type inet:ipv4-address;
      }
      container stub {
        status obsolete;
        description
          "Set address-family in stubbed mode";
        presence "true";
        leaf connected {
          status obsolete;
          description
            "Do advertise connected routes";
          type empty;
        }
        leaf summary {
          status obsolete;
          description
            "Do advertise summary routes";
          type empty;
        }
        leaf redistributed {
          status obsolete;
          description
            "Do advertise redistributed routes";
          type empty;
        }
        leaf leak-map {
          status obsolete;
          description
            "Allow dynamic prefixes based on the leak-map";
          type string;
        }
        leaf receive-only {
          status obsolete;
          description
            "Set receive only neighbor";
          type empty;
        }
        leaf static {
          status obsolete;
          description
            "Do advertise static routes";
          type empty;
        }
      }
      leaf stub-site {
          status obsolete;
        description
          "ASN:nn, Dotted-Decimal:nn or 4BASN:nn  Stub-Site ID in aa:nn format";
        type string;
      }
    }
    leaf maximum-paths {
      status obsolete;
      description
        "Number of paths";
      type uint8 {
        range "1..32";
      }
    }
    container metric {
      status obsolete;
      description
        "Modify metrics and parameters for advertisement";
      leaf maximum-hops {
        status obsolete;
        description
          "Hop count";
        type uint8 {
          range "1..255";
        }
      }
      leaf weights {
        status obsolete;
        description
          "Type (Only TOS 0 supported)";
        type uint8 {
          range "0..8";
        }
     }
    }
    container neighbor {
      status obsolete;
      description
        "Specify a neighbor router";
      list ipv4 {
        status obsolete;
        key "ipv4";
        leaf ipv4 {
          status obsolete;
          description
            "Neighbor address";
          type inet:ipv4-address;
        }
        container interface {
          status obsolete;
          description
            "Specify interface for global address";
          uses ios-ifc:interface-grouping;
        }
      }
    }
    list network {
      status deprecated;
      description
        "Enable routing on an IP network";
      key number;
      leaf number {
        status deprecated;
        description
          "Network number";
        type inet:ipv4-address;
      }
      leaf wild-card {
        status deprecated;
        description
          "EIGRP wild card bits";
        type inet:ipv4-address;
      }
    }
    leaf nsf {
      status obsolete;
      description
        "Non-stop forwarding";
      type empty;
    }
    container offset-list {
      status obsolete;
      description
        "Add or subtract offset from EIGRP metrics";
      list nsr-list {
        status obsolete;
        key "nsr-list";
        leaf nsr-list {
          status obsolete;
          description
            "Access list of networks to apply offset (extended range)";
          type uint16 {
            range "1300..1999";
          }
        }
        leaf in {
          status obsolete;
          description
            "Perform offset on incoming updates";
          type empty;
        }
        leaf out {
          status obsolete;
          description
            "Perform offset on outgoing updates";
          type empty;
        }
      }
      list ol-acl {
        status obsolete;
        key "ol-acl";
        leaf ol-acl {
          status obsolete;
          description
            "Access-list name";
          type string;
        }
        leaf in {
          status obsolete;
          description
            "Perform offset on incoming updates";
          type empty;
        }
        leaf out {
          status obsolete;
          description
            "Perform offset on outgoing updates";
          type empty;
        }
      }
    }
    container redistribute {
      status obsolete;
      description
        "Redistribute IPv4 routes from another routing protocol";
      list bgp {
        status obsolete;
        description
          "Border Gateway Protocol (BGP)";
        key "rdr-as";
        leaf rdr-as {
          status obsolete;
          description
            "Autonomous system number";
          type ios-types:bgp-as-number-type;
        }
        container metric {
          status obsolete;
          description
            "Metric for redistributed routes";
          leaf bandwith {
            status obsolete;
            description
              "Bandwidth metric in Kbits per second";
            type uint32 {
              range "1..4294967295";
            }
          }
          leaf delay {
            status obsolete;
            description
              "EIGRP delay metric, in 10 microsecond units";
            type uint32 {
              range "0..4294967295";
            }
          }
          leaf reliability {
            status obsolete;
            description
              "EIGRP reliability metric where 255 is 100% reliable";
            type uint8 {
              range "0..255";
            }
          }
          leaf Effective {
            status obsolete;
            description
              "EIGRP Effective bandwidth metric (Loading) where 255 is 100% loaded";
            type uint8 {
              range "1..255";
            }
          }
          leaf mtu {
            status obsolete;
            description
              "EIGRP MTU of the path";
            type uint16 {
              range "1..65535";
            }
          }
        }
        leaf route-map {
          status obsolete;
          description
            "Route map reference";
          type string;
        }
        leaf rd-LESSER_1_PERIOD_0-XX_PERIOD_YY_GREATER_ {
          status obsolete;
          description
            "Autonomous system number";
          type empty;
        }
      }
      container connected {
        status obsolete;
        description
          "Connected";
        presence "true";
        leaf metric {
          status obsolete;
          description
            "Metric for redistributed routes";
          type empty;
        }
        leaf route-map {
          status obsolete;
          description
            "Route map reference";
          type empty;
        }
      }
      leaf eigrp {
        status obsolete;
        description
          "Autonomous system number";
        type uint16 {
          range "1..65535";
        }
      }
      container isis {
        status obsolete;
        description
          "ISO IS-IS";
        presence "true";
        leaf is-tag {
          status obsolete;
          description
            "ISO routing area tag";
          type string;
        }
        leaf level-1 {
          status obsolete;
          description
            "IS-IS level-1 routes only";
          type empty;
        }
        leaf level-1-2 {
          status obsolete;
          description
            "IS-IS level-1 and level-2 routes";
          type empty;
        }
        leaf level-2 {
          status obsolete;
          description
            "IS-IS level-2 routes only";
          type empty;
        }
        leaf metric {
          status obsolete;
          description
            "Metric for redistributed routes";
          type empty;
        }
        leaf route-map {
          status obsolete;
          description
            "Route map reference";
          type empty;
        }
      }
      container lisp {
        status obsolete;
        description
          "Locator ID Separation Protocol (LISP)";
        presence "true";
        leaf metric {
          status obsolete;
          description
            "Metric for redistributed routes";
          type empty;
        }
        leaf route-map {
          status obsolete;
          description
            "Route map reference";
          type empty;
        }
      }
      container mobile {
        status obsolete;
        description
          "Mobile routes";
        presence "true";
        leaf metric {
          status obsolete;
          description
            "Metric for redistributed routes";
          type empty;
        }
        leaf route-map {
          status obsolete;
          description
            "Route map reference";
          type empty;
        }
      }
      container odr {
        status obsolete;
        description
          "On Demand stub Routes";
        presence "true";
        leaf metric {
          status obsolete;
          description
            "Metric for redistributed routes";
          type empty;
        }
        leaf route-map {
          status obsolete;
          description
            "Route map reference";
          type empty;
        }
      }
      leaf ospf {
        status obsolete;
        description
          "Process ID";
        type uint16 {
          range "1..65535";
        }
      }
      container rip {
        status obsolete;
        description
          "Routing Information Protocol (RIP)";
        presence "true";
        leaf metric {
          status obsolete;
          description
            "Metric for redistributed routes";
          type empty;
        }
        leaf route-map {
          status obsolete;
          description
            "Route map reference";
          type empty;
        }
      }
      container static {
        status obsolete;
        description
          "Static routes";
        presence "true";
        leaf metric {
          status obsolete;
          description
            "Metric for redistributed routes";
          type empty;
        }
        leaf route-map {
          status obsolete;
          description
            "Route map reference";
          type empty;
        }
      }
      container vrf {
        status obsolete;
        description
          "Specify a source virtual routing/forwarding instance";
        leaf name {
          status obsolete;
          description
            "Virtual Routing/Forwarding instance name";
          type string;
        }
        leaf global {
          status obsolete;
          description
            "global VRF";
          type empty;
        }
      }
    }
    leaf shutdown {
      status obsolete;
      description
        "Shutdown this instance of EIGRP";
      type empty;
    }
    container summary-metric {
      status obsolete;
      description
        "Specify summary to apply metric/filtering";
      list ipv4 {
        status obsolete;
        key "ipv4";
        leaf ipv4 {
          status obsolete;
          description
            "Summary to configure static metric";
          type inet:ipv4-address;
        }
        leaf mask {
          status obsolete;
          description
            "Network mask";
          type inet:ipv4-address;
        }
      }
      leaf A_PERIOD_B_PERIOD_C_PERIOD_D_SLASH_nn {
        status obsolete;
        description
          "Summary <network>/<length>, e.g., 192.168.0.0/16";
        type empty;
      }
    }
    container timers {
      status obsolete;
      description
        "Adjust routing timers";
      container active-time {
        status obsolete;
        description
          "time limit for active state";
        leaf atimer {
          status obsolete;
          description
            "active state time limit in minutes";
          type uint16 {
            range "1..65535";
          }
        }
        leaf disabled {
          status obsolete;
          description
            "disable time limit for active state";
          type empty;
        }
      }
      container graceful-restart {
        status obsolete;
        description
          "EIGRP Graceful Restart timer";
        leaf purge-time {
          status obsolete;
          description
            "EIGRP stale route purge time";
          type empty;
        }
      }
      container nsf {
        status obsolete;
        description
          "EIGRP NSF timer";
        leaf converge {
          status obsolete;
          description
            "EIGRP time limit for convergence after switchover";
          type empty;
        }
        leaf signal {
          status obsolete;
          description
            "EIGRP time limit for signaling NSF restart";
          type empty;
        }
      }
    }
    container traffic-share {
      status obsolete;
      description
        "How to compute traffic share over alternate paths";
      leaf balanced {
        status obsolete;
        description
          "Share inversely proportional to metric";
        type empty;
      }
      container min {
        status obsolete;
        description
          "All traffic shared among min metric paths";
        leaf across-interfaces {
          status obsolete;
          description
            "Use different interfaces for equal-cost paths";
          type empty;
        }
      }
    }
    leaf variance {
      status obsolete;
      description
        "Metric variance multiplier";
      type uint8 {
        range "1..128";
      }
    }
  }

  grouping config-router-eigrp-grouping {
    status deprecated;
    list eigrp { //69666
      status deprecated;
      description
        "Enhanced Interior Gateway Routing Protocol (EIGRP) (DEPRECATED, use router-eigrp)";
      key "id";
      leaf id {
        status deprecated;
        description
          "Autonomous System ID";
        type union {
          type uint16 {
            range "1..65535";
          }
          type string;
        }
      }

      container passive-interface {
        status obsolete;
        description "Suppress routing updates on an interface";
        leaf interface {
          status obsolete;
          description "interface name";
          type string;
        }
        leaf Tunnel {
          status obsolete;
          description "Tunnel interface number";
          type uint32 {
            range "0..2147483647";
          }
        }
        leaf Vlan {
          status obsolete;
          description "Vlan interface number";
          type uint16 {
             range "1..4094";
          }
        }
        leaf default {
          status obsolete;
          description "Suppress routing updates on all interfaces";
          type empty;
        }
      }

      list address-family {
        status deprecated;
        description
          "Enter Address Family command mode";
        key "type";
        leaf type {
          status deprecated;
          type enumeration {
            enum "ipv4";
            enum "ipv6";
          }
        }

        list af-ip-list {
          status obsolete;
          description
            "Address family IPv4/IPv6";
          key "unicast-multicast";
          leaf unicast-multicast {
            status obsolete;
            type enumeration {
              enum "unicast";
              enum "multicast";
            }
          }
          leaf autonomous-system {
            status obsolete;
            description
              "Specify Address-Family Autonomous System Number";
            type uint16 {
              range "1..65535";
            }
          }
          uses eigrp-address-family-grouping;
          uses eigrp-topology-base-grouping;
        }

        list af-ip-vrf-list {
          status deprecated;
          description
            "Address family IPv4/IPv6 VRF";
          key "vrf";
          leaf vrf {
            status deprecated;
	    must "/ios:native/ios:vrf/ios:definition[ios:name=current()] or /ios:native/ios:ip/ios:vrf[ios:name=current()]" {
	      error-message "VRF must be created 1st, deleted last";
            }
            type string;
          }
          leaf unicast-multicast {
            status deprecated;
            type enumeration {
              enum "unicast";
              enum "multicast";
            }
          }
          leaf autonomous-system {
            status deprecated;
            description
            "Specify Address-Family Autonomous System Number?";
            type uint16;
          }
          uses eigrp-address-family-grouping;
          uses eigrp-topology-base-grouping;
        }
      }
      uses eigrp-address-family-grouping;
    }
  }

  grouping config-router-ipv6-eigrp-grouping {
    status obsolete;
    container default-metric {
      status obsolete;
      description
        "Set metric of redistributed routes";
      leaf dm-rdr {
        status obsolete;
        description
          "Bandwidth in Kbits per second";
        type uint32 {
          range "1..4294967295";
        }
      }
      leaf dm-rdr0 {
        status obsolete;
        description
          "delay metric in 10 microsecond units";
        type uint32 {
          range "0..4294967295";
        }
      }
      leaf dm-rdr-pct {
        status obsolete;
        description
          "Reliability metric where 255 is 100% reliable";
        type uint8 {
          range "0..255";
        }
      }
      leaf effective-bandwith-metric {
        status obsolete;
        description
          "Effective bandwidth metric (Loading) where 255 is 100% loaded";
        type uint8;
      }
      leaf mtu {
        status obsolete;
        description
          "Maximum Transmission Unit metric of the path ";
        type uint16;
      }
    }
    container distance {
      status obsolete;
      description
        "Define an administrative distance";
      container eigrp {
        status obsolete;
        description
          "EIGRP-IPV6 distance";
        leaf internal-route {
          status obsolete;
          description
            "Distance for internal routes";
          type uint8;
        }
        leaf external-route {
          status obsolete;
          description
            "Distance for external routes";
          type uint8;
        }
      }
    }
    uses ipv6-router-distribute-list-grouping;
    container eigrp {
      status obsolete;
      description
        "EIGRP specific commands";
      leaf router-id {
        status obsolete;
        description
          "router id for this EIGRP process";
        type inet:ipv4-address;
      }
    }
    list passive-interface {
      status obsolete;
      description
        "Suppress routing updates on an interface";
      key "name";
      leaf name {
        status obsolete;
        type union {
          type string;
          type enumeration {
            enum "default";
          }
        }
      }
    }
  }

  grouping config-route-tag-grouping {
      container list {
        list rt-name {
          key "rt-name";
          leaf rt-name {
            type string;
          }
          container deny {
            list ipv4 {
              key "ipv4";
              leaf ipv4 {
                type inet:ipv4-address;
              }
              leaf mask {
                type inet:ipv4-address;
              }
            }
          }
          container permit {
            list ipv4 {
              key "ipv4";
              leaf ipv4 {
                type inet:ipv4-address;
              }
              leaf mask {
                type inet:ipv4-address;
              }
            }
          }
          container seq {
            list seq-num {
              key "seq-num";
              leaf seq-num {
                type uint32 {
                  range "1..4294967294";
                }
              }
              container deny {
                leaf ipv4 {
                  type inet:ipv4-address;
                }
                leaf mask {
                  type inet:ipv4-address;
                }
              }
              container permit {
                leaf ipv4 {
                  type inet:ipv4-address;
                }
                leaf mask {
                  type inet:ipv4-address;
                }
              }
            }
          }
        }
      }
      container notation {
        leaf dotted-decimal {
          type empty;
        }
      }
  }
}
