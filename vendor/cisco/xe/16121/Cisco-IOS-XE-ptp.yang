module Cisco-IOS-XE-ptp {
  namespace "http://cisco.com/ns/yang/Cisco-IOS-XE-ptp";
  prefix ios-ptp;

  import cisco-semver {
    prefix cisco-semver;
  }
 
  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Precision Time Protocol (PTP) Yang Model.
     Copyright (c) 2016-2017 by Cisco Systems, Inc.
     All rights reserved.";

  // =========================================================================
  // REVISION
  // =========================================================================

  revision 2019-07-01 {
    description "Establish semantic version baseline";
    cisco-semver:module-version "1.0.0";
  }
  revision 2017-09-19 {
    description
      "Extension for edison";
  }

  revision 2017-02-07 {
    description
      "Initial revision";
  }



  grouping config-ptp-grouping {
    container ptp {
      description
        "Precision Time Protocol";
      container clock {
        description
          "Configure PTP clock";
        container ordinary {
          description
            "Configure PTP Ordinary clock";
          leaf domain {
            description
              "PTP domain";
            type int8 {
              range "0..127";
            }
          }
        }
        container clock-port {
          description
            "Configure clock port";
          leaf name {
            description
              "Port name";
            type string;
          }
          leaf slave {
            description
              "Configure as Slave";
            type empty;
          }
          leaf master {
            description
              "Configure as Master";
            type empty;
          }
          container transport {
            description
              "Set port transport parameters";
            leaf ipv4 {
              description
                "Use IPv4 encapsulation";
              type empty;
            }
            container unicast {
              description
                "Use unicast communication channel";
              leaf interface {
                type string;
              }
              leaf negotiation {
                description
                  "Enable unicast negotiation";
                type empty;
              }
            }
          }
          container clock {
            leaf source {
              type inet:ipv4-address;
            }
          }
        }
      }
    }
  }

  grouping config-ptp-grouping2 {
  // container ptp {
        leaf domain {
            description "Clock domain number";
            type uint8;
        }
        container profile {
            leaf dot1as {
                type empty;
            }
        }
        leaf neighbor-propagation-delay-threshold {
            description "in nanoseconds";
            type uint32 {
                range "1..2147483646";
            }
        }
        leaf priority1 {
            description "clock priority1 number";
            type uint8 {
                range "0..255";
            }
        }
        leaf priority2 {
            description "clock priority2 number";
            type uint8 {
                range "0..255";
            }
        }
        container mode {
            container boundary {
                leaf delay-req {
                    type empty;
                }
                leaf pdelay-req {
                    type empty;
                }
            }
            leaf e2etransparent {
                type empty;
            }
            leaf p2ptransparent {
                type empty;
            }
        }
 //   }
 }

  /////////////////////////////////////////////////////////
  // native / ptp
  /////////////////////////////////////////////////////////
  augment "/ios:native/ios:ptp" {
    uses config-ptp-grouping2;
  }
}
