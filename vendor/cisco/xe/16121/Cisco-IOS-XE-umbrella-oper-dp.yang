module Cisco-IOS-XE-umbrella-oper-dp {
  namespace "http://cisco.com/ns/yang/Cisco-IOS-XE-umbrella-oper-dp";
  prefix ios-xe-umbrella-oper-dp;

  import cisco-semver {
    prefix cisco-semver;
  }
 
  import ietf-inet-types {
    prefix inet;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Umbrella Operational Yang model for DP.
     Copyright (c) 2018 by Cisco Systems, Inc.
     All rights reserved.";

  // =========================================================================
  // REVISION
  // =========================================================================
  revision 2019-07-01 {
    description "Establish semantic version baseline";
    cisco-semver:module-version "1.0.0";
  }
  revision 2018-08-23 {
    description
      "Update umbrella data-plane stats for matching-flow-found";
  }

  // =========================================================================
  // REVISION
  // =========================================================================
  revision 2018-07-27 {
    description
      "Update umbrella data-plane stats";
  }

  // =========================================================================
  // REVISION
  // =========================================================================
  revision 2018-05-10 {
    description
      "Initial revision";
  }

  //==========================================================================
  // Operations
  //==========================================================================

  container umbrella-oper-dp {

    container stats {
      config "false";

      leaf redirect-pkts {
        type uint64;
      }
             
      leaf local-domain-bypass-pkts {
        type uint64;
      }
            
      leaf parser-unknown-pkts {
        type uint64;
      }

      leaf parser-errors {
        type uint64;
      }
           
      leaf flow-create-requests {
        type uint64;
      }

      leaf matching-flow-found {
        type uint64;
      }
              
      leaf flow-create-failures {
        type uint64;
      }
          
      leaf flow-lookup-requests {
        type uint64;
      }
        
      leaf flow-lookup-failures {
        type uint64;
      }
          
      leaf flow-detach-requests {
        type uint64;
      }
                 
      leaf flow-detach-failures {
        type uint64;
      }
            
      leaf flow-ageout-count {
        type uint64;
      }
            
      leaf flow-update-requests {
        type uint64;
      }
              
      leaf flow-update-failures {
        type uint64;
      }
      
      leaf dnscrypt-enc-sent {
        type uint64;
      }
      
      leaf dnscrypt-dec-rcvd {
        type uint64;
      }
        
      leaf dnscrypt-clear-sent {
        type uint64;
      }
      
      leaf dnscrypt-clear-rcvd {
        type uint64;
      }
      
      leaf dnscrypt-errors {
        type uint64;
      }
    }
  }

  //==========================================================================
  // Notifications
  //==========================================================================

  typedef umbrella-netconf-notification-severity {
    type enumeration {
      enum critical {
        value 0;
      }
      enum major {
        value 1;
      }
      enum minor {
        value 2;
      }
    }
  }
 
  notification umbrella-anycast-server-switch {
    leaf severity-level {
      type umbrella-netconf-notification-severity;
    }
   
    leaf host-name {
      type string;
    }
   
    leaf system-ip {
      type inet:ip-address;
    }
   
    leaf reason {
      type string;
    }
  }

  notification umbrella-max-cft-flows {
    leaf severity-level {
      type umbrella-netconf-notification-severity;
    }
   
    leaf host-name {
      type string;
    }
   
    leaf system-ip {
      type inet:ip-address;
    }
   
    leaf reason {
      type string;
    }
  }
}
