module Cisco-IOS-XE-nat {
  namespace "http://cisco.com/ns/yang/Cisco-IOS-XE-nat";
  prefix ios-nat;

  import cisco-semver {
    prefix cisco-semver;
  }
 
  import ietf-inet-types {
    prefix inet;
  }


  import Cisco-IOS-XE-types {
    prefix ios-types;
  }

  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Network Address Translation (NAT) Yang model.
     Copyright (c) 2016-2019 by Cisco Systems, Inc.
     All rights reserved.";

  // =========================================================================
  // REVISION
  // =========================================================================
  revision 2019-07-01 {
    description 
      "- Establish semantic version baseline
       - Implementation of NAT64 DIA route support
       - Implementation of create, switchover, settings, service and missing
         parts of translation max-entries
       - Add ip nat to interface BD-VIF";
    cisco-semver:module-version "1.0.0";
  }
  revision 2019-02-04 {
    description
      "fixed issue with config for ip nat source list interface to allow
      more than one config";
  }
  revision 2019-01-22 {
     description
      "Added leaf for App-hosting Gigabit Ethernet interface";
  }
  revision 2018-12-18 {
    description
      "fix ip nat inside static with multiple vrf get-config missing config issue";
  }
  revision 2018-12-07 {
    description
      "Move nat64 timeout configuration for protocols into timeout container";
  }
  revision 2018-11-21 {
      description
      "Cleanup spelling errors in description statements";
  }
  revision 2018-11-15 {
    description
      "Add correct dependencies on VRF to 'ip nat route'";
  }
  revision 2018-10-04 {
      description
         "fix to allow multiple pool/interface under different vrf";
  }

  revision 2018-08-31 {
      description
         "add nat inside/outside to Vlan interfaces";
  }

  revision 2018-08-22 {
      description
         "fix the deletion of ip nat inside source static <ip> <ip> vrf";
  }  

  revision 2018-08-18 {
      description
         "Changed source inside source list to use only one pool/interface";
  }  

  revision 2018-08-08 {
      description
         "force overload to 'ip nat inside source list interface/vrf' and 'ip
nat inside source route-map interface/vrf'";
  }  

  revision 2018-07-07 {
      description
         "Added ip nat to interface Multilink";
  }  

  revision 2018-06-30{
    description
        "fixing source list pool/interface and source route-map pool/interface
issues";
  }
  revision 2018-06-28{
    description
        "Added must constraints for deleting vrf";
  }
  revision 2018-05-29{
    description
        "Add ip nat inside source static <ip> <interface>";
  }
  revision 2018-05-18{
    description
        "Add NAT models under ATM interface and sub interface";
  }
  revision 2018-05-17 {
     description
       "Added ip nat to interface Dialer";
  }
  revision 2018-04-03 {
     description
       "Added ip nat to interface Serial";
  }
  revision 2018-03-21 {
     description
       "Make ip nat inside source list interface/pool vrf list";
  }
  revision 2018-03-14 {
     description
       "Added ip nat to interface VirtualPortGroup";
  }

  revision 2018-02-22 {
     description
       "Added ip nat to interface Cellular";
  }

  revision 2018-01-25 {
     description
       "Added model for ip nat translation max-entries host";
  }

  revision 2017-11-27 {
     description
       "Added Change 25GE name";
  }

  revision 2017-11-14 {
    description 
      "Add 40 and 100GE support";
  }

  revision 2017-11-10 {
    description 
      "Add translation timeout support";
  }
  revision 2017-11-06 {
    description 
      "Add ip nat to interface BDI";
  }
  revision 2017-10-06 {
    description
      "Model for ip nat route vrf <vrfname> <ipaddr> <netmask> global";
  }
  revision 2017-09-15 {
    description 
      "This revison has changes for new 2gig interface addition";
  }
  revision 2017-08-16 {
    description
      "This revision has changes for new 5gig and 25gig interfaces addition";
  }

  revision 2017-08-03 {
    description
      " Static NAT with VRF and route-map results in incorrect CLI order";
  }
  revision 2017-06-16 {
    description
      "Native Yang Support for NATv6";
  }
  revision 2017-03-14 {
    description
      "Add Container node Pool, Oer and Overload 
       under node Route-map.";
  }

  revision 2017-02-07 {
    description
      "Initial revision";
  }

  grouping config-interface-ip-nat-grouping {
    container nat {
      description
          "NAT interface commands";
      leaf allow-static-host {
        description
          "Allow static-ip clients";
        type empty;
      }
      leaf enable {
        description
          "Enable Address Translation (NVI)";
        type empty;
      }
      leaf stick {
        description
          "Stick(Hairpin) interface for address translations";
        type empty;
      }
      choice nat-choice {
        leaf inside {
          description
            "Inside interface for address translation";
          type empty;
        }
        leaf outside {
          description
            "Outside interface for address translation";
          type empty;
        }
      }
    }
  }
 
  grouping config-ip-nat-source-route-map-pool-base-grouping {
    leaf overload {
      description
        "Overload an address translation";
      type empty;
    }
    leaf extended {
      description
        "Overload extended";
      when "../overload";
      type empty;
    }
    leaf oer {
      description
        "Use with vtemplate only. On new translation, if OER BR is UP,
         OER will select IP from outgoing Interface.
         All packets matching translation are forwarded over Interface
         for duration of translation.";
      type empty;
    }
    leaf reversible {
      description
        "Allow out->in traffic";
      type empty;
    }
  }

  grouping config-ip-nat-source-pool-vrf-base-grouping {
    list vrf {
      description
        "Specify vrf";
      
      key "name";
      leaf name {
        must "/ios:native/ios:vrf/ios:definition[ios:name=current()] or /ios:native/ios:ip/ios:vrf[ios:name=current()]" {
          error-message "VRF must be created 1st, deleted last";
        }
        type string;
      }
      leaf match-in-vrf {
        description
          "Match incoming vrf";
        type empty;
      }
      leaf overload {
        description
          "Overload an address translation";
        type empty;
      }
    }
  }

  grouping config-ip-nat-source-route-map-pool-option-grouping {
    list redundancy {
      
      key "name";
      leaf name {
        type uint8 {
          range "1..2";
        } 
      }
      list mapping-id {
        description
          "Associate a mapping id to this mapping";
      
      key "name";
      leaf name {
        type uint32 {
          range "1..2147483647";
        }
      }
      uses config-ip-nat-source-route-map-pool-base-grouping;
      }
    }
    uses config-ip-nat-source-route-map-pool-base-grouping;
  }

  grouping config-ip-nat-source-pool-vrf-grouping {
    list redundancy {
      
      key "name";
      leaf name {
        type uint8 {
          range "1..2";
        } 
      }
      list mapping-id {
        description
          "Associate a mapping id to this mapping";
        
        key "name";
        leaf name {
          type uint32 {
            range "1..2147483647";
          }
        }
        uses config-ip-nat-source-pool-vrf-base-grouping;
      }
    }
    uses config-ip-nat-source-pool-vrf-base-grouping;
  }

  grouping config-ip-nat-source-interface-base-grouping {
    leaf overload {
      description
        "Overload an address translation";
      mandatory true;
      type empty;
    }
    leaf extended {
      description
        "Overload extended";
      when "../overload";
      type empty;
    }
    leaf oer {
      description
        "Use with vtemplate only.  On new translation,
         if OER BR is UP, OER will select IP from outgoing
         Interface.  All packets matching translation are
         forwarded over Interface for duration of translation.";
      type empty;
    }
  }

  grouping config-ip-nat-source-interface-vrf-grouping {
    list vrf {
      description
        "Specify vrf";
      
      key "vrf-name";
      leaf vrf-name {
        description
          "vrf name";
        type string;
      }
      uses config-ip-nat-source-interface-base-grouping;
    }
  }

  grouping config-ip-nat-source-list-pool-base-grouping {
    leaf overload {
      description
        "Overload an address translation";
      type empty;
    }
    leaf extended {
      description
        "Overload extended";
      when "../overload";
      type empty;
    }
    leaf oer {
      description
        "Use with vtemplate only. On new translation, if OER BR is UP,
         OER will select IP from outgoing Interface.
         All packets matching translation are forwarded over Interface
         for duration of translation.";
      type empty;
    }
  }

  grouping config-ip-nat-source-list-pool-option-grouping {
    list redundancy {
      
      key "name";
      leaf name {
        type uint8 {
          range "1..2";
        } 
      }
      list mapping-id {
        description
          "Associate a mapping id to this mapping";
      
      key "name";
      leaf name {
        type uint32 {
          range "1..2147483647";
        }
      }
      uses config-ip-nat-source-list-pool-base-grouping;
      }
    }
    uses config-ip-nat-source-list-pool-base-grouping;
  }

  grouping config-ip-nat-inside-source-pool-with-vrf-grouping {
    container pool-with-vrf {
      list pool {
        description
          "Name pool of global addresses";
        
        key "name";
        leaf name {
          type string;
        }
        uses config-ip-nat-source-pool-vrf-grouping;
      }
    }
  }

  grouping config-ip-nat-inside-source-interface-grouping {
    list interface {
      description
        "Specify interface for global address";
      
      key "name";
      leaf name {
        type string;
      }
      uses config-ip-nat-source-interface-base-grouping;
    }

    // ip nat inside source list * interface * vrf *
    container interface-with-vrf {
      list interface {
        description
          "Specify interface for global address";
        
        key "name";
        leaf name {
          type string;
        }
        uses config-ip-nat-source-interface-vrf-grouping;
      }
    }
  }
     
  grouping config-ip-nat-source-route-map-pool-interface-grouping {            
    // ip nat inside source route-map pool *
    choice pool-or-interface {
      case pool-choice {
        list pool {
          description
            "Name pool of global addresses";
          
          max-elements "1";
          key "pool-name";
          leaf pool-name {
            description 
              "Pool name for global addresses";
            type string;
          }
          uses config-ip-nat-source-route-map-pool-option-grouping;
        }

        // ip nat inside source route-map pool * vrf *
        uses config-ip-nat-inside-source-pool-with-vrf-grouping;
      }

      case interface-choice {
         // ip nat inside source route-map interface 
         uses config-ip-nat-inside-source-interface-grouping;
      }
    }
  }

  grouping config-ip-nat-source-list-pool-interface-grouping {
    // ip nat inside source list * pool
    choice pool-or-interface {
      case pool-choice {
        list pool {
          description
            "Name pool of global addresses";
          
          max-elements "1";
          key "name";
          leaf name {
            description
              "Pool name for global addresses";
            type string;
          }
          uses config-ip-nat-source-list-pool-option-grouping;
        }
        
        // ip nat inside source list * pool * vrf *
        uses config-ip-nat-inside-source-pool-with-vrf-grouping;
      }

      // ip nat inside source list * interface
      // Note: "overload" will always in show running 
      //       so add incomplete command in interface.
      case interface-choice {
         // ip nat inside source route-map interface 
         uses config-ip-nat-inside-source-interface-grouping;
      }
    }
  }
  
  grouping ip-nat-translation-port-number-grouping {
    container protocol {
      
      leaf port-numer {
        description
          "Port number";
        type uint16 {
          range "1..63535";
        }
      }
      leaf time-val {
        description
          "Timeout in seconds";
        type uint32 {
          range "0..536870";
        }
      }
      leaf never {
        description
          "Never timeout";
        type empty;
      }
    }
  }

  grouping ip-nat-translation-timeout-grouping {
    leaf time-val {
      description
        "Timeout in seconds";
      type uint32 {
        range "0..536870";
      }
    }
    leaf never {
      description
        "Never timeout";
      type empty;
    }
  }

  grouping config-ip-nat-source-static-transport-common-part-one-grouping {
    leaf proto {
      
      type enumeration {
        enum "tcp";
        enum "udp";
      }
    }
    leaf network {
      description
        "Subnet translation";
      
      type empty;
    }
    leaf local-port {
      
      type uint16 {
        range "1..65535";
      }
    }
    leaf mask {
      type union {
        type inet:ipv4-address;
        type string;
      }
    }
    leaf global-port {
      type uint16 {
        range "1..65535";
      }
    }
    leaf extendable {
      description
        "Extend this translation when used";
      type empty;
    }
    leaf no-alias {
      description
        "Do not create an alias for the global address";
      type empty;
    }
    leaf no-payload {
      description
        "No translation of embedded address/port in the payload";
      type empty;
    }
    leaf route-map {
      description
        "Specify route-map";
      type string;
    }
    leaf reversible {
      when "../route-map";
      type empty;
    }
    leaf redundancy {
      description
        "NAT redundancy operation";
      type union {
        type uint8;
        type string;
      }
    }
    leaf mapping-id {
      description
        "Associate a mapping id to this mapping";
      when "../redundancy";
      type uint32 {
        range "1..2147483647";
      }
    }
  }

  grouping config-ip-nat-source-static-transport-common-part-two-grouping {
    leaf forced {
      description
        "Delete this entry and its children, even if in use";
      type empty;
    }
    leaf overload {
      description
        "Overload an address translation";
      type empty;
    }
  }

  grouping config-ip-nat-grouping {
    container nat { //43751
      description
        "NAT configuration commands";
      // ip nat pool *
      list pool {
        description
          "Define pool of addresses";
        
        key "id";
        leaf id {
          type string;
        }
        leaf start-address {
          type inet:ipv4-address;
        }
        leaf end-address {
          when "../start-address" {
          }
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum "match-host";
              enum "rotary";
            }
          }
          leaf add-route {
            description
              "Add special route to Virtual Interface";
            type empty;
          }
        }
      }
      // ip nat inside
      container inside {
        description
          "Inside address translation";
        // ip nat inside source
        container source {
          description
            "Source address translation";
          // ip nat inside source list *
          list list {
            description
              "Specify access list describing local addresses";
            key "id";
            leaf id {
              type union {
                type uint16 {
                  range "1..2699";
                }
                type string;
              }
            }
            uses config-ip-nat-source-list-pool-interface-grouping;             
          }

          // ip nat inside source route-map *
          list route-map {
            description
              "Specify route-map";
            key "route-map-name";
            leaf route-map-name {
              description
                "Route-map name";
              type string;
            }
            uses config-ip-nat-source-route-map-pool-interface-grouping;             
          } 

          // ip nat inside source static
          container static {
            description
              "Specify static local->global mapping";
            list nat-static-transport-list-with-vrf {
              
              key "local-ip global-ip vrf";
              leaf local-ip {
                type inet:ipv4-address;
              }
              leaf global-ip {
                type inet:ipv4-address;
              }
              leaf vrf {
                description
                  "Specify vrf";
                type string;
              }
              uses config-ip-nat-source-static-transport-common-part-one-grouping;
              leaf match-in-vrf {
                description
                  "Match incoming vrf";
                when "../vrf";
                type empty;
              }
              uses config-ip-nat-source-static-transport-common-part-two-grouping;
            }
            list nat-static-transport-list {
              
              key "local-ip global-ip";
              leaf local-ip {
                type inet:ipv4-address;
              }
              leaf global-ip {
                type inet:ipv4-address;
              }
              uses config-ip-nat-source-static-transport-common-part-one-grouping;
              uses config-ip-nat-source-static-transport-common-part-two-grouping;
            }
            list nat-static-proto-transport-interface-list {
              
              key "proto local-ip local-port";
              leaf proto {
                type enumeration {
                  enum "tcp";
                  enum "udp";
                }
              }
              leaf local-ip {
                type inet:ipv4-address;
              }
              leaf local-port {
                type uint16 {
                  range "1..65535";
                }
              }
              container interface {
                description
                  "Specify interface for global address";
                uses ios-ifc:interface-grouping;
              }
              leaf global-port {
                type uint16 {
                  range "1..65535";
                }
              }
            }
            list nat-static-transport-interface-list {
              
              key "local-ip";
              leaf local-ip {
                type inet:ipv4-address;
              }
              container interface {
                description
                  "Specify interface for global address";
                uses ios-ifc:interface-grouping;
              }
            }
          }
        }
        // ip nat inside destination
        container destination {
          description
            "Destination address translation";
          // ip nat inside destination list *
          list list {
            description
              "Specify access list describing global addresses";
            
            key "id";
            leaf id {
              type union {
                type uint16 {
                  range "1..2699";
                }
                type string;
              }
            }
            // ip nat inside destination list * pool *
            leaf pool {
              description
                "Name pool of local addresses";
              type string;
              
            }
            // [ redundancy redundancy-id ]
            leaf redundancy {
              description
                "NAT redundancy operation";
              type uint8 {
                range "1..2";
              }
            }
            leaf mapping-id {
              description
                "Associate a mapping id to this mapping";
              type uint32 {
                range "1..2147483647";
              }
            }
          }
        }
      }

      // ip nat outside
      container outside {
        description
          "Outside address translation";
        container source {
          description
            "Source address translation";
          // ip nat outside source static 
          container static {
            description 
              "Specify static global->local mapping";
            list nat-static-transport-list {
                                        
              key "global-ip local-ip";  
              leaf global-ip {
                type inet:ipv4-address;
              }
              leaf local-ip {
                type inet:ipv4-address;
              } 
              leaf vrf {
                description
                  "Specify vrf";
                type string;
              }
              leaf extendable {
                description
                  "Extend this translation when used";
                type empty;
              }
              leaf no-payload {
                description
                  "No translation of embedded address/port in the payload";
                type empty;
              }
            }
          }
        }

        list list {
          description
            "Specify access list describing global addresses";
          
          key "id";
          leaf id {
            type union {
              type uint16 {
                range "1..2699";
              }
              type string;
            }
          }
          leaf pool {
            description
              "Name pool of local addresses";
            type string;
            
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          
          key "id";
          leaf id {
            type string;
          }
          leaf pool {
            description
              "Name pool of local addresses";
            type string;
            
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
      container translation {
        container dns-timeout {
          description
            "Specify timeout for NAT DNS flows";
          uses ip-nat-translation-timeout-grouping;
        }
        container finrst-timeout {
          description
            "Specify timeout for NAT TCP flows after a FIN or RST";
          uses ip-nat-translation-timeout-grouping;
        }
        container icmp-timeout {
          description
            "Specify timeout for NAT ICMP flows";
          uses ip-nat-translation-timeout-grouping;
        }
        container routemap-entry-timeout {
          description
            "Specify timeout for routemap created half entry";
          uses ip-nat-translation-timeout-grouping;
        }
        container syn-timeout {
          description
            "Specify timeout for NAT TCP flows after a SYN" +
            "and no further data";
          uses ip-nat-translation-timeout-grouping;
        }
        container tcp-timeout {
          description
            "Specify timeout for NAT TCP/UDP port specific flows";
          uses ip-nat-translation-timeout-grouping;
        }
        container timeout {
          description
            "Specify timeout for dynamic NAT translations";
          uses ip-nat-translation-timeout-grouping;
        }
        container udp-timeout {
          description
            "Specify timeout for NAT UDP flows";
          uses ip-nat-translation-timeout-grouping;
        }
        container port-timeout {
          description
            "Specify timeout for NAT TCP/UDP port specific flows";
          container tcp {
            description
              "TCP protocol";
            uses ip-nat-translation-port-number-grouping;
          }
          container udp {
            description
              "UDP protocol";
            uses ip-nat-translation-port-number-grouping;
          }
        }
        container max-entries {
          description
            "Specify maximum number of NAT entries";
          list host {
            description
              "Specify per-host NAT entry limit";
            
            key "host-ip";
            leaf host-ip {
              type inet:ipv4-address;
            }
            leaf number-of-entries {
              type uint32 {
                range "1..2147483647";
              }
            }
          }
          leaf num-entries {
            description "Number of entries";
            type uint32 {
              range "1..2147483637";
            }
          } //num-entries
          leaf all-host {
            description "Specify maximum number of NAT entries for each host";
            type uint32 {
              range "1..2147483637";
            }
          } //all-host
          leaf all-vrf {
            description "Specify maximum number of NAT entries for each vrf";
            type uint32 {
              range "1..2147483637";
            }
          } //all-vrf
          list redundancy {
            description "Specify maximum number of NAT entries for RG";
            ordered-by user;
            key "id";
            leaf id {
              type enumeration {
                enum "1";
                enum "2";
              } 
            } //id   
            leaf num-entries {
              description "Number of entries";
              type uint32 {
                range "1..2147483637";
              }
            } //num-entries
          } //redundancy
          list list {
            description "Specify access list based NAT entry limit";
            key "id";
            leaf id {
              type union {
                type uint32 {
                  range "1..199";
                }
                type string;
              }
            }
            leaf num-entries {
              description "Number of entries";
              type uint32 {
                range "1..2147483637";
              }
            } //num-entries
          } //list
          list vrf {
            description "Specify per-VRF NAT entry limit";
            key "id";
            leaf id {
              must "/ios:native/ios:vrf/ios:definition[ios:name=current()] or /ios:native/ios:ip/ios:vrf[ios:name=current()]" {
                error-message "VRF must be created 1st, deleted last";
              }
              type string;
            }
            leaf num-entries {
              description "Number of entries";
              type uint32 {
                range "1..2147483637";
              }
            } //num-entries
          } //vrf
        }
      }

      // ip nat route vrf <vrfname> <ipaddr> <netmask> global
      list route {
        description
          "Establish NAT static routes";
        ordered-by user;
        key "vrf ipaddr mask";
        leaf vrf {
          description "Configure NAT static route for a VPN Routing/Forwarding instance";
          must "(/ios:native/ios:vrf/ios:definition[ios:name=current()] and " +
               "(/ios:native/ios:vrf/ios:definition[ios:name=current()]/ios:address-family/ios:ipv4) or
                (/ios:native/ios:vrf/ios:definition[ios:name=current()]/ios:address-family/ios:ipv6)) or " +
               "/ios:native/ios:ip/ios:vrf[ios:name=current()]" {
            error-message "VRF must be created first, deleted last";
          }
          type string;
        }
        leaf ipaddr {
          description "IP address";
          type inet:ipv4-address;
        }
        leaf mask {
          description "Network mask";
          type inet:ipv4-address;
        }
        leaf global {
          description "Next hop address is global";
          type empty;
        }
      }

      container settings {
        description "NAT general settings";
        container mode {
          description "NAT operating mode";
          choice choice-mode {
            leaf cgn {
              description "The carrier grade NAT operating mode";
              type empty;
            }
            leaf default {
              description "The default NAT operating mode";
              type empty;
            }
          }
        }
        container cfg-check {
          description "NAT setting for configuration removal check";
          leaf static-map-removal {
            description "static map removal";
            type empty;
          }
        }
        leaf gatekeeper-size {
          description "Gatekeeper cache size";
          type uint32 {
            range "512..262144";
          }
        }
        leaf nonpatdrop {
          description "Drop non PAT packets";
          type empty;
        }
        container pool {
          description "Pool related settings";
          container watermark {
            description "Specify high/low watermark";
            leaf high {
              description "high watermark percentage";
              type uint32 {
                range "1..100";
              }
            }
            leaf low {
              description "low watermark percentage";
              type uint32 {
                range "1..100";
              }
            }
          }
        }
        container scale {
          description "Increase NAT scale";
          leaf bind {
            description "Scale bind";
            type empty;
          }
        }
        container support {
          description "NAT configuration support";
          container mapping {
            description "NAT mapping configuration support";
            leaf outside {
              description "NAT outside mapping configuration support.";
              type empty;
            }
          }
        }
      }

      container create {
        description "Create flow entries";
        leaf flow-entries {
          description "NAT create flow based entries";
          type empty;
        }
      }

      container switchover {
        description "Session replication";
        container replication {
          description "Session replication";
          container http {
            description "HTTP session replication";
            presence true;
            leaf port {
              description "port";
              type uint32 {
                range "1..65535";
              }
            }
          }
        }
      }

      container service {
        description "Special translation for application using non-standard port";
        leaf H225 {
          description "H.225  protocol";
          type empty;
        }
        leaf all-algs {
          description "Enable all NAT Application Level Gateways";
          type empty;
        }
        container dns {
          description "DNS protocol";
          leaf tcp {
            description "TCP protocol";
            type empty;
          }
          leaf udp {
            description "UDP protocol";
            type empty;
          }
        }
        leaf dns-reset-ttl {
          description "Reset dns canonical name ttl value";
          type empty;
        }
        leaf dns-v6 {
          description "dns v6 packet processing";
          type empty;
        }
        leaf ftp {
         description "ftp protocol";
         type empty;
       }
       container fullrange {
         description "allocate all available port of 1024 to 65535";
         container tcp {
           description "TCP protocol";
           leaf-list port {
             description "TCP port number";
             type uint16 { 
               range "1..511";
             }
           } //port
         } //tcp
         container udp {
           description "UDP protocol";
           leaf-list port {
             description "UDP port number";
             type uint16 {
               range "1..511";
             }
           } //port 
         } //udp
       } //fullrange
       leaf gatekeeper {
         description "Gatekeeper protocol";
         type empty;
       }
       container ipsec-esp {
         description "ipsec esp packet processing options";
         leaf enable {
           description "enable esp processing";
           type empty;
         }
       }
       leaf ldap {
         description "LDAP protocol";
         type empty;
       }
       container modify-in-progress {
         description "Packet processing options when config is being modified and/or cleared";
         leaf drop {
           description "Drop all NAT packets when a modify is in progress";
           type empty;
         }
       }
       container list {
         list esp-ike-list {
           description
             "Specify access list describing global addresses";
           key "type";
           leaf type {
             type enumeration {
               enum "ESP";
               enum "IKE";
             } //enum
           } //type
           leaf acl {
             mandatory true;
             type union {
               type uint32{
                 range "1..2699";
               }
               type string;
             } //union
           } //acl
           leaf spi-match{
             when "../type = 'ESP'";
             description "SPI matching IPsec passthrough";
             type empty;
           } //spi-match
           leaf preserve-port {
             when "../type = 'IKE'";
             description "preserve IKE port, as required by some IPsec servers";
             type empty;
           } //preserve-port
         } //esp-ike-list
         list ftp-list {
           description
             "Specify access list describing global addresses";
           key "id";
           leaf id {
             type union {
               type uint32 {
                 range "1..2699";
               }
               type string;
             }
           }
           container ftp {
             description "ftp protocol";
             container tcp {
               description "TCP protocol";
               leaf-list port {
                 description
                   "TCP port number";
                 type uint32 {
                   range "1..65535";
                 }
               } //port
             } //tcp
           } //ftp
         } //ftp-list
       } //list
       container msrpc {
         description "MS-RPC protocol";
         leaf tcp {
           description "TCP protocol";
           type empty;
         }
       } //msrpc
       leaf multi-wan-link {
         description "multiple wan link support for outside interface";
         type empty;
       } //multi-wan-link
       leaf netbios-dgm {
         description "NetBios datagram protocol";
         type empty;
       } //netbios-dgm
       container netbios-ns {
         description "NetBios name protocol";
         leaf tcp {
           description "TCP protocol";
           type empty;
         }
         leaf udp {
           description "UDP protocol";
           type empty;
         }
       } //netbios-ns
       leaf netbios-ssn {
         description "NetBios session protocol";
         type empty;
       }
       leaf pptp {
         description "Point-to-Point Tunneling protocol";
         type empty;
       }
       leaf ras {
         description "H323-RAS protocol";
         type empty;
       }
       leaf rcmd {
         description "RCMD protocol";
         type empty;
       }
       container rtsp {
         description "RTSP protocol";
         leaf tcp {
           description "TCP protocol";
           type empty;
         }
         leaf udp {
            description "UDP protocol";
            type empty;
          }
       } //rtsp
       container sip {
          description "SIP protocol";
          container tcp {
            description "TCP protocol";
            leaf-list port {
              description "TCP port number";
              type uint32 {
                range "1..65535";
              }
            } //port
          } //tcp
          container udp {
            description "UDP protocol";
            leaf-list port {
              description "UDP port number";
              type uint32 {
                range "1..65535";
              }
            } //port
          } //udp
        } //sip
        container skinny {
          description "skinny protocol";
          container tcp {
            description "TCP protocol";
            leaf-list port {
              description 
                "TCP port number";
              type uint32 {
                range "1..65535";
              }
            } //port
          } //tcp
        } //skinny      
        leaf tftp {
          description "TFTP Protocol";
          type empty;
        } //tftp
        container sunrpc {
          description "Enable SUN RPC protocol";
          leaf tcp {
            description "TCP protocol";
            type empty;
          }
          leaf udp {
            description "UDP protocol";
            type empty;
          }
        } //sunrpc
      } //service
    }
  }


  grouping config-nat66-grouping {
    container nat66 {
      description
        "NAT66 configuration commands";
      container prefix {
        description
          "NAT66 prefix";
        list inside {
          description
            "inside prefix";

          key "inside-pfx";
          leaf inside-pfx {
            description
              "IPv6 prefix";
            type ios-types:ipv6-prefix;
          }

          leaf outside {
            description
              "outside prefix";
            type ios-types:ipv6-prefix;
          }
        }
      }
    }
  }

  grouping config-interface-nat66-grouping {
    leaf nat66 {
      description
        "NAT66 interface commands";
      type enumeration {
        enum "inside";
        enum "outside";
      }
    }
  }

  //
  // NAT64 support under interface
  //
  grouping config-interface-nat64-grouping {
    container nat64 {
      // nat64 enable
      // nat64 prefix ...
      description "NAT64 interface commands";
      // nat64 enable
      leaf enable {
        description "Enable NAT64 on interface";
        type empty;
      }

      // nat64 prefix stateful X:X:X:X::X
      container prefix {
        description "NAT64 stateful prefix";
        container stateful {
          description "NAT64 prefix stateful";
          leaf ipv6-prefix {
            description "IPv6 prefix";
            type ios-types:ipv6-prefix;
          }
          leaf vrf {
            description "Configure NAT static route for a VPN Routing/Forwarding instance";
            must "(/ios:native/ios:vrf/ios:definition[ios:name=current()] and " +
                "(/ios:native/ios:vrf/ios:definition[ios:name=current()]/ios:address-family/ios:ipv4) or
                (/ios:native/ios:vrf/ios:definition[ios:name=current()]/ios:address-family/ios:ipv6)) or " +
                "/ios:native/ios:ip/ios:vrf[ios:name=current()]" {
              error-message "VRF must be created first, deleted last";
            }
            type string;
          }
        }
      }
    }
  }

 //
 // NAT64 support under global configuration
 //

  grouping config-nat64-v6v4-map-base-grouping {
    // [ vrf name [overload] ]
    list vrf {
      description
        "Specify vrf";
      
      key name;
      leaf name {
        must "(/ios:native/ios:vrf/ios:definition[ios:name=current()] and " +
             "(/ios:native/ios:vrf/ios:definition[ios:name=current()]/ios:address-family/ios:ipv4) or
              (/ios:native/ios:vrf/ios:definition[ios:name=current()]/ios:address-family/ios:ipv6)) or " +
             "/ios:native/ios:ip/ios:vrf[ios:name=current()]" {
           error-message "VRF must be created first, deleted last";
        }
        type string;
      }
      leaf overload {
        description
          "Overload an address translation";
        type empty;
      }
    }
    leaf overload {
      description
        "Overload an address translation";
      type empty;
    }
  }
  grouping config-nat64-v6v4-map-grouping {
    choice pool-or-interface {
      case pool-choice {
        // ip nat inside source list * pool
        list pool {
          description
            "Name pool of global addresses";
          
          key name;
          leaf name {
            type string;
          }
          uses config-nat64-v6v4-map-base-grouping;
        }
      }

      case interface-choice {
        // ip nat inside source list * interface
        // Note: "overload" will always in show running so add incomplete command in interface.
        list interface {
          description
            "Specify interface for global address";
          
          key name;
          leaf name {
            type string;
          }
          list vrf {
            status deprecated;
            description
              "Specify vrf";
            key name;
            leaf name {
              type string;
            }
            leaf overload {
              description
                "Overload an address translation";
              type empty;
            }
          }
          leaf overload {
            description
              "Overload an address translation";
            type empty;
          }
        }
      }
    }
  }

  grouping config-nat64-grouping {
    container nat64 {
      description "NAT64 configuration commands";
      container v4 {
        description "IPv4 configuration";
        // nat64 v4 pool ....
        list pool {
          description "Define pool of addresses";
          
          key "pool-name";
          leaf pool-name {
            description "NAT64 pool";
              type string;
            }
          leaf start-address {
            description "Starting address of pool address range";
            type inet:ipv4-address;
          }
          leaf end-address {
            description "Ending address of pool address range";
            when "../start-address" {
            }
            type inet:ipv4-address;
          }
        }
      }

      container v6v4 {
        description "IPv6 to IPv4 mapping";
        container list {
          description "Specify access list describing local addresses";
          list list {
            
            key "id";
            leaf id {
              type union {
                type uint16 {
                  range "1..2699";
                }
                type string;
              }
            }
            uses config-nat64-v6v4-map-grouping;
          }
        }
        container static {
          container ipv6address {
            list ipv6address {
              
              key "ipv6-address";
              leaf ipv6-address {
                description "IPv6 Address";
                type inet:ipv6-address;
              }
              leaf ipv4-address {
                description "IPv4 Address";
                type inet:ipv4-address;
              }
            }
          }
          container tcp {
            list tcp {
              
              key "ipv6-address";
              leaf ipv6-address {
                description "IPv6 Address";
                type inet:ipv6-address;
              }
              leaf v6-port-number {
                description "TCP v6 port";
                type uint16 {
                  range "1..65535";
                }
              }
              leaf ipv4-address {
                description "IPv4 Address";
                type inet:ipv4-address;
              }
              leaf v4-port-number {
                description "TCP v4 port";
                type uint16 {
                  range "1..65535";
                }
              }
            }
          }
          container udp {
            list udp {
              key "ipv6-address";
              leaf ipv6-address {
                description "IPv6 Address";
                type inet:ipv6-address;
              }
              leaf v6-port-number {
                description "UDP v6 port";
                type uint16 {
                  range "1..65535";
                }
              }
              leaf ipv4-address {
                description "IPv4 Address";
                type inet:ipv4-address;
              }
              leaf v4-port-number {
                description "UDP v4 port";
                type uint16 {
                  range "1..65535";
                }
              }
            }
          }
        }
      }

      container v4v6 {
        description "IPv4 to IPv6 mapping";
        container static {
          container ipv4address {
            list ipv4address {
              
              key "ipv4-address";
              leaf ipv4-address {
                description "IPv4 Address";
                type inet:ipv4-address;
              }
              leaf ipv6-address {
                description "IPv6 Address";
                type inet:ipv6-address;
              }
            }
          }
          container tcp {
            list tcp {
              
              key "ipv4-address";
              leaf ipv4-address {
                description "IPv4 Address";
                type inet:ipv4-address;
              }
              leaf v4-port-number {
                description "TCP v4 port";
                type uint16 {
                  range "1..65535";
                }
              }
              leaf ipv6-address {
                description "IPv6 Address";
                type inet:ipv6-address;
              }
              leaf v6-port-number {
                description "TCP v6 port";
                type uint16 {
                  range "1..65535";
                }
              }
            }
          }
          container udp {
            list udp {
              key "ipv4-address";
              leaf ipv4-address {
                description "IPv6 Address";
                type inet:ipv4-address;
              }
              leaf v4-port-number {
                description "UDP v4 port";
                type uint16 {
                  range "1..65535";
                }
              }
              leaf ipv6-address {
                description "IPv6 Address";
                type inet:ipv6-address;
              }
              leaf v6-port-number {
                description "UDP v6 port";
                type uint16 {
                  range "1..65535";
                }
              }
            }
          }
        }
      }
      // nat64 prefix stateful X:X:X:X::X [ vrf <name> ]
      container prefix {
        description "NAT64 prefix";
        container stateful {
          description "NAT64 stateful prefix";
          leaf ipv6-prefix {
            description "IPv6 prefix";
            type ios-types:ipv6-prefix;
          }
        }
        container stateful-with-vrf {
          list stateful {
            description "NAT64 stateful prefix";
            key "vrf";
            leaf vrf {
              description "Specify vrf";
              must "(/ios:native/ios:vrf/ios:definition[ios:name=current()] and " +
                  "(/ios:native/ios:vrf/ios:definition[ios:name=current()]/ios:address-family/ios:ipv4) or
                  (/ios:native/ios:vrf/ios:definition[ios:name=current()]/ios:address-family/ios:ipv6)) or " +
                  "/ios:native/ios:ip/ios:vrf[ios:name=current()]" {
                error-message "VRF must be created first, deleted last";
              }
              type string;
            }
            leaf ipv6-prefix {
              description "IPv6 prefix";
              type ios-types:ipv6-prefix;
            }
          }
        }
      }
      container translation {
        container timeout {
          container bind {
            description
              "Specify the timeout for NAT64 binds";
            uses ip-nat-translation-timeout-grouping;
          }
          container icmp {
            description
              "Specify the timeout for NAT64 ICMP flows";
            uses ip-nat-translation-timeout-grouping;
          }
          container tcp {
            description
              "Specify the timeout for NAT64 TCP flows";
            uses ip-nat-translation-timeout-grouping;
          }
          container tcp-transient {
            description
              "Specify the timeout for NAT64 transient TCP flows";
            uses ip-nat-translation-timeout-grouping;
          }
          container udp {
            description
              "Specify the timeout for NAT64 UDP flows";
            uses ip-nat-translation-timeout-grouping;
          }
        }
        container max-entries {
          description
          "Specify maximum number of NAT entries";
          leaf max-entries {
            type uint32 {
            range "1..2147483647";
            }
          }
        }
      }
      // nat64  route vrf <vrfname> <v6-prefix> global
      list route {
        description
          "Establish NAT64 DIA routes";
        key "vrf ipv6-prefix";
        leaf vrf {
          description
            "Configure NAT64 DIA route for a VPN Routing/Forwarding instance";
          must "(/ios:native/ios:vrf/ios:definition[ios:name=current()] and 
                 /ios:native/ios:vrf/ios:definition[ios:name=current()]/ios:address-family/ios:ipv6)" {
            error-message "IPV6 VRF must be created first, deleted last";
          }
          type string;
        }
        leaf ipv6-prefix {
          description
            "IPV6 prefix";
          type ios-types:ipv6-prefix;
        }
        leaf global {
          description
            "Next hop address is global";
          type empty;
        }
      }
    }
  }

  /////////////////////////////////////////////////////////
  // native / ip / nat
  /////////////////////////////////////////////////////////
  augment "/ios:native/ios:ip" {
    uses config-ip-nat-grouping;
  }


  /////////////////////////////////////////////////////////
  // native / interface * / ip
  /////////////////////////////////////////////////////////
  augment "/ios:native/ios:interface/ios:Ethernet/ios:ip" {
    uses config-interface-ip-nat-grouping;
  }
  augment "/ios:native/ios:interface/ios:FastEthernet/ios:ip" {
    uses config-interface-ip-nat-grouping;
  }

  augment "/ios:native/ios:interface/ios:GigabitEthernet/ios:ip" {
    uses config-interface-ip-nat-grouping;
  }

  augment "/ios:native/ios:interface/ios:TenGigabitEthernet/ios:ip" {
    uses config-interface-ip-nat-grouping;
  }

  augment "/ios:native/ios:interface/ios:FiveGigabitEthernet/ios:ip" {
    uses config-interface-ip-nat-grouping;
  }

  augment "/ios:native/ios:interface/ios:AppGigabitEthernet/ios:ip" {
    uses config-interface-ip-nat-grouping;
  }

  augment "/ios:native/ios:interface/ios:TwentyFiveGigE/ios:ip" {
    uses config-interface-ip-nat-grouping;
  }

  augment "/ios:native/ios:interface/ios:TwoGigabitEthernet/ios:ip" {
    uses config-interface-ip-nat-grouping;
  }

  augment "/ios:native/ios:interface/ios:FortyGigabitEthernet/ios:ip" {
    uses config-interface-ip-nat-grouping;
  }

  augment "/ios:native/ios:interface/ios:HundredGigE/ios:ip" {
    uses config-interface-ip-nat-grouping;
  }

  augment "/ios:native/ios:interface/ios:Port-channel/ios:ip" {
    uses config-interface-ip-nat-grouping;
  }

  augment "/ios:native/ios:interface/ios:Loopback/ios:ip" {
    uses config-interface-ip-nat-grouping;
  }

  augment "/ios:native/ios:interface/ios:BDI/ios:ip" {
    uses config-interface-ip-nat-grouping;
  }

  augment "/ios:native/ios:interface/ios:Cellular/ios:ip" {
    uses config-interface-ip-nat-grouping;
  }

  augment "/ios:native/ios:interface/ios:Dialer/ios:ip" {
    uses config-interface-ip-nat-grouping;
  }
  augment "/ios:native/ios:interface/ios:VirtualPortGroup/ios:ip" {
    uses config-interface-ip-nat-grouping;
  }

  augment "/ios:native/ios:interface/ios:Serial/ios:ip" {
    uses config-interface-ip-nat-grouping;
  }
  
  augment "/ios:native/ios:interface/ios:Multilink/ios:ip" {
    uses config-interface-ip-nat-grouping;
  }

  augment "/ios:native/ios:interface/ios:ATM/ios:ip" {
    uses config-interface-ip-nat-grouping;
 }

  augment "/ios:native/ios:interface/ios:ATM-subinterface/ios:ATM/ios:ip" {
    uses config-interface-ip-nat-grouping;
  }
 
  augment "/ios:native/ios:interface/ios:Vlan/ios:ip" {
    uses config-interface-ip-nat-grouping;
  }
  augment "/ios:native/ios:interface/ios:Tunnel/ios:ip" {
    uses config-interface-ip-nat-grouping;
  }
  augment "/ios:native/ios:interface/ios:vasileft/ios:ip" {
    uses config-interface-ip-nat-grouping;
  }
  augment "/ios:native/ios:interface/ios:vasiright/ios:ip" {
    uses config-interface-ip-nat-grouping;
  }

  /////////////////////////////////////////////////////////
  // native / nat66
  /////////////////////////////////////////////////////////
  augment "/ios:native" {
    uses config-nat66-grouping;
  }
  /////////////////////////////////////////////////////////
  // native / nat64
  /////////////////////////////////////////////////////////
  augment "/ios:native" {
    uses config-nat64-grouping;
  }

  /////////////////////////////////////////////////////////
  // native / interface *
  /////////////////////////////////////////////////////////
  augment "/ios:native/ios:interface/ios:FastEthernet" {
    uses config-interface-nat66-grouping;
  }

  augment "/ios:native/ios:interface/ios:GigabitEthernet" {
    uses config-interface-nat66-grouping;
  }

  augment "/ios:native/ios:interface/ios:TenGigabitEthernet" {
    uses config-interface-nat66-grouping;
  }

  augment "/ios:native/ios:interface/ios:FiveGigabitEthernet" {
    uses config-interface-nat66-grouping;
  }

  augment "/ios:native/ios:interface/ios:AppGigabitEthernet" {
    uses config-interface-nat66-grouping;
  }

  augment "/ios:native/ios:interface/ios:TwentyFiveGigE" {
    uses config-interface-nat66-grouping;
  }

  augment "/ios:native/ios:interface/ios:TwoGigabitEthernet" {
    uses config-interface-nat66-grouping;
  }

  augment "/ios:native/ios:interface/ios:FortyGigabitEthernet" {
    uses config-interface-nat66-grouping;
  }

  augment "/ios:native/ios:interface/ios:HundredGigE" {
    uses config-interface-nat66-grouping;
  }

  augment "/ios:native/ios:interface/ios:Port-channel" {
    uses config-interface-nat66-grouping;
  }

  augment "/ios:native/ios:interface/ios:Loopback" {
    uses config-interface-nat66-grouping;
  }

  augment "/ios:native/ios:interface/ios:Tunnel" {
    uses config-interface-nat66-grouping;
  }

  augment "/ios:native/ios:interface/ios:ATM" {
    uses config-interface-nat66-grouping;
  }
 
  augment "/ios:native/ios:interface/ios:ATM-subinterface" {
    uses config-interface-nat66-grouping;
  }

  augment "/ios:native/ios:interface/ios:Vlan" {
    uses config-interface-nat66-grouping;
  }

  /////////////////////////////////////////////////////////
  // native / interface NAT64
  /////////////////////////////////////////////////////////
  augment "/ios:native/ios:interface/ios:FastEthernet" {
    uses config-interface-nat64-grouping;
  }

  augment "/ios:native/ios:interface/ios:GigabitEthernet" {
    uses config-interface-nat64-grouping;
  }

  augment "/ios:native/ios:interface/ios:TenGigabitEthernet" {
    uses config-interface-nat64-grouping;
  }

  augment "/ios:native/ios:interface/ios:FiveGigabitEthernet" {
    uses config-interface-nat64-grouping;
  }

  augment "/ios:native/ios:interface/ios:AppGigabitEthernet" {
    uses config-interface-nat64-grouping;
  }

  augment "/ios:native/ios:interface/ios:TwentyFiveGigE" {
    uses config-interface-nat64-grouping;
  }

  augment "/ios:native/ios:interface/ios:TwoGigabitEthernet" {
    uses config-interface-nat64-grouping;
  }

  augment "/ios:native/ios:interface/ios:FortyGigabitEthernet" {
    uses config-interface-nat64-grouping;
  }

  augment "/ios:native/ios:interface/ios:HundredGigE" {
    uses config-interface-nat64-grouping;
  }

  augment "/ios:native/ios:interface/ios:Port-channel" {
    uses config-interface-nat64-grouping;
  }

  augment "/ios:native/ios:interface/ios:Loopback" {
    uses config-interface-nat64-grouping;
  }

  augment "/ios:native/ios:interface/ios:Tunnel" {
    uses config-interface-nat64-grouping;
  }

  augment "/ios:native/ios:interface/ios:ATM" {
    uses config-interface-nat64-grouping;
  }

  augment "/ios:native/ios:interface/ios:ATM-subinterface" {
    uses config-interface-nat64-grouping;
  }

  augment "/ios:native/ios:interface/ios:BD-VIF/ios:ip" {
    uses config-interface-ip-nat-grouping;
  }
  
}
