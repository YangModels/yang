module Cisco-IOS-XE-pnp {
  namespace "http://cisco.com/ns/yang/Cisco-IOS-XE-pnp";
  prefix ios-pnp;

  import cisco-semver {
    prefix cisco-semver;
  }
 
  import Cisco-IOS-XE-native {
    prefix ios;
  }


  import ietf-inet-types {
    prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE PnP Yang model.
     Copyright (c) 2018-2019 by Cisco Systems, Inc.
     All rights reserved.";

  // =========================================================================
  // REVISION
  // =========================================================================
  revision 2019-07-01 {
    description "Establish semantic version baseline";
    cisco-semver:module-version "1.0.0";
  }
  revision 2018-08-13 {
    description
      "Added model for PnP transport https";
  }
  revision 2018-07-10 {
    description
      "Initial revision";
  }

  grouping config-pnp-grouping {
    container pnp {
      description
        "Configure PNP";
      leaf startup-vlan {
        description
          "PNP startup-vlan";
        type uint16 {
          range "2..4094";
        }
      }
      list profile {
        description
          "PNP profile";
        key "name";
        leaf "name" {
          type string;
        }
        container transport {
          description
            "The transport to use"; 
          container https {
            description
              "Use https (encrypted) transport";
            
            container ipv4 {
              description
                "ipv4 address";
              leaf ipv4-address {
                description
                  "IPv4 address of the server";
                type inet:ipv4-address;
              }
              leaf port {
                description
                  "port number";
                type uint16 {
                  range "1..65535";
                }
              }
            }
          }
        }
      }
    }
  }

  /////////////////////////////////////////////////////////
  // native / pnp
  /////////////////////////////////////////////////////////
  augment "/ios:native" {
    uses config-pnp-grouping;
  }
} //module
