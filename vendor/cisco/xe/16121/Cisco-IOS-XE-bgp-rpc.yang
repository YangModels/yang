submodule Cisco-IOS-XE-bgp-rpc {
  belongs-to Cisco-IOS-XE-rpc {
    prefix ios-xe-rpc;
  }

  import cisco-semver {
    prefix cisco-semver;
  }
 
  import ietf-inet-types {
    prefix inet;
  }

  organization "Cisco Systems";

  contact
    <mailto:cs-yang@cisco.com>;

  description
    "NED BGP RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2018-12-06 {
    description
      "created for NED RPC modularisation";
  }

  grouping clear-choice-ip-case-ip-protocol-bgp-case-grouping {
    container bgp {
      description
        "Clear BGP connections";
      leaf peer-address-drop-node-name {
        description
          "BGP neighbor address to clear";
        type union {
          type inet:ipv4-address;
          type inet:ipv6-address;
        }
      }
      leaf vrf {
        description
          "Select a VPN Routing/Forwarding instance";
        type string;
      }
    } 
  }
}
