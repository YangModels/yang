module Cisco-IOS-XE-card {
  namespace "http://cisco.com/ns/yang/Cisco-IOS-XE-card";
  prefix ios-card;

  import cisco-semver {
    prefix cisco-semver;
  }
 
  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Card Yang model.
     Copyright (c) 2017-2018 by Cisco Systems, Inc.
     All rights reserved.";

  // =========================================================================
  // REVISION
  // =========================================================================
  revision 2019-07-01 {
    description "Establish semantic version baseline";
    cisco-semver:module-version "1.0.0";
  }
  revision 2018-04-24 {
    description
      "Make card type list";
  }
  revision 2018-03-27 {
    description
      "Move top level card to native before controller to keep the sequence.";
  }
  revision 2017-02-07 {
    description
      "Initial revision";
  }

  grouping config-card-grouping {
    list type {
      key "card-type slot bay";
      leaf card-type {
        type enumeration {
          enum "t1";
          enum "e1";
        }
      }
      leaf slot {
        type uint32;
      }
      leaf bay {
        type uint32;
      }
    }
  }

  /////////////////////////////////////////////////////////
  // native / card
  /////////////////////////////////////////////////////////
  augment "/ios:native/ios:card" {
    uses config-card-grouping;
  }
} //module
