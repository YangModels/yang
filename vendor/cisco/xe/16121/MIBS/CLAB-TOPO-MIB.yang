/*
 * Generated by confdc --mib2yang-std
 * Source: mgmt/dmi/model/mib/src/CLAB-TOPO-MIB.mib
 */
/*
 * This YANG module has been generated by smidump 0.5.0:
 *
 *      smidump -f yang CLAB-TOPO-MIB
 *
 * Do not edit. Edit the source file instead!
 */

module CLAB-TOPO-MIB {

  namespace "urn:ietf:params:xml:ns:yang:smiv2:CLAB-TOPO-MIB";
  prefix CLAB-TOPO-MIB;

  import IF-MIB {
    prefix "if-mib";
  }

  import SNMP-FRAMEWORK-MIB {
    prefix "snmp-framework";
  }

  import SNMPv2-TC {
    prefix "snmpv2-tc";
  }

  import ietf-yang-smiv2 {
    prefix "smiv2";
  }

  organization
   "Cable Television Laboratories, Inc.";

  contact
   "
    Postal: Cable Television Laboratories, Inc.
    858 Coal Creek Circle
    Louisville, Colorado 80027-9750
    U.S.A.
    Phone: +1 303-661-9100
    Fax: +1 303-661-9199
    E-mail: mibs@cablelabs.com";

  description
   "This MIB module contains the management objects for the
    management of fiber nodes in the Cable plant.";

  revision 2006-12-07 {
    description
     "Initial version, published as part of the CableLabs
      OSSIv3.0 specification CM-SP-OSSIv3.0-I01-061207
      Copyright 1999-2006 Cable Television Laboratories, Inc.
      All rights reserved.";
  }

  typedef NodeName {
    type binary {
      length "0..16";
    }
    description
     "This data type is a human readable string that represents
      the name of a fiber node. Internationalization is supported
      by conforming to the SNMP textual convention SnmpAdminString.";
    reference
     "RFC 3411.";
  }


  container CLAB-TOPO-MIB {
    config false;

    container clabTopoFiberNodeCfgTable {
      description
       "This object defines the cable HFC plant Fiber Nodes
        known at a CMTS.
        This object supports the creation and deletion of multiple
        instances.";
      smiv2:oid "1.3.6.1.4.1.4491.4.2.1.1";

      list clabTopoFiberNodeCfgEntry {
        key "clabTopoFiberNodeCfgNodeName";
        description
         "The conceptual row of clabTopoFiberNodeCfg.
          The CMTS persists all instances of FiberNodeCfg
          across reinitializations.";
        smiv2:oid "1.3.6.1.4.1.4491.4.2.1.1.1";

        leaf clabTopoFiberNodeCfgNodeName {
          type CLAB-TOPO-MIB:NodeName {
            length "1..16";
          }
          description
           "This key represents a human-readable name for a fiber
            node.";
          reference
           "DOCSIS 3.0 MAC and Upper Layer Protocols Interface
            Specification CM-SP-MULPIv3.0-I01-060804, RF Topology 
            Configuration section.";
          smiv2:max-access "not-accessible";
          smiv2:oid "1.3.6.1.4.1.4491.4.2.1.1.1.1";
        }

        leaf clabTopoFiberNodeCfgNodeDescr {
          type snmp-framework:SnmpAdminString;
          description
           "Administratively configured human-readable description
            of the fiber node";
          smiv2:defval "";
          smiv2:max-access "read-write";
          smiv2:oid "1.3.6.1.4.1.4491.4.2.1.1.1.2";
        }

        leaf clabTopoFiberNodeCfgRowStatus {
          type snmpv2-tc:RowStatus;
          description
           "The status of this instance.";
          smiv2:max-access "read-write";
          smiv2:oid "1.3.6.1.4.1.4491.4.2.1.1.1.3";
        }
      }
    }

    container clabTopoChFnCfgTable {
      description
       "This object defines the RF topology by defining the
        connectivity of a CMTS's downstream and upstream channels
        to the fiber nodes. Each instance of this object
        describes connectivity of one downstream or upstream
        channel with a single fiber node.
        This object supports the creation and deletion of multiple
        instances.";
      smiv2:oid "1.3.6.1.4.1.4491.4.2.1.2";

      list clabTopoChFnCfgEntry {
        key "clabTopoFiberNodeCfgNodeName clabTopoChFnCfgChIfIndex";
        description
         "The conceptual row of clabTopoChFnCfg.
          The CMTS persists all instances of ChFnCfg
          across reinitializations.";
        smiv2:oid "1.3.6.1.4.1.4491.4.2.1.2.1";

        leaf clabTopoFiberNodeCfgNodeName {
          type leafref {
            path "/CLAB-TOPO-MIB:CLAB-TOPO-MIB/CLAB-TOPO-MIB:clabTopoFiberNodeCfgTable/CLAB-TOPO-MIB:clabTopoFiberNodeCfgEntry/CLAB-TOPO-MIB:clabTopoFiberNodeCfgNodeName";
          }
        }

        leaf clabTopoChFnCfgChIfIndex {
          type if-mib:InterfaceIndex;
          description
           "This key represents the interface index of an upstream
            or downstream channel associated with this fiber
            node. In the upstream direction, only ifIndices
            docsCableUpstream channels are reflected.";
          smiv2:max-access "not-accessible";
          smiv2:oid "1.3.6.1.4.1.4491.4.2.1.2.1.1";
        }

        leaf clabTopoChFnCfgRowStatus {
          type snmpv2-tc:RowStatus;
          description
           "The status of this instance.";
          smiv2:max-access "read-write";
          smiv2:oid "1.3.6.1.4.1.4491.4.2.1.2.1.2";
        }
      }
    }
  }

  smiv2:alias "clabTopoMib" {
    smiv2:oid "1.3.6.1.4.1.4491.4.2";
  }

  smiv2:alias "clabTopoMibObjects" {
    smiv2:oid "1.3.6.1.4.1.4491.4.2.1";
  }

  smiv2:alias "clabTopoMibConformance" {
    smiv2:oid "1.3.6.1.4.1.4491.4.2.2";
  }

  smiv2:alias "clabTopoMibCompliances" {
    smiv2:oid "1.3.6.1.4.1.4491.4.2.2.1";
  }

  smiv2:alias "clabTopoMibGroups" {
    smiv2:oid "1.3.6.1.4.1.4491.4.2.2.2";
  }

}
