module Cisco-IOS-XE-trustsec-oper {
  yang-version 1;
  namespace "http://cisco.com/ns/yang/Cisco-IOS-XE-trustsec-oper";
  prefix trustsec-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of Cisco Trustsec operational information on
     Role based permissions, IP-SGT bindings and SXP connections.
     Copyright (c) 2016-2017, 2019 by Cisco Systems, Inc.
     All rights reserved.";

  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2017-02-07 {
    description
      "Initial revision";
    reference "1.0.0";
    cisco-semver:module-version "1.0.0";
  }

  typedef cts-odm-binding-source {
    type enumeration {
      enum "default" {
        value 0;
        description
          "Default Security Group Tag binding value in this device
           for the given IP-Address";
      }
      enum "from-vlan" {
        value 1;
        description
          "Security Group Tag binding value in this device for the given
           IP-Address is learned from a VLAN";
      }
      enum "from-cli" {
        value 2;
        description
          "Security Group Tag binding value in this device
           for the given
           IP-Address is configure from CLI (Command Line Interface)";
      }
      enum "from-l3if" {
        value 3;
        description
          "Security Group Tag binding value in this device
           for the given IP-Address is learned from a L3 (Layer 3) interface";
      }
      enum "from-cfp" {
        value 4;
        description
          "Security Group Tag binding value in this device
           for the given IP-Address is learned via SXP
           binding exchange protocol";
      }
      enum "from-ip-arp" {
        value 5;
        description
          "Security Group Tag binding value in this
           device for the given
           IP-Address is learned via IP-ARP protocol";
      }
      enum "from-local" {
        value 6;
        description
          "Security Group Tag binding value in this device
           for the given IP-Address is learned locally";
      }
      enum "from-sgt-caching" {
        value 7;
        description
          "Security Group Tag binding value in this device
           for the given IP-Address is learned via Security Group Tag
           caching from data path.";
      }
      enum "from-cli-hi" {
        value 8;
        description
          "Security Group Tag binding value in this device
           for the given IP-Address is configured from CLI-high priority.";
      }
    }
    description
      "Binding Source enumeration";
  }

  typedef sxp-con-state {
    type enumeration {
      enum "state-off" {
        value 0;
        description
          "SXP Connection state is OFF";
      }
      enum "state-pending-on" {
        value 1;
        description
          "SXP Connection state is Pending-On";
      }
      enum "state-on" {
        value 2;
        description
          "SXP Connection state is ON";
      }
      enum "state-delete-hold-down" {
        value 3;
        description
          "SXP Connection state is Delete-Hold-Down";
      }
      enum "state-not-applicable" {
        value 4;
        description
          "SXP Connection state is Not-Applicable";
      }
    }
    description
      "SXP Connection state";
  }

  typedef sxp-con-mode {
    type enumeration {
      enum "con-mode-invalid" {
        value 0;
        description
          "SXP Connection mode is Invalid";
      }
      enum "con-mode-speaker" {
        value 1;
        description
          "SXP Connection mode is Speaker";
      }
      enum "con-mode-listener" {
        value 2;
        description
          "SXP Connection mode is Listener";
      }
      enum "con-mode-both" {
        value 3;
        description
          "SXP Connection mode is Both (Speaker and Listener)";
      }
    }
    description
      "SXP Connection mode";
  }

  grouping cts-ip-sgt-map-key {
    description
      "IP-Address information to find corresponding CTS Security Group Tag binding";
    leaf ip {
      type inet:ip-prefix;
      description
        "IP-Prefix information to find its corresponding
         Secure Group Tag. Only IPv4 prefix information is
         supported currently to get the Security Group Tag
         binding in this device";
    }
    leaf vrf-name {
      type string;
      description
        "VRF-Name to find the Security Group Tag for the
         corresponding IP-Address in
         this VRF instance. Only default VRF is supported
         currently which is indicated by (empty string)";
    }
  }

  grouping cts-ip-sgt-map {
    description
      "Trustsec Security Group Tag binding information";
    leaf sgt {
      type int32;
      description
        "Security Group Tag value corresponding to the
         given IP-Address";
    }
    leaf source {
      type trustsec-ios-xe-oper:cts-odm-binding-source;
      description
        "Source information via which the Security
         Group Tag binding was learned in this device";
    }
  }

  grouping cts-role-based-policy-key {
    description
      "Source Security Group Tag and Destination Security
       Group Tag information to find the list of Security
       Group Access Control List that are currently
       applied between two security groups in the device";
    leaf src-sgt {
      type int32;
      description
        "Source Security Group Tag number.
         This value must be in the inclusive range of -1 to 65519";
    }
    leaf dst-sgt {
      type int32;
      description
        "Destination Security Tag number.
         This value must be in the inclusive range of -1 to 65519";
    }
  }

  grouping cts-role-based-policy {
    description
      "Trustsec Role based permissions between a Source
       Security Group and the Destination Security Group";
    leaf sgacl-name {
      type string;
      description
        "List of Security Group Access Control List names
         separated by semi-colon(;)";
    }
    leaf num-of-sgacl {
      type uint32;
      description
        "Number of Security Group Access Control Lists that
         are currently applied between
         the Source Security Group and the Destination
         Security Group. This should match
         the number of Security Group Access Control List
         names in sgacl-name";
    }
    leaf monitor-mode {
      type boolean;
      description
        "Indicates the monitor mode status between the Source
         Security Group and Destination
         Security Group is currently enabled or disabled.
         This will be TRUE if monitor
         mode is enabled and FALSE if it is disabled";
    }
    leaf policy-life-time {
      type uint64;
      description
        "Duration of the Role based permissions that are
         applied between a Source Security Group
         and a Destination Security Group. The duration
         is represented in seconds";
    }
    leaf last-updated-time {
      type yang:date-and-time;
      description
        "Indicates the time when the Role based permissions
         between a Source Security Group and a Destination
         Security Group was modified or updated last. The
         value will be represented as date and time 
         corresponding to the local time zone of the
         Identify Services Engine when the Role based 
         permissions was modified or updated last";
    }
    leaf total-deny-count {
      type uint64;
      description
        "Total number of packets that have been denied by
         the Role based permissions
         between a Source Security Group and a Destination
         Security Group. This corresponds to
         total packets denied in both hardware and software
         forwarding paths of the device";
    }
    leaf total-permit-count {
      type uint64;
      description
        "Total number of packets that have been permitted
         by the Role based permissions
         between a Source Security Group and a Destination
         Security Group. This corresponds to
         total packets allowed in both hardware and software
         forwarding paths of the device";
    }
    leaf software-deny-count {
      type uint64;
      description
        "Number of packets that have been denied in the 
         software forwarding path of the device
         by the Role based permissions between a Source
         Security Group and a Destination
         Security Group";
    }
    leaf software-permit-count {
      type uint64;
      description
        "Number of packets that have been permitted in the
         software forwarding path of the device
         by the Role based permissions between a Source
         Security Group and a Destination Security Group";
    }
    leaf hardware-deny-count {
      type uint64;
      description
        "Number of packets that have been denied in the
         hardware forwarding path of the device by
         the Role based permissions between a Source
         Security Group and a Destination Security Group";
    }
    leaf hardware-permit-count {
      type uint64;
      description
        "Number of packets that have been permitted in the
         hardware forwarding path of the device
         by the Role based permissions between a Source
         Security Group and a Destination Security Group.";
    }
    leaf software-monitor-count {
      type uint64;
      description
        "Number of packets that have been monitored in the
         software forwarding path of the device
         by the Role based permissions between a Source
         Security Group and a Destination Security Group";
    }
    leaf hardware-monitor-count {
      type uint64;
      description
        "Number of packets that have been monitored in the
         hardware forwarding path of the device
         by the Role based permissions between a Source
         Security Group and a Destination Security Group";
    }
  }

  grouping cts-sxp-con-key {
    description
      "The peer IP-Address of a CTS SXP connection and
       vrf-name of the VRF instance
       in this device to which this IP-Address is configured.
       This information is used
       to get additional details of the SXP connection";
    leaf peer-ip {
      type inet:ip-address;
      description
        "IP-Address information of the peer of an SXP
         connection in this device. Only IPv4
         address is currently supported.";
    }
    leaf vrf-name {
      type string;
      description
        "vrf-name string of the VRF instance in this device,
         to which the peer of an SXP connection
         belongs to. Only default VRF is supported currently
         which is indicated by empty string";
    }
  }

  grouping cts-sxp-con {
    description
      "SXP connection information";
    leaf source-ip {
      type inet:ip-address;
      description
        "Source IP-Address of the SXP connection in this
         device for the given peer IP-Address.";
    }
    leaf speaker-state {
      type trustsec-ios-xe-oper:sxp-con-state;
      description
        "SXP speaker state information of the SXP
         connection in this device. This information is
         valid only if the local mode of the SXP
         connection in this device is Speaker";
    }
    leaf speaker-duration {
      type uint64;
      description
        "Duration of the SXP speaker of the SXP connection
         in this device. This information is valid
         only if the local mode of the SXP connection is Speaker";
    }
    leaf listener-state {
      type trustsec-ios-xe-oper:sxp-con-state;
      description
        "SXP listener state information of the SXP 
         connection in this device. This information is
         valid only if the local mode of the SXP
         connection in the device is Listener";
    }
    leaf listener-duration {
      type uint64;
      description
        "Duration of the SXP listener of the SXP connection
         in this device. This information is valid
         Only if the local mode of the SXP connection is Listener";
    }
    leaf local-mode {
      type trustsec-ios-xe-oper:sxp-con-mode;
      description
        "SXP connection mode of this device for the SXP
         connection with the given peer";
    }
  }

  container trustsec-state {
    config false;
    description
      "This is top level container for Cisco Trusted Security
       solution operational data.
       It can have Security Group Tag binding information for
       the given IP-Address, Role based permissions between a
       Source Security Group Tag and a Destination Security
       Group, SXP Connection information for a given peer
       IP-Address in this device";
    container cts-rolebased-sgtmaps {
      description
        "Security Group Tag value corresponding to an IP-Address 
         in the given VRF instance in this device";
      list cts-rolebased-sgtmap {
        key "ip vrf-name";
        description
          "Security Group Tag is assigned for an IP-Address
           based on the user permissions and authorization 
           level as configured by the network administrator
           in Identity Service Engine server or in the device locally";
        uses trustsec-ios-xe-oper:cts-ip-sgt-map-key;
        uses trustsec-ios-xe-oper:cts-ip-sgt-map;
      }
    }
    container cts-rolebased-policies {
      description
        "Role based permissions between a Source Security Group
         and a Destination Security Group are configured by the
         administrator in the Identity Services Engine or in the Device";
      list cts-rolebased-policy {
        key "src-sgt dst-sgt";
        description
          "Role based permissions between a Source Security Group
           and a Destination Security Group can be retrieved from
           the device using a Security Group Tag and Destination
           Group Tag value";
        uses trustsec-ios-xe-oper:cts-role-based-policy-key;
        uses trustsec-ios-xe-oper:cts-role-based-policy;
      }
    }
    container cts-sxp-connections {
      description
        "Trustsec SXP connection is used between Cisco devices
         to propagate Security Group Tags from one device to 
         another device. One of the device will be in Speaker 
         mode or Listener mode or both the devices can be in
         both the connection modes";
      list cts-sxp-connection {
        key "peer-ip vrf-name";
        description
          "Trustsec SXP connection information from a device
           can be retrieved with the SXP connection peer IP
           address. Only IPv4 address as Peer IP and default
           VRF instance in device is supported currently";
        uses trustsec-ios-xe-oper:cts-sxp-con-key;
        uses trustsec-ios-xe-oper:cts-sxp-con;
      }
    }
  }
}
