module openconfig-system-wifi-ext {

  yang-version "1";

  namespace "http://openconfig.net/yang/wifi";

  // Assign this module a prefix to be used by other modules, when imported.
  prefix "oc-system-wifi-ext";
  import openconfig-extensions { prefix oc-ext; }
  import openconfig-inet-types { prefix oc-inet; }
  // Original model this is augmenting
  import openconfig-system { prefix "oc-sys"; }

  // meta
  organization "OpenConfig working group";

  contact
    "OpenConfig working group
    www.openconfig.net";

  description
    "Model for managing Controller-specific Config & State for
    system-level elements. This explicitly excludes any 802.11
    MAC/PHY layer elements.";

  oc-ext:openconfig-version "0.3.0";

  revision "2018-01-04" {
    description
      "Remove joined-aps.";
    reference "0.3.0";
  }

  revision "2017-10-01" {
    description
      "Add country-code and hostname to MAC.";
    reference "0.2.0";
  }

  revision "2017-07-25" {
    description
      "Initial revision";
    reference "0.1.0";
  }

  // grouping statements
  grouping assigned-controllers-config {
    description
      "Controller(s) an AP may join. If cloud controller, this will be
      the cloud instance(s). This config is applied to APs, not Controllers.";

    leaf id {
      type string;
      description
        "id serves as a reference point to the [1-n] Controller(s) this AP
        is assigned to.";
      }

    leaf fqdn {
      type oc-inet:domain-name;
      description
        "The FQDN of a Controller this AP is assigned to. The list should be
        ordered, according to priority. eg Primary first,
        Secondary second, Tertiary third etc.";
    }

    leaf controller-ipv4-address {
      type oc-inet:ipv4-address;
      description
        "IPv4 address of Controller for this AP. The list should be
        ordered, according to priority. eg. Primary first, Secondary second,
        Tertiary third etc.";
    }

    leaf-list controller-ipv6-address {
      type oc-inet:ipv6-address;
      description
        "IPv6 address of Controller for this AP. The list should be
        ordered, according to priority. eg. Primary first, Secondary second,
        Tertiary third etc.";
    }
  }

  grouping assigned-controllers-state {
    description
      "Controller(s) an AP may join. If cloud controller, this will be
      the cloud instance(s).";

    leaf joined {
      type boolean;
      description
        "True only if this AP is currently joined to a controller. If this AP
        is configured to join controller(s), however is not currently joined
        to any controller, this MUST return False.";
    }
  }

  grouping controller-ap-parameters-top {
    description
      "Top-level grouping for assigning AP's to Controller(s).";

    container assigned-controllers {
      description
        "Wireless Controller(s) this AP is assigned to. eg. Primary
        Secondary, Tertiary etc.";

      list controller {
        key "id";
        description
          "Controller(s) this AP is assinged to, referenced by id.";

        leaf id {
          type leafref {
            path "../config/id";
          }
          description
            "id serves as a reference point to the [1-n] Controller(s) this AP
            is assigned to.";
        }

        container config {
          description
            "Config. container for assigning APs to Controllers.";

          uses assigned-controllers-config;
        }

        container state {
          config false;
          description
            "State container for APs assigned to Controllers.";

          uses assigned-controllers-config;
          uses assigned-controllers-state;
        }
      }
    }
  }

  augment "/oc-sys:system" {
  description
    "Augmentation to opeconfig-system.yang to include WiFi Controller.";

  uses controller-ap-parameters-top;
  }

  // hostname is set using openconfig-wifi-aps model.
  deviation /oc-sys:system/oc-sys:config/oc-sys:hostname {
    deviate not-supported;
  }

  deviation /oc-sys:system/oc-sys:state/oc-sys:hostname {
    deviate not-supported;
  }
}
