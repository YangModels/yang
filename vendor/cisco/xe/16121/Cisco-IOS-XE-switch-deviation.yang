module Cisco-IOS-XE-switch-deviation {
  namespace "http://cisco.com/ns/yang/Cisco-IOS-XE-switch-deviation";
  prefix ios-sw-d;

  import cisco-semver {
    prefix cisco-semver;
  }
 

  import Cisco-IOS-XE-native {
     prefix ios;
  }

  import Cisco-IOS-XE-policy {
     prefix ios-policy;
  }

  import Cisco-IOS-XE-switch {
     prefix ios-sw;
  }

  organization "Cisco Systems";

  description
     "Cisco XE Native Deviation YANG module for IOS
      Copyright (c) 2016 by Cisco Systems, Inc.
      All rights reserved.";

  ////////////////////////////////////////////////////////////////////////////
  // REVISION
  ///////////////////////////////////////////////////////////////////////////
  revision 2019-07-01 {
    description "Establish semantic version baseline";
    cisco-semver:module-version "1.0.0";
  }
  revision 2016-12-01 {
     description "Added interface switchport deviation";
  }

  ////////////////////////////////////////////////////////////////////////////////
  // DEVIATION
  ///////////////////////////////////////////////////////////////////////////////

  deviation "/ios:native/ios:policy/ios-policy:class-map/" +
      "ios-policy:match/ios-policy:access-group/ios-policy:index" {
    deviate replace {
      type uint32 {
        range "1..2799";
      }
    }
  }
  deviation "/ios:native/ios:policy/ios-policy:policy-map/" +
      "ios-policy:class/ios-policy:action-list/ios-policy:action-param/" +
      "ios-policy:bandwidth-case/ios-policy:bandwidth/ios-policy:bits" {
    deviate replace {
      type uint32 {
    range "100..40000000";
      }
    }
  }
  deviation "/ios:native/ios:policy/ios-policy:policy-map/" +
      "ios-policy:class/ios-policy:action-list/ios-policy:action-param/" +
      "ios-policy:priority-case/ios-policy:priority/" +
      "ios-policy:priority-type/ios-policy:kilo-bits/ios-policy:kilo-bits" {
    deviate replace {
      type uint32 {
        range "8..40000000"; // switch range
      }
    }
  }
  deviation "/ios:native/ios:line/ios:vty/ios:first" {
    deviate replace {
      type uint16 {
        range "0..97";
      }
    }
  }
  deviation "/ios:native/ios:line/ios:vty/ios:last" {
    deviate replace {
      type uint16 {
        range "1..97";
      }
    }
  }
  deviation "/ios:native/ios:interface/ios:FastEthernet/ios:switchport/" +
      "ios-sw:port-security/ios-sw:maximum/ios-sw:max-addresses" {
    deviate replace {
      type uint16 {
    range "1..4096";
      }
    }
  }
  deviation "/ios:native/ios:interface/ios:GigabitEthernet/ios:switchport/" +
      "ios-sw:port-security/ios-sw:maximum/ios-sw:max-addresses" {
    deviate replace {
      type uint16 {
    range "1..4096";
      }
    }
  }
  deviation "/ios:native/ios:interface/ios:TenGigabitEthernet/" +
      "ios:switchport/ios-sw:port-security/ios-sw:maximum/" +
      "ios-sw:max-addresses" {
    deviate replace {
      type uint16 {
    range "1..4096";
      }
    }
  }
  deviation "/ios:native/ios:interface/ios:Port-channel/" +
      "ios:switchport/ios-sw:port-security/ios-sw:maximum/" +
      "ios-sw:max-addresses" {
    deviate replace {
      type uint16 {
    range "1..4096";
      }
    }
  }
  deviation "/ios:native/ios:interface/ios:Port-channel-subinterface/" +
      "ios:Port-channel/ios:switchport/ios-sw:port-security/" +
      "ios-sw:maximum/ios-sw:max-addresses" {
    deviate replace {
      type uint16 {
    range "1..4096";
      }
    }
  }
}
