module nvo {
  namespace "urn:ietf:params:xml:ns:yang:nvo";
  
  prefix nvo;

  import cisco-semver {
    prefix cisco-semver;
  }
 
  import ietf-inet-types {
    prefix inet;
  }
  import ietf-interfaces {
    prefix if;
  }
  import ietf-routing {
    prefix rt;
  }
  import pim {
    prefix pim;
  }

  organization "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco VxLAN feature configuration.
     
     Copyright (c) 2013-2014 by Cisco Systems, Inc.
     All rights reserved.";

  revision 2019-07-01 {
    description "Establish semantic version baseline";
    cisco-semver:module-version "1.0.0";
  }
  revision 2015-06-02 {
    description
      "Revision based on Gov Review.";
    reference "";
  }

  typedef virtual-network-id-type {
    type uint32 {
      range "1..16777214";
    }
    description
      "Virtual Network Identifier type";
  }

  identity overlay-encap-type {
    description
      "Base identity from which identities describing different
       encapsulationtypes are derived.";
  }

  identity vxlan-type {
    base overlay-encap-type;
    description
      "This identity represents vxlan encapsulation.";
  }

  identity nvgre-type {
    base overlay-encap-type;
    description
      "This identity represents nvgre encapsulation.";
  }

  container nvo-instances {
    description "vxlan instances";
    list nvo-instance {
      key "nvo-id";
      description "List of instances";
      leaf nvo-id {
        type uint16;
        description
          "Network Virtualization Overlay Instance 
           Identifier";
      }
      leaf overlay-encapsulation {
        type identityref {
          base overlay-encap-type;
        }
        description
          "Encapsulation type";
      }
      leaf source-interface {
        type if:interface-ref;
        mandatory true;
        description
          "Source interface name";
      }
      list virtual-network {
        key "vni-start vni-end";
        description
          "VNI member attributes";
        leaf vni-start {
          type virtual-network-id-type;
          mandatory true;
          description
            "Single Virtual Network Identifier 
             or start of range";
        }
        leaf vni-end {
          type virtual-network-id-type;
          mandatory true;
          description
            "End of Virtual Network Identifier range 
             (make equal to vni-start for single vni";
        }
        choice replication-mode {
          mandatory true;
          description "vxlan replication";
           case ip-multicast {
            container multicast {
              description
                "Mulitcast group range associated 
                 with the VxLAN segment(s)";
              leaf multicast-group-min {
                type pim:IPv4-Multicast-Group-Address;
                description
                  "Single IPV4 Multicast group 
                   address or start of range";
              }
              leaf multicast-group-max {
                type pim:IPv4-Multicast-Group-Address;
                description
                  "End of IPV4 Multicast group 
                   address (leave unspecified for single value";
              }
            }
          }
          case static-peer-list {
            list peers {
              key "peer-ip";
              description
                "List of VTEP peers";
              leaf peer-ip {
                type inet:ip-address;
                description
                  "VTEP peer IP address";
              }
            }
          }
          case bgp {
            leaf bgp {
              type empty;
              description
                "Use control protocol BGP to discover 
                 peers";
            }
          }
        }
        leaf routing-instance {
          type rt:routing-instance-ref;
          description
            "VRF Name";
        }
        leaf end-host-discovery {
          type enumeration {
            enum "flood-and-learn" {
              description
                "Discover end-hosts using data plane 
                               flood and learn";
            }
            enum "bgp" {
              description
                "Discover end-hosts using bgp-evpn";
            }
          }
          default "flood-and-learn";
          description "How to peform endpoint discovery";
        }
        leaf suppress-arp {
          type empty;
          description
            "Enable ARP request suppression for this VNI";
          
        }
      }
    }
  }
}
