submodule Cisco-IOS-XE-dhcp-rpc {
  belongs-to Cisco-IOS-XE-rpc {
    prefix ios-xe-rpc;
  }

  import cisco-semver {
    prefix cisco-semver;
  }

  organization "Cisco Systems";

  contact
    <mailto:cs-yang@cisco.com>;

  description
    "NED DHCP RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2018-12-06 {
    description
      "created for NED RPC modularisation";
  }

  grouping clear-choice-ip-case-ip-protocol-dhcp-case-grouping {
    container dhcp {
      description
        "Delete items from the DHCP database";
      container binding {
        description
          "DHCP address bindings";
        leaf vrf {
          description 
            "DHCP vrf bindings";
          type string;
        }
        leaf all-drop-node-name {
          description 
            "Clear all automatic bindings";
          mandatory true;
          type string {
            pattern "[*]";
          }
        }
      }
    }
  }
}
