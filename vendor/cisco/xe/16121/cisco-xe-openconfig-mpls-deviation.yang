module cisco-xe-openconfig-mpls-deviation {
  namespace "http://cisco.com/ns/cisco-xe-openconfig-mpls-deviation";

  prefix oc-mpls-devs;

  import openconfig-network-instance {
    prefix oc-netinst;
  }

  import openconfig-mpls {
    prefix oc-mpls;
  }

  organization
    "Cisco Systems, Inc.";

  contact
    "Cisco Systems, Inc.
    Customer Service

    Postal: 170 W Tasman Drive
    San Jose, CA 95134

    Tel: +1 1800 553-NETS

    E-mail: cs-yang@cisco.com";

  description
    "This module defines deviation statements for openconfig-mpls module.";

  revision 2019-06-27 {
    description
      "Added not-supported to oc-mpls xpath";
  }

  revision 2018-12-05 {
    description
      "Initial Revision";
  }

  deviation "/oc-netinst:network-instances/oc-netinst:network-instance/oc-netinst:mpls" {
    deviate not-supported;
    description "Not supported in 16.12 release";
  }

  deviation "/oc-mpls:mpls" {
    deviate not-supported;
    description "Not supported in 16.12 release";
  }
}
