module Cisco-IOS-XE-device-sensor {
  namespace "http://cisco.com/ns/yang/Cisco-IOS-XE-device-sensor";
  prefix ios-ds;

  import cisco-semver {
    prefix cisco-semver;
  }
 
  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Device Sensor Yang model.
     Copyright (c) 2016 by Cisco Systems, Inc.
     All rights reserved.";

  // =========================================================================
  // REVISION
  // =========================================================================
  revision 2019-07-01 {
    description "Establish semantic version baseline";
    cisco-semver:module-version "1.0.0";
  }
  revision 2017-02-07 {
    description
      "Initial revision";
  }

  grouping config-device-sensor-grouping {
    container device-sensor {
      description 
        "IOS Sensor Commands";
      leaf accounting {
        description 
          "Trigger accounting updates with sensor TLVs/Options";
        type empty;
      }
      container notify {
        description 
          "Options for when to trigger identity update events";
        leaf all-changes {
          description
            "Trigger identity update when TLVs are added/modified/removed";
          type empty;
        }		  
      }
    }  
  }

  /////////////////////////////////////////////////////////
  // native / device-sensor 
  /////////////////////////////////////////////////////////
  augment "/ios:native" {
    uses config-device-sensor-grouping;
  }
}
