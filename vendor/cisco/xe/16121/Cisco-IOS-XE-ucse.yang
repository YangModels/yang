module Cisco-IOS-XE-ucse {
  namespace "http://cisco.com/ns/yang/Cisco-IOS-XE-ucse";
  prefix ios-ucse;

  import cisco-semver {
    prefix cisco-semver;
  }
 
  import Cisco-IOS-XE-native {
    prefix ios;
  }


  import ietf-inet-types {
    prefix inet;
  }

  organization
    "Cisco Systems, Inc.";

  contact
    "Cisco Systems, Inc.
    Customer Service
  
    Postal: 170 W Tasman Drive
    San Jose, CA 95134
  
    Tel: +1 1800 553-NETS
  
    E-mail: cs-yang@cisco.com";
  
  description
    "Cisco XE Native UCS-E Yang model.
    Copyright (c) 2018-2019 by Cisco Systems, Inc.
    All rights reserved.";

  // =========================================================================
  // REVISION
  // =========================================================================
  revision 2019-07-01 {
    description 
      "- Establish semantic version baseline
       - UCSE support - initial revision";
    cisco-semver:module-version "1.0.0";
  }

  grouping ucse-imc-grouping {
    container access-port {
      description "UCSE server access port configuration";

      choice access-port-choice {
        case dedicated-mgmt-port {
          leaf dedicated {
            description "Dedicated Management Port";
            type empty;
          }
        }

        case shared-lom-port {
          container shared-lom {
            description "Shared LOM";

            choice port-choice {
              leaf ge1 {
                description "GE1";
                type empty;
              }

              leaf ge2 {
                description "GE2";
                type empty;
              }

              leaf ge3 {
                description "GE3";
                type empty;
              }

              leaf te2 {
                description "TE2";
                type empty;
              }

              leaf te3 {
                description "TE3";
                type empty;
              }
              
              leaf console {
                description "Console";
                type empty;
              }

              container failover {
                description "Failover";

                container failover-ge-case {
                  description "Failover";

                  leaf ge2 {
                    description "GE2";
                    mandatory true;
                    type empty;
                  }
    
                  leaf ge3 {
                    description "GE3";
                    mandatory true;
                    type empty;
                  }
                } // container failover-ge

                container failover-te-case {
                  description "Failover";

                  leaf te2 {
                    description "TE2";
                    mandatory true;
                    type empty;
                  }

                  leaf te3 {
                    description "TE3";
                    mandatory true;
                    type empty;
                  }
                } // container failover-te
              } // container failover
            } // port-choice
          } // container shared-lom
        } // case shared-lom-port
      } // access-port-choice
    } // container access-port

    container ip {
      description "Interface Internet Protocol";

      choice ip-static-vs-dhcp-choice {
        container static-case {
          

          leaf address {
            description "IP address";
            type inet:ipv4-address;
            mandatory true;
          }

          leaf mask {
            description "IP subnet mask";
            type inet:ipv4-address;
            mandatory true;
          }

          leaf default-gateway {
            description "Default gateway";
            type inet:ipv4-address;
          }
        } // container static-case
  
        container dhcp-case {
          leaf dhcp {
            description "IP dhcp";
            type empty;
          }
        } // dhcp-case
      } // ip-static-vs-dhcp-choice
    } // container ip

    container vlan {
      description "VLAN ID with optional vlan-priority";
      

      leaf vlan-id {
        description "VLAN ID";
        type uint16 {
          range "2..4095";
        }
      }

      leaf priority {
        description "VLAN priority";
        type uint8 {
          range "0..7";
        }
      }
    } // container vlan
  } // ucse-imc-grouping

  grouping ucse-platform-grouping {
    list switchport {
      description "UCSE switchport configuration";
      

      key "port-number";
      leaf port-number {
        description "Port number <0-1>";
        type uint8 {
          range "0..1";
        }
      }

      leaf svi {
        description "SVI switch-virtual-interface";
        mandatory true;
        type empty;
      }
    }
  } // ucse-platform-grouping

  grouping config-ucse-grouping {
    container ucse {
      description "UCSE configuration";

      list subslot {
        description "Subslot information";
  
        key "subslot-name";
        leaf subslot-name {
          description "<0-2>/<0-3>;;Enter card slot/subslot number";
          type string;
        }
  
        container imc {
          description "UCSE BMC configuration";
          uses ucse-imc-grouping;
        }
  
        container platform {
          description "UCSE Platform configuration";
          uses ucse-platform-grouping;
        }
      } // list subslot
    } // container ucse
  } // config-ucse-grouping

  /////////////////////////////////////////////////////////
  // native / ucse
  /////////////////////////////////////////////////////////
  augment "/ios:native" {
    uses config-ucse-grouping;
  }
} // module Cisco-IOS-XE-ucse
