module cisco-xe-openconfig-bgp-deviation {
  namespace "http://cisco.com/ns/yang/cisco-xe-openconfig-bgp-deviation";

  prefix oc-bgp-devs;

  import openconfig-network-instance {
    prefix oc-netinst;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-network-instance
     module.
     Copyright (c) 2017, 2018 by Cisco Systems, Inc.
     All rights reserved.";
  
  revision 2018-05-21{
    description
      "Added not supported deviation for the minimum-advertisement-interval timer leaf under the neighbour config.";

    reference
      "RFC 6020: YANG - A Data Modeling Language for the
      Network Configuration Protocol (NETCONF)";

  }
  revision 2017-05-24{
    description
      "Initial Revision";

    reference
      "RFC 6020: YANG - A Data Modeling Language for the
      Network Configuration Protocol (NETCONF)";

  }
  deviation "/oc-netinst:network-instances/oc-netinst:network-instance/oc-netinst:protocols/oc-netinst:protocol" +
   "/oc-netinst:bgp/oc-netinst:global/oc-netinst:state/oc-netinst:total-paths" {
      deviate not-supported;
      description
        "Not supported 16.7 release.";
  }
  deviation "/oc-netinst:network-instances/oc-netinst:network-instance/oc-netinst:protocols/oc-netinst:protocol" +
   "/oc-netinst:bgp/oc-netinst:global/oc-netinst:state/oc-netinst:total-prefixes" {
      deviate not-supported;
      description
        "Not supported 16.7 release.";
  }
  deviation "/oc-netinst:network-instances/oc-netinst:network-instance/oc-netinst:protocols/oc-netinst:protocol" +
   "/oc-netinst:bgp/oc-netinst:global/oc-netinst:default-route-distance/oc-netinst:config" +
   "/oc-netinst:external-route-distance" {
     deviate add {
       must "../oc-netinst:internal-route-distance" {
         error-message "When External route distance is set, internal route distance must be set too";
       }
     }
  }

  deviation "/oc-netinst:network-instances/oc-netinst:network-instance/oc-netinst:protocols/oc-netinst:protocol" +
   "/oc-netinst:bgp/oc-netinst:global/oc-netinst:default-route-distance/oc-netinst:config" +
   "/oc-netinst:internal-route-distance" {
     deviate add {
       must "../oc-netinst:external-route-distance" {
         error-message "When internal route distance is set, external route distance must be set too";
       }
     }
  }
  deviation "/oc-netinst:network-instances/oc-netinst:network-instance/oc-netinst:protocols/oc-netinst:protocol" +
   "/oc-netinst:bgp/oc-netinst:global/oc-netinst:afi-safis/oc-netinst:afi-safi/oc-netinst:ipv4-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:ipv6-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:ipv4-labeled-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:ipv6-labeled-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l3vpn-ipv4-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l3vpn-ipv6-unicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l3vpn-ipv4-multicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l3vpn-ipv6-multicast" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l2vpn-vpls" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:l2vpn-evpn" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:route-selection-options" +
   "/oc-netinst:config/oc-netinst:always-compare-med" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:route-selection-options" +
   "/oc-netinst:config/oc-netinst:external-compare-router-id" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:use-multiple-paths/oc-netinst:ebgp" +
   "/oc-netinst:config/oc-netinst:allow-multiple-as" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:route-selection-options" +
   "/oc-netinst:config/oc-netinst:ignore-as-path-length" {
      deviate not-supported;
      description
        "Not supported 16.7 release.";
  }
  deviation "/oc-netinst:network-instances/oc-netinst:network-instance/oc-netinst:protocols/oc-netinst:protocol" +
    "/oc-netinst:bgp/oc-netinst:global/oc-netinst:afi-safis/oc-netinst:afi-safi/oc-netinst:route-selection-options" +
    "/oc-netinst:config/oc-netinst:advertise-inactive-routes" {
      deviate delete {
        default false;
      }
    }
  deviation "/oc-netinst:network-instances/oc-netinst:network-instance/oc-netinst:protocols/oc-netinst:protocol" +
   "/oc-netinst:bgp/oc-netinst:global/oc-netinst:afi-safis/oc-netinst:afi-safi/oc-netinst:route-selection-options" +
   "/oc-netinst:config/oc-netinst:enable-aigp" {
      deviate not-supported;
      description
        "Not supported 16.7 release.";
  }
  deviation "/oc-netinst:network-instances/oc-netinst:network-instance/oc-netinst:protocols/oc-netinst:protocol" +
   "/oc-netinst:bgp/oc-netinst:global/oc-netinst:afi-safis/oc-netinst:afi-safi/oc-netinst:route-selection-options" +
   "/oc-netinst:state/oc-netinst:enable-aigp" {
      deviate not-supported;
      description
        "Not supported 16.7 release.";
  }
  deviation "/oc-netinst:network-instances/oc-netinst:network-instance/oc-netinst:protocols/oc-netinst:protocol" +
   "/oc-netinst:bgp/oc-netinst:global/oc-netinst:graceful-restart/oc-netinst:config/oc-netinst:helper-only" {
      deviate not-supported;
      description
        "Not supported 16.7 release.";
  }
  deviation "/oc-netinst:network-instances/oc-netinst:network-instance/oc-netinst:protocols/oc-netinst:protocol" +
   "/oc-netinst:bgp/oc-netinst:global/oc-netinst:graceful-restart/oc-netinst:state/oc-netinst:helper-only" {
      deviate not-supported;
      description
        "Not supported 16.7 release.";
  }
  deviation "/oc-netinst:network-instances/oc-netinst:network-instance/oc-netinst:protocols/oc-netinst:protocol" +
   "/oc-netinst:bgp/oc-netinst:global/oc-netinst:use-multiple-paths/oc-netinst:ebgp/oc-netinst:config/oc-netinst:allow-multiple-as" {
      deviate not-supported;
      description
        "Not supported 16.7 release.";
  }
  deviation "/oc-netinst:network-instances/oc-netinst:network-instance/oc-netinst:protocols/oc-netinst:protocol" +
   "/oc-netinst:bgp/oc-netinst:global/oc-netinst:use-multiple-paths/oc-netinst:ebgp/oc-netinst:config/oc-netinst:maximum-paths" {
      deviate not-supported;
      description
        "Not supported 16.7 release.";
  }
  deviation "/oc-netinst:network-instances/oc-netinst:network-instance/oc-netinst:protocols/oc-netinst:protocol" +
   "/oc-netinst:bgp/oc-netinst:global/oc-netinst:use-multiple-paths/oc-netinst:ebgp/oc-netinst:state/oc-netinst:maximum-paths" {
      deviate not-supported;
      description
        "Not supported 16.7 release.";
  }
  deviation "/oc-netinst:network-instances/oc-netinst:network-instance/oc-netinst:protocols/oc-netinst:protocol" +
   "/oc-netinst:bgp/oc-netinst:global/oc-netinst:use-multiple-paths/oc-netinst:ibgp/oc-netinst:config/oc-netinst:maximum-paths" {
      deviate not-supported;
      description
        "Not supported 16.7 release.";
  }
  deviation "/oc-netinst:network-instances/oc-netinst:network-instance/oc-netinst:protocols/oc-netinst:protocol" +
   "/oc-netinst:bgp/oc-netinst:global/oc-netinst:use-multiple-paths/oc-netinst:ibgp/oc-netinst:state/oc-netinst:maximum-paths" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:config/oc-netinst:enabled" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:state/oc-netinst:last-established" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:state/oc-netinst:established-transitions" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor" +
   "/oc-netinst:timers/oc-netinst:config/oc-netinst:connect-retry" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor" +
   "/oc-netinst:timers/oc-netinst:config/oc-netinst:minimum-advertisement-interval" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor" +
   "/oc-netinst:error-handling/oc-netinst:config" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor" +
   "/oc-netinst:error-handling/oc-netinst:state/oc-netinst:erroneous-update-messages" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:use-multiple-paths/oc-netinst:ebgp" +
   "/oc-netinst:config/oc-netinst:allow-multiple-as" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:add-paths" +
   "/oc-netinst:config/oc-netinst:eligible-prefix-policy" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:config/oc-netinst:restart-time" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:config/oc-netinst:stale-routes-time" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:config/oc-netinst:helper-only" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:state/oc-netinst:helper-only" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:state/oc-netinst:peer-restart-time" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:state/oc-netinst:peer-restarting" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:state/oc-netinst:local-restarting" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:graceful-restart" +
   "/oc-netinst:state/oc-netinst:mode" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:afi-safis/oc-netinst:afi-safi" +
   "/oc-netinst:state/oc-netinst:active" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:afi-safis/oc-netinst:afi-safi" +
   "/oc-netinst:graceful-restart/oc-netinst:state/oc-netinst:advertised" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:afi-safis/oc-netinst:afi-safi" +
   "/oc-netinst:graceful-restart/oc-netinst:state/oc-netinst:received" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:afi-safis/oc-netinst:afi-safi" +
   "/oc-netinst:use-multiple-paths/oc-netinst:config/oc-netinst:enabled" {
      deviate not-supported;
      description
        "Not supported 16.7 release.";
  }
  deviation "/oc-netinst:network-instances/oc-netinst:network-instance/oc-netinst:protocols/oc-netinst:protocol" +
   "/oc-netinst:bgp/oc-netinst:neighbors/oc-netinst:neighbor/oc-netinst:afi-safis/oc-netinst:afi-safi" +
   "/oc-netinst:use-multiple-paths/oc-netinst:ebgp/oc-netinst:config/oc-netinst:allow-multiple-as" {
      deviate not-supported;
      description
        "Not supported 16.7 release.";
  }
  deviation "/oc-netinst:network-instances/oc-netinst:network-instance/oc-netinst:protocols/oc-netinst:protocol" +
    "/oc-netinst:bgp/oc-netinst:peer-groups/oc-netinst:peer-group/oc-netinst:state/oc-netinst:total-paths" {
      deviate not-supported;
      description
        "Not supported 16.7 release.";
  }
  deviation "/oc-netinst:network-instances/oc-netinst:network-instance/oc-netinst:protocols/oc-netinst:protocol" +
    "/oc-netinst:bgp/oc-netinst:peer-groups/oc-netinst:peer-group/oc-netinst:state/oc-netinst:total-prefixes" {
      deviate not-supported;
      description
        "Not supported 16.7 release.";
  }
  deviation "/oc-netinst:network-instances/oc-netinst:network-instance/oc-netinst:protocols/oc-netinst:protocol" +
    "/oc-netinst:bgp/oc-netinst:peer-groups/oc-netinst:peer-group/oc-netinst:afi-safis/oc-netinst:afi-safi" +
    "/oc-netinst:config/oc-netinst:enabled" {
      deviate not-supported;
      description
        "Not supported 16.7 release.";
    }

  deviation "/oc-netinst:network-instances/oc-netinst:network-instance/oc-netinst:protocols/oc-netinst:protocol" +
   "/oc-netinst:bgp/oc-netinst:peer-groups/oc-netinst:peer-group/oc-netinst:use-multiple-paths" +
   "/oc-netinst:ebgp/oc-netinst:config/oc-netinst:allow-multiple-as" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:use-multiple-paths" +
   "/oc-netinst:ebgp/oc-netinst:config/oc-netinst:maximum-paths" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:use-multiple-paths" +
   "/oc-netinst:ibgp/oc-netinst:config/oc-netinst:maximum-paths" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:graceful-restart" +
   "/oc-netinst:config/oc-netinst:restart-time" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:graceful-restart" +
   "/oc-netinst:config/oc-netinst:stale-routes-time" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:graceful-restart" +
   "/oc-netinst:config/oc-netinst:helper-only" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:graceful-restart" +
   "/oc-netinst:state/oc-netinst:helper-only" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:route-selection-options" +
   "/oc-netinst:config/oc-netinst:ignore-next-hop-igp-metric" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:route-selection-options" +
   "/oc-netinst:config/oc-netinst:always-compare-med" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:route-selection-options" +
   "/oc-netinst:config/oc-netinst:external-compare-router-id" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:route-selection-options" +
   "/oc-netinst:config/oc-netinst:advertise-inactive-routes" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:route-selection-options" +
   "/oc-netinst:config/oc-netinst:ignore-as-path-length" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:use-multiple-paths" +
   "/oc-netinst:ebgp/oc-netinst:config/oc-netinst:maximum-paths" {
      deviate not-supported;
      description
        "Not supported 16.7 release.";
  }
  deviation "/oc-netinst:network-instances/oc-netinst:network-instance/oc-netinst:protocols/oc-netinst:protocol" +
   "/oc-netinst:bgp/oc-netinst:peer-groups/oc-netinst:peer-group/oc-netinst:afi-safis/oc-netinst:afi-safi/oc-netinst:use-multiple-paths" +
   "/oc-netinst:ibgp/oc-netinst:config/oc-netinst:maximum-paths" {
      deviate not-supported;
      description
        "Not supported 16.7 release.";
  }
}
