module cisco-xe-openconfig-interfaces-deviation {
  // namespace
  namespace "http://openconfig.net/yang/cisco-xe-openconfig-interfaces-deviation";

  prefix oc-if-devs;

  import openconfig-interfaces {
    prefix oc-if;
  }

  import openconfig-vlan {
    prefix oc-vlan;
  }

  import openconfig-if-ip {
    prefix oc-ip;
  }

  organization
    "C Systems, Inc.";

  contact
    " Cisco Systems, Inc.
    Customer Service

    Postal: 170 W Tasman Drive
    San Jose, CA 95134

    Tel: +1 1800 553-NETS

    E-mail: cs-yang@cisco.com";

  description
    "This module defines deviation statements for openconfig-interfaces module.";

  revision 2018-08-21 {
    description
      "Removed the replace deviations for the interface and subinterface enable leafs.";
  }

  revision 2018-08-14 {
    description
      "Deviated out hold-time/up and down leafs as they are not supported on IOS XE.";
  }

  revision 2018-07-01 {
    description
      "Add deviation for the enabled leafs on the interfaces.";
  }

  revision 2018-03-27 {
    description
      "Add deviation for carrier-transitions.";
  }

  revision 2018-03-07 {
    description
      "Modify vrrp and remove aggregate deviation.";
  }

  revision 2018-02-06 {
    description
      "Deviate out if/loopback-mode, dhcp-client and ipv6/router-advertisement for 16.9.1";
  }

  revision 2018-02-05 {
    description
      "Remove deviation changing last-change leaf type to date-and-time";
  }

  revision 2017-12-07 {
    description
      "Remove oc-interfaces deviation removing ethernet state";
  }

  revision 2017-10-30 {
    description
      "Add deviations to remove vrrp from subinterfaces tree";
  }

  revision 2017-05-08 {
    description
      "Add deviations to change last-change type under subinterfaces to yang:date-and-time";
  }

  revision 2017-04-13 {
    description
      "Add deviations to hide features not implemented in 16.6.1";
  }

  revision 2017-03-10 {
    description
      "Change type of last-change to yang:date-and-time";
  }

  revision 2017-02-21 {
    description
      "Initial Revision";

    reference
      "RFC 6020: YANG - A Data Modeling Language for the
       Network Configuration Protocol (NETCONF)";
  }


 deviation "/oc-if:interfaces/oc-if:interface/oc-if:subinterfaces/oc-if:subinterface" +
            "/oc-ip:ipv6/oc-ip:config/oc-ip:enabled" { 
       deviate replace {
        default false;
       }
      description
        "Dy default the IPv6 on Interface is disabled in IOS XE.";
  }

  deviation "/oc-if:interfaces/oc-if:interface/oc-if:hold-time" {
      deviate not-supported;
      description
        "Hold-time for L2 interfaces is not supported in IOS XE";
  }

  deviation "/oc-if:interfaces/oc-if:interface/oc-if:subinterfaces/oc-if:subinterface" +
            "/oc-ip:ipv4/oc-ip:addresses/oc-ip:address/oc-ip:vrrp/oc-ip:vrrp-group" +
            "/oc-ip:config/oc-ip:accept-mode" {
      deviate not-supported;
      description
        "IPv4 VRRP accept mode not supported in 16.9.1.";
  }

  deviation "/oc-if:interfaces/oc-if:interface/oc-if:subinterfaces/oc-if:subinterface" +
            "/oc-ip:ipv4/oc-ip:addresses/oc-ip:address/oc-ip:vrrp/oc-ip:vrrp-group" +
            "/oc-ip:state/oc-ip:accept-mode" {
      deviate not-supported;
      description
        "IPv4 VRRP accept mode state not supported in 16.9.1.";
  }

  deviation "/oc-if:interfaces/oc-if:interface/oc-if:subinterfaces/oc-if:subinterface" +
            "/oc-ip:ipv6/oc-ip:addresses/oc-ip:address/oc-ip:vrrp/oc-ip:vrrp-group" +
            "/oc-ip:config/oc-ip:accept-mode" {
      deviate not-supported;
      description
        "IPv6 VRRP accept mode not supported in 16.9.1.";
  }

  deviation "/oc-if:interfaces/oc-if:interface/oc-if:subinterfaces/oc-if:subinterface" +
            "/oc-ip:ipv6/oc-ip:addresses/oc-ip:address/oc-ip:vrrp/oc-ip:vrrp-group" +
            "/oc-ip:state/oc-ip:accept-mode" {
      deviate not-supported;
      description
        "IPv6 VRRP accept mode state not supported in 16.9.1.";
  }

  deviation "/oc-if:interfaces/oc-if:interface/oc-vlan:routed-vlan" +
            "/oc-ip:ipv4/oc-ip:addresses/oc-ip:address/oc-ip:vrrp/oc-ip:vrrp-group" +
            "/oc-ip:config/oc-ip:accept-mode" {
      deviate not-supported;
      description
        "IPv4 VRRP accept mode for routed vlan not supported in 16.9.1.";
  }

  deviation "/oc-if:interfaces/oc-if:interface/oc-vlan:routed-vlan" +
            "/oc-ip:ipv4/oc-ip:addresses/oc-ip:address/oc-ip:vrrp/oc-ip:vrrp-group" +
            "/oc-ip:state/oc-ip:accept-mode" {
      deviate not-supported;
      description
        "IPv4 VRRP accept mode state for routed vlan not supported in 16.9.1.";
  }

  deviation "/oc-if:interfaces/oc-if:interface/oc-vlan:routed-vlan" +
            "/oc-ip:ipv6/oc-ip:addresses/oc-ip:address/oc-ip:vrrp/oc-ip:vrrp-group" +
            "/oc-ip:config/oc-ip:accept-mode" {
      deviate not-supported;
      description
        "IPv6 VRRP accept mode for routed vlan not supported in 16.9.1.";
  }

  deviation "/oc-if:interfaces/oc-if:interface/oc-vlan:routed-vlan" +
            "/oc-ip:ipv6/oc-ip:addresses/oc-ip:address/oc-ip:vrrp/oc-ip:vrrp-group" +
            "/oc-ip:state/oc-ip:accept-mode" {
      deviate not-supported;
      description
        "IPv6 VRRP accept mode state for routed vlan not supported in 16.9.1.";
  }

  deviation "/oc-if:interfaces/oc-if:interface/oc-if:config/oc-if:loopback-mode" {
      deviate not-supported;
      description
        "looback-mode not supported in IOS-XE or 16.9.1.";
  }

  deviation "/oc-if:interfaces/oc-if:interface/oc-if:state/oc-if:loopback-mode" {
      deviate not-supported;
      description
        "looback-mode not supported in IOS-XE or 16.9.1.";
  }

  deviation "/oc-if:interfaces/oc-if:interface/oc-if:subinterfaces/oc-if:subinterface/oc-ip:ipv4" +
            "/oc-ip:config/oc-ip:dhcp-client" {
      deviate not-supported;
      description
        "dhcp client not supported in 16.9.1.";
  }

  deviation "/oc-if:interfaces/oc-if:interface/oc-if:subinterfaces/oc-if:subinterface/oc-ip:ipv4" +
            "/oc-ip:state/oc-ip:dhcp-client" {
      deviate not-supported;
      description
        "dhcp client not supported in 16.9.1.";
  }

  deviation "/oc-if:interfaces/oc-if:interface/oc-if:subinterfaces/oc-if:subinterface/oc-ip:ipv6" +
            "/oc-ip:config/oc-ip:dhcp-client" {
      deviate not-supported;
      description
        "dhcp client not supported in 16.9.1.";
  }

  deviation "/oc-if:interfaces/oc-if:interface/oc-if:subinterfaces/oc-if:subinterface/oc-ip:ipv6" +
            "/oc-ip:state/oc-ip:dhcp-client" {
      deviate not-supported;
      description
        "dhcp client not supported in 16.9.1.";
  }

  deviation "/oc-if:interfaces/oc-if:interface/oc-if:subinterfaces/oc-if:subinterface/oc-ip:ipv6" +
            "/oc-ip:router-advertisement" {
      deviate not-supported;
      description
        "ipv6 router-advertisement not supported in 16.9.1.";
  }

  deviation "/oc-if:interfaces/oc-if:interface/oc-if:state/oc-if:counters/oc-if:carrier-transitions" {
      deviate not-supported;
      description
        "carrier-transitions not supported in IOS-XE or 16.9.1.";
  }

  deviation "/oc-if:interfaces/oc-if:interface/oc-if:subinterfaces/oc-if:subinterface/oc-if:state/oc-if:counters/oc-if:carrier-transitions" {
      deviate not-supported;
      description
        "carrier-transitions for subinterfaces not supported in IOS-XE or 16.9.1.";
  }


}
