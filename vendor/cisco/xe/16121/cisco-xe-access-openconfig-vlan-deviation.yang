module cisco-xe-access-openconfig-vlan-deviation {

  namespace "http://cisco.com/ns/yang/cisco-xe-access-openconfig-vlan-deviation";

  prefix cisco-xe-access-oc-vlan-devs;
  
  import openconfig-interfaces { 
    prefix oc-if; 
  }
 
  import openconfig-vlan { 
    prefix oc-vlan; 
  }

  organization "Cisco Systems";

  description
   "This module defines deviation statements for openconfig-vlan model applicable to IOS XE SP Access platforms.";

  revision 2018-12-12 {
    description
      "Initial revision";

    reference
      "RFC 6020: YANG - A Data Modeling Language for the
       Network Configuration Protocol (NETCONF)";
  }


  deviation "/oc-vlan:vlans" {
    deviate not-supported;
  }

  deviation "/oc-if:interfaces/oc-if:interface" + 
            "/oc-if:subinterfaces/oc-if:subinterface/oc-vlan:vlan" {
    deviate not-supported;
  }
}
