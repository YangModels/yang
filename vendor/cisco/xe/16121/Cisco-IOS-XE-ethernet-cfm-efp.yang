submodule Cisco-IOS-XE-ethernet-cfm-efp {
    belongs-to Cisco-IOS-XE-ethernet {
        prefix ios-eth;
    }
    
  import cisco-semver {
    prefix cisco-semver;
  }
 

  import Cisco-IOS-XE-types {
    prefix ios-types;        
  }                          

  import Cisco-IOS-XE-features {
    prefix ios-features;        
  }                             

  organization
    "Cisco Systems, Inc.";

  contact
    "Cisco Systems, Inc.
     Customer Service   

     Postal: 170 W Tasman Drive
     San Jose, CA 95134        

     Tel: +1 1800 553-NETS
                          
    E-mail: cs-yang@cisco.com";

  description
    "Cisco XE Native Yang model for the following sub modules,
        * ethernet-cfm                                        
        * ethernet-efp                                        
     Copyright (c) 2018 by Cisco Systems, Inc.           
     All rights reserved.";                                   

  // =========================================================================
  // REVISION                                                                 
  // =========================================================================
  revision 2019-07-01 {
    description "Establish semantic version baseline";
    cisco-semver:module-version "1.0.0";
  }
  revision 2019-03-11 {
    description
    "This revision has changes for EVC-CFM mep mode additions";
  }
  revision 2019-02-18 {
    description
    "This revision has changes for CFM additions";
  }
  revision 2018-12-13 {                                                       
    description                                                               
      "Initial revision";                                                     
  }                                                                           

  grouping config-interface-efp-l2protocol-grouping {
    leaf-list protocol {                             
      type enumeration {                             
        enum "R4";                                   
        enum "R5";                                   
        enum "R6";                                   
        enum "R8";                                   
        enum "R9";                                   
        enum "RA";                                   
        enum "RB";                                   
        enum "RC";                                   
        enum "RD";                                   
        enum "RF";                                   
        enum "cdp";                                  
        enum "dtp";                                  
        enum "elmi";                                 
        enum "esmc";                                 
        enum "lacp";                                 
        enum "lldp";                                 
        enum "loam";                                 
        enum "pagp";                                 
        enum "ptppd";                                
        enum "stp";                                  
        enum "udld";                                 
        enum "vtp";                                  
      }                                              
    }                                                
  }                                                  

  grouping config-ethernet-cfm-alarm-grouping {
    leaf delay {
      description
        "msec (default 2500 msec)";
      type uint16 {
        range "2500..10000";
      }
      default 2500;
    }
    container notification {
      description
        "CFM alarm notification";
      leaf all {
        description
          "Report all defects: DefRDI, DefMACStatus, DefRemote, DefError, DefXcon";
        type empty;
      }
      leaf error-xcon {
        description
          "Report only: DefError and DefXcon";
        type empty;
      }
      leaf mac-remote-error-xcon {
        description
          "Report only: DefMACStatus, DefRemote, DefError and DefXcon (default)";
        type empty;
      }
      leaf none {
        description
          "No defects to be reported";
        type empty;
      }
      leaf remote-error-xcon {
        description
          "Report only: DefRemote, DefError and DefXcon";
        type empty;
      }
      leaf xcon {
        description
          "Report only: DefXcon";
        type empty;
      }
    }
    leaf reset {
      description
        "msec (default 10000 msec)";
      type uint16 {
        range "2500..10000";
      }
      default 10000;
    }
  }

  grouping config-interface-ethernet-cfm-efp-grouping {

    // interface * / service instance * ethernet
    container service {                         
      description                               
        "Configure Ether Service";              
      list instance {                           
        description                             
          "Configure Ether Service Instance";   
        // interface overlay aslo has service, but not ethernet-grouping
        key "id";                                                       
        leaf id {                                                       
          type uint32;                                                  
        }                                                               
        leaf trunk {                                                    
          description                                                   
            "Trunk Service Instance";                                   
          type empty;                                                   
        }                                                               
        leaf GigabitEthernet {                                          
          description                                                   
            "Configure an GigabitEthernet Instance";                    
          type empty;                                                   
        }                                                               
        leaf ethernet {                                                 
          description                                                   
            "Configure an Ethernet Instance";                           
          type empty;                                                   
        }                                                               
        leaf ethernet-evc-name {                                        
          type string;                                                  
        }                                                               
        // interface * / service instance * ethernet / description      
        leaf description {                                              
          description                                                   
            "Service instance specific description";                    
          type string {                                                 
            length "0..240";                                            
          }                                                             
        }                                                               
        // interface * / service instance * ethernet / evc-name         
        leaf evc-name {                                                 
          type string {                                                 
            length "1..100";                                            
          }                                                             
        }                                                               
        // interface * / service instance * ethernet / encapsulation    
        container encapsulation {                                       
          description                                                   
            "Configure ethernet frame match criteria";                  
          leaf default {                                                
            description                                                 
              "catch-all unconfigured encapsulation";                   
            type empty;                                                 
          }                                                             
          container dot1ad {                                            
            description                                                 
              "802.1ad - Provider Bridges";                             
            leaf-list id {                                              
              type union {                                              
                type uint16 {                                           
                  range "1..4094";                                      
                }                                                       
                type enumeration {                                      
                  enum "any";                                           
                }                                                       
                type string;                                            
              }                                                         
            }                                                           
            leaf-list cos {                                             
              description                                               
                "CoS value to use for CFM packets";                     
              type uint8 {                                              
                range "0..7";                                           
              }                                                         
            }                                                           
            leaf-list dot1q {                                           
              description                                               
                "Second tag (dot1q)";                                   
              type union {                                              
                type uint16 {                                           
                  range "1..4094";                                      
                }                                                       
                type enumeration {                                      
                  enum "any";                                           
                }                                                       
                type string;                                            
              }                                                         
            }                                                           
            container cos2 {                                            
              leaf-list cos {                                           
                description                                             
                  "CoS value to use for CFM packets";                   
                type uint8 {                                            
                  range "0..7";                                         
                }                                                       
              }                                                         
            }                                                           
            leaf-list etype {                                           
              description                                               
                "payload ethertype after Vlan Field";                   
              type enumeration {                                        
                enum "ipv4";                                            
                enum "ipv6";                                            
                enum "pppoe-all";                                       
                enum "pppoe-discovery";                                 
                enum "pppoe-session";                                   
              }                                                         
            }                                                           
            leaf exact {                                                
              description                                               
                "payload Ethertype does not include 802.1q/802.1ad Tags.";
              type empty;                                                 
            }                                                             
          }                                                               
          container dot1q {                                               
            description                                                   
              "IEEE 802.1Q Virtual LAN or S-VLAN";                        
                                                                         
            leaf-list id {                                                
              type union {                                                
                type uint16 {                                             
                  range "1..4094";                                        
                }                                                         
                type enumeration {                                        
                  enum "any";                                             
                }                                                         
                type string;                                              
              }                                                           
            }                                                             
            leaf-list cos {                                               
              description                                                 
                "cos Vlan";                                               
              type uint8 {                                                
                range "0..7";                                             
              }                                                           
            }                                                             
            leaf-list second-dot1q {                                      
              description                                                 
                "inner 802.1Q Virtual LAN or C-VLAN";                     
              type union {                                                
                type uint16 {                                             
                  range "1..4094";                                        
                }                                                         
                type enumeration {                                        
                  enum "any";                                             
                }                                                         
                type string;                                              
              }                                                           
            }                                                             
            container cos2 {                                              
              leaf-list cos {                                             
                description                                               
                  "cos Vlan";                                             
                type uint8 {                                              
                  range "0..7";                                           
                }                                                         
              }                                                           
            }                                                             
            leaf-list etype {                                             
              description                                                 
                "payload ethertype after Vlan Field";                     
              type enumeration {                                          
                enum "ipv4";                                              
                enum "ipv6";                                              
                enum "pppoe-all";                                         
                enum "pppoe-discovery";                                   
                enum "pppoe-session";                                     
              }                                                           
            }                                                             
            leaf exact {                                                  
              description                                                 
                "payload Ethertype does not include 802.1q/802.1ad Tags.";
              type empty;                                                 
            }                                                             
            leaf vlan-type {                                              
              description                                                 
                "Vlan Protocol Type";                                     
              type enumeration {                                          
                enum "0x88A8";                                            
                enum "0x9100";                                            
                enum "0x9200";                                            
              }                                                           
            }                                                             
          }                                                               
          container priority-tagged {                                     
            description                                                   
              "Priority tagged EFP";                                      
            presence "true";                                              
            leaf-list cos {                                               
             description                                                  
              "cos Vlan";                                                 
             type uint8 {                                                 
              range "0..7";                                               
             }                                                            
            }                                                             
            leaf-list etype {                                             
              description                                                 
                "payload ethertype after Vlan Field";                     
              type enumeration {                                          
                enum "ipv4";                                              
                enum "ipv6";                                              
                enum "pppoe-all";                                         
                enum "pppoe-discovery";                                   
                enum "pppoe-session";                                     
              }                                                           
            }                                                             
          }                                                               
          container untagged {                                            
            description                                                   
              "Untagged encapsulation";                                   
            presence "true";                                              
          }                                                               
        }                                                                 
        // interface * / service instance * ethernet / ip                 
        container ip {                                                    
          description                                                     
            "Interface Internet Protocol config commands";                
          container acl {                                                 
            leaf access-group {                                           
              description                                                 
                "Specify access control for packets";                     
              type ios-types:exp-acl-type;                                
            }                                                             
            leaf in {                                                     
              description                                                 
                "inbound packets";                                        
              type empty;                                                 
            }                                                             
            leaf out {                                                    
              description                                                 
                "outbound packets";                                       
              type empty;                                                 
            }                                                             
          }                                                               
          container dhcp {                                                
            description                                                   
              "DHCP";                                                     
            container relay {                                             
              description                                                 
                "DHCP relay";                                             
              container information {                                     
                description                                               
                  "DHCP relay information";                               
                container option {                                        
                  description                                             
                    "DHCP relay information option";                      
                  leaf subscriber-id {                                    
                    description                                           
                      "DHCP relay information option subscriber-id";      
                    type string;                                          
                  }                                                       
                }                                                         
              }                                                           
            }                                                             
          }                                                               
          container verify {                                              
            description                                                   
              "verify";                                                   
            leaf source {                                                 
              description                                                 
                "source address";                                         
              type empty;                                                 
            }                                                             
            leaf vlan {                                                   
              description                                                 
                "vlan specification";                                     
              type empty;                                                 
            }                                                             
            leaf dhcp-snooping {                                          
              description                                                 
                "snooping enable vlan";                                   
              type empty;                                                 
            }                                                             
            leaf port-security {                                          
              description                                                 
                "port security";                                          
              type empty;                                                 
            }                                                             
          }                                                               
        }                                                                 
        // interface * / service instance * ethernet / ipv6               
        container ipv6 {                                                  
          description                                                     
            "IPv6 interface subcommands";                                 
          leaf traffic-filter {                                           
            description                                                   
              "Access control list for packets";                          
            type string;                                                  
          }                                                               
          leaf in {                                                       
            description                                                   
              "inbound packets";                                          
            type empty;                                                   
          }                                                               
          leaf out {                                                      
            description                                                   
              "outbound packets";                                         
            type empty;                                                   
          }                                                               
        }                                                                 
        // interface * / service instance * ethernet / rewrite            
        container rewrite {                                               
          description                                                     
            "Configure ethernet rewrite criteria";                        
          container ingress {                                             
            description                                                   
              "Ingress Rewrite";                                          
            container tag {                                               
              description                                                 
                "Configure Rewrite Tag";                                  
              container pop {                                             
                description                                               
                  "Pop the tag";                                          
                leaf way {                                                
                  type enumeration {                                      
                    enum "1";                                             
                    enum "2";                                             
                  }                                                       
                }                                                         
                leaf mode {                                               
                  type enumeration {                                      
                    enum "symmetric";                                     
                  }                                                       
                }                                                         
              }                                                           
              container push {                                            
                description                                               
                  "Rewrite Operation of push";                            
                leaf dot1q {                                              
                  description                                             
                    "Push dot1q tag";                                     
                  type uint16 {                                           
                    range "1..4094";                                      
                  }                                                       
                }                                                         
                leaf mode {                                               
                  type enumeration {                                      
                    enum "symmetric";                                     
                  }                                                       
                }                                                         
              }                                                           
              container translate {                                       
                description                                               
                  "Translate Tag";                                        
                container t1-to-1 {                                       
                  description                                             
                    "Translate 1-to-1";                                   
                  leaf dot1q {                                            
                    description                                           
                      "Ethertype dot1q of the translation";               
                    type uint16 {                                         
                      range "1..4094";                                    
                    }                                                     
                  }                                                       
                  leaf mode {                                             
                    type enumeration {                                    
                      enum "symmetric";                                   
                    }                                                     
                  }                                                       
                }                                                         
                container t1-to-2 {                                       
                  description                                             
                    "Translate 1-to-2";                                   
                  leaf dot1q {                                            
                    description                                           
                      "Translate ethertype of dot1q";                     
                    type uint16 {                                         
                      range "1..4094";                                    
                    }                                                     
                  }                                                       
                  leaf second-dot1q {                                     
                    description                                           
                      "Second dot1q tag";                                 
                    type uint16 {                                         
                      range "1..4094";                                    
                    }                                                     
                  }                                                       
                  leaf mode {                                             
                    type enumeration {                                    
                      enum "symmetric";                                   
                    }                                                     
                  }                                                       
                }                                                         
                container t2-to-1 {                                       
                  description                                             
                    "Translate 2-to-1";                                   
                  leaf dot1q {                                            
                    description                                           
                      "Ethertype dot1q of the translation";               
                    type uint16 {                                         
                      range "1..4094";                                    
                    }                                                     
                  }                                                       
                  leaf mode {                                             
                    type enumeration {                                    
                      enum "symmetric";                                   
                    }                                                     
                  }                                                       
                }                                                         
                container t2-to-2 {                                       
                  description                                             
                    "Translate 2-to-2";                                   
                  leaf dot1q {                                            
                    description                                           
                      "Translate ethertype of dot1q";                     
                    type uint16 {                                         
                      range "1..4094";                                    
                    }                                                     
                  }                                                       
                  leaf second-dot1q {                                     
                    description                                           
                      "Second dot1q tag";                                 
                    type uint16 {                                         
                      range "1..4094";                                    
                    }                                                     
                  }                                                       
                  leaf mode {                                             
                    type enumeration {                                    
                      enum "symmetric";                                   
                    }                                                     
                  }                                                       
                }                                                         
              }                                                           
            }                                                             
          }                                                               
        }                                                                 
        // interface * / service instance * ethernet / group              
        leaf group {                                                      
          type uint32;                                                    
        }                                                                 
        // interface * / service instance * ethernet / errdisable         
        container errdisable {                                            
          description                                                     
            "Configure error disable";                                    
          container recovery {                                            
            description                                                   
              "enable auto recovery";                                     
            container cause {                                             
              description                                                 
                "error disable cause";                                    
              leaf mac-security {                                         
                description                                               
                  "mac-security violation";                               
                type uint32 {                                             
                  range "30..86400";                                      
                }                                                         
              }                                                           
            }                                                             
          }                                                               
        }                                                                 
        // interface * / service instance * ethernet / ethernet           
        container ethernet-container {                                    
           //in order not to collide with submode ethernet                
          container ethernet {                                            
            description                                                   
              "ethernet";                                                 
            container lmi {                                               
              description                                                 
                "Configure ether lmi parameters";                         
              container ce-vlan {                                         
                description                                               
                  "Configure ether lmi customer vlans";                   
                container map {                                           
                  description                                             
                    "Configure ether lmi ce-vlan/evc map";                
                  choice map-choice {                                     
                    leaf any {                                            
                      description                                         
                        "For all VLANS [1-4094,untagged]";                
                      type empty;                                         
                    }                                                     
                    leaf default {                                        
                      description                                         
                        "Default EFP";                                    
                      type empty;                                         
                    }                                                     
                    leaf untagged {                                       
                      description                                         
                        "Untagged frames";                                
                      type empty;                                         
                    }                                                     
                    leaf vlan-range {                                     
                      type string {                                       
                        pattern "(\\d+(.*-.*\\d+)?)(,.*\\d+(.*-.*\\d+)?)*(,.*untagged)?";
                      }
                    }
                  }
                }
              }
            }
            container loopback {
                description
                    "Ethernet Dataplane Loopback";
                container permit {
                    description
                        "Allow data plane loopback to be activated";
                    leaf external {
                        description
                            "Allow to loopback the traffic from the wire";
                        type empty;
                    }
                    leaf internal {
                        description
                            "Allow to loopback the traffic from the relay";
                        type empty;
                    }
                }
            }
          }
        }
        // interface * / service instance * ethernet / snmp
        container snmp {
            description
                "Modify SNMP service instance parameters";
            container trap {
                description
                    "Allow a specific SNMP trap";
                leaf link-status {
                    description
                        "Allow SNMP LINKUP and LINKDOWN traps";
                    type empty;
                }
            }
            container ifindex {
                description
                    "Persist ifindex for the service instance";
                leaf persist {
                    description
                        "Enable/Disable ifIndex persistence";
                    type empty;
                }
            }
        }
        // interface * / service instance * ethernet / bridge-domain
        container bridge-domain {
            description
                "Bridge-domain";
                  leaf bridge-id {
                              must "../../encapsulation/default or ../../encapsulation/dot1ad/id or ../../encapsulation/dot1q/id"
                                  + " or ../../encapsulation/priority-tagged or ../../encapsulation/untagged" {
                                      error-message "bridge-domain depends on encapsulation configuration";
                                  }
                              type uint16;
                  }
                  container split-horizon {
                      description
                          "Configure this port as a member of a split horizon group";
                              leaf group {
                                  description
                                      "Split-horizon group";
                                  type uint8 {
                                      range "0..13";
                                  }
                              }
                  }
                  leaf from-encapsulation {
                      description
                          "from-encapsulation";
                      type empty;
                  }
        }
        // interface * / service instance * ethernet / mac
        container mac {
            description
                "Commands for MAC Address-based features";
            container security {
                description
                    "MAC Security commands";
                      presence "true";
                      container maximum {
                          description
                              "Configure an upper bound";
                          leaf addresses {
                              description
                                  "Maximum addresses that can be learnt on this service instance";
                              type uint16 {
                                  range "1..1000";
                              }
                          }
                      }
                      leaf violation {
                          description
                              "Configure the response when a MAC security policy is violated";
                                      type enumeration {
                                          enum "protect";
                                          enum "restrict";
                                      }
                      }
            }
            list access-group {
                description
                    "Specify access control for packets";
                          key "acl-name";
                          leaf acl-name {
                              description
                                  "ACL name";
                              type "string";
                          }
                          leaf in {
                              description
                                  "Apply to ingress";
                              type empty;
                          }
                          leaf out {
                              description
                                  "Apply to Egress";
                              type empty;
                          }
            }
        }
        // interface * / service instance * ethernet / service-policy
        container service-policy {
            description
                "Attach a policy-map to an EFP";
            list input {
                description
                    "service policy input";
                          key "name";
                          leaf name {
                              type string;
                          }
            }
            list output {
                description
                    "service policy output";
                          key "name";
                          leaf name {
                              type string;
                          }
            }
        }
        
        // interface * / service instance * ethernet / shutdown
        leaf shutdown {                                        
          description                                          
            "Take the Service Instance out of Service";        
          type empty;                                          
        }                                                      

        // interface * / service instance * ethernet / cfm
        container cfm {                                   
          description                                     
            "Ethernet CFM EFP subcommands";               
          container encapsulation {                       
            description                                   
              "Configure CFM ethernet frame encapsulation";
            container dot1ad {                             
              description                                  
                "802.1ad - Provider Bridges";              
              leaf vlan-id {                               
                type uint16 {                              
                  range "1..4094";                         
                }                                          
              }                                            
              leaf cos {                                   
                description                                
                  "CoS value to use for CFM packets";      
                type uint8 {                               
                  range "0..7";                            
                }                                          
              }                                            
              leaf dot1q {                                 
                description                                
                  "Second tag (dot1q)";                    
                type uint16 {                              
                  range "1..4094";                         
                }                                          
              }                                            
            }                                              
            container dot1q {                              
              description                                  
                "IEEE 802.1Q Virtual LAN or S-VLAN";       
              leaf vlan-id {                               
                type uint16 {                              
                  range "1..4094";                         
                }                                          
              }                                            
              leaf cos {                                   
                description                                
                  "CoS value to use for CFM packets";      
                type uint8 {                               
                  range "0..7";                            
                }                                          
              }                                            
              leaf second-dot1q {                          
                description                                
                  "inner 802.1Q Virtual LAN or C-VLAN";    
                type uint16 {                              
                  range "1..4094";                         
                }                                          
              }                                            
            }                                              
          }                                                

          container mep {
            description  
              "Maintenance End Point";
            leaf domain {
              description
                "Configure a domain for this mep";
              type string;                        
            }                                     
            leaf mpid {                           
              description                         
                "Maintenance End Point Identifier";
              type uint16 {                        
                range "1..8191";
              }
            }
            container alarm {
              description 
                "CFM Alarm";
              uses config-ethernet-cfm-alarm-grouping;
            }
            leaf cos {
              description
                "Specify Class of Service sent in CFM messages for EFP MEP";
              type uint16 {
                range "1..7";
              }
            }
            container continuity-check {
              description
                "Configure Continuity Check for MA";
              container static {
                description
                  "Verify MEP in received CCM is valid";
                leaf rmep {
                  description
                    "MEP defined using mep mpid";
                  type empty;
                }
              }
            }
            container rmep {
              description
                "Static Remote MEP associated with this DOWN MEP";
              leaf mpid {
                description
                  "Maintenance End Point Identifier";
                type uint16{
                  range "1..8191";
                }
              }
            }
          }                                        

          container mip {
            description  
              "Maintenance Intermediate Point";
            leaf level {                       
              description                      
                "Maintenance Level";           
              type uint8;
            }                                  
          }                                    
        }                                      

        // interface * / service instance * ethernet / l2protocol
        container l2protocol {                                   
          description                                            
            "Configure l2 control protocol processing";          
          container discard {                                    
            description                                          
              "discard L2 control protocol packets as data";     
            presence "true";                                     
            uses config-interface-efp-l2protocol-grouping;       
          }                                                      
          container peer {                                       
            description                                          
              "peer L2 control protocol packets as data";        
            presence "true";                                     
            uses config-interface-efp-l2protocol-grouping;       
          }                                                      
          container forward {                                    
            description                                          
              "forward L2 control protocol packets as data";     
            presence "true";                                     
            uses config-interface-efp-l2protocol-grouping;       
          }                                                      
          container tunnel {                                     
            description                                          
              "tunnel L2 control protocol packets as data";      
            presence "true";                                     
            uses config-interface-efp-l2protocol-grouping;       
          }                                                      
        }                                                        
      }                                                          
    }                                                            
  } // config-interface-ethernet-grouping                        

  grouping config-ethernet-cfm-efp-grouping {
    list evc {                               
      if-feature ios-features:eth-evc;       
      description                            
        "define an Ethernet virtual connection (EVC)";
      key "name";                                     
      leaf name {                                     
        type string {                                 
          length "1..100";                            
        }                                             
      }                                               
    }                                                 
                                                      
    // ethernet cfm                                   
    container cfm {                                   
      description                                     
        "Connectivity Fault Management";              
      container ais {                                 
        description                                   
          "AIS Maintenance Condition";                
        container link-status {                       
          description                                 
            "8023ah SMEP or link state up/down";      
          container global {                          
            description                               
              "8023ah SMEP or link state state up/down AIS global configuration";
            presence "true";                                                     
            container cfm-Mode__config-ais-link-cfm {                            
              leaf disable {                                                     
                description                                                      
                  "Disable AIS transmission";                                    
                type empty;                                                      
              }                                                                  
              leaf level {                                                       
                description                                                      
                  "Maintenance Level";                                           
                type uint8 {                                                     
                  range "0..7";                                                  
                }                                                                
              }                                                                  
              container period {                                                 
                description                                                      
                  "AIS Transmission period";                                     
                leaf tp-1 {                                                      
                  type empty;                                                    
                }                                                                
                leaf tp-60 {                                                     
                  description                                                    
                    "Seconds";                                                   
                  type empty;                                                    
                }                                                                
              }                                                                  
            }                                                                    
          }                                                                      
        }                                                                        
      }                                                                          
      container alarm {                                                          
        description                                                              
          "CFM Alarm";                                                           
        uses config-ethernet-cfm-alarm-grouping;

        leaf packet {
          description
            "max DefError and DefXcon packets";
          type uint16 {
            range "1..65535";
          }
        }
      }
      leaf ieee {
          description
              "CFM IEEE enable";
          type empty;
      }
      leaf global {
          description
              "CFM global enable";
          type empty;
      }
      list domain {
          description
            "Configure a domain";
                    key "name";
                    leaf name {
                        description
                          "Domain Name";
                        type string;
                    }
                    leaf level {
                        description
                            "Maintenance Level";
                        type uint8;
                    }
                    list service {
                        description
                            "Maintenance Association within Domain";
                              key "name";
                              leaf name {
                                  type string;
                              }
                              leaf evc {
                                  if-feature ios-features:eth-evc;
                                  description
                                      "Specify EVC";
                                  type string;
                                  
                              }
                              leaf vlan {
                                description
                                  "VLAN id";
                                type uint16 {
                                  range "1..4094";
                               }
                              }
                              container ais {
                                description
                                  "AIS Maintenance Condition";
                                leaf expiry-threshold {
                                  description
                                    "AIS Expiry Threshold";
                                  type uint8 {
                                    range "2..255";
                                  }
                                  default 3;
                                }
                                leaf level {
                                  description
                                    "Maintenance Level to send AIS";
                                  type uint8{
                                    range "0..7";
                                  }
                                }
                                leaf period {
                                  description
                                    "AIS Transmission period";
                                  type enumeration {
                                    enum "1";
                                    enum "60";
                                  }
                                  default 60;
                                }
                                leaf suppress-alarms {
                                  description
                                    "Suppress Alarms";
                                  type empty;
                                }
                              }
                              container continuity-check {
                                description
                                  "Enable Continuity Check for Maintenance Association";
                                presence "true"; 
                              }
                              container lck {
                                description
                                  "LCK Maintenance Condition";
                                leaf expiry-threshold {
                                  description
                                    "LCK Expiry Threshold";
                                  type uint8 {
                                    range "2..255";
                                  }
                                  default 3;
                                }
                                leaf level {
                                  description
                                    "Maintenance Level to send LCK";
                                  type uint8{
                                    range "0..7";
                                  }
                                }
                                leaf period {
                                  description
                                    "LCK Transmission period";
                                  type enumeration {
                                    enum "1";
                                    enum "60";
                                  }
                                  default 60;
                                }
                              }
                              container maximum {
                                description
                                  "Maximum MEPs allowed across network";
                                leaf meps {
                                  description
                                    "Maximum meps";
                                  type uint16{
                                    range "1..65535";
                                  }
                                  default 100;
                                }
                              }
                              container mep {
                                description
                                  "Static MEP within a Maintenance Association";
                                leaf mpid {
                                  description
                                    "Maintenance End Point Identifier";
                                  type uint16{
                                    range "1..8191";
                                  }
                                }
                              }
                              container mip {
                                description
                                  "MIP commands";
                                container auto-create {
                                  description
                                    "Specify MIP auto creation policy";
                                  presence "true";    
                                  choice mip-case {
                                    case lower-mep-case {
                                      leaf lower-mep-only {
                                        description
                                          "Create auto MIP only if lower MEP found";
                                        type empty;
                                      }
                                    }
                                    case none-case {
                                      leaf none {
                                        description
                                          "No MIP auto create";
                                        type empty;
                                      }
                                    }
                                  }
                                }
                              }
                              container offload {
                                description
                                  "Offload options";
                                leaf sampling {
                                  description
                                    "Sampling rate";
                                  type uint16{
                                    range "10..1000";    
                                  }
                                }
                              }
                              leaf sender-id {
                                description
                                  "Include Sender ID TLV";
                                  type enumeration {
                                    enum "chassis";
                                    enum "none";
                                  }
                              } // sender-id 
                    } // list service
      } // list domain

      container logging {                                           
        description                                                 
          "Enable CFM syslog messages";                             
        presence "true";                                            
        leaf ais {                                                  
          description                                               
            "AIS logging";                                          
          type empty;                                               
        }                                                           
        container alarm {                                           
          description                                               
            "Alarm logging";                                        
          leaf cisco {                                              
            description                                             
              "Cisco MIB syslogs";                                  
            type empty;                                             
          }                                                         
          leaf ieee {                                               
            description                                             
              "IEEE MIB syslogs";                                   
            type empty;                                             
          }                                                         
        }                                                           
      }                                                             
      container mep {                                               
        description                                                 
          "Maintenance End Point";                                  
        container crosscheck {                                      
          description                                               
            "Cross Check remote MEPs";                              
          leaf start-delay {                                        
            description                                             
              "seconds (30 seconds default)";                       
            type uint16 {                                           
              range "1..65535";                                     
            }                                                       
          }                                                         
        }                                                           
      }                                                             
      container mip {                                               
        description                                                 
          "CFM MIP commands";                                       
        container auto-create {                                     
          description                                               
            "CFM MIP auto creation";                                
          container level {                                         
            description                                             
              "Maintenance Level";                                  
            list mef-num {                                          
              key "mef-num";                                        
              leaf mef-num {                                        
                description                                         
                  "maintenance level number";                       
                type uint8 {                                        
                  range "0..7";
                }
              }
              leaf evc {
                description
                  "EVC name";
                type string;
              }
              leaf vlan {
                description
                  "VLAN id";
                type uint16 {
                  range "1..4094";
                }
              }
            }
          }
        }
        leaf filter {
          description
            "CFM MIP filter";
          type empty;
        }
      }
      container traceroute {
        description
          "CFM Traceroute";
        container cache {
          description
            "CFM Traceroute Cache";
          presence "true";
          leaf hold-time {
            description
              "minutes (default 100)";
            type uint16 {
              range "1..65535";
            }
          }
          leaf size {
            description
              "Number of cached lines (default 100)";
            type uint16 {
              range "1..4095";
            }
          }
        }
      }
    }
  }
}
