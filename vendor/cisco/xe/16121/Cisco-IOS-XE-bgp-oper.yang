module Cisco-IOS-XE-bgp-oper {
  yang-version 1;
  namespace "http://cisco.com/ns/yang/Cisco-IOS-XE-bgp-oper";
  prefix bgp-ios-xe-oper;

  import Cisco-IOS-XE-bgp-common-oper {
    prefix bgp-common-ios-xe-oper;
  }
  import Cisco-IOS-XE-bgp-route-oper {
    prefix bgp-route-ios-xe-oper;
  }
  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for bgp operational data.
     Copyright (c) 2016-2019 by Cisco Systems, Inc.
     All rights reserved.";

  revision 2019-05-01 {
    description
      "- Added AO leaf descriptions.
       - Added semantic version";
    reference "2.4.0";
    cisco-semver:module-version "2.4.0";
  }
  revision 2018-10-29 {
    description
      "Cleaned up spelling errors in descriptions.";
    reference "2.3.0";
    cisco-semver:module-version "2.3.0";
  }
  revision 2017-09-25 {
    description
      "Properly indicated leaf-list ordering";
    reference "2.2.0";
    cisco-semver:module-version "2.2.0";
  }
  revision 2017-05-12 {
    description
      "Added the BGP RD description";
    reference "2.1.0";
    cisco-semver:module-version "2.1.0";
  }
  revision 2017-04-01 {
    description
      "Top level container name change. Enumeration name changes.";
    reference "2.0.0";
    cisco-semver:module-version "2.0.0";
  }
  revision 2017-02-07 {
    description
      "Initial revision";
    reference "1.0.0";
    cisco-semver:module-version "1.0.0";
  }

  typedef bgp-link {
    type enumeration {
      enum "internal" {
        value 0;
        description
          "iBGP neighbors";
      }
      enum "external" {
        value 1;
        description
          "eBGP neighbors";
      }
    }
    description
      "Operational state relevant to bgp global neighbor";
  }

  typedef bgp-fsm-state {
    type enumeration {
      enum "fsm-idle" {
        value 0;
        description
          "neighbor is in Idle state";
      }
      enum "fsm-connect" {
        value 1;
        description
          "neighbor is in Connect state";
      }
      enum "fsm-active" {
        value 2;
        description
          "neighbor is in Active state";
      }
      enum "fsm-opensent" {
        value 3;
        description
          "neighbor is in OpenSent state";
      }
      enum "fsm-openconfirm" {
        value 4;
        description
          "neighbor is in OpenConfirm state";
      }
      enum "fsm-established" {
        value 5;
        description
          "neighbor is in Established state";
      }
      enum "fsm-nonnegotiated" {
        value 6;
        description
          "neighbor is Non Negotiated";
      }
    }
    description
      "BGP FSM State";
  }

  typedef bgp-mode {
    type enumeration {
      enum "mode-active" {
        value 0;
        description
          "active connection";
      }
      enum "mode-passive" {
        value 1;
        description
          "passive connection";
      }
    }
    description
      "BGP mode";
  }

  grouping bgp-message-counters {
    description
      "BGP message counters";
    leaf opens {
      type uint32;
      description
        "OPEN message count";
    }
    leaf updates {
      type uint32;
      description
        "UPDATE message count";
    }
    leaf notifications {
      type uint32;
      description
        "NOTIFICATION message count";
    }
    leaf keepalives {
      type uint32;
      description
        "KEEPALIVE message count";
    }
    leaf route-refreshes {
      type uint32;
      description
        "Route refresh message count";
    }
  }

  grouping bgp-prefix-counters {
    description
      "Grouping for various prefix counters";
    leaf current-prefixes {
      type uint64;
      description
        "The current number of accepted prefixes";
    }
    leaf total-prefixes {
      type uint64;
      description
        "The total number of accepted prefixes";
    }
    leaf implicit-withdraw {
      type uint64;
      description
        "The number of times a prefix has been
         withdrawn and readvertised";
    }
    leaf explicit-withdraw {
      type uint64;
      description
        "The number of times a prefix has been
         withdrawn because it is no longer feasible";
    }
    leaf bestpaths {
      type uint64;
      description
        "The number of received prefixes installed as best paths";
    }
    leaf multipaths {
      type uint64;
      description
        "The number of received prefixes installed as multipaths";
    }
  }

  grouping negotiated-keepalive-timers {
    description
      "Negotiated keepalive timers details";
    leaf hold-time {
      type uint16;
      description
        "Hold time";
    }
    leaf keepalive-interval {
      type uint16;
      description
        "Keepalive interval";
    }
  }

  grouping neighbor-summary {
    description
      "Information regarding the current state of a neighbor";
    leaf id {
      type string;
      description
        "Neighbor address";
    }
    leaf bgp-version {
      type uint32;
      description
        "BGP protocol version";
    }
    leaf messages-received {
      type uint64;
      description
        "Number of messages received from this neighbor";
    }
    leaf messages-sent {
      type uint64;
      description
        "Number of messages sent to this neighbor";
    }
    leaf table-version {
      type uint64;
      description
        "BGP table version";
    }
    leaf input-queue {
      type uint64;
      description
        "Number of messages in input queue";
    }
    leaf output-queue {
      type uint64;
      description
        "Number of messages in output queue";
    }
    leaf up-time {
      type string;
      description
        "Neighbor session uptime";
    }
    leaf state {
      type bgp-ios-xe-oper:bgp-fsm-state;
      description
        "BGP session state";
    }
    leaf prefixes-received {
      type uint64;
      description
        "Number of prefixes received from the neighbor";
    }
    leaf dynamically-configured {
      type boolean;
      description
        "Indication of whether the neighbor was
         dynamically configured";
    }
    leaf as {
      type uint32;
      description
        "BGP neighbor AS number";
    }
  }

  grouping bgp-connection {
    description
      "Data for current BGP connection state";
    leaf state {
      type bgp-common-ios-xe-oper:tcp-fsm-state;
      description
        "TCP FSM state";
    }
    leaf mode {
      type bgp-ios-xe-oper:bgp-mode;
      description
        "BGP transport connection mode";
    }
    leaf total-established {
      type uint32;
      description
        "The number of times a TCP and BGP 
         connection has been successfully established";
    }
    leaf total-dropped {
      type uint32;
      description
        "The number of times that a valid
         session has failed or been taken down";
    }
    leaf last-reset {
      type string;
      description
        "Time since peering session was last reset";
    }
    leaf reset-reason {
      type string;
      description
        "The reason for the last reset";
    }
  }

  grouping bgp-transport {
    description
      "BGP transport information";
    leaf path-mtu-discovery {
      type boolean;
      description
        "Indication whether path MTU discovery is enabled";
    }
    leaf local-port {
      type uint32;
      description
        "Local TCP port used for TCP session";
    }
    leaf local-host {
      type inet:ip-address;
      description
        "Local address used for the TCP session";
    }
    leaf foreign-port {
      type uint32;
      description
        "Remote port used by the peer for the TCP session";
    }
    leaf foreign-host {
      type inet:ip-address;
      description
        "Remote address of the BGP session";
    }
    leaf mss {
      type uint32;
      description
        "Maximum Data segment size";
    }
    leaf ao-keychain-name {
      type string;
      description
        "Name of the Key Chain for AO";
    }
    leaf ao-key-id {
      type int32;
      description
        "ID of the key for AO";
    }
    leaf ao-incl-tcp-opts {
      type boolean;
      description
        "AO Include TCP Options";
    }
    leaf ao-accept-mismatch-conn {
      type boolean;
      description
        "AO Accept Mismatched Connections";
    }
  }

  grouping bgp-af-prefix-activity {
    description
      "Address family prefix statistics";
    container sent {
      description
        "Number of prefixes sent";
      uses bgp-ios-xe-oper:bgp-prefix-counters;
    }
    container received {
      description
        "Number of prefixes received";
      uses bgp-ios-xe-oper:bgp-prefix-counters;
    }
  }

  grouping bgp-neighbor-counters {
    description
      "BGP neighbor session counters";
    container sent {
      description
        "Number of messages sent";
      uses bgp-ios-xe-oper:bgp-message-counters;
    }
    container received {
      description
        "Number of messages received";
      uses bgp-ios-xe-oper:bgp-message-counters;
    }
    leaf inq-depth {
      type uint32;
      description
        "Input Q depth";
    }
    leaf outq-depth {
      type uint32;
      description
        "Output Q depth";
    }
  }

  grouping neighbor-key {
    description
      "Grouping for neighbor key";
    leaf afi-safi {
      type bgp-common-ios-xe-oper:afi-safi;
      description
        "Afi-safi key";
    }
    leaf vrf-name {
      type string;
      description
        "VRF name";
    }
    leaf neighbor-id {
      type string;
      description
        "Neighbor identifier";
    }
  }

  grouping neighbor {
    description
      "BGP neighbor state information";
    leaf description {
      type string;
      description
        "Neighbor description string";
    }
    leaf bgp-version {
      type uint16;
      description
        "BGP version being used to communicate
         with the remote router";
    }
    leaf link {
      type bgp-ios-xe-oper:bgp-link;
      description
        "Neighbor link type";
    }
    leaf up-time {
      type string;
      description
        "Amount of time the bgp session has been
         up since being established";
    }
    leaf last-write {
      type string;
      description
        "Time since BGP last sent a message to the neighbor";
    }
    leaf last-read {
      type string;
      description
        "Time since BGP last received a message from the neighbor";
    }
    leaf installed-prefixes {
      type uint32;
      description
        "The number of installed prefixes";
    }
    leaf session-state {
      type bgp-ios-xe-oper:bgp-fsm-state;
      description
        "BGP neighbor session state";
    }
    container negotiated-keepalive-timers {
      description
        "Negotiated keepalive timers status of BGP neighbor";
      uses bgp-ios-xe-oper:negotiated-keepalive-timers;
    }
    leaf-list negotiated-cap {
      type string;
      ordered-by user;
      description
        "Negotiated capabilities for neighbor session";
    }
    container bgp-neighbor-counters {
      description
        "BGP neighbor session counters";
      uses bgp-ios-xe-oper:bgp-neighbor-counters;
    }
    container connection {
      description
        "BGP neighbor connection";
      uses bgp-ios-xe-oper:bgp-connection;
    }
    container transport {
      description
        "BGP neighbor transport";
      uses bgp-ios-xe-oper:bgp-transport;
    }
    container prefix-activity {
      description
        "BGP neighbor activity";
      uses bgp-ios-xe-oper:bgp-af-prefix-activity;
    }
    leaf as {
      type uint32;
      description
        "BGP neighbor AS number";
    }
  }

  grouping entry-stats {
    description
      "BGP entry statistics";
    leaf total-entries {
      type uint64;
      description
        "The total number of prefix entries";
    }
    leaf memory-usage {
      type uint64;
      description
        "Total memory usage in byte";
    }
  }

  grouping activities {
    description
      "BGP activity information";
    leaf prefixes {
      type uint64;
      description
        "Total number of prefixes";
    }
    leaf paths {
      type uint64;
      description
        "Total number of paths";
    }
    leaf scan-interval {
      type string;
      description
        "Scan interval in seconds";
    }
  }

  grouping address-family-key {
    description
      "Address family key";
    leaf afi-safi {
      type bgp-common-ios-xe-oper:afi-safi;
      description
        "Afi-safi value";
    }
    leaf vrf-name {
      type string;
      description
        "VRF name";
    }
  }

  grouping address-family-summary {
    description
      "Summary of address family";
    leaf router-id {
      type inet:ip-address;
      description
        "Router ID";
    }
    leaf bgp-table-version {
      type uint64;
      description
        "BGP table version number";
    }
    leaf routing-table-version {
      type uint64;
      description
        "Routing table version number";
    }
    container prefixes {
      description
        "Prefix entry statistics";
      uses bgp-ios-xe-oper:entry-stats;
    }
    container path {
      description
        "Path entry statistics";
      uses bgp-ios-xe-oper:entry-stats;
    }
    container as-path {
      description
        "AS path entry statistics";
      uses bgp-ios-xe-oper:entry-stats;
    }
    container route-map {
      description
        "Route map entry statistics";
      uses bgp-ios-xe-oper:entry-stats;
    }
    container filter-list {
      description
        "Filter list entry statistics";
      uses bgp-ios-xe-oper:entry-stats;
    }
    container activities {
      description
        "BGP activity information";
      uses bgp-ios-xe-oper:activities;
    }
    leaf total-memory {
      type uint64;
      description
        "Total memory in use";
    }
    container bgp-neighbor-summaries {
      description
        "Neighbor summary";
      list bgp-neighbor-summary {
        key "id";
        description
          "List of neighbor summaries";
        uses bgp-ios-xe-oper:neighbor-summary;
      }
    }
    leaf local-as {
      type uint32;
      description
        "Local AS number";
    }
  }

  grouping bgp-state {
    description
      "BGP state information";
    container neighbors {
      description
        "BGP neighbor information";
      list neighbor {
        key "afi-safi vrf-name neighbor-id";
        description
          "List of BGP neighbors";
        uses bgp-ios-xe-oper:neighbor-key;
        uses bgp-ios-xe-oper:neighbor;
      }
    }
    container address-families {
      description
        "BGP address family";
      list address-family {
        key "afi-safi vrf-name";
        description
          "List of BGP address families";
        uses bgp-ios-xe-oper:address-family-key;
        uses bgp-ios-xe-oper:address-family-summary;
      }
    }
    container bgp-route-vrfs {
      description
        "BGP VRFs";
      list bgp-route-vrf {
        key "vrf";
        description
          "List of BGP VRFs";
        uses bgp-route-ios-xe-oper:vrf-record;
      }
    }
    container bgp-route-rds {
      description
        "BGP RDs";
      list bgp-route-rd {
        key "rd-value";
        description
          "List of BGP RDs";
        uses bgp-route-ios-xe-oper:bgp-rd-record;
      }
    }
  }

  container bgp-state-data {
    config false;
    description
      "BGP operational state data";
    uses bgp-ios-xe-oper:bgp-state;
  }
}
