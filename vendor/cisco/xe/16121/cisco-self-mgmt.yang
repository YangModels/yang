module cisco-self-mgmt {
  namespace "http://cisco.com/yang/cisco-self-mgmt";
  prefix cisco-sfm;

  import cisco-semver {
    prefix cisco-semver;
  }
    
  description
    "Copyright (c) 2016 by Cisco Systems, Inc."+
    "All rights reserved.";

  revision 2019-07-01 {
    description "Establish semantic version baseline";
    cisco-semver:module-version "1.0.0";
  }
  revision 2016-05-14 {
    description "Initial version with netconf-yang container";
  }

  container netconf-yang {
    description
      "Top level container shared by cisco-ia and cisco-odm models";
  }
}
