module Cisco-IOS-XE-interfaces-oper {
  yang-version 1;
  namespace "http://cisco.com/ns/yang/Cisco-IOS-XE-interfaces-oper";
  prefix interfaces-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the interfaces in a Network Element.
     Copyright (c) 2016-2019 by Cisco Systems, Inc.
     All rights reserved.";

  revision 2019-05-01 {
    description
      "- Added ethernet error counters.
       - Added semantic version";
    reference "3.2.0";
    cisco-semver:module-version "3.2.0";
  }
  revision 2018-10-29 {
    description
      "Cleaned up spelling errors in descriptions.";
    reference "3.1.0";
    cisco-semver:module-version "3.1.0";
  }
  revision 2018-06-29 {
    description
      "- Add switching interface speed values
       - Add synchronous serial interface model";
    reference "3.0.0";
    cisco-semver:module-version "3.0.0";
  }
  revision 2018-02-01 {
    description
      "IPv6 addresses";
    reference "2.0.0";
    cisco-semver:module-version "2.0.0";
  }
  revision 2017-10-10 {
    description
      "Initial revision";
    reference "1.0.0";
    cisco-semver:module-version "1.0.0";
  }

  typedef qos-match-type {
    type enumeration {
      enum "qos-match-dscp" {
        value 0;
      }
      enum "qos-match-src-ip" {
        value 1;
      }
      enum "qos-match-dst-ip" {
        value 2;
      }
      enum "qos-match-src-port" {
        value 3;
      }
      enum "qos-match-dst-port" {
        value 4;
      }
      enum "qos-match-proto" {
        value 5;
      }
    }
    description
      "QOS match type";
  }

  typedef thresh-unit {
    type enumeration {
      enum "thresh-units-default" {
        value 0;
      }
      enum "thresh-units-bytes" {
        value 1;
      }
      enum "thresh-units-sec" {
        value 2;
      }
      enum "thresh-units-packets" {
        value 3;
      }
      enum "thresh-units-cells" {
        value 4;
      }
      enum "thresh-units-percent" {
        value 5;
      }
    }
    description
      "Units of threshold";
  }

  typedef qos-direction {
    type enumeration {
      enum "qos-inbound" {
        value 0;
        description
          "Direction of traffic coming into the network entry";
      }
      enum "qos-outbound" {
        value 1;
        description
          "Direction of traffic going out of the network entry";
      }
    }
    description
      "QoS direction indication";
  }

  typedef aggregation-type {
    type enumeration {
      enum "lag-off" {
        value 0;
        description
          "LAG mode is off";
      }
      enum "lag-auto" {
        value 1;
        description
          "LAG mode is auto";
      }
      enum "lag-active" {
        value 2;
        description
          "LAG mode is active";
      }
      enum "lag-passive" {
        value 3;
        description
          "LAG mode is passive";
      }
    }
    description
      "Type to define the lag-type, i.e., how the LAG is
       defined and managed";
  }

  typedef intf-state {
    type enumeration {
      enum "if-state-unknown" {
        value 0;
      }
      enum "if-state-up" {
        value 1;
      }
      enum "if-state-down" {
        value 2;
      }
      enum "if-state-test" {
        value 3;
      }
    }
    description
      "The desired state of the interface.
       This leaf has the same read semantics as ifAdminStatus.
       Reference:
       RFC 2863: The Interfaces Group MIB - ifAdminStatus";
  }

  typedef ether-duplex {
    type enumeration {
      enum "full-duplex" {
        value 0;
      }
      enum "half-duplex" {
        value 1;
      }
      enum "auto-duplex" {
        value 2;
      }
      enum "unknown-duplex" {
        value 3;
      }
    }
    description
      "The duplex setting of the interface";
  }

  typedef ether-speed {
    type enumeration {
      enum "speed-10mb" {
        value 0;
      }
      enum "speed-100mb" {
        value 1;
      }
      enum "speed-1gb" {
        value 2;
      }
      enum "speed-10gb" {
        value 3;
      }
      enum "speed-25gb" {
        value 4;
      }
      enum "speed-40gb" {
        value 5;
      }
      enum "speed-50gb" {
        value 6;
      }
      enum "speed-100gb" {
        value 7;
      }
      enum "speed-unknown" {
        value 8;
      }
      enum "speed-auto" {
        value 9;
      }
    }
    description
      "The speed setting of the interface";
  }

  typedef oper-state {
    type enumeration {
      enum "if-oper-state-invalid" {
        value 0;
      }
      enum "if-oper-state-ready" {
        value 1;
      }
      enum "if-oper-state-no-pass" {
        value 2;
      }
      enum "if-oper-state-test" {
        value 3;
      }
      enum "if-oper-state-unknown" {
        value 4;
      }
      enum "if-oper-state-dormant" {
        value 5;
      }
      enum "if-oper-state-not-present" {
        value 6;
      }
      enum "if-oper-state-lower-layer-down" {
        value 7;
      }
    }
    description
      "The current operational state of the interface.
       This leaf has the same semantics as ifOperStatus.
       Reference:
       RFC 2863: The Interfaces Group MIB - ifOperStatus";
  }

  typedef ietf-intf-type {
    type enumeration {
      enum "iana-iftype-other" {
        value 1;
      }
      enum "iana-iftype-regular1822" {
        value 2;
      }
      enum "iana-iftype-hdh1822" {
        value 3;
      }
      enum "iana-iftype-ddnx25" {
        value 4;
      }
      enum "iana-iftype-rfc877x25" {
        value 5;
      }
      enum "iana-iftype-ethernet-csmacd" {
        value 6;
      }
      enum "iana-iftype-iso88023-csmacd" {
        value 7;
      }
      enum "iana-iftype-iso88024-tokenbus" {
        value 8;
      }
      enum "iana-iftype-iso88025-tokenring" {
        value 9;
      }
      enum "iana-iftype-iso88026-man" {
        value 10;
      }
      enum "iana-iftype-starlan" {
        value 11;
      }
      enum "iana-iftype-proteon10mbit" {
        value 12;
      }
      enum "iana-iftype-proteon80mbit" {
        value 13;
      }
      enum "iana-iftype-hyperchannel" {
        value 14;
      }
      enum "iana-iftype-fddi" {
        value 15;
      }
      enum "iana-iftype-lapb" {
        value 16;
      }
      enum "iana-iftype-sdlc" {
        value 17;
      }
      enum "iana-iftype-ds1" {
        value 18;
      }
      enum "iana-iftype-e1" {
        value 19;
      }
      enum "iana-iftype-basicisdn" {
        value 20;
      }
      enum "iana-iftype-primaryisdn" {
        value 21;
      }
      enum "iana-iftype-prop-p2p-serial" {
        value 22;
      }
      enum "iana-iftype-ppp" {
        value 23;
      }
      enum "iana-iftype-sw-loopback" {
        value 24;
      }
      enum "iana-iftype-eon" {
        value 25;
      }
      enum "iana-iftype-ethernet3mbit" {
        value 26;
      }
      enum "iana-iftype-nsip" {
        value 27;
      }
      enum "iana-iftype-slip" {
        value 28;
      }
      enum "iana-iftype-ultra" {
        value 29;
      }
      enum "iana-iftype-ds3" {
        value 30;
      }
      enum "iana-iftype-sip" {
        value 31;
      }
      enum "iana-iftype-framerelay" {
        value 32;
      }
      enum "iana-iftype-rs232" {
        value 33;
      }
      enum "iana-iftype-para" {
        value 34;
      }
      enum "iana-iftype-arcnet" {
        value 35;
      }
      enum "iana-iftype-arcnetplus" {
        value 36;
      }
      enum "iana-iftype-atm" {
        value 37;
      }
      enum "iana-iftype-miox25" {
        value 38;
      }
      enum "iana-iftype-sonet" {
        value 39;
      }
      enum "iana-iftype-x25ple" {
        value 40;
      }
      enum "iana-iftype-iso88022-llc" {
        value 41;
      }
      enum "iana-iftype-localtalk" {
        value 42;
      }
      enum "iana-iftype-smdsdxi" {
        value 43;
      }
      enum "iana-iftype-framerelay-service" {
        value 44;
      }
      enum "iana-iftype-v35" {
        value 45;
      }
      enum "iana-iftype-hssi" {
        value 46;
      }
      enum "iana-iftype-hippi" {
        value 47;
      }
      enum "iana-iftype-modem" {
        value 48;
      }
      enum "iana-iftype-aal5" {
        value 49;
      }
      enum "iana-iftype-sonetpath" {
        value 50;
      }
      enum "iana-iftype-sonetvt" {
        value 51;
      }
      enum "iana-iftype-smdsicip" {
        value 52;
      }
      enum "iana-iftype-propvirtual" {
        value 53;
      }
      enum "iana-iftype-propmultiplexor" {
        value 54;
      }
      enum "iana-iftype-ieee80212" {
        value 55;
      }
      enum "iana-iftype-fiberchannel" {
        value 56;
      }
      enum "iana-iftype-hippi-interface" {
        value 57;
      }
      enum "iana-iftype-framerelay-interconnect" {
        value 58;
      }
      enum "iana-iftype-aflane8023" {
        value 59;
      }
      enum "iana-iftype-aflane8025" {
        value 60;
      }
      enum "iana-iftype-cctemul" {
        value 61;
      }
      enum "iana-iftype-fastether" {
        value 62;
      }
      enum "iana-iftype-isdn" {
        value 63;
      }
      enum "iana-iftype-v11" {
        value 64;
      }
      enum "iana-iftype-v36" {
        value 65;
      }
      enum "iana-iftype-g703at64k" {
        value 66;
      }
      enum "iana-iftype-g703at2mb" {
        value 67;
      }
      enum "iana-iftype-qllc" {
        value 68;
      }
      enum "iana-iftype-fastetherfx" {
        value 69;
      }
      enum "iana-iftype-channel" {
        value 70;
      }
      enum "iana-iftype-ieee80211" {
        value 71;
      }
      enum "iana-iftype-ibm370parchan" {
        value 72;
      }
      enum "iana-iftype-escon" {
        value 73;
      }
      enum "iana-iftype-dlsw" {
        value 74;
      }
      enum "iana-iftype-isdns" {
        value 75;
      }
      enum "iana-iftype-isdnu" {
        value 76;
      }
      enum "iana-iftype-lapd" {
        value 77;
      }
      enum "iana-iftype-ipswitch" {
        value 78;
      }
      enum "iana-iftype-rsrb" {
        value 79;
      }
      enum "iana-iftype-atmlogical" {
        value 80;
      }
      enum "iana-iftype-ds0" {
        value 81;
      }
      enum "iana-iftype-ds0bundle" {
        value 82;
      }
      enum "iana-iftype-bsc" {
        value 83;
      }
      enum "iana-iftype-async" {
        value 84;
      }
      enum "iana-iftype-cnr" {
        value 85;
      }
      enum "iana-iftype-iso88025-dtr" {
        value 86;
      }
      enum "iana-iftype-eplrs" {
        value 87;
      }
      enum "iana-iftype-arap" {
        value 88;
      }
      enum "iana-iftype-propcnls" {
        value 89;
      }
      enum "iana-iftype-hostpad" {
        value 90;
      }
      enum "iana-iftype-termpad" {
        value 91;
      }
      enum "iana-iftype-framerelay-mpi" {
        value 92;
      }
      enum "iana-iftype-x213" {
        value 93;
      }
      enum "iana-iftype-adsl" {
        value 94;
      }
      enum "iana-iftype-radsl" {
        value 95;
      }
      enum "iana-iftype-sdsl" {
        value 96;
      }
      enum "iana-iftype-vdsl" {
        value 97;
      }
      enum "iana-iftype-iso88025-crfpint" {
        value 98;
      }
      enum "iana-iftype-myrinet" {
        value 99;
      }
      enum "iana-iftype-voiceem" {
        value 100;
      }
      enum "iana-iftype-voicefxo" {
        value 101;
      }
      enum "iana-iftype-voicefxs" {
        value 102;
      }
      enum "iana-iftype-voiceencap" {
        value 103;
      }
      enum "iana-iftype-voip" {
        value 104;
      }
      enum "iana-iftype-atmdxi" {
        value 105;
      }
      enum "iana-iftype-atmfuni" {
        value 106;
      }
      enum "iana-iftype-atmima" {
        value 107;
      }
      enum "iana-iftype-ppp-multilinkbundle" {
        value 108;
      }
      enum "iana-iftype-ipovercdlc" {
        value 109;
      }
      enum "iana-iftype-ipoverclaw" {
        value 110;
      }
      enum "iana-iftype-stack2stack" {
        value 111;
      }
      enum "iana-iftype-virtualipaddress" {
        value 112;
      }
      enum "iana-iftype-mpc" {
        value 113;
      }
      enum "iana-iftype-ipoveratm" {
        value 114;
      }
      enum "iana-iftype-iso88025-fiber" {
        value 115;
      }
      enum "iana-iftype-tdlc" {
        value 116;
      }
      enum "iana-iftype-gige" {
        value 117;
      }
      enum "iana-iftype-hdlc" {
        value 118;
      }
      enum "iana-iftype-lapf" {
        value 119;
      }
      enum "iana-iftype-v37" {
        value 120;
      }
      enum "iana-iftype-x25mlp" {
        value 121;
      }
      enum "iana-iftype-x25huntgroup" {
        value 122;
      }
      enum "iana-iftype-transphdlc" {
        value 123;
      }
      enum "iana-iftype-interleave" {
        value 124;
      }
      enum "iana-iftype-fast" {
        value 125;
      }
      enum "iana-iftype-ip" {
        value 126;
      }
      enum "iana-iftype-docs-cable-maclayer" {
        value 127;
      }
      enum "iana-iftype-docs-cable-downstream" {
        value 128;
      }
      enum "iana-iftype-docs-cable-upstream" {
        value 129;
      }
      enum "iana-iftype-a12mppswitch" {
        value 130;
      }
      enum "iana-iftype-tunnel" {
        value 131;
      }
      enum "iana-iftype-coffee" {
        value 132;
      }
      enum "iana-iftype-ces" {
        value 133;
      }
      enum "iana-iftype-atmsubinterface" {
        value 134;
      }
      enum "iana-iftype-l2vlan" {
        value 135;
      }
      enum "iana-iftype-l3ipvlan" {
        value 136;
      }
      enum "iana-iftype-l3ipxvlan" {
        value 137;
      }
      enum "iana-iftype-digital-powerline" {
        value 138;
      }
      enum "iana-iftype-media-mailoverip" {
        value 139;
      }
      enum "iana-iftype-dtm" {
        value 140;
      }
      enum "iana-iftype-dcn" {
        value 141;
      }
      enum "iana-iftype-ipforward" {
        value 142;
      }
      enum "iana-iftype-msdsl" {
        value 143;
      }
      enum "iana-iftype-ieee1394" {
        value 144;
      }
      enum "iana-iftype-gsn" {
        value 145;
      }
      enum "iana-iftype-dvbrcc-maclayer" {
        value 146;
      }
      enum "iana-iftype-dvbrcc-downstream" {
        value 147;
      }
      enum "iana-iftype-dvbrcc-upstream" {
        value 148;
      }
      enum "iana-iftype-atmvirtual" {
        value 149;
      }
      enum "iana-iftype-mplstunnel" {
        value 150;
      }
      enum "iana-iftype-srp" {
        value 151;
      }
      enum "iana-iftype-voiceoveratm" {
        value 152;
      }
      enum "iana-iftype-voiceoverframerelay" {
        value 153;
      }
      enum "iana-iftype-idsl" {
        value 154;
      }
      enum "iana-iftype-compositelink" {
        value 155;
      }
      enum "iana-iftype-ss7siglink" {
        value 156;
      }
      enum "iana-iftype-propwireless-p2p" {
        value 157;
      }
      enum "iana-iftype-frforward" {
        value 158;
      }
      enum "iana-iftype-rfc1483" {
        value 159;
      }
      enum "iana-iftype-usb" {
        value 160;
      }
      enum "iana-iftype-ieee8023-adlag" {
        value 161;
      }
      enum "iana-iftype-bgppolicy-accounting" {
        value 162;
      }
      enum "iana-iftype-frf16mfrbundle" {
        value 163;
      }
      enum "iana-iftype-h323gatekeeper" {
        value 164;
      }
      enum "iana-iftype-h323proxy" {
        value 165;
      }
      enum "iana-iftype-mpls" {
        value 166;
      }
      enum "iana-iftype-mfsiglink" {
        value 167;
      }
      enum "iana-iftype-hdsl2" {
        value 168;
      }
      enum "iana-iftype-shdsl" {
        value 169;
      }
      enum "iana-iftype-ds1fdl" {
        value 170;
      }
      enum "iana-iftype-pos" {
        value 171;
      }
      enum "iana-iftype-dvbasiin" {
        value 172;
      }
      enum "iana-iftype-dvbasiout" {
        value 173;
      }
      enum "iana-iftype-plc" {
        value 174;
      }
      enum "iana-iftype-nfas" {
        value 175;
      }
      enum "iana-iftype-tr008" {
        value 176;
      }
      enum "iana-iftype-gr303rdt" {
        value 177;
      }
      enum "iana-iftype-gr303idt" {
        value 178;
      }
      enum "iana-iftype-isup" {
        value 179;
      }
      enum "iana-iftype-prop-docs-wireless-maclayer" {
        value 180;
      }
      enum "iana-iftype-prop-docs-wireless-downstream" {
        value 181;
      }
      enum "iana-iftype-prop-docs-wireless-upstream" {
        value 182;
      }
      enum "iana-iftype-hiperlan2" {
        value 183;
      }
      enum "iana-iftype-prop-bwap2mp" {
        value 184;
      }
      enum "iana-iftype-sonetoverheadchannel" {
        value 185;
      }
      enum "iana-iftype-digital-wrapperoverheadchannel" {
        value 186;
      }
      enum "iana-iftype-aal2" {
        value 187;
      }
      enum "iana-iftype-radiomac" {
        value 188;
      }
      enum "iana-iftype-atmradio" {
        value 189;
      }
      enum "iana-iftype-imt" {
        value 190;
      }
      enum "iana-iftype-mvl" {
        value 191;
      }
      enum "iana-iftype-reachhdsl" {
        value 192;
      }
      enum "iana-iftype-frdlciendpt" {
        value 193;
      }
      enum "iana-iftype-atmvciendpt" {
        value 194;
      }
      enum "iana-iftype-opticalchannel" {
        value 195;
      }
      enum "iana-iftype-opticaltransport" {
        value 196;
      }
      enum "iana-iftype-propatm" {
        value 197;
      }
      enum "iana-iftype-voiceovercable" {
        value 198;
      }
      enum "iana-iftype-infiniband" {
        value 199;
      }
      enum "iana-iftype-telink" {
        value 200;
      }
      enum "iana-iftype-q2931" {
        value 201;
      }
      enum "iana-iftype-virtualatg" {
        value 202;
      }
      enum "iana-iftype-siptg" {
        value 203;
      }
      enum "iana-iftype-sipsig" {
        value 204;
      }
      enum "iana-iftype-docs-cable-upstreamchannel" {
        value 205;
      }
      enum "iana-iftype-econet" {
        value 206;
      }
      enum "iana-iftype-pon155" {
        value 207;
      }
      enum "iana-iftype-pon622" {
        value 208;
      }
      enum "iana-iftype-bridge-if" {
        value 209;
      }
      enum "iana-iftype-linegroup" {
        value 210;
      }
      enum "iana-iftype-voiceemfgd" {
        value 211;
      }
      enum "iana-iftype-voiceefgdeana" {
        value 212;
      }
      enum "iana-iftype-voicedid" {
        value 213;
      }
      enum "iana-iftype-mpegtransport" {
        value 214;
      }
      enum "iana-iftype-sixtofour" {
        value 215;
      }
      enum "iana-iftype-gtp" {
        value 216;
      }
      enum "iana-iftype-pdnetherloop1" {
        value 217;
      }
      enum "iana-iftype-pdnetherloop2" {
        value 218;
      }
      enum "iana-iftype-opticalchannel-group" {
        value 219;
      }
      enum "iana-iftype-homepna" {
        value 220;
      }
      enum "iana-iftype-gfp" {
        value 221;
      }
      enum "iana-iftype-ciscoislvlan" {
        value 222;
      }
      enum "iana-iftype-actelismetaloop" {
        value 223;
      }
      enum "iana-iftype-fciplink" {
        value 224;
      }
      enum "iana-iftype-rpr" {
        value 225;
      }
      enum "iana-iftype-qam" {
        value 226;
      }
      enum "iana-iftype-lmp" {
        value 227;
      }
      enum "iana-iftype-cblvectastar" {
        value 228;
      }
      enum "iana-iftype-docs-cable-mcmts-downtream" {
        value 229;
      }
      enum "iana-iftype-adsl2" {
        value 230;
      }
      enum "iana-iftype-macseccontrolledif" {
        value 231;
      }
      enum "iana-iftype-macsecuncontrolledif" {
        value 232;
      }
      enum "iana-iftype-aviciopticalether" {
        value 233;
      }
      enum "iana-iftype-atmbond" {
        value 234;
      }
      enum "iana-iftype-voicefgdos" {
        value 235;
      }
      enum "iana-iftype-mocaversion1" {
        value 236;
      }
      enum "iana-iftype-ieee80216-wman" {
        value 237;
      }
      enum "iana-iftype-adsl2plus" {
        value 238;
      }
      enum "iana-iftype-dvbrcsmaclayer" {
        value 239;
      }
      enum "iana-iftype-dvbtdm" {
        value 240;
      }
      enum "iana-iftype-dvbrcstdma" {
        value 241;
      }
      enum "iana-iftype-x86laps" {
        value 242;
      }
      enum "iana-iftype-wwanpp" {
        value 243;
      }
      enum "iana-iftype-wwanpp2" {
        value 244;
      }
      enum "iana-iftype-voiceebs" {
        value 245;
      }
      enum "iana-iftype-ifpwtype" {
        value 246;
      }
      enum "iana-iftype-ilan" {
        value 247;
      }
      enum "iana-iftype-pip" {
        value 248;
      }
      enum "iana-iftype-aluelp" {
        value 249;
      }
      enum "iana-iftype-gpon" {
        value 250;
      }
      enum "iana-iftype-vdsl2" {
        value 251;
      }
      enum "iana-iftype-capwapdot11-profile" {
        value 252;
      }
      enum "iana-iftype-capwapdot11-bss" {
        value 253;
      }
      enum "iana-iftype-capwapwtp-virtualradio" {
        value 254;
      }
      enum "iana-iftype-bits" {
        value 255;
      }
      enum "iana-iftype-docs-cable-upstreamrfport" {
        value 256;
      }
      enum "iana-iftype-cable-downstreamrfport" {
        value 257;
      }
      enum "iana-iftype-vmware-virtualnic" {
        value 258;
      }
      enum "iana-iftype-ieee802154" {
        value 259;
      }
      enum "iana-iftype-otnodu" {
        value 260;
      }
      enum "iana-iftype-otnotu" {
        value 261;
      }
      enum "iana-iftype-ifvfitype" {
        value 262;
      }
      enum "iana-iftype-g9981" {
        value 263;
      }
      enum "iana-iftype-g9982" {
        value 264;
      }
      enum "iana-iftype-g9983" {
        value 265;
      }
      enum "iana-iftype-aluepon" {
        value 266;
      }
      enum "iana-iftype-aluepon-onu" {
        value 267;
      }
      enum "iana-iftype-aluepon-physicaluni" {
        value 268;
      }
      enum "iana-iftype-aluepon-logicalink" {
        value 269;
      }
      enum "iana-iftype-alugpon-onu" {
        value 270;
      }
      enum "iana-iftype-alugpon-physicaluni" {
        value 271;
      }
      enum "iana-iftype-vmwarenicteam" {
        value 272;
      }
      enum "iana-iftype-docs-ofdm-downstream" {
        value 277;
      }
      enum "iana-iftype-docs-ofdma-upstream" {
        value 278;
      }
      enum "iana-iftype-gfast" {
        value 279;
      }
      enum "iana-iftype-sdci" {
        value 280;
      }
      enum "iana-iftype-xbox-wireless" {
        value 281;
      }
      enum "iana-iftype-fastdsl" {
        value 282;
      }
    }
    description
      "IANAifType
       This data type is used as the syntax of the ifType
       object in the (updated) definition of MIB-II's ifTable";
  }

  typedef dot3-stats-versions {
    type enumeration {
      enum "not-supported" {
        value 0;
        description
          "Dot 3 error counters are not supported";
      }
      enum "dot3-version-2" {
        value 1;
        description
          "Version 2 dot 3 error counters";
      }
    }
    description
      "The version of dot 3 error counters.";
  }

  typedef serial-crc {
    type enumeration {
      enum "serial-crc32" {
        value 0;
        description
          "32-bit Cyclic Redundancy Code";
      }
      enum "serial-crc16" {
        value 1;
        description
          "16 bit Cyclic Redundancy Code";
      }
    }
    description
      "The Cyclic Redundancy Code type";
  }

  typedef subrate-speed {
    type enumeration {
      enum "dsx1-subrate-56kbps" {
        value 0;
        description
          "56 kilobits per second subrate";
      }
      enum "dsx1-subrate-64kbps" {
        value 1;
        description
          "64 kilobits per second subrate";
      }
    }
    description
      "The subrate on a serial interface";
  }

  typedef t1e1-loopback-mode {
    type enumeration {
      enum "t1e1-no-loopback" {
        value 0;
        description
          "No loopback mode";
      }
      enum "t1e1-cli-local-loopback" {
        value 1;
        description
          "Command line interface enforced local loopback";
      }
      enum "t1e1-line-cli-local-loopback" {
        value 2;
        description
          "Command line interface enforced line local loopback";
      }
      enum "t1e1-payload-cli-local-loopback" {
        value 3;
        description
          "Command line interface enforced payload local loopback";
      }
      enum "t1e1-local-line-loopback" {
        value 4;
        description
          "Local line loopback";
      }
      enum "t1e1-local-payload-loopback" {
        value 5;
        description
          "Local payload loopback";
      }
      enum "t1e1-local-ansi-fdl-remote-loopback" {
        value 6;
        description
          "Line ANSI FDL remote loopback";
      }
      enum "t1e1-line-att-fdl-remote-loopback" {
        value 7;
        description
          "Line ATT FDL remote loopback";
      }
      enum "t1e1-payload-ansi-fdl-remote-loopback" {
        value 8;
        description
          "Payload ANSI FDL remote loopback";
      }
      enum "t1e1-payload-att-fdl-remote-loopback" {
        value 9;
        description
          "Payload ATT FDL remote loopback";
      }
      enum "t1e1-line-iboc-remote-loopback" {
        value 10;
        description
          "Line IBOC remote loopback";
      }
      enum "t1e1-line-ansi-fdl-local-loopback" {
        value 11;
        description
          "Line ANSI FDL local loopback";
      }
      enum "t1e1-line-att-fdl-local-loopback" {
        value 12;
        description
          "Line ATT FDL local loopback";
      }
      enum "t1e1-payload-ansi-fdl-local-loopback" {
        value 13;
        description
          "Payload ANSI FDL local loopback";
      }
      enum "t1e1-payload-att-fdl-local-loopback" {
        value 14;
        description
          "Payload ATT FDL local loopback";
      }
      enum "t1e1-line-iboc-local-loopback" {
        value 15;
        description
          "Line IBOC local loopback";
      }
    }
    description
      "Loopback mode type";
  }

  typedef signal-status {
    type enumeration {
      enum "down" {
        value 0;
        description
          "Signal is down";
      }
      enum "up" {
        value 1;
        description
          "Signal is up";
      }
    }
    description
      "Synchronous serial interface signal status";
  }

  typedef idle-character-type {
    type enumeration {
      enum "flag" {
        value 0;
        description
          "Send HDLC flag characters between packets";
      }
      enum "marks" {
        value 1;
        description
          "Send mark characters between packets";
      }
    }
    description
      "Synchronous serial idle character";
  }

  grouping wred-class-counts {
    description
      "WRED class count types";
    leaf wred-tx-pkts {
      type uint64;
      description
        "Transmitted packets";
    }
    leaf wred-tx-bytes {
      type uint64;
      description
        "Transmitted bytes";
    }
    leaf wred-tail-drop-pkts {
      type uint64;
      description
        "Tail drop packets";
    }
    leaf wred-tail-drop-bytes {
      type uint64;
      description
        "Tail drop bytes";
    }
    leaf wred-early-drop-pkts {
      type uint64;
      description
        "Early drop packets";
    }
    leaf wred-early-drop-bytes {
      type uint64;
      description
        "Early drop bytes";
    }
  }

  grouping marking-dscp-stats {
    description
      "Statistics for set dscp";
    leaf dscp {
      type uint32;
      description
        "dscp marking";
    }
    leaf marked-pkts {
      type uint64;
      description
        "Number of packets been marked";
    }
  }

  grouping marking-dscp-tunnel-stats {
    description
      "Statistics for set dscp tunnel";
    leaf dscp-val {
      type uint32;
      description
        "dscp value";
    }
    leaf marked-pkts {
      type uint64;
      description
        "Number of packets been marked";
    }
  }

  grouping marking-cos-stats {
    description
      "Statistics for set cos";
    leaf cos-val {
      type uint32;
      description
        "cos value";
    }
    leaf marked-pkts {
      type uint64;
      description
        "Number of packets been marked";
    }
  }

  grouping marking-cos-inner-stats {
    description
      "Statistics for set cos-inner";
    leaf cos-inner-val {
      type uint32;
      description
        "cos inner value";
    }
    leaf marked-pkts {
      type uint64;
      description
        "Number of packets been marked";
    }
  }

  grouping marking-discard-class-stats {
    description
      "Statistics for set discard-class";
    leaf disc-class-val {
      type uint32;
      description
        "discard-class value";
    }
    leaf marked-pkts {
      type uint64;
      description
        "Number of packets been marked";
    }
  }

  grouping marking-qos-grp-stats {
    description
      "Statistics for set qos-group";
    leaf qos-grp-val {
      type uint32;
      description
        "qos group value";
    }
    leaf marked-pkts {
      type uint64;
      description
        "Number of packets been marked";
    }
  }

  grouping marking-prec-stats {
    description
      "Statistics for set precedence";
    leaf prec-val {
      type uint32;
      description
        "precedence value";
    }
    leaf marked-pkts {
      type uint64;
      description
        "Number of packets been marked";
    }
  }

  grouping marking-prec-tunnel-stats {
    description
      "Statistics for set precedence tunnel";
    leaf prec-val {
      type uint32;
      description
        "precedence value";
    }
    leaf marked-pkts {
      type uint64;
      description
        "Number of packets been marked";
    }
  }

  grouping marking-mpls-exp-imp-stats {
    description
      "Statistics for set mpls exp imposition";
    leaf mpls-exp-imp-val {
      type uint32;
      description
        "mpls exp value";
    }
    leaf marked-pkts {
      type uint64;
      description
        "Number of packets been marked";
    }
  }

  grouping marking-mpls-exp-top-stats {
    description
      "Statistics for set mpls exp imposition";
    leaf mpls-exp-top-val {
      type uint32;
      description
        "mpls exp value";
    }
    leaf marked-pkts {
      type uint64;
      description
        "Number of packets been marked";
    }
  }

  grouping marking-fr-de-stats {
    description
      "Statistics for set fr-de";
    leaf fr-de {
      type boolean;
      description
        "fr de set or not";
    }
    leaf marked-pkts {
      type uint64;
      description
        "Number of packets been marked";
    }
  }

  grouping marking-fr-fecn-becn-stats {
    description
      "Statistics for set fr-fecn-becn";
    leaf fecn-becn-val {
      type uint32;
      description
        "fecn becn value. qos:percent-value-1to100";
    }
    leaf marked-pkts {
      type uint64;
      description
        "Number of packets been marked";
    }
  }

  grouping marking-atm-clp-stats {
    description
      "Statistics for set atm-clp";
    leaf atm-clp-val {
      type uint8;
      description
        "atm clp value";
    }
    leaf marked-pkts {
      type uint64;
      description
        "Number of packets been marked";
    }
  }

  grouping marking-vlan-inner-stats {
    description
      "Statistics for set vlan-inner";
    leaf vlan-inner-val {
      type uint32;
      description
        "vlan value";
    }
    leaf marked-pkts {
      type uint64;
      description
        "Number of packets been marked";
    }
  }

  grouping marking-dei-stats {
    description
      "Statistics for set dei";
    leaf dei-imp-value {
      type uint32;
      description
        "dei value";
    }
    leaf marked-pkts {
      type uint64;
      description
        "Number of packets been marked";
    }
  }

  grouping marking-dei-imp-stats {
    description
      "Statistics for set dei-imposition";
    leaf dei-imp-value {
      type uint32;
      description
        "dei value";
    }
    leaf marked-pkts {
      type uint64;
      description
        "Number of packets been marked";
    }
  }

  grouping marking-srp-priority-stats {
    description
      "Statistics for set srp-priority";
    leaf srp-priority-value {
      type uint8;
      description
        "srp priority value";
    }
    leaf marked-pkts {
      type uint64;
      description
        "Number of packets been marked";
    }
  }

  grouping marking-wlan-user-priority-stats {
    description
      "Statistics for set wlan-user-priority";
    leaf wlan-user-priority-value {
      type uint8;
      description
        "wlan user priority value";
    }
    leaf marked-pkts {
      type uint64;
      description
        "Number of packets been marked";
    }
  }

  grouping marking-stats {
    description
      "Marking statistics";
    container marking-dscp-stats-val {
      description
        "Statistics for set dscp";
      uses interfaces-ios-xe-oper:marking-dscp-stats;
    }
    container marking-dscp-tunnel-stats-val {
      description
        "Statistics for set dscp tunnel";
      uses interfaces-ios-xe-oper:marking-dscp-tunnel-stats;
    }
    container marking-cos-stats-val {
      description
        "Statistics for set cos";
      uses interfaces-ios-xe-oper:marking-cos-stats;
    }
    container marking-cos-inner-stats-val {
      description
        "Statistics for set cos-inner";
      uses interfaces-ios-xe-oper:marking-cos-inner-stats;
    }
    container marking-discard-class-stats-val {
      description
        "Statistics for set discard-class";
      uses interfaces-ios-xe-oper:marking-discard-class-stats;
    }
    container marking-qos-grp-stats-val {
      description
        "Statistics for set qos-group";
      uses interfaces-ios-xe-oper:marking-qos-grp-stats;
    }
    container marking-prec-stats-val {
      description
        "Statistics for set precedence";
      uses interfaces-ios-xe-oper:marking-prec-stats;
    }
    container marking-prec-tunnel-stats-val {
      description
        "Statistics for set precedence tunnel";
      uses interfaces-ios-xe-oper:marking-prec-tunnel-stats;
    }
    container marking-mpls-exp-imp-stats-val {
      description
        "Statistics for set mpls exp imposition";
      uses interfaces-ios-xe-oper:marking-mpls-exp-imp-stats;
    }
    container marking-mpls-exp-top-stats-val {
      description
        "Statistics for set mpls exp topmost";
      uses interfaces-ios-xe-oper:marking-mpls-exp-top-stats;
    }
    container marking-fr-de-stats-val {
      description
        "Statistics for set fr-de";
      uses interfaces-ios-xe-oper:marking-fr-de-stats;
    }
    container marking-fr-fecn-becn-stats-val {
      description
        "Statistics for set fr-fecn-becn";
      uses interfaces-ios-xe-oper:marking-fr-fecn-becn-stats;
    }
    container marking-atm-clp-stats-val {
      description
        "Statistics for set atm-clp";
      uses interfaces-ios-xe-oper:marking-atm-clp-stats;
    }
    container marking-vlan-inner-stats-val {
      description
        "Statistics for set vlan-inner";
      uses interfaces-ios-xe-oper:marking-vlan-inner-stats;
    }
    container marking-dei-stats-val {
      description
        "Statistics for set dei";
      uses interfaces-ios-xe-oper:marking-dei-stats;
    }
    container marking-dei-imp-stats-val {
      description
        "Statistics for set dei-imposition";
      uses interfaces-ios-xe-oper:marking-dei-imp-stats;
    }
    container marking-srp-priority-stats-val {
      description
        "Statistics for set srp-priority";
      uses interfaces-ios-xe-oper:marking-srp-priority-stats;
    }
    container marking-wlan-user-priority-stats-val {
      description
        "Statistics for set wlan-user-priority";
      uses interfaces-ios-xe-oper:marking-wlan-user-priority-stats;
    }
  }

  grouping cos-key {
    description
      "COS key type";
    leaf cos-min {
      type uint32;
      description
        "Min COS value";
    }
    leaf cos-max {
      type uint32;
      description
        "Max COS value";
    }
  }

  grouping disc-class-key {
    description
      "Discard class key type";
    leaf disc-class-min {
      type uint32;
      description
        "Minimum value for discard class in the range";
    }
    leaf disc-class-max {
      type uint32;
      description
        "Maximum value for discard class in the range";
    }
  }

  grouping dscp-key {
    description
      "DSCP key type";
    leaf dscp-min {
      type uint32;
      description
        "Minimum of dscp range";
    }
    leaf dscp-max {
      type uint32;
      description
        "Maximum of dscp range";
    }
  }

  grouping qos-grp-key {
    description
      "QoS group key type";
    leaf qos-group-min {
      type uint32;
      description
        "Specifies the minimum value range from 0 to used to identify a QoS group value";
    }
    leaf qos-group-max {
      type uint32;
      description
        "Specifies the maximum value range from 0 to used to identify a QoS group value";
    }
  }

  grouping mpls-exp-key {
    description
      "MPLS EXP key type";
    leaf exp-min {
      type uint32;
      description
        "The minimum EXP field value to be used as match criteria. Any number from 0 to 7";
    }
    leaf exp-max {
      type uint32;
      description
        "The maximum EXP field value to be used as match criteria. Any number from 0 to 7";
    }
  }

  grouping prec-key {
    description
      "Precedence key type";
    leaf prec-min {
      type uint32;
      description
        "Precedence min";
    }
    leaf prec-max {
      type uint32;
      description
        "Precedence max";
    }
  }

  grouping dei-key {
    description
      "DEI key type";
    leaf dei-min {
      type uint32;
      description
        "Dei min";
    }
    leaf dei-max {
      type uint32;
      description
        "Dei max";
    }
  }

  grouping clp-key {
    description
      "CLP key type";
    leaf clp-val {
      type uint32;
      description
        "Composed by multiple atm clp values";
    }
  }

  grouping subclass-list {
    description
      "Subclass data";
    leaf match-type {
      type interfaces-ios-xe-oper:qos-match-type;
      description
        "Subclass match type";
    }
    list cos-counters {
      key "cos-min cos-max";
      description
        "Counters for sub-class matching a range of
         Class-of-Service (COS) value (and, optionally, additional COS range";
      uses interfaces-ios-xe-oper:cos-key;
      uses interfaces-ios-xe-oper:wred-class-counts;
    }
    container cos-default {
      description
        "statistics for cos default";
      uses interfaces-ios-xe-oper:wred-class-counts;
    }
    list dscp-counters {
      key "dscp-min dscp-max";
      description
        "List for statistics based on dscp value range";
      uses interfaces-ios-xe-oper:dscp-key;
      uses interfaces-ios-xe-oper:wred-class-counts;
    }
    container dscp-default {
      description
        "Statistics for dscp default";
      uses interfaces-ios-xe-oper:wred-class-counts;
    }
    list discard-class-counters {
      key "disc-class-min disc-class-max";
      description
        "Composed multiple discard class ranges";
      uses interfaces-ios-xe-oper:disc-class-key;
      uses interfaces-ios-xe-oper:wred-class-counts;
    }
    container disc-class-default {
      description
        "Statistics for discard class default";
      uses interfaces-ios-xe-oper:wred-class-counts;
    }
    list precedence-counters {
      key "prec-min prec-max";
      description
        "List for statistics based on precedence value range";
      uses interfaces-ios-xe-oper:prec-key;
      uses interfaces-ios-xe-oper:wred-class-counts;
    }
    container prec-default {
      description
        "Precedence default";
      uses interfaces-ios-xe-oper:wred-class-counts;
    }
    list mpls-exp-counters {
      key "exp-min exp-max";
      description
        "List for statistics based on mpls exp value range";
      uses interfaces-ios-xe-oper:mpls-exp-key;
      uses interfaces-ios-xe-oper:wred-class-counts;
    }
    container mpls-exp-default {
      description
        "Statistics for mpls-exp default";
      uses interfaces-ios-xe-oper:wred-class-counts;
    }
    list dei-counters {
      key "dei-min dei-max";
      description
        "Composed by multiple dei ranges";
      uses interfaces-ios-xe-oper:dei-key;
      uses interfaces-ios-xe-oper:wred-class-counts;
    }
    container dei-counts-default {
      description
        "Statistics for dei default";
      uses interfaces-ios-xe-oper:wred-class-counts;
    }
    list clp-counters {
      key "clp-val";
      description
        "Statistics for each value range for a specific subclass type";
      uses interfaces-ios-xe-oper:clp-key;
      uses interfaces-ios-xe-oper:wred-class-counts;
    }
    container clp-default {
      description
        "Statistic for atm clp default";
      uses interfaces-ios-xe-oper:wred-class-counts;
    }
  }

  grouping classifier-entry-statistics {
    description
      "Classifier entry statistics";
    leaf classified-pkts {
      type uint64;
      description
        "Number of total packets which filtered to the classifier-entry";
    }
    leaf classified-bytes {
      type uint64;
      description
        "Number of total bytes which filtered to the classifier-entry";
    }
    leaf classified-rate {
      type uint64;
      description
        "Rate of average data flow through the classifier-entry";
    }
  }

  grouping diffserv-target-classifier-statistics-key {
    description
      "Diffserv classifier statistics key";
    leaf classifier-entry-name {
      type string;
      description
        "Classifier Entry Name";
    }
    leaf parent-path {
      type string;
      description
        "Path of the Classifier Entry in a hierarchical policy";
    }
  }

  grouping wred-stats {
    description
      "WRED counters";
    leaf early-drop-pkts {
      type uint64;
      description
        "Early drop packets";
    }
    leaf early-drop-bytes {
      type uint64;
      description
        "Early drop bytes";
    }
    leaf mean-queue-depth {
      type uint16;
      description
        "Current mean queue depth";
    }
    leaf transmitted-pkts {
      type uint64;
      description
        "Transmitted packets";
    }
    leaf transmitted-bytes {
      type uint64;
      description
        "Transmitted bytes";
    }
    leaf tail-drop-pkts {
      type uint64;
      description
        "Total number of packets dropped";
    }
    leaf tail-drop-bytes {
      type uint64;
      description
        "Total number of bytes dropped";
    }
    leaf drop-pkts-flow {
      type uint64;
      description
        "Total number of packets dropped";
    }
    leaf drop-pkts-no-buffer {
      type uint64;
      description
        "Number of packets dropped due to buffers being
         unavailable system-wide or at the associated interface.
         This is a sub-set of drop-pkts";
    }
    leaf queue-peak-size-pkts {
      type uint64;
      description
        "Queue max que depth Packets";
    }
    leaf queue-peak-size-bytes {
      type uint64;
      description
        "Queue max que depth Bytes";
    }
    leaf bandwidth-exceed-drops {
      type uint64;
      description
        "Priority stats. Bandwidth exceed drops";
    }
  }

  grouping cac-stats {
    description
      "CAC statistics";
    leaf num-admitted-flows {
      type uint32;
      description
        "Number of admitted flows";
    }
    leaf num-non-admitted-flows {
      type uint32;
      description
        "Number of non-admitted flows";
    }
  }

  grouping queuing-statistics {
    description
      "Queue related statistics";
    leaf output-pkts {
      type uint64;
      description
        "Number of packets transmitted from queue";
    }
    leaf output-bytes {
      type uint64;
      description
        "Number of bytes transmitted from queue";
    }
    leaf queue-size-pkts {
      type uint64;
      description
        "Number of packets currently buffered ";
    }
    leaf queue-size-bytes {
      type uint64;
      description
        "Number of bytes currently buffered";
    }
    leaf drop-pkts {
      type uint64;
      description
        "Total number of packets dropped";
    }
    leaf drop-bytes {
      type uint64;
      description
        "Total number of bytes dropped";
    }
    container wred-stats {
      description
        "WRED Counters";
      uses interfaces-ios-xe-oper:wred-stats;
    }
    container cac-stats {
      description
        "CAC statistics";
      uses interfaces-ios-xe-oper:cac-stats;
    }
  }

  grouping meter-statistics {
    description
      "Metering Counters";
    leaf meter-id {
      type uint16;
      description
        "Meter Identifier";
    }
    leaf meter-succeed-pkts {
      type uint64;
      description
        "Number of packets which succeed the meter";
    }
    leaf meter-succeed-bytes {
      type uint64;
      description
        "Bytes of packets which succeed the meter";
    }
    leaf meter-failed-pkts {
      type uint64;
      description
        "Number of packets which failed the meter";
    }
    leaf meter-failed-bytes {
      type uint64;
      description
        "Bytes of packets which failed the meter";
    }
  }

  grouping diffserv-target-classifier-statistics {
    description
      "Diffserv classifier statistics";
    container classifier-entry-stats {
      description
        "Classifier Counters";
      uses interfaces-ios-xe-oper:classifier-entry-statistics;
    }
    list meter-stats {
      key "meter-id";
      description
        "Meter statistics";
      uses interfaces-ios-xe-oper:meter-statistics;
    }
    container queuing-stats {
      description
        "Queuing Counters";
      uses interfaces-ios-xe-oper:queuing-statistics;
    }
    list subclass-list {
      key "match-type";
      description
        "List of statistics for random-detect
         based on subclass type and value pair
         Technically these are a field in the queuing
         statistics -> wred statistics, but GREEN EI
         does not allow that nesting structure";
      uses interfaces-ios-xe-oper:subclass-list;
    }
    container marking-stats {
      description
        "Statistics for marking actions";
      uses interfaces-ios-xe-oper:marking-stats;
    }
  }

  grouping diffserv-target-entry-key {
    description
      "Key to the diffserv";
    leaf direction {
      type interfaces-ios-xe-oper:qos-direction;
      description
        "Direction fo the traffic flow either inbound or outbound";
    }
    leaf policy-name {
      type string;
      description
        "Policy entry name";
    }
  }

  grouping agg-priority-stats {
    description
      "Type for counters in aggregate priority";
    leaf output-pkts {
      type uint64;
      description
        "Number of packets transmitted from queue";
    }
    leaf output-bytes {
      type uint64;
      description
        "Number of bytes transmitted from queue";
    }
    leaf queue-size-pkts {
      type uint64;
      description
        "Number of packets currently buffered";
    }
    leaf queue-size-bytes {
      type uint64;
      description
        "Number of bytes currently buffered";
    }
    leaf drop-pkts {
      type uint64;
      description
        "Total number of packets dropped";
    }
    leaf drop-bytes {
      type uint64;
      description
        "Total number of bytes dropped";
    }
    leaf drop-pkts-flow {
      type uint64;
      description
        "Number of packets that were dropped by
         flow-based fair-queuing (fair-queue).
         This is a sub-set of drop-pkts";
    }
    leaf drop-pkts-no-buffer {
      type uint64;
      description
        "Number of packets dropped due to buffers being
         unavailable system-wide or at the associated interface.
         This is a sub-set of drop-pkts";
    }
  }

  grouping threshold {
    description
      "Threshold Parameters";
    leaf bytes {
      type uint64;
      description
        "Threshold bytes";
    }
    leaf thresh-size-metric {
      type uint32;
      description
        "Threshold size unit";
    }
    leaf unit-val {
      type interfaces-ios-xe-oper:thresh-unit;
      description
        "Threshold size basic units";
    }
    leaf threshold-interval {
      type uint64;
      description
        "Threshold interval";
    }
    leaf thresh-interval-metric {
      type uint32;
      description
        "Threshold units metric";
    }
    leaf interval-unit-val {
      type interfaces-ios-xe-oper:thresh-unit;
      description
        "Threshold interval basic units";
    }
  }

  grouping priority-oper-list {
    description
      "Priority based statistics";
    leaf priority-level {
      type uint16;
      description
        "Priority Level, 0 means no priority level set";
    }
    container agg-priority-stats {
      description
        "Counters in aggregate priority";
      uses interfaces-ios-xe-oper:agg-priority-stats;
    }
    container qlimit-default-thresh {
      description
        "queue limit default threshold";
      uses interfaces-ios-xe-oper:threshold;
    }
    list qlimit-cos-thresh-list {
      key "cos-min cos-max";
      description
        "cos-based queue limit data";
      uses interfaces-ios-xe-oper:cos-key;
      uses interfaces-ios-xe-oper:threshold;
    }
    list qlimit-disc-class-thresh-list {
      key "disc-class-min disc-class-max";
      description
        "discard-class-based queue limit data";
      uses interfaces-ios-xe-oper:disc-class-key;
      uses interfaces-ios-xe-oper:threshold;
    }
    list qlimit-qos-grp-thresh-list {
      key "qos-group-min qos-group-max";
      description
        "qos-group-based queue limit data";
      uses interfaces-ios-xe-oper:qos-grp-key;
      uses interfaces-ios-xe-oper:threshold;
    }
    list qlimit-mpls-exp-thresh-list {
      key "exp-min exp-max";
      description
        "mpls-exp-based queue limit data";
      uses interfaces-ios-xe-oper:mpls-exp-key;
      uses interfaces-ios-xe-oper:threshold;
    }
    list qlimit-dscp-thresh-list {
      key "dscp-min dscp-max";
      description
        "queue limit per dscp range";
      uses interfaces-ios-xe-oper:dscp-key;
      uses interfaces-ios-xe-oper:threshold;
    }
  }

  grouping diffserv-target-entry {
    description
      "Diffserv target data";
    list diffserv-target-classifier-stats {
      key "classifier-entry-name parent-path";
      description
        "Statistics for each Classifier Entry in a Policy";
      uses interfaces-ios-xe-oper:diffserv-target-classifier-statistics-key;
      uses interfaces-ios-xe-oper:diffserv-target-classifier-statistics;
    }
    list priority-oper-list {
      key "priority-level";
      description
        "Statistics for aggregate priority per policy instance";
      uses interfaces-ios-xe-oper:priority-oper-list;
    }
  }

  grouping lag-aggregate-state {
    description
      "Operational state variables for logical
       aggregate / LAG interfaces";
    leaf aggregate-id {
      type string;
      description
        "Specify the logical aggregate interface to which
         this id belongs";
    }
    leaf lag-type {
      type interfaces-ios-xe-oper:aggregation-type;
      description
        "Type to define the lag-type, i.e., how the LAG is
         defined and managed";
    }
    leaf min-links {
      type uint16;
      description
        "Specifies the minimum number of member
         interfaces that must be active for the aggregate interface
         to be available";
    }
    leaf lag-speed {
      type uint32;
      description
        "Reports effective speed of the aggregate interface,
         based on speed of active member interfaces";
    }
    leaf-list members {
      type string;
      ordered-by user;
      description
        "List of current member interfaces for the aggregate,
         expressed as references to existing interfaces";
    }
  }

  grouping protocol-statistics {
    description
      "Protocol specific statistics";
    leaf in-pkts {
      type uint64;
      description
        "The total number of packets received for the specified
         address family, including those received in error";
    }
    leaf in-octets {
      type uint64;
      description
        "The total number of octets received in input packets
         for the specified address family, including those received
         in error.";
    }
    leaf in-error-pkts {
      type uint64;
      description
        "Number of packets discarded due to errors for the
         specified address family, including errors in the
         header, no route found to the destination, invalid
         address, unknown protocol, etc.";
    }
    leaf in-forwarded-pkts {
      type uint64;
      description
        "The number of input packets for which the device was not
         their final destination and for which the device
         attempted to find a route to forward them to that final
         destination.";
    }
    leaf in-forwarded-octets {
      type uint64;
      description
        "The number of octets received in input packets
         for the specified address family for which the device was
         not their final destination and for which the
         device attempted to find a route to forward them to that
         final destination.";
    }
    leaf in-discarded-pkts {
      type uint64;
      description
        "The number of input IP packets for the
         specified address family, for which no problems were
         encountered to prevent their continued processing, but
         were discarded (e.g., for lack of buffer space).";
    }
    leaf out-pkts {
      type uint64;
      description
        "The total number of IP packets for the
         specified address family that the device supplied
         to the lower layers for transmission.  This includes
         packets generated locally and those forwarded by the
         device.";
    }
    leaf out-octets {
      type uint64;
      description
        "The total number of octets in IP packets for the
         specified address family that the device
         supplied to the lower layers for transmission.  This
         includes packets generated locally and those forwarded by
         the device.";
    }
    leaf out-error-pkts {
      type uint64;
      description
        "Number of IP packets for the specified address family
         locally generated and discarded due to errors, including
         no route found to the IP destination.";
    }
    leaf out-forwarded-pkts {
      type uint64;
      description
        "The number of packets for which this entity was not their
         final IP destination and for which it was successful in
         finding a path to their final destination.text";
    }
    leaf out-forwarded-octets {
      type uint64;
      description
        "The number of octets in packets for which this entity was
         not their final IP destination and for which it was
         successful in finding a path to their final destination.";
    }
    leaf out-discarded-pkts {
      type uint64;
      description
        "The number of output IP packets for the
         specified address family for which no problem was
         encountered to prevent their transmission to their
         destination, but were discarded (e.g., for lack of
         buffer space).";
    }
  }

  grouping intf-statistics {
    description
      "Interface statistics";
    leaf discontinuity-time {
      type yang:date-and-time;
      description
        "The time on the most recent occasion at which any one or
         more of this interface's counters suffered a
         discontinuity.  If no such discontinuities have occurred
         since the last re-initialization of the local management
         subsystem, then this node contains the time the local
         management subsystem re-initialized itself";
    }
    leaf in-octets {
      type uint64;
      description
        "The total number of octets received on the interface,
         including framing characters.
         Discontinuities in the value of this counter can occur
         at re-initialization of the management system, and at
         other times as indicated by the value of discontinuity-time";
    }
    leaf in-unicast-pkts {
      type uint64;
      description
        "The number of packets, delivered by this sub-layer to a
         higher (sub-)layer, that were not addressed to a
         multicast or broadcast address at this sub-layer.
         Discontinuities in the value of this counter can occur
         at re-initialization of the management system, and at
         other times as indicated by the value of
         'discontinuity-time'.";
    }
    leaf in-broadcast-pkts {
      type uint64;
      description
        "The number of packets, delivered by this sub-layer to a
         higher (sub-)layer, that were addressed to a broadcast
         address at this sub-layer.
         Discontinuities in the value of this counter can occur
         at re-initialization of the management system, and at
         other times as indicated by the value of
         'discontinuity-time'";
    }
    leaf in-multicast-pkts {
      type uint64;
      description
        "The number of packets, delivered by this sub-layer to a
         higher (sub-)layer, that were addressed to a multicast
         address at this sub-layer.  For a MAC-layer protocol,
         this includes both Group and Functional addresses.
         Discontinuities in the value of this counter can occur
         at re-initialization of the management system, and at
         other times as indicated by the value of
         'discontinuity-time'";
    }
    leaf in-discards {
      type uint32;
      description
        "The number of inbound packets that were chosen to be
         discarded even though no errors had been detected to
         prevent their being deliverable to a higher-layer
         protocol.  One possible reason for discarding such a
         packet could be to free up buffer space.
         Discontinuities in the value of this counter can occur
         at re-initialization of the management system, and at
         other times as indicated by the value of
         'discontinuity-time'";
    }
    leaf in-errors {
      type uint32;
      description
        "For packet-oriented interfaces, the number of inbound
         packets that contained errors preventing them from being
         deliverable to a higher-layer protocol.  For character-
         oriented or fixed-length interfaces, the number of
         inbound transmission units that contained errors
         preventing them from being deliverable to a higher-layer protocol.
         Discontinuities in the value of this counter can occur
         at re-initialization of the management system, and at
         other times as indicated by the value of
         'discontinuity-time'";
    }
    leaf in-unknown-protos {
      type uint32;
      description
        "For packet-oriented interfaces, the number of packets
         received via the interface that were discarded because
         of an unknown or unsupported protocol.  For
         character-oriented or fixed-length interfaces that
         support protocol multiplexing, the number of transmission
         units received via the interface that were discarded because
         of an unknown or unsupported protocol.
         For any interface that does not support protocol
         multiplexing, this counter is not present.
         Discontinuities in the value of this counter can occur
         at re-initialization of the management system, and at
         other times as indicated by the value of 'discontinuity-time'";
    }
    leaf out-octets {
      type uint32;
      description
        "The total number of octets transmitted out of the
         interface, including framing characters.
         Discontinuities in the value of this counter can occur
         at re-initialization of the management system, and at
         other times as indicated by the value of
         'discontinuity-time'";
    }
    leaf out-unicast-pkts {
      type uint64;
      description
        "The total number of packets that higher-level protocols
         requested be transmitted, and that were not addressed
         to a multicast or broadcast address at this sub-layer,
         including those that were discarded or not sent.
         Discontinuities in the value of this counter can occur
         at re-initialization of the management system, and at
         other times as indicated by the value of 'discontinuity-time'";
    }
    leaf out-broadcast-pkts {
      type uint64;
      description
        "The total number of packets that higher-level protocols
         requested be transmitted, and that were addressed to a
         broadcast address at this sub-layer, including those
         that were discarded or not sent.
         Discontinuities in the value of this counter can occur
         at re-initialization of the management system, and at
         other times as indicated by the value of
         'discontinuity-time'";
    }
    leaf out-multicast-pkts {
      type uint64;
      description
        "The total number of packets that higher-level protocols
         requested be transmitted, and that were addressed to a
         multicast address at this sub-layer, including those
         that were discarded or not sent.  For a MAC-layer
         protocol, this includes both Group and Functional addresses.
         Discontinuities in the value of this counter can occur
         at re-initialization of the management system, and at
         other times as indicated by the value of
         'discontinuity-time'";
    }
    leaf out-discards {
      type uint64;
      description
        "The number of outbound packets that were chosen to be
         discarded even though no errors had been detected to
         prevent their being transmitted.  One possible reason
         for discarding such a packet could be to free up buffer space.
         Discontinuities in the value of this counter can occur
         at re-initialization of the management system, and at
         other times as indicated by the value of
         'discontinuity-time'";
    }
    leaf out-errors {
      type uint64;
      description
        "For packet-oriented interfaces, the number of outbound
         packets that could not be transmitted because of errors.
         For character-oriented or fixed-length interfaces, the
         number of outbound transmission units that could not be
         transmitted because of errors.
         Discontinuities in the value of this counter can occur
         at re-initialization of the management system, and at
         other times as indicated by the value of
         'discontinuity-time'";
    }
    leaf rx-pps {
      type uint64;
      description
        "The receive packet per second rate on this interface";
    }
    leaf rx-kbps {
      type uint64;
      description
        "The receive kilobits per second rate on this interface";
    }
    leaf tx-pps {
      type uint64;
      description
        "The transmit packet per second rate on this interface";
    }
    leaf tx-kbps {
      type uint64;
      description
        "The transmit kilobits per second rate on this interface";
    }
    leaf num-flaps {
      type uint64;
      description
        "The number of times the interface state
         transitioned between up and down";
    }
    leaf in-crc-errors {
      type uint64;
      description
        "Number of receive error events due to FCS/CRC check
         failure";
    }
  }

  grouping ethernet-state {
    description
      "Ethernet State";
    leaf negotiated-duplex-mode {
      type interfaces-ios-xe-oper:ether-duplex;
      description
        "When auto-negotiate is set to TRUE, and the 
         interface has completed auto-negotiation with the 
         remote peer, this value shows the duplex mode that 
         has been negotiated.";
    }
    leaf negotiated-port-speed {
      type interfaces-ios-xe-oper:ether-speed;
      description
        "When auto-negotiate is set to TRUE, and 
         the interface has completed auto-negotiation with 
         the remote peer, this value shows the interface 
         speed that has been negotiated.";
    }
    leaf auto-negotiate {
      type boolean;
      description
        "Set to TRUE to request the interface to 
         auto-negotiate transmission parameters with its 
         peer interface. When set to FALSE, the transmission
         parameters are specified manually.";
    }
    leaf enable-flow-control {
      type boolean;
      description
        "Enable or disable flow control for this 
         interface. Ethernet flow control is a mechanism by 
         which a receiver may send PAUSE frames to a sender
         to stop transmission for a specified time.
         
         This setting should override auto-negotiated flow 
         control settings. If left unspecified, and 
         auto-negotiate is TRUE, flow control mode is 
         negotiated with the peer interface.";
    }
  }

  grouping dot3-v2-error-counters {
    description
      "dot 3 version 2 error counters";
    leaf dot3-alignment-errors {
      type uint64;
      description
        "A count of frames received that are not an integral number of
         octets in length and do not pass the FCS check.";
    }
    leaf dot3-fcs-errors {
      type uint64;
      description
        "A count of frames received that are an integral number of
         octets in length and do not pass the FCS check.";
    }
    leaf dot3-single-collision-frames {
      type uint64;
      description
        "A count of frames that are involved in a single
         collision, and are subsequently transmitted
         successfully.";
    }
    leaf dot3-multiple-collision-frames {
      type uint64;
      description
        "A count of frames that are involved in more
         than one collision and are subsequently
         transmitted successfully.";
    }
    leaf dot3-sqe-test-errors {
      type uint64;
      description
        "A count of times that the signal quality error
         test errors is received on a particular interface.";
    }
    leaf dot3-deferred-transmissions {
      type uint64;
      description
        "A count of frames for which the first
         transmission attempt on a particular interface
         is delayed because the medium is busy.";
    }
    leaf dot3-late-collisions {
      type uint64;
      description
        "The number of times that a collision is
         detected on a particular interface later than
         one slot time into the transmission of a packet.";
    }
    leaf dot3-excessive-collisions {
      type uint64;
      description
        "A count of frames for which transmission on a
         particular interface fails due to excessive
         collisions.";
    }
    leaf dot3-internal-mac-transmit-errors {
      type uint64;
      description
        "A count of frames for which transmission on a
         particular interface fails due to an internal
         MAC sublayer transmit error.";
    }
    leaf dot3-carrier-sense-errors {
      type uint64;
      description
        "The number of times that the carrier sense
         condition was lost or never asserted when
         attempting to transmit a frame on a particular
         interface.";
    }
    leaf dot3-frame-too-longs {
      type uint64;
      description
        "A count of frames received on a particular
         interface that exceed the maximum permitted
         frame size.";
    }
    leaf dot3-internal-mac-receive-errors {
      type uint64;
      description
        "A count of frames for which reception on a
         particular interface fails due to an internal
         MAC sublayer receive error.";
    }
    leaf dot3-symbol-errors {
      type uint64;
      description
        "For an interface operating at 100 Mb/s, the
         number of times there was an invalid data symbol
         when a valid carrier was present.";
    }
    leaf dot3-duplex-status {
      type uint64;
      description
        "The current mode of operation of the MAC
         entity.  'unknown' indicates that the current
         duplex mode could not be determined.
         The possible value as defined by RFC 3635 are:
            unknown     1
            half duplex 2
            full duplex 3";
    }
    leaf dot3-hc-alignment-errors {
      type uint64;
      description
        "A count of frames received that are not an integral number of
         octets in length and do not pass the FCS check on interfaces 
         operating at 10 Gb/s or faster.";
    }
    leaf dot3-hc-inpause-frames {
      type uint64;
      description
        "MAC layer PAUSE frames received on the interface";
    }
    leaf dot3-hc-outpause-frames {
      type uint64;
      description
        "MAC layer PAUSE frames sent on the interface";
    }
    leaf dot3-hc-fcs-errors {
      type uint64;
      description
        "A count of frames received that are an integral number of
         octets in length and do not pass the FCS check on interfaces 
         operating at 10 Gb/s or faster.";
    }
    leaf dot3-hc-frame-too-longs {
      type uint64;
      description
        "A count of frames received on a particular
         interface that exceed the maximum permitted
         frame size on interfaces operating at 10 Gb/s or faster.";
    }
    leaf dot3-hc-internal-mac-transmit-errors {
      type uint64;
      description
        "A count of frames for which transmission on a
         particular interface fails due to an internal
         MAC sublayer transmit error on interfaces 
         operating at 10 Gb/s or faster.";
    }
    leaf dot3-hc-internal-mac-receive-errors {
      type uint64;
      description
        "A count of frames for which reception on a
         particular interface fails due to an internal
         MAC sublayer receive error on interfaces 
         operating at 10 Gb/s or faster.";
    }
    leaf dot3-hc-symbol-errors {
      type uint64;
      description
        "For an interface operating at 10 Gb/s or higher, the
         number of times the receiving media is non-idle
         (a carrier event) for a period of time equal to
         or greater than minimum frame size, and during which
         there was at least one occurrence of an event
         that causes the PHY to indicate 'Receive Error'";
    }
  }

  grouping dot3-counters {
    description
      "Dot 3 error counters";
    leaf dot3-stats-version {
      type interfaces-ios-xe-oper:dot3-stats-versions;
      description
        "Version of dot 3 error counters";
    }
    container dot3-error-counters-v2 {
      description
        "The Ethernet dot 3 version 2 error counters";
      uses interfaces-ios-xe-oper:dot3-v2-error-counters;
    }
  }

  grouping ethernet-statistics {
    description
      "Ethernet statistics";
    leaf in-mac-control-frames {
      type uint64;
      description
        "MAC layer control frames received on the interface";
    }
    leaf in-mac-pause-frames {
      type uint64;
      description
        "MAC layer PAUSE frames received on the interface";
    }
    leaf in-oversize-frames {
      type uint64;
      description
        "Number of oversize frames received on the interface";
    }
    leaf in-jabber-frames {
      type uint64;
      description
        "Number of jabber frames received on the
         interface.  Jabber frames are typically defined as oversize
         frames which also have a bad CRC.  Implementations may use
         slightly different definitions of what constitutes a jabber
         frame.  Often indicative of a NIC hardware problem.";
    }
    leaf in-fragment-frames {
      type uint64;
      description
        "Number of fragment frames received on the interface.";
    }
    leaf in-8021q-frames {
      type uint64;
      description
        "Number of 802.1q tagged frames received on the interface";
    }
    leaf out-mac-control-frames {
      type uint64;
      description
        "MAC layer control frames sent on the interface";
    }
    leaf out-mac-pause-frames {
      type uint64;
      description
        "MAC layer PAUSE frames sent on the interface";
    }
    leaf out-8021q-frames {
      type uint64;
      description
        "Number of 802.1q tagged frames sent on the interface";
    }
    leaf dot3-counters-supported {
      type empty;
      description
        "When present, the dot 3 version 2 error counters
         are valid";
    }
    container dot3-counters {
      when "boolean(../dot3-counters-supported)";
      description
        "dot 3 error counters";
      uses interfaces-ios-xe-oper:dot3-counters;
    }
  }

  grouping t1e1-serial-state {
    description
      "The T1/E1 serial state";
    leaf crc-type {
      type interfaces-ios-xe-oper:serial-crc;
      description
        "Cyclic Redundancy Code type configured on the interface";
    }
    leaf loopback {
      type interfaces-ios-xe-oper:t1e1-loopback-mode;
      description
        "Loopback mode the interface is operating in";
    }
    leaf keeplive {
      type uint32;
      description
        "Keep alive interval in seconds";
    }
    leaf timeslot {
      type uint32;
      description
        "Time slots bitmap occupied by this serial interface";
    }
    leaf subrate {
      type interfaces-ios-xe-oper:subrate-speed;
      description
        "Subrate operating per slot";
    }
  }

  grouping t1e1-serial-stats {
    description
      "The serial specific statistics";
    leaf in-abort-clock-error {
      type uint32;
      description
        "Number of receive abort packets due to clock slides";
    }
  }

  grouping dce-state {
    description
      "Synchronous serial DCE mode state";
    leaf dce-terminal-timing-enable {
      type boolean;
      description
        "Enable DCE terminal timing";
    }
    leaf ignore-dtr {
      type boolean;
      description
        "Ignore DTR signal";
    }
    leaf serial-clock-rate {
      type uint32;
      units "bps";
      description
        "Serial clock rate in bps";
    }
  }

  grouping dte-state {
    description
      "Synchronous serial DTE mode state";
    leaf tx-invert-clk {
      type boolean;
      description
        "Invert transmit clock";
    }
    leaf ignore-dcd {
      type boolean;
      description
        "Ignore DCD signal";
    }
    leaf rx-clockrate {
      type uint32;
      units "bps";
      description
        "Received clock rate";
    }
    leaf rx-clock-threshold {
      type uint32;
      units "bps";
      description
        "Received clock rate threshold limit";
    }
  }

  grouping sync-serial-state {
    description
      "The synchronous serial state";
    leaf carrier-delay {
      type uint32;
      units "milli-seconds";
      description
        "Delay for interface transitions";
    }
    leaf dtr-pulse-time {
      type uint32;
      units "milli-seconds";
      description
        "DTR pulse time on reset";
    }
    leaf restart-delay {
      type uint32;
      units "milli-seconds";
      description
        "Serial interface restart-delay";
    }
    leaf cable-type {
      type string;
      description
        "Cable type attached on the interface";
    }
    leaf loopback {
      type boolean;
      description
        "Whether the interface is in loopback mode";
    }
    leaf nrzi-encoding {
      type boolean;
      description
        "Enable use of NRZI encoding";
    }
    leaf idle-character {
      type interfaces-ios-xe-oper:idle-character-type;
      description
        "Idle character type";
    }
    leaf rts-signal {
      type interfaces-ios-xe-oper:signal-status;
      description
        "RTS signal state";
    }
    leaf cts-signal {
      type interfaces-ios-xe-oper:signal-status;
      description
        "CTS signal state";
    }
    leaf dtr-signal {
      type interfaces-ios-xe-oper:signal-status;
      description
        "DTR signal state";
    }
    leaf dcd-signal {
      type interfaces-ios-xe-oper:signal-status;
      description
        "DCD signal state";
    }
    leaf dsr-signal {
      type interfaces-ios-xe-oper:signal-status;
      description
        "DSR signal state";
    }
    container dce-mode-state {
      description
        "Special state in DCE mode";
      uses interfaces-ios-xe-oper:dce-state;
    }
    container dte-mode-state {
      description
        "Special state in DTE mode";
      uses interfaces-ios-xe-oper:dte-state;
    }
  }

  grouping interface-state {
    description
      "Interface state details";
    leaf name {
      type string;
      description
        "The name of the interface.
         A server implementation MAY map this leaf to the ifName
         MIB object.  Such an implementation needs to use some
         mechanism to handle the differences in size and characters
         allowed between this leaf and ifName.  The definition of
         such a mechanism is outside the scope of this document";
    }
    leaf interface-type {
      type interfaces-ios-xe-oper:ietf-intf-type;
      description
        "When an interface entry is created, a server MAY
         initialize the type leaf with a valid value, e.g., if it
         is possible to derive the type from the name of the interface.
         If a client tries to set the type of an interface to a
         value that can never be used by the system, e.g., if the
         type is not supported or if the type does not match the
         name of the interface, the server MUST reject the request.
         A NETCONF server MUST reply with an rpc-error with the
         error-tag 'invalid-value' in this case";
    }
    leaf admin-status {
      type interfaces-ios-xe-oper:intf-state;
      description
        "The desired state of the interface.
         This leaf has the same read semantics as ifAdminStatus";
    }
    leaf oper-status {
      type interfaces-ios-xe-oper:oper-state;
      description
        "The current operational state of the interface.
         This leaf has the same semantics as ifOperStatus";
    }
    leaf last-change {
      type yang:date-and-time;
      description
        "The time the interface entered its current operational
         state. If the current state was entered prior to the
         last re-initialization of the local network management
         subsystem, then this node is not present";
    }
    leaf if-index {
      type int32;
      description
        "The ifIndex value for the ifEntry represented by this interface";
    }
    leaf phys-address {
      type yang:mac-address;
      description
        "The interface's address at its protocol sub-layer.  For
         example, for an 802.x interface, this object normally
         contains a Media Access Control (MAC) address.  The
         interface's media-specific modules must define the bit
         and byte ordering and the format of the value of this
         object.  For interfaces that do not have such an address
         (e.g., a serial line), this node is not present";
    }
    leaf-list higher-layer-if {
      type string;
      ordered-by user;
      description
        "A list of references to interfaces layered on top of this interface";
    }
    leaf-list lower-layer-if {
      type string;
      ordered-by user;
      description
        "A list of references to interfaces layered underneath this interface";
    }
    leaf speed {
      type uint64;
      description
        "An estimate of the interface's current bandwidth in bits
         per second.  For interfaces that do not vary in
         bandwidth or for those where no accurate estimation can
         be made, this node should contain the nominal bandwidth.
         For interfaces that have no concept of bandwidth, this
         node is not present";
    }
    container statistics {
      description
        "A collection of interface-related statistics objects";
      uses interfaces-ios-xe-oper:intf-statistics;
    }
    list diffserv-info {
      key "direction policy-name";
      description
        "diffserv related details";
      uses interfaces-ios-xe-oper:diffserv-target-entry-key;
      uses interfaces-ios-xe-oper:diffserv-target-entry;
    }
    leaf vrf {
      type string;
      description
        "VRF to which this interface belongs to. If the 
         interface is not in a VRF then it is 'Global'";
    }
    leaf ipv4 {
      type inet:ip-address;
      description
        "IPv4 address configured on interface";
    }
    leaf ipv4-subnet-mask {
      type inet:ip-address;
      description
        "IPv4 Subnet Mask";
    }
    leaf description {
      type string;
      description
        "Interface description";
    }
    leaf mtu {
      type uint32;
      description
        "Maximum transmission unit";
    }
    leaf input-security-acl {
      type string;
      description
        "Input Security ACL";
    }
    leaf output-security-acl {
      type string;
      description
        "Output Security ACL";
    }
    container v4-protocol-stats {
      description
        "IPv4 traffic statistics for this interface";
      uses interfaces-ios-xe-oper:protocol-statistics;
    }
    container v6-protocol-stats {
      description
        "IPv6 traffic statistics for this interface";
      uses interfaces-ios-xe-oper:protocol-statistics;
    }
    leaf bia-address {
      type yang:mac-address;
      description
        "The burnt-in mac address that was associated with this
         interface from manufacturing. This is only relevant for
         interfaces that have the concept of burnt in ethernet 
         addresses, otherwise it is zero.";
    }
    leaf-list ipv6-addrs {
      type inet:ip-address;
      ordered-by user;
      description
        "A list of the IPv6 addresses associated with the interface.
         This contains all the IPv6 addresses, including the link local
         addresses, assigned to the interface";
    }
    list lag-aggregate-state {
      key "aggregate-id";
      description
        "Operational state variables for logical
         aggregate / LAG interfaces";
      uses interfaces-ios-xe-oper:lag-aggregate-state;
    }
    leaf ipv4-tcp-adjust-mss {
      type uint16;
      description
        "When ip tcp adjust-mss is configured, this value shows
         the tcp mss, or the value is zero.";
    }
    leaf ipv6-tcp-adjust-mss {
      type uint16;
      description
        "When ipv6 tcp adjust-mss is configured, this value shows
         the tcp mss, or the value is zero.";
    }
    choice interface-class-choice {
      description
        "The broad class that the interface belongs";
      case interface-class-ethernet {
        container ether-state {
          description
            "The Ethernet state information";
          uses interfaces-ios-xe-oper:ethernet-state;
        }
        container ether-stats {
          description
            "The Ethernet statistics";
          uses interfaces-ios-xe-oper:ethernet-statistics;
        }
      }
      case interface-class-t1e1serial {
        container serial-state {
          description
            "The T1E1 serial state information";
          uses interfaces-ios-xe-oper:t1e1-serial-state;
        }
        container serial-stats {
          description
            "The T1E1 statistics";
          uses interfaces-ios-xe-oper:t1e1-serial-stats;
        }
      }
      case interface-class-unspecified {
        leaf intf-class-unspecified {
          type boolean;
          description
            "No specific interface class information";
        }
      }
      case interface-class-syncserial {
        container syncserial-state {
          description
            "The synchronous serial state information";
          uses interfaces-ios-xe-oper:sync-serial-state;
        }
      }
    }
  }

  container interfaces {
    config false;
    description
      "Operational state of interfaces";
    list interface {
      key "name";
      description
        "List of interfaces";
      uses interfaces-ios-xe-oper:interface-state;
    }
  }
}
