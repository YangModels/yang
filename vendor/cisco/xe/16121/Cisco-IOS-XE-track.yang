module Cisco-IOS-XE-track {
  namespace "http://cisco.com/ns/yang/Cisco-IOS-XE-track";
  prefix ios-track;

  import cisco-semver {
    prefix cisco-semver;
  }
 

  import ietf-inet-types {
    prefix inet;
  }

  import Cisco-IOS-XE-native {
    prefix ios;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Object Tracking Yang Model.
     Copyright (c) 2016, 2018, 2019 by Cisco Systems, Inc.
     All rights reserved.";

  // =========================================================================
  // REVISION
  // =========================================================================
  revision 2019-07-01 {
    description 
      "- Establish semantic version baseline
       - Added IPv6 resolution command in track";
    cisco-semver:module-version "1.0.0";
  }
  revision 2018-10-23 {
    description
      "Added redundancy command track inside application redundancy"; 
  }
  revision 2018-09-07 {
    description
      "fix track ip option missing issue";
  }
  revision 2018-08-10 {
    description
      "removed default-track-grouping container";
  }
  revision 2018-08-07 {
    description
      "updated threshold and carrier-delay leaf";
  }
  revision 2017-04-28 {
    description
      "inet:ipv6-prefix changed to ios-types:ipv6-prefix";
  }
  revision 2017-02-07 {
    description
      "Initial revision";
  }

  grouping track-timer-grouping {
    choice timer-val {
      case time-sec {
        leaf sec {
          type uint32 {
            range "1..3000";
          }
        }
      }
      case time-msec {
        leaf msec {
          description
            "Specify polling interval in milliseconds";
          type uint32 {
            range "500..5000";
          }
        }
      }
    }
    leaf seconds {
      status obsolete;
      type uint32 {
        range "1..3000";
      }
    }
    leaf ms {
      status obsolete;
      description
        "Specify polling interval in milliseconds";
      type uint32 {
        range "500..5000";
      }
    }
  }

  grouping track-grouping {
    container delay {
      description
        "Tracking delay";
      leaf down {
        description
          "Delay down change notification";
        type uint32 {
          range "0..180";
        }
      }
      leaf up {
        description
          "Delay up change notification";
        type uint32 {
          range "0..180";
        }
      }
    }
    leaf carrier-delay {
      description
        "Report state change after interface carrier-delay timer";
        when "../interface/protocol";
        type empty;
    }
    container threshold {
      description
        "Threshold parameters";
      container metric {
        description
          "Scaled metric threshold";
        when "../../ip/route/metric-ip or ../../ipv6/route/metric-ipv6";
        leaf up {
          description
            "Up threshold";
          type uint32 {
            range "0..254";
          }
        }
        leaf down {
          description
            "Down threshold";
          type uint32 {
            range "2..255";
          }
        }
      }
      container weight {
        description
          "Weight threshold";
        when "../../list/threshold-config = 'weight'";
        leaf up {
          description 
            "Up threshold";
          type uint32 {
            range "0..255";
          }
        }
        leaf down {
          description 
            "Down threshold";
          type uint32 {
            range "0..255";
          }
        }
      }
      container percentage {
        description
          "Percentage threshold";
        when "../../list/threshold-config = 'percentage'";
        leaf up {
          description 
            "Up threshold value in percentage";
          type uint32 {
            range "0..100";
          }
        }
        leaf down {
          description 
            "Down threshold value in percentage";
          type uint32 {
            range "0..100";
          }
        }
      }
    }
    leaf default-state {
      description
        "default object state";
      when "../stub-object or ../ip/sla/reachability-sla or ../ip/sla/state-sla or ../ip/sla/number" ;
      type enumeration {
        enum "down";
        enum "up";
      }
    }
    list object {
      description
        "Add a tracked object to list";
      key "number";
      leaf number {
        type uint32 {
          range "1..1000";
        }
      }
      leaf not {
        description
          "Negate the state of object";
        when "../../list/boolean-config = 'or'  or ../../list/boolean-config = 'and'";
        type empty;
      }
      leaf weight {
        description
          "Assign a weight to object";
       when "../../list/threshold-config = 'weight'";
        type uint32 {
          range "1..255";
        }
      }
    }
    container ip-wrapper {
      container ipv6 {
        description
          "Tracking IPv6 object configuration";
        when "../../ipv6/route/address";
        leaf vrf {
          description
            "VPN Routing/Forwarding table name";
          type string;
        }
      }
      container ip {
        description
          "Tracking IP object configuration";
        when "../../ip/route/address";
        leaf vrf {
          description
            "VPN Routing/Forwarding table name";
          type string;
        }
      }
    }
  }
  grouping track-resolution-grouping {
    container route {
      description
        "Route metric resolution";
      leaf bgp {
        description
          "BGP route metric resolution";
        type uint32 {
          range "1..16843008";
        }
      }
      leaf eigrp {
        description
          "EIGRP route metric resolution";
        type uint32 {
          range "256..40000000";
        }
      }
      leaf isis {
        description
          "ISIS route metric resolution";
        type uint32 {
          range "1..1000";
        }
      }
      leaf ospf {
        description
          "OSPF route metric resolution";
        type uint32 {
          range "1..1562";
        }
      }
      leaf static {
        description
          "Static route metric resolution";
        type uint32 {
          range "1..100000";
        }
      }
    }
  }

  grouping config-track-grouping {
    list tracked-object {
      key "object-number";
      leaf object-number {
        type uint32 {
          range "1..1000";
        }
      }
      container interface {
        description
          "Select an interface to track";
        leaf name {
          must "not (contains(current(), '.') and ../../carrier-delay)" {
            error-message "Cannot track a sub-interface with carrier-delay";
          }
          type string;
        }
        leaf protocol {
          type enumeration {
            enum "ip";
            enum "ipv6";
            enum "line-protocol";
          }
        }
        leaf routing {
          description
            "Track interface IPv6 routing capability";
          when "../protocol = 'ip' or ../protocol = 'ipv6'";
          type empty;
        }
      }
      container ip {
        description
          "IP protocol";
        container route {
          leaf address {
            type inet:ipv4-address;
          }
          leaf mask {
            type inet:ipv4-address;
          }
          choice option {
            case reachability-case {
              leaf reachability-ip {
                description
                  "Route reachability state";
                type empty;
               }
            }
            case metric-case {
              leaf metric-ip {
                description
                  "Route metric";
                type enumeration {
                  enum "threshold";
                }
              }
            }
          }
          leaf reachability {
            status obsolete;
            description
              "Route reachability state";
            type empty;
          }
          leaf metric { 
            status obsolete;
            description
              "Route metric";
            type enumeration {
              enum "threshold";
            }
          }
        }
        container sla {
          description
            "IP Service Level Agreement";
          leaf number {
            description
              "Entry number";
            type uint32;
          }
          choice option {
            case reachability-case {
              leaf reachability-sla {
                description
                  "Reachability";
                type empty;
               }
            }
            case state-case {
              leaf state-sla {
                  description
                    "Return code state";
                 type empty;
              }
            }
          }  
          leaf reachability {
            status obsolete;
            description
              "Reachability";
            type empty;
          }
          leaf state { 
            status obsolete;
            description
              "Return code state";
            type empty;
          }
        }
      }
      container ipv6 {
        description
          "IPv6 protocol";
        container route {
          description
            "IPv6 route";
          leaf address {
            type ios-types:ipv6-prefix;
          }
          choice option {
            case reachability-case {
              leaf reachability-ipv6 {
                  description
                    "Route reachability state";
                  type empty;
              }
            }
            case metric-case {
              leaf metric-ipv6 {
                  description
                    "Route metric";
                   type enumeration {
                     enum "threshold";
                 }
              }
            }
          }
          leaf reachability {
            status obsolete;
            description
              "Route reachability state";
            type empty;
          }
          leaf metric {
            status obsolete;
            description
              "Route metric";
            type enumeration {
              enum "threshold";
            }
          }
        }
      }
      container list {
        description
          "Group objects in a list";
        choice option {
          case boolean-case {
            leaf boolean-config {
              description
                "List state based on a boolean calculation on objects";
              type enumeration {
                enum "and";
                enum "or";
              }
            }
          }
          case threshold-case {
            leaf threshold-config {
              description
                "List state based on a threshold of UP and DOWN objects";
              type enumeration {
                enum "percentage";
                enum "weight";
              }
            }
          }
        } 
        leaf boolean {
          status obsolete;
          description
            "List state based on a boolean calculation on objects";
          type enumeration {
            enum "and";
            enum "or";
          }
        }
        leaf threshold {
          status obsolete;
          description
            "List state based on a threshold of UP and DOWN objects";
          type enumeration {
            enum "percentage";
            enum "weight";
          }
        }
      }
      leaf stub-object {
        description
          "Stub tracking object";
        type empty;
      }
      uses track-grouping;
    }
    container resolution {
      description
        "Tracking resolution parameters";
      container ip {
        description
          "IP protocol";
        uses track-resolution-grouping; 
      }
      container ipv6 {
        description
          "IPv6 protocol";
        uses track-resolution-grouping; 
      }
    }
    container timer {
      description
        "Polling interval timers";
      container interface {
        description
          "Interface polling timer";
        uses track-timer-grouping;
      }
      container ip {
        description
          "IP protocol";
        container route {
          description
            "IP route polling timer";
          uses track-timer-grouping;
        }
        container sla {
          description
            "IP SLA polling timer";
          uses track-timer-grouping;
        }
      }
      container ipv6 {
        description
          "IPv6 protocol";
        container route {
          description
            "IPv6 route polling timer";
          uses track-timer-grouping;
        }
      }
      container list {
        description
          "Boolean list polling timer";
        uses track-timer-grouping;
      }
      container stub-object {
        description
          "EEM stub polling timer";
        uses track-timer-grouping;
      }
    }
  }

  grouping config-application-red-group-track-options {
    list track {
      description
        "RG group tracking";
      key object-number;
      leaf object-number {
        description "Tracked object number";

        type leafref {
          path "/ios:native/ios:track/ios-track:tracked-object/ios-track:object-number";
        }
      }
      choice decrement-shutdown {
        case decrement-case {
          leaf decrement {
            description "Decrement Value";
            type uint8 {
              range "1..255";
            }
          }
        }
        case shutdown-case {
          leaf shutdown {
            description "Shutdown group";
            type empty;
          }
        }
      }
   }
  }

  /////////////////////////////////////////////////////////
  // native / track *
  /////////////////////////////////////////////////////////
  augment "/ios:native/ios:track" {
    uses config-track-grouping;
  }
  augment "/ios:native/ios:redundancy/ios:application/ios:redundancy/ios:group" {
    uses config-application-red-group-track-options;
  }
}
