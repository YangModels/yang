module Cisco-IOS-XE-http {
  namespace "http://cisco.com/ns/yang/Cisco-IOS-XE-http";
  prefix ios-http;

  import cisco-semver {
    prefix cisco-semver;
  }
 

  import Cisco-IOS-XE-native {
    prefix ios;
  }

  import Cisco-IOS-XE-aaa {
    prefix ios-aaa;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Hypertext Transfer Protocol (HTTP) Yang Model.
     Copyright (c) 2016, 2018-2019 by Cisco Systems, Inc.
     All rights reserved.";

  // =========================================================================
  // REVISION
  // =========================================================================
  revision 2019-07-01 {
    description 
      "- Establish semantic version baseline
       - Added support for session-idle-timeout
       - Added support for ctc authentication";
    cisco-semver:module-version "1.0.0";
  }
  revision 2018-10-26 {
    description
      "Added support for 'ip http tls-version'";
  }
  
  revision 2018-09-26 {
    description
      "Added support for 'ip http authentication aaa'";
  }
  
  revision 2018-01-24 {
    description
      "Updated ip http configurations to prevent full sync";
  }

  revision 2017-12-04 {
    description
      "Added ip http configurations to prevent full sync";
  }

  revision 2017-02-07 {
    description
      "Initial revision";
  }

  grouping config-ip-http-grouping {
    container http {
      description
        "HTTP server configuration";
      leaf access-class {
        description
          "Restrict http server access by access-class";
        type uint8 {
          range "1..99";
        }
      }
      // ip http authentication
      container authentication {
        description
          "Set http server authentication method";
        choice authentication-choice {
          container aaa {
            description
              "Use AAA access control methods";
            presence true;
            list command-authorization {
              description
                "Set method list for command authorization";
              
              key "level";
              leaf level {
                description
                  "Enable level";
                type uint8 {
                  range "0..15";
                }
              }
              leaf name {
                description
                  "Use an authorization list with this name";
                mandatory true;
                type string;
              }
            }
            leaf exec-authorization {
              description
                "Set method list for exec authorization";
                type string;
            }
            leaf login-authentication {
              description
                "Set method list for login authentication";
                type string;
            }
          }
          leaf local {
            description
              "Use local username and passwords";
            type empty;
          }
        }
      }
      // ip http server
      leaf server {
        description
          "Enable http server";
        type boolean;
      }
      // ip http secure-server
      leaf secure-server {
        description
          "Enable HTTP secure server";
        type boolean;
      }
      // ip http secure-trustpoint
      leaf secure-trustpoint {
        description
          "Set http secure server certificate trustpoint";
        type string;
      }
      // ip http tls-version
      leaf tls-version {
        description 
          "Set TLS version for HTTP secure server";
        type enumeration {
          enum TLSv1.0;
          enum TLSv1.1;
          enum TLSv1.2;
        }
      }
      // ip http timeout-policy
      container timeout-policy {
        description
          "Set http server time-out policy parameters";
        leaf idle {
          description
            "Idle time-out of a http server connection in seconds";
          type uint16 {
            range "1..600";
          }
        }
        leaf life {
          description
            "Life time of a http server connection in seconds";
          type uint32 {
            range "1..86400";
          }
        }
        leaf requests {
          description
            "Maximum number of requests allowed on a http server connection";
          type uint32 {
            range "1..86400";
          }
        }
      }
      // ip http client
      container client {
        description
          "Set http client parameters";
        leaf secure-trustpoint {
          description
            "Set http client certificate secure trustpoint";
          type string;
        }
        leaf source-interface {
          description
            "Specify interface for source address in all HTTP(S) client connections";
          type string;
        }
        container proxy-server {
          description
            "Specify proxy server name for HTTP file system client connections";
          leaf proxy-server-name {
            description
              "Proxy server name";
            type string;
          }
          leaf proxy-port {
            description
              "Proxy port number";
            type uint16 {
              range "1..65535";
            }
          }
        }
      }

      // ip http port - add to support DNA-C configuration
      leaf port {
        description
          "http port number";
        type uint16 {
          range "1..65535";
        }
      }

      // ip http max-connections - add to support DNA-C configuration
      leaf max-connections {
        description
          "max http connections";
        type uint16 {
          range "1..50";
        }
      }

      // ip http active-session-modules - add to support DNA-C configuration
      leaf active-session-modules {
        description
          "Set active session modules";
        type union {
          type enumeration {
            enum none;
            enum all;
          }
          type string;
        }
      }

      // ip http secure-active-session-modules - add to support DNA-C configuration
      leaf secure-active-session-modules {
        description
          "Set secure active session modules";
        type union {
          type enumeration {
            enum none;
            enum all;
          }
          type string;
        }
      }

      leaf secure-client-auth {
        description
          "Set http secure server with client authentication";
        type empty;
      }

      // ip http path
      leaf path {
         description
           "Set http path name";
         type string;
      }

      // ip http session-idle-timeout
      leaf session-idle-timeout {
         description
           "Set http server session idle timeout";
         type uint16 {
           range "180..1200";
         }
      }

      // ip http ctc authentication
      container ctc {
        description
          "Set http ctc configuration";
        leaf authentication {
          description
            "Enable ctc authentication";
          type empty;
        }
      }
    }
  }

  /////////////////////////////////////////////////////////
  // native / ip / http
  /////////////////////////////////////////////////////////
  augment "/ios:native/ios:ip" {
    uses config-ip-http-grouping;
  }
}
