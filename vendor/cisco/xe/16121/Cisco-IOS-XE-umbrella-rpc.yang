module Cisco-IOS-XE-umbrella-rpc {
  namespace "http://cisco.com/ns/yang/Cisco-IOS-XE-umbrella-rpc";
  prefix ios-xe-umbrella-rpc;

  import cisco-semver {
    prefix cisco-semver;
  }
 
  import Cisco-IOS-XE-rpc {
    prefix ios-xe-rpc;
  }

  organization "Cisco Systems";

  contact
    <mailto:cs-yang@cisco.com>;

  description
    "NED Umbrella RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2019-02-22 {
    description
      "Move feature-choices into cases";
  }

  revision 2018-12-06 {
    description
      "created for NED RPC modularisation";
  }

  augment "/ios-xe-rpc:clear/ios-xe-rpc:input/ios-xe-rpc:clear-choice/ios-xe-rpc:platform-case/ios-xe-rpc:platform/ios-xe-rpc:hardware/ios-xe-rpc:qfp/ios-xe-rpc:active/ios-xe-rpc:feature/ios-xe-rpc:feature-choice" {
    case umbrella-case {
      container umbrella {
        description
          "Clear QFP Umbrella";
        container datapath {
          description
            "Clear Umbrella datapath";
          leaf stats {
            description
              "Clear Umbrella datapath stats";
            type empty;
          }
        }
      }
    }
  }
}
