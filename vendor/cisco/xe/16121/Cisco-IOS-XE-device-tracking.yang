module Cisco-IOS-XE-device-tracking {
  namespace "http://cisco.com/ns/yang/Cisco-IOS-XE-device-tracking";
  prefix ios-dt;

  import cisco-semver {
    prefix cisco-semver;
  }
 
  import Cisco-IOS-XE-types {
    prefix ios-types;
  }

  import Cisco-IOS-XE-native {
    prefix ios;
  }


  import ietf-inet-types {
    prefix inet;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Device Tracking Yang model.
     Copyright (c) 2016-2019 by Cisco Systems, Inc.
     All rights reserved.";

  // =========================================================================
  // REVISION
  // =========================================================================
  revision 2019-07-01 {
    description 
      "- Establish semantic version baseline
       - Add new containers (prefix-glean, destination-glean and trusted port)in device-tracking policy list
       - Assign default value for protocol options";
    cisco-semver:module-version "1.0.0";
  }
  revision 2018-01-29 {
    description
      "Add device-tracking tracking reachable-lifetime";
  }
  revision 2017-06-07 {
    description
      "Add device-tracking tracking support";
  }
  revision 2017-02-07 {
    description
      "Initial revision";
  }

  grouping config-interface-device-tracking-grouping {
      // interface * / device-tracking
      container device-tracking {
        description
          "Configure device-tracking on the interface";
        presence "Attach default device-tracking on interface";
        if-feature ios-features:switching-platform;
        
        
        must "not (../ios:switchport-conf/ios:switchport) or (../ios:switchport-conf/ios:switchport = 'true')" {
          error-message "To configure attach device-tracking policy, set switchport-conf to true first; To set switchport from true to false, detach device-tracking policy first";
        }
        leaf attach-policy {
          description
            "Apply a policy for feature device-tracking";
          type string;
          
          
          must "(/ios:native/ios:device-tracking/ios-dt:policy[ios-dt:word=current()])" {
            error-message "Create policy first, then attach policy; Detach policy first then remove policy";
          }
        }
      }
  }

  grouping config-interface-switchport-device-tracking-grouping {
      // This group will be obsoleted.
      // It is used in augment '/ios:native/ios:interface/ios:<interface_type>/ios:switchport'
      // When enable 'device-tracking' feature under this augment, it will casue 'bad-command' error
      // interface/switchport * / device-tracking
      container device-tracking {
        description
          "Obsolete - Configure device-tracking on the interface";
        presence "Attach default device-tracking on interface";
        status obsolete;
        leaf attach-policy {
          description
            "Obsolete - Apply a policy for feature device-tracking";
          status obsolete;
          type string;
          
          
          must "(/ios:native/ios:device-tracking/ios-dt:policy[ios-dt:word=current()])" {
            error-message "Create policy first, then attach policy; Detach policy first then remove policy";
          }
        }
      }
  }

  grouping config-vlan-device-tracking-grouping {
      // This group will be obsoleted.
      // When enable 'device-tracking' feature by this group, 'bad-command' error occurs
      // vlan * / device-tracking
      container device-tracking {
        description
          "Obsolete - Configure device-tracking on the interface";
        presence "Attach default device-tracking on interface";
        status obsolete;
        leaf attach-policy {
          description
            "Obsolete - Apply a policy for feature device-tracking";
          status obsolete;
          type string;
          
          
          must "(/ios:native/ios:device-tracking/ios-dt:policy[ios-dt:word=current()])" {
            error-message "Create policy first, then attach policy; Detach policy first then remove policy";
          }
        }
      }
  }

  grouping config-device-tracking-grouping {
    list policy {
      description
        "Configure a policy for feature device-tracking";
      key "word";
      leaf word {
        type string;
      }
      container device-role {
        description
          "Sets the role of the device attached to the port";
        choice device-role-choice {
          case node {
            leaf node {
              type boolean;
              default true;
            }
          }
          case switch {
            leaf switch {
              type empty;
            }
          }
        }
      }
      container prefix-glean {
        presence "Enable prefix-glean";
        description
          "Glean prefixes in RA and DHCP-PD traffic";
      }
      container destination-glean {
        description
        "binding recovery by data traffic destination address gleaning";
        leaf log-only {
            type empty;
        }
      }
      container protocol {
        description
          "Set the protocol to glean (default all)";
        leaf udp {
          type boolean;
        }
        leaf arp {
          description
            "Glean addresses in ARP packets";
          type boolean;
          default true;
        }
        leaf dhcp4 {
          description
            "Glean addresses in DHCPv4 packets";
          type boolean;
          default true;
        }
        leaf dhcp6 {
          description
            "Glean addresses in DHCPv6 packets";
          type boolean;
          default true;
        }
        leaf ndp {
          description
            "Glean addresses in NDP packets";
          type boolean;
          default true;
        }
      }
      container tracking {
        description
          "Override default tracking behavior";
        container enable {
          presence "true";
          container reachable-lifetime {
            description
              "Time entry is kept REACHABLE";
            leaf seconds {
              description
                "Seconds";
              type uint32 {
                range "1..86400";
              }
            }
          }
        }
        leaf disable {
          description
            "Tracking on or off";
          type empty;
        }
      }
      container limit {
        description
          "Specifies a limit";
        leaf address-count {
          description
            "Configure maximum address per port";
          type uint16 {
            range "1..32000";
          }
        }
      }
      container security-level {
        description
          "setup security level";
        leaf glean {
          description
            "glean addresses passively";
          type empty;
        }
      }
      leaf trusted-port {
        description "setup trusted port";
        type empty;
      }
    }
    container tracking { 
      presence "true";
      container auto-source {
        presence "true";
        container fallback {
          description
            "Specify IP and MASK to use as last resort";
          choice ip-subnet-choice {
            case ip-addr-and-mask {
              description "IPv4 and MASK of fallback source";
              container ipv4-subnet-type1 {
                leaf ipv4 {
                  description
                    "IPv4 address";
                  type inet:ipv4-address;
                }
                leaf mask {
                  description
                    "IP prefix mask";
                  type inet:ipv4-address;
                }
                leaf override {
                  description
                    "Do not select source address from device track table";
                  type empty;
                }
              }
            }
            case ip-addr-and-prefix-len {
              description "IPv4 and MASK of fallback source";
              container ipv4-subnet-type2 {
                leaf ipv4-prefix-name {
                  description
                    "ip address/length <network>/<length>, e.g., 192.168.12.12/16";
                  type ios-types:ipv4-address-slash-prefix-len; 
                }
                leaf override {
                  description
                    "Do not select source address from device track table";
                  type empty;
                }
              }
            }
          } 
        }      
        leaf override {
          description
            "Do not select source address from device track table";
          type empty;
        }
      }
      leaf retry-interval {
        description "Interval time  between two probing";
        type uint16 {
            range "1..3600";
        }
      } 
    }
  }

  grouping config-ip-device-grouping {
    container tracking {
      description
        "Device tracking";
      presence "true";
      container probe {
        description
          "Probe";
        container auto-source {
          description
            "Probe source selection algorithm";
          presence "true";
          container fallback {
            description
              "Specify IP and MASK to use as last resort";
            leaf src-ip {
              description
                "IP and MASK of fallback source";
              type inet:ipv4-address;
            }
            leaf mask {
              description
                "IP prefix mask";
              type inet:ipv4-address;
            }
          }
          leaf override {
            description
              "Do not select source address from device track table";
            type empty;
          }
        }
        leaf count {
          description
            "Probe count";
          type uint8;
        }
        leaf delay {
          description
            "Probe delay";
          type uint8 {
            range "1..120";
          }
        }
        leaf interval {
          description
            "Probe interval";
          type uint32 {
            range "30..1814400";
          }
        }
      }
      leaf trace-buffer {
        description
          "Enable Tracing Support";
        type empty;
      }
    }
  }

  /////////////////////////////////////////////////////////
  // native / device-tracking
  /////////////////////////////////////////////////////////
  augment "/ios:native/ios:device-tracking" {
    uses config-device-tracking-grouping; 
  }

  /////////////////////////////////////////////////////////
  // native / ip / device
  /////////////////////////////////////////////////////////
  augment "/ios:native/ios:ip/ios:device" {
    uses config-ip-device-grouping {
      if-feature ios-features:device-tracking;    
    }
  }
}
