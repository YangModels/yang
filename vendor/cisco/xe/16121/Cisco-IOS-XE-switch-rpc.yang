module Cisco-IOS-XE-switch-rpc {
  namespace "http://cisco.com/ns/yang/Cisco-IOS-XE-switch-rpc";
  prefix ios-xe-sw-rpc;

  import cisco-semver {
    prefix cisco-semver;
  }
 

  import Cisco-IOS-XE-rpc {
    prefix ios-xe-rpc;
  }

  organization "Cisco Systems";

  contact
    <mailto:cs-yang@cisco.com>;

  description
    "NED Switch RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2019-02-11 {
    description
      "increased stacking switch range from 9 to 16";
  }

  revision 2018-12-06 {
    description
      "created for NED RPC modularisation";
  }

  rpc switch {
    input {
      leaf switch-number-drop-node-name {
        mandatory true;
        type uint8 {
          range "1..16";
         }
      }
      choice pri-renum-stack {
        mandatory true;
        case priority-case {
          leaf priority {
	    description 
	      "<1-15>  Switch Priority";
            type uint8 {
	      range "1..15";
            }
          }
	}
	case renumver-case {
          leaf renumber {
	    description 
	      "<1-16>  New number of the Switch";
            type uint8 {
	      range "1..16";
            }
          }
	}
	case stack-case {
	  container statck {
            leaf port {
	      description 
	        "<1-2>  Stack port number to enable/disable";
              type uint8 {
	        range "1..2";
              }
            }
          }
        }
      }
    }
    output {
      uses ios-xe-rpc:cisco-xe-rpc-output; 
    }
  }
}
