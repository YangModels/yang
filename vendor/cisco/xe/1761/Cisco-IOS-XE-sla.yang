module Cisco-IOS-XE-sla {
  namespace "http://cisco.com/ns/yang/Cisco-IOS-XE-sla";
  prefix ios-sla;

  import cisco-semver {
    prefix cisco-semver;
  }
  import ietf-inet-types {
    prefix inet;
  }
  import Cisco-IOS-XE-native {
    prefix ios;
  }
  import Cisco-IOS-XE-types {
    prefix ios-types;
  }
  import Cisco-IOS-XE-features {
    prefix ios-features;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Native Service Level Agreements (SLA) Yang model.
     Copyright (c) 2016, 2018-2019, 2021 by Cisco Systems, Inc.
     All rights reserved.";

  revision 2021-07-01 {
    description
      "- Added status deprecated for the responder container and the nodes under it
       - Added new nodes to support responder, twamp and twamp-light configuration";
    cisco-semver:module-version "4.3.0";
  }
  revision 2021-03-01 {
    description
      "- Extended the model to support TWAMP Light configuration
       - Updated the dependency between sla entry list, schedule list and
         reaction-configuration list
       - Updated the dependency between mpls-lsp-monitor entry list, schedule list and
         reaction-configuration list
       - Updated the dependency between ethernet-monitor entry list, schedule list and
         reaction-configuration list";
    cisco-semver:module-version "4.2.0";
  }
  revision 2020-11-01 {
    description
      "- Extended the model to support secure http operation";
    cisco-semver:module-version "4.1.0";
  }
  revision 2020-07-01 {
    description
      "- Added if-feature for service performance container";
    cisco-semver:module-version "4.0.0";
  }
  revision 2020-03-01 {
    description
      "- Added mandatory true for some of the leaves
       - Added status obsolete for the child nodes under ethernet-monitor-modification-configuration
       - Added status obsolete for the child nodes under modification-configuration";
    cisco-semver:module-version "3.0.0";
  }
  revision 2019-11-01 {
    description
      "- Extended the model to support mpls probe and group schedule
       - Extended the model to support permanent port responder and twamp responder
       - Added status obsolete for container jitter and it's child nodes
       - Added status obsolete for choice vrf";
    cisco-semver:module-version "2.0.0";
  }
  revision 2019-07-01 {
    description
      "- Establish semantic version baseline
       - Extended the model to support probe - 'auto ip sla mpls-lsp-monitor'
       - Extended the model to support probe - 'service-performance'
       - Support for ethernet echo probe
       - Support for ethernet jitter probe
       - Support for ethernet y1731 probe";
    cisco-semver:module-version "1.0.0";
  }
  revision 2018-11-07 {
    description
      "Cleanup spelling errors in description statements";
  }
  revision 2018-08-03 {
    description
      "Added loss support for ethernet-y1731.";
  }
  revision 2018-07-04 {
    description
      "Add icmp-jitter, tcp-connect, dns cases and its options. Add
       other options for the existing cases.";
  }
  revision 2018-06-28 {
    description
      "Added leafref for ip sla schedule entry-number";
  }
  revision 2018-05-23 {
    description
      "Add http-raw request support and the other options for http probe";
  }
  revision 2018-04-11 {
    description
      "Add source-port, control and codec options for ip sla udp-jitter probe";
  }
  revision 2018-01-15 {
    description
      "Add ethernet case and its options under ip sla";
  }
  revision 2017-08-31 {
    description
      "Add dependency between ip sla schedule and ip sla reaction configuration";
  }
  revision 2017-08-03 {
    description
      "Add dependency between ip sla schedule and ip sla entry";
  }
  revision 2017-02-07 {
    description
      "Initial revision";
  }

  grouping ip-sla-sub-mode-commands-grouping {
    leaf owner {
      description
        "Owner of Entry";
      type string;
    }
    leaf tag {
      description
        "User defined tag";
      type string;
    }
    leaf frequency {
      description
        "Frequency of an operation";
      units "seconds";
      type uint32 {
        range "1..604800";
      }
      default "60";
    }
    leaf timeout {
      description
        "Timeout of an operation";
      units "miliseconds";
      type uint32 {
        range "0..604800000";
      }
      default "5000";
    }
    leaf threshold {
      description
        "Operation threshold in milliseconds";
      units "miliseconds";
      type uint32 {
        range "0..60000";
      }
      default "5000";
    }
  }

  grouping ip-sla-full-history-grouping {
    container history {
      description
        "History and Distribution Data";
      container enhanced {
        description
          "Enable enhanced history collection";
        leaf interval {
          description
            "Aggregation interval";
          type uint16 {
            range "1..3600";
          }
          default "900";
        }
        leaf buckets {
          description
            "Number of buckets to collect data";
          type uint8 {
            range "1..100";
          }
          default "100";
        }
      }
      leaf buckets-kept {
        description
          "Maximum number of history buckets to collect";
        type uint8 {
          range "1..60";
        }
        default "50";
      }
      leaf distributions-of-statistics-kept {
        description
          "Maximum number of statistics distribution buckets to capture";
        type uint8 {
          range "1..20";
        }
        default "1";
      }
      leaf filter {
        description
          "Add operation to History when...";
        type enumeration {
          enum all;
          enum failures;
          enum none;
          enum overThreshold;
        }
        default "none";
      }
      leaf hours-of-statistics-kept {
        description
          "Maximum number of statistics hour groups to capture";
        type uint8 {
          range "0..25";
        }
        default "2";
      }
      leaf lives-kept {
        description
          "Maximum number of history lives to collect";
        type uint8 {
          range "0..2";
        }
        default "0";
      }
      leaf statistics-distribution-interval {
        description
          "Statistics distribution interval size";
        type uint8 {
          range "1..100";
        }
        default "20";
      }
    }
  }

  grouping ip-sla-history-without-enhanced-grouping {
    container history {
      description
        "History and Distribution Data";
      leaf buckets-kept {
        description
          "Maximum number of history buckets to collect";
        type uint8 {
          range "1..60";
        }
        default "50";
      }
      leaf distributions-of-statistics-kept {
        description
          "Maximum number of statistics distribution buckets to capture";
        type uint8 {
          range "1..20";
        }
        default "1";
      }
      leaf filter {
        description
          "Add operation to History when...";
        type enumeration {
          enum all;
          enum failures;
          enum none;
          enum overThreshold;
        }
        default "none";
      }
      leaf hours-of-statistics-kept {
        description
          "Maximum number of statistics hour groups to capture";
        type uint8 {
          range "0..25";
        }
      }
      leaf lives-kept {
        description
          "Maximum number of history lives to collect";
        type uint8 {
          range "0..2";
        }
      }
      leaf statistics-distribution-interval {
        description
          "Statistics distribution interval size";
        type uint8 {
          range "1..100";
        }
      }
    }
  }

  grouping ip-sla-jitter-percentile {
    container percentile {
      description
        "Set percentile statistics levels";
      leaf jitteravg {
        description
          "% of Average Jitter values to use (default 100%)";
        type uint8 {
          range "90..100";
        }
        default "100";
      }
      leaf jitterds {
        description
          "% of destination to source Jitter value to use (default 100%)";
        type uint8 {
          range "90..100";
        }
        default "100";
      }
      leaf jittersd {
        description
          "% of source to destination value to use (default 100%)";
        type uint8 {
          range "90..100";
        }
        default "100";
      }
      leaf owds {
        description
          "% of One way destination to source Jitter value to use (default 100%)";
        type uint8 {
          range "90..100";
        }
        default "100";
      }
      leaf owsd {
        description
          "% of One way source to destination value to use (default 100%)";
        type uint8 {
          range "90..100";
        }
        default "100";
      }
      leaf rtt {
        description
          "% of Round trip time value to use (default 100%)";
        type uint8 {
          range "90..100";
        }
        default "100";
      }
    }
  }

  grouping ip-sla-path-echo-grouping {
    leaf paths-of-statistics-kept {
      description
        "Maximum number of statistics paths to capture";
      type uint8 {
        range "1..128";
      }
      default "5";
    }
    leaf samples-of-history-kept {
      description
        "Maximum number of history samples to collect";
      type uint8 {
        range "1..30";
      }
      default "16";
    }
    leaf hops-of-statistics-kept {
      description
        "Maximum number of statistics hops to capture";
      type uint8 {
        range "1..30";
      }
      default "16";
    }
    leaf-list lsr-path {
      description
        "Loose Source Routing Path";
      type union {
        type string;
        type inet:ipv4-address;
      }
    }
    leaf request-data-size {
      description
        "Request data size";
      type uint32 {
        range "0..16384";
      }
      default "28";
    }
    choice tos-param {
      case tos {
        leaf tos {
          description
            "Type Of Service";
          type uint8 {
            range "0..255";
          }
          default "0";
        }
      }
      case traffic-class {
        leaf traffic-class {
          description
            "Traffic class";
          type uint8 {
            range "0..255";
          }
        }
      }
    }
    leaf verify-data {
      description
        "Verify data";
      type boolean;
    }
    leaf vrf {
      description
        "Configure IP SLAs for a VPN Routing/Forwarding instance";
      type string;
    }
    uses ip-sla-history-without-enhanced-grouping;
  }

  grouping ip-sla-path-jitter-grouping {
    leaf-list lsr-path {
      description
        "Loose Source Routing Path";
      type union {
        type string;
        type inet:ipv4-address;
      }
    }
    leaf request-data-size {
      description
        "Request data size";
      type uint32 {
        range "0..16384";
      }
      default "28";
    }
    choice tos-param {
      case tos {
        leaf tos {
          description
            "Type Of Service";
          type uint8 {
            range "0..255";
          }
        }
      }
      case traffic-class {
        leaf traffic-class {
          description
            "Traffic class";
          type uint8 {
            range "0..255";
          }
        }
      }
    }
    leaf flow-label {
      description
        "Flow Label Value for IPv6 destination";
      type uint64 {
        range "0..1048575";
      }
    }
    leaf verify-data {
      description
        "Verify data";
      type boolean;
    }
    leaf vrf {
      description
        "Configure IP SLAs for a VPN Routing/Forwarding instance";
      type string;
    }
  }

  grouping ip-sla-default-path-jitter-grouping {
    leaf frequency {
      description
        "Frequency of an operation";
      type empty;
    }
    leaf lsr-path {
      description
        "Loose Source Routing Path";
      type empty;
    }
    leaf owner {
      description
        "Owner of Entry";
      type empty;
    }
    leaf request-data-size {
      description
        "Request data size";
      type empty;
    }
    leaf tag {
      description
        "User defined tag";
      type empty;
    }
    leaf threshold {
      description
        "Operation threshold in milliseconds";
      type empty;
    }
    leaf timeout {
      description
        "Timeout of an operation";
      type empty;
    }
    leaf tos {
      description
        "Type Of Service";
      type empty;
    }
    leaf verify-data {
      description
        "Verify data";
      type boolean;
    }
    leaf vrf {
      description
        "Configure IP SLAs for a VPN Routing/Forwarding instance";
      type empty;
    }
  }

  grouping ip-sla-udp-jitter-grouping {
    container history {
      description
        "History and Distribution Data";
      leaf distributions-of-statistics-kept {
        description
          "Maximum number of statistics distribution buckets to capture";
        type uint8 {
          range "1..20";
        }
        default "1";
      }
      container enhanced {
        description
          "Enable enhanced history collection";
        leaf interval {
          description
            "Aggregation interval";
          type uint16 {
            range "1..3600";
          }
        }
        leaf buckets {
          description
            "Number of buckets to collect data";
          type uint8 {
            range "1..100";
          }
        }
      }
      leaf hours-of-statistics-kept {
        description
          "Maximum number of statistics hour groups to capture";
        type uint8 {
          range "0..25";
        }
        default "2";
      }
      leaf statistics-distribution-interval {
        description
          "Statistics distribution interval size";
        type uint8 {
          range "1..100";
        }
        default "20";
      }
    }
    container control_sub_mode {
      container control {
        description
          "Set control protocol parameters";
        leaf retry {
          description
            "How often the control message should do a retry (default 3 times)";
          type uint8 {
            range "1..5";
          }
          default "3";
        }
        leaf timeout {
          description
            "How long to wait for control message timeout (default 5 seconds)";
          type uint16 {
            range "1..10000";
          }
          default "5";
        }
      }
    }
    leaf data-pattern {
      status obsolete;
      description
        "Data Pattern in Hex 0-FFFFFFFF (OBSOLETE)";
      type string;
    }
    leaf request-data-size {
      description
        "Number of bytes in payload";
      type uint16 {
        range "16..17512";
      }
      default "32";
    }
    leaf response-data-size {
      description
        "Number of bytes in response payload";
      type uint16 {
        range "20..17512";
      }
    }
    choice tos-param {
      case tos {
        leaf tos {
          description
            "Type Of Service";
          type uint8 {
            range "0..255";
          }
        }
      }
      case traffic-class {
        leaf traffic-class {
          description
            "Traffic class";
          type uint8 {
            range "0..255";
          }
        }
      }
    }
    leaf vrf {
      description
        "Configure IP SLAs for a VPN Routing/Forwarding instance";
      type string;
    }
    leaf verify-data {
      description
        "Verify data";
      type boolean;
    }
    leaf precision {
      description
        "Set precision of measurement";
      type enumeration {
        enum microseconds;
        enum milliseconds;
      }
      default "milliseconds";
    }
    leaf optimize {
      description
        "Optimize timestamp of measurement";
      type enumeration {
        enum timestamp;
      }
    }
    leaf enhanced {
      description
        "Improve the accuracy of measurement";
      type enumeration {
        enum timestamp;
      }
    }
    leaf operation-packet-priority {
      description
        "Set operation packet properties";
      type enumeration {
        enum high;
        enum normal;
      }
      default "normal";
    }
    container clock-tolerance-config {
      description
        "Set acceptable clock synchronization error";
      container ntp {
        description
          "Acceptable clock synchronization error due to NTP";
        container oneway {
          description
            "Acceptable clock synchronization error in one-way measurement";
          choice clock-tolerance-param {
            case absolute-type {
              leaf absolute {
                description
                  "Acceptable error in microseconds";
                type uint32 {
                  range "0..100000";
                }
              }
            }
            case percent-type {
              leaf percent {
                description
                  "Acceptable error as percent of value measured";
                type uint8 {
                  range "0..100";
                }
              }
            }
          }
        }
      }
    }
    container clock-tolerance {
      status deprecated;
      description
        "Set acceptable clock synchronization error. (DEPRECATED, use clock-tolerance-config container)";
      presence "true";
      container ntp {
        status deprecated;
        description
          "Acceptable clock synchronization error due to NTP";
        presence "true";
        container oneway {
          status deprecated;
          description
            "Acceptable clock synchronization error in one way measurement";
          choice clock-tolerance-param {
            status deprecated;
            case absolute-type {
              status deprecated;
              leaf absolute {
                status deprecated;
                description
                  "Acceptable error in microseconds";
                type uint32 {
                  range "0..100000";
                }
              }
            }
            case percent-type {
              status deprecated;
              leaf percent {
                status deprecated;
                description
                  "Acceptable error as percent of value measured";
                type uint8 {
                  range "0..100";
                }
              }
            }
          }
        }
      }
    }
  }

  grouping ip-sla-udp-echo-grouping {
    uses ip-sla-full-history-grouping;
    leaf request-data-size {
      description
        "Number of bytes in payload";
      type uint16 {
        range "4..1500";
      }
      default "16";
    }
    choice tos-param {
      case tos {
        leaf tos {
          description
            "Type Of Service";
          type uint8 {
            range "0..255";
          }
        }
      }
      case traffic-class {
        leaf traffic-class {
          description
            "Traffic class";
          type uint8 {
            range "0..255";
          }
        }
      }
    }
    leaf verify-data {
      description
        "Verify data";
      type boolean;
    }
    leaf vrf {
      description
        "Configure IP SLAs for a VPN Routing/Forwarding instance";
      type string;
    }
    leaf data-pattern {
      description
        "Data Pattern in Hex 0-FFFFFFFF";
      type string;
    }
  }

  grouping ip-sla-ethernet-delay-grouping {
    container aggregate {
      description
        "Aggregate parameters";
      leaf interval {
        description
          "Specify interval period";
        type uint32 {
          range "1..65535";
        }
      }
    }
    container history {
      description
        "History parameters";
      leaf interval {
        description
          "Specify number of intervals";
        type uint8 {
          range "1..10";
        }
      }
    }
  }

  grouping ip-sla-ethernet-distribution-grouping {
    container distribution {
      description
        "Specify the distribution statistics parameters";
      container delay {
        description
          "Specify delay distribution parameters";
        container one-way {
          leaf one-way {
            description
              "Specify one-way distribution parameters";
            type uint8 {
              range "1..10";
            }
          }
          leaf bin-upper-boundry {
            description
              "Specify a comma separated list of bin upper boundaries in micro-second";
            type string;
          }
        }
        container two-way {
          when "../../../ios-sla:name='DMM' or
                ../../../ios-sla:name='DMMv1'";
          leaf two-way {
            description
              "Specify two-way distribution parameters";
            type uint8 {
              range "1..10";
            }
          }
          leaf bin-upper-boundry {
            description
              "Specify a comma separated list of bin upper boundaries in micro-second";
            type string;
          }
        }
      }
      container delay-variation {
        description
          "Specify delay-variation distribution parameters";
        container one-way {
          leaf one-way {
            description
              "Specify one-way distribution parameters";
            type uint8 {
              range "1..10";
            }
          }
          leaf bin-upper-boundry {
            description
              "Specify a comma separated list of bin upper boundaries in micro-second";
            type string;
          }
        }
        container two-way {
          when "../../../ios-sla:name='DMM' or
                ../../../ios-sla:name='DMMv1'";
          leaf two-way {
            description
              "Specify two-way distribution parameters";
            type uint8 {
              range "1..10";
            }
          }
          leaf bin-upper-boundry {
            description
              "Specify a comma separated list of bin upper boundaries in micro-second";
            type string;
          }
        }
      }
    }
  }

  grouping ip-sla-ethernet-y1731-grouping {
    choice delay-or-loss {
      case delay-case {
        container delay {
          description
            "Y1731 Delay and Delay Variation Operation";
          choice sender-or-receiver {
            case sender-case {
              container sender {
                leaf name {
                  description
                    "Y1731 Delay option";
                  mandatory true;
                  type enumeration {
                    enum 1DM;
                    enum DMM;
                    enum DMMv1;
                  }
                }
                leaf burst {
                  description
                    "Enable bursting of delay frames";
                  type empty;
                }
                uses ip-sla-ethernet-delaysender-loss-common-grouping;
                container clock {
                  description
                    "Specify clock parameters";
                  when "../ios-sla:name='DMM' or
                        ../ios-sla:name='DMMv1'";
                  leaf sync {
                    description
                      "Clocks are in sync on sender and responder";
                    type boolean;
                  }
                }
                uses ip-sla-ethernet-distribution-grouping;
                container frame {
                  description
                    "Specify frame parameters";
                  leaf interval {
                    description
                      "Specify inter-frame period";
                    type frame-interval-type;
                  }
                  leaf size {
                    description
                      "Specify payload size in 4 octet increments";
                    type uint16 {
                      range "64..1400";
                    }
                  }
                  leaf burst {
                    description
                      "Number of frames to send per burst";
                    when '(../../burst)';
                    type uint16 {
                      range "1..65535";
                    }
                  }
                  leaf offset {
                    description
                      "Specify the frame offset to be used for calculations";
                    when "../../ios-sla:name='DMM' or
                          ../../ios-sla:name='DMMv1' or
                          ../../../ios-sla:receive/ios-sla:name='1DM'";
                    type uint8 {
                      range "1..10";
                    }
                  }
                }
              }
            }
            case receive-case {
              container receive {
                leaf name {
                  description
                    "Y1731 Delay option";
                  mandatory true;
                  type enumeration {
                    enum 1DM;
                  }
                }
                leaf domain {
                  description
                    "Specify the Ethernet OAM domain";
                  mandatory true;
                  type string;
                }
                choice evc-or-vlan {
                  mandatory true;
                  leaf evc {
                    description
                      "Specify the Ethernet Virtual Circuit Identifier";
                    type string;
                  }
                  leaf vlan {
                    description
                      "Specify the VLAN";
                    type uint16 {
                      range "1..4096";
                    }
                  }
                }
                leaf cos {
                  description
                    "Specify the Class of Service";
                  mandatory true;
                  type uint8 {
                    range "0..7";
                  }
                }
                choice mac-or-mpid {
                  mandatory true;
                  leaf mac-address {
                    description
                      "Specify the remote mac-address";
                    type ios-types:cisco-mac-address-type;
                  }
                  leaf mpid {
                    description
                      "Specify the remote MPID";
                    type uint16 {
                      range "1..8191";
                    }
                  }
                }
                uses ip-sla-ethernet-sub-command-grouping;
                container aggregate {
                  description
                    "Aggregate parameters";
                  leaf interval {
                    description
                      "Specify interval period";
                    type uint16 {
                      range "1..65535";
                    }
                  }
                }
                container frame {
                  description
                    "Specify frame parameters";
                  leaf offset {
                    description
                      "Specify the frame offset to be used for calculations";
                    type uint8 {
                      range "1..10";
                    }
                  }
                }
                container distribution {
                  description
                    "Specify the distribution statistics parameters";
                  container delay {
                    description
                      "Specify delay distribution parameters";
                    container one-way {
                      leaf one-way {
                        description
                          "Specify one-way distribution parameters";
                        type uint8 {
                          range "1..10";
                        }
                      }
                      leaf bin-upper-boundry {
                        description
                          "Specify a comma separated list of bin upper boundaries in micro-second";
                        type string;
                      }
                    }
                  }
                  container delay-variation {
                    description
                      "Specify delay-variation distribution parameters";
                    container one-way {
                      leaf one-way {
                        description
                          "Specify one-way distribution parameters";
                        type uint8 {
                          range "1..10";
                        }
                      }
                      leaf bin-upper-boundry {
                        description
                          "Specify a comma separated list of bin upper boundaries in micro-second";
                        type string;
                      }
                    }
                  }
                }
              }
            }
          }
        }
      }
      case loss-case {
        container loss {
          description
            "Y1731 Loss Operation";
          container wrapper-container {
            leaf name {
              description
                "Y1731 Delay option";
              mandatory true;
              type enumeration {
                enum LMM {
                  description
                    "Loss Measurement Message/Loss Measurement Reply frames";
                }
                enum SLM {
                  description
                    "Synthetic Loss Message/Synthetic Loss Reply frames";
                }
              }
            }
            leaf burst {
              description
                "Enable bursting of delay frames. Applicable only to SLM option";
              when "../name='SLM'";
              type empty;
            }
            uses ip-sla-ethernet-delaysender-loss-common-grouping;
            container frame {
              description
                "Specify frame parameters";
              leaf interval {
                description
                  "Specify inter-frame period";
                type frame-interval-type;
              }
              leaf consecutive {
                description
                  "Specify the consecutive frames to be used for calculations";
                type uint16 {
                  range "1..10";
                }
              }
              leaf size {
                description
                  "Specify payload size in 4 octet increments";
                when "../../name='SLM'";
                type uint16 {
                  range "64..1400";
                }
              }
              leaf burst {
                description
                  "Number of frames to send per burst";
                when '(../../burst)';
                type uint16 {
                  range "1..65535";
                }
              }
            }
            container availability {
              description
                "Specify the availability parameters";
              container algorithm {
                description
                  "Specify the algorithm to use";
                leaf sliding-window {
                  description
                    "Use a sliding window";
                  type boolean;
                }
                leaf static-window {
                  description
                    "Use a static window";
                  type boolean;
                }
              }
            }
          }
        }
      }
    }
  }

  grouping ip-sla-ethernet-delaysender-loss-common-grouping {
    leaf domain {
      description
        "Specify the Ethernet OAM domain";
      mandatory true;
      type string;
    }
    choice evc-or-vlan {
      mandatory true;
      leaf evc {
        description
          "Specify the Ethernet Virtual Circuit Identifier";
        type string;
      }
      leaf vlan {
        description
          "Specify the VLAN";
        type uint16 {
          range "1..4096";
        }
      }
    }
    choice mac-or-mpid {
      mandatory true;
      leaf mac-address {
        description
          "Specify the remote mac-address";
        type ios-types:cisco-mac-address-type;
      }
      leaf mpid {
        description
          "Specify the remote MPID";
        type uint16 {
          range "1..8191";
        }
      }
    }
    leaf cos {
      description
        "Specify the Class of Service";
      mandatory true;
      type uint8 {
        range "0..7";
      }
    }
    container source {
      description
        "Specify the local MPID or MAC-Address";
      choice mac-or-mpid {
        mandatory true;
        leaf mac-address {
          description
            "Specify the local mac-address";
          type ios-types:cisco-mac-address-type;
        }
        leaf mpid {
          description
            "Specify the local MPID";
          type uint16 {
            range "1..8191";
          }
        }
      }
    }
    uses ip-sla-ethernet-sub-command-grouping;
    container aggregate {
      description
        "Aggregate parameters";
      container interval {
        description
          "Specify interval period";
        leaf interval-period {
          description
            "Specify interval period";
          when 'not (current()/../../../ios-sla:burst)';
          type uint32 {
            range "1..65535";
          }
        }
        leaf burst-cycles {
          description
            "Specify number of burst cycles";
          when 'current()/../../../ios-sla:burst';
          type uint16 {
            range "1..900";
          }
        }
      }
    }
    leaf frequency {
      description
        "Number of seconds after which to repeat burst";
      when 'current()/../ios-sla:burst';
      type uint16 {
        range "1..900";
      }
      default "60";
    }
  }

  grouping ip-sla-ethernet-sub-command-grouping {
    container history {
      description
        "History parameters";
      leaf interval {
        description
          "Specify number of intervals";
        type uint8 {
          range "1..10";
        }
      }
    }
    leaf max-delay {
      description
        "Specify the max delay";
      when "../ios-sla:name = 'DMM' or
            ../ios-sla:name = 'DMMv1' or
            ../ios-sla:name = '1DM' or
            ../ios-sla:name = 'LMM'";
      type uint16 {
        range "1..65535";
      }
    }
    leaf owner {
      description
        "Specify operation owner";
      type string;
    }
  }

  grouping ip-sla-service-performance-packet-direction-sub-command-grouping {
    container packet {
      description
        "Packet Profiles";
      leaf outer-vlan {
        description
          "Specify the Outer VLAN";
        type uint16 {
          range "0..4095";
        }
      }
      leaf packet-size {
        description
          "Packet Size";
        type packet-size-type;
      }
    }
  }

  grouping ip-sla-service-performance-traffic-direction-sub-command-grouping {
    container traffic {
      description
        "Service Performance traffic profile";
      leaf direction {
        description
          "Traffic direction";
        type enumeration {
          enum external {
            description
              "external direction";
          }
          enum internal {
            description
              "internal direction";
          }
        }
      }
      leaf cbs {
        description
          "Committed Burst Size";
        type uint32 {
          range "0..16000000";
        }
        units "Kbps";
      }
      leaf cir {
        description
          "Committed Information Rate. The range mentioned is for 10G interface. For 1G interface, the range is 0..1000000";
        type uint32 {
          range "0..10000000";
        }
        units "Kbps";
      }
      leaf ebs {
        description
          "Excess Burst Size";
        type uint32 {
          range "0..16000000";
        }
        units "Kbps";
      }
      leaf eir {
        description
          "Excess Information Rate. The range mentioned is for 10G interface. For 1G interface, the range is 0..1000000";
        type uint32 {
          range "0..10000000";
        }
        units "Kbps";
      }
      container rate-step {
        description
          "Rate Step";
        choice Kbps_or_pps {
          container Kbps {
            description
              "Kilobits per second rate. The range mentioned is for 10G interface. For 1G interface, the range is 0..1000000";
            leaf step1 {
              description
                "Step 1 (Kbps/pps)";
              type uint32 {
                range "1..10000000";
              }
              units "Kbps/pps";
            }
            leaf step2 {
              description
                "Step 2 (Kbps/pps), Step 2 >= Step 1";
              type uint32 {
                range "1..10000000";
              }
              units "Kbps/pps";
            }
            leaf step3 {
              description
                "Step 3 (Kbps/pps), Step 3 >= Step 2";
              type uint32 {
                range "1..10000000";
              }
              units "Kbps/pps";
            }
            leaf step4 {
              description
                "Step 4 (Kbps/pps), Step 4 >= Step 3";
              type uint32 {
                range "1..10000000";
              }
              units "Kbps/pps";
            }
            leaf step5 {
              description
                "Step 5 (Kbps/pps), Step 5 >= Step 4";
              type uint32 {
                range "1..10000000";
              }
              units "Kbps/pps";
            }
            leaf step6 {
              description
                "Step 6 (Kbps/pps), Step 6 >= Step 5";
              type uint32 {
                range "1..10000000";
              }
              units "Kbps/pps";
            }
            leaf step7 {
              description
                "Step 7 (Kbps/pps), Step 7 >= Step 6";
              type uint32 {
                range "1..10000000";
              }
              units "Kbps/pps";
            }
            leaf step8 {
              description
                "Step 8 (Kbps/pps), Step 8 >= Step 7";
              type uint32 {
                range "1..10000000";
              }
              units "Kbps/pps";
            }
            leaf step9 {
              description
                "Step 9 (Kbps/pps), Step 9 >= Step 8";
              type uint32 {
                range "1..10000000";
              }
              units "Kbps/pps";
            }
            leaf step10 {
              description
                "Step 10 (Kbps/pps), Step 10 >= Step 9";
              type uint32 {
                range "1..10000000";
              }
              units "Kbps/pps";
            }
          }
          container pps {
            description
              "Packet per second rate";
            leaf step1 {
              description
                "Step 1 (Kbps/pps)";
              type uint32 {
                range "1..15000000";
              }
              units "Kbps/pps";
            }
            leaf step2 {
              description
                "Step 2 (Kbps/pps), Step 2 >= Step 1";
              type uint32 {
                range "1..15000000";
              }
              units "Kbps/pps";
            }
            leaf step3 {
              description
                "Step 3 (Kbps/pps), Step 3 >= Step 2";
              type uint32 {
                range "1..15000000";
              }
              units "Kbps/pps";
            }
            leaf step4 {
              description
                "Step 4 (Kbps/pps), Step 4 >= Step 3";
              type uint32 {
                range "1..15000000";
              }
              units "Kbps/pps";
            }
            leaf step5 {
              description
                "Step 5 (Kbps/pps), Step 5 >= Step 4";
              type uint32 {
                range "1..15000000";
              }
              units "Kbps/pps";
            }
            leaf step6 {
              description
                "Step 6 (Kbps/pps), Step 6 >= Step 5";
              type uint32 {
                range "1..15000000";
              }
              units "Kbps/pps";
            }
            leaf step7 {
              description
                "Step 7 (Kbps/pps), Step 7 >= Step 6";
              type uint32 {
                range "1..15000000";
              }
              units "Kbps/pps";
            }
            leaf step8 {
              description
                "Step 8 (Kbps/pps), Step 8 >= Step 7";
              type uint32 {
                range "1..15000000";
              }
              units "Kbps/pps";
            }
            leaf step9 {
              description
                "Step 9 (Kbps/pps), Step 9 >= Step 8";
              type uint32 {
                range "1..15000000";
              }
              units "Kbps/pps";
            }
            leaf step10 {
              description
                "Step 10 (Kbps/pps), Step 10 >= Step 9";
              type uint32 {
                range "1..15000000";
              }
              units "Kbps/pps";
            }
          }
        }
      }
    }
  }

  grouping ip-sla-service-performance-measurement-type-sub-command-grouping {
    leaf direction {
      description
        "Measurement direction";
      type enumeration {
        enum external {
          description
            "external direction";
        }
        enum internal {
          description
            "internal direction";
        }
      }
    }
    container conform-color {
      description
        "conform-color";
    }
    container exceed-color {
      description
        "exceed-color";
    }
    leaf delay {
      description
        "Delay measurement";
      type empty;
    }
    leaf jitter {
      description
        "Jitter measurement";
      type empty;
    }
    leaf loss {
      description
        "loss measurement";
      type empty;
    }
    leaf receive {
      description
        "Received bytes/packets measurement";
      type empty;
    }
    leaf throughput {
      description
        "Throughput measurement";
      type empty;
    }
  }

  grouping ip-sla-service-performance-sub-command-grouping {
    container aggregation {
      description
        "Statistics aggregation";
      container interval {
        description
          "Statistics aggregation period";
        leaf buckets {
          description
            "interval statistic buckets";
          type uint8 {
            range "1..30";
          }
        }
      }
    }
    leaf description {
      description
        "Operation Description";
      type string;
    }
    container duration {
      description
        "Service Performance duration configuration";
      leaf time {
        description
          "Time based duration";
        type uint16 {
          range "10..40950";
        }
      }
    }
    container frequency_serv_perf {
      description
        "Scheduled frequency";
      leaf time {
        description
          "Frequency period";
        type uint32 {
          range "20..604800";
        }
      }
      container frequency-iteration {
        description
          "Frequency iteration configuration";
        leaf iteration {
          description
            "Iteration number";
          type uint8 {
            range "1..100";
          }
        }
        leaf delay {
          description
            "Delay between interactions";
          type uint8 {
            range "0..10";
          }
        }
      }
    }
    container loopback {
      description
        "loopback";
      container direction {
        description
          "loopback direction";
        leaf internal {
          description
            "internal direction";
          type boolean;
        }
        leaf external {
          description
            "external direction";
          type boolean;
        }
      }
    }
    container profile {
      description
        "Service Performance Profile";
    }
    container measurement-type {
      description
        "Measurement";
    }
    leaf signature {
      description
        "Payload Contents";
      type string;
    }
  }

  grouping config-ip-sla-react-threshold-type-grouping {
    container threshold-type {
      choice threshold-type-param {
        case xOfy-type {
          container xOfy {
            presence "true";
            leaf x-val {
              description
                "X value";
              type uint8 {
                range "1..16";
              }
            }
            leaf y-val {
              description
                "Y value";
              type uint8 {
                range "1..16";
              }
            }
          }
        }
        case average-type {
          container average {
            presence "true";
            description
              "Average over N attempts";
            leaf average-val {
              description
                "N value";
              type uint8 {
                range "1..16";
              }
            }
          }
        }
        case consecutive-type {
          container consecutive {
            presence "true";
            description
              "Consecutive occurrences";
            leaf consecutive-val {
              description
                "Number of occurrences";
              type uint8 {
                range "1..16";
              }
            }
          }
        }
        case immediate-type {
          leaf immediate {
            description
              "React immediately";
            type empty;
          }
        }
        case never-type {
          leaf never {
            description
              "Never react";
            type empty;
          }
        }
      }
    }
  }

  grouping config-ip-sla-react-threshold-value-grouping {
    container threshold-value {
      description
        "Threshold value";
      leaf upper-limit-val {
        description
          "Upper limit";
        type uint32 {
          range "1..60000";
        }
      }
      leaf lower-limit-val {
        description
          "Lower limit";
        type uint32 {
          range "1..60000";
        }
      }
    }
  }

  typedef hour-min {
    type string {
      pattern '(0[0-9]|1[0-9]|2[0-3]):[0-5][0-9]';
    }
  }

  typedef hour-min-sec {
    type string {
      pattern '(0[0-9]|1[0-9]|2[0-3]):[0-5][0-9]:[0-5][0-9]';
    }
  }

  typedef reply-dscp-bits-type {
    type enumeration {
      enum af11 {
        value 100;
        description
          "Match packets with AF11 dscp (001010)";
      }
      enum af12 {
        description
          "Match packets with AF12 dscp (001100)";
      }
      enum af13 {
        description
          "Match packets with AF13 dscp (001110)";
      }
      enum af21 {
        description
          "Match packets with AF21 dscp (010010)";
      }
      enum af22 {
        description
          "Match packets with AF22 dscp (010100)";
      }
      enum af23 {
        description
          "Match packets with AF23 dscp (010110)";
      }
      enum af31 {
        description
          "Match packets with AF31 dscp (011010)";
      }
      enum af32 {
        description
          "Match packets with AF32 dscp (011100)";
      }
      enum af33 {
        description
          "Match packets with AF33 dscp (011110)";
      }
      enum af41 {
        description
          "Match packets with AF41 dscp (100010)";
      }
      enum af42 {
        description
          "Match packets with AF42 dscp (100100)";
      }
      enum af43 {
        description
          "Match packets with AF43 dscp (100110)";
      }
      enum cs1 {
        description
          "Match packets with CS1(precedence 1) dscp (001000)";
      }
      enum cs2 {
        description
          "Match packets with CS2(precedence 2) dscp (010000)";
      }
      enum cs3 {
        description
          "Match packets with CS3(precedence 3) dscp (011000)";
      }
      enum cs4 {
        description
          "Match packets with CS4(precedence 4) dscp (100000)";
      }
      enum cs5 {
        description
          "Match packets with CS5(precedence 5) dscp (101000)";
      }
      enum cs6 {
        description
          "Match packets with CS6(precedence 6) dscp (110000)";
      }
      enum cs7 {
        description
          "Match packets with CS7(precedence 7) dscp (111000)";
      }
      enum default {
        description
          "Match packets with default dscp (000000)";
      }
      enum ef {
        description
          "Match packets with EF dscp (101110)";
      }
    }
  }

  typedef frame-interval-type {
    type enumeration {
      enum 10 {
        description
          "Frame interval 10 ms";
      }
      enum 100 {
        description
          "Frame interval 100 ms";
      }
      enum 1000 {
        description
          "Frame interval 1000 ms";
      }
      enum 20 {
        description
          "Frame interval 20 ms";
      }
      enum 25 {
        description
          "Frame interval 25 ms";
      }
      enum 50 {
        description
          "Frame interval 50 ms";
      }
    }
  }

  typedef packet-size-type {
    type enumeration {
      enum 1024 {
        description
          "1024 byte";
      }
      enum 128 {
        description
          "128 byte";
      }
      enum 1280 {
        description
          "1280 byte";
      }
      enum 1518 {
        description
          "1518 byte";
      }
      enum 256 {
        description
          "256 byte";
      }
      enum 512 {
        description
          "512 byte";
      }
      enum 64 {
        description
          "64 byte";
      }
      enum 9216 {
        description
          "9216 byte";
      }
      enum imix {
        description
          "imix packet size";
      }
    }
  }

  grouping mpls-lsp-monitor-type-common-grouping {
    leaf access-list {
      description
        "Apply Access-List";
      type uint16 {
        range "1..9";
      }
    }
    leaf delete-scan-factor {
      description
        "Scan Factor for automatic deletion";
      type uint32 {
        range "0..2147483647";
      }
      default "1";
    }
    leaf exp {
      description
        "EXP value";
      type uint8 {
        range "0..7";
      }
      default "0";
    }
    leaf lsp-selector {
      description
        "Local-Host address used to select the LSP";
      type inet:ipv4-address;
    }
    leaf scan-interval {
      description
        "Scan Interval for automatic discovery in minutes";
      type uint32 {
        range "1..70560";
      }
      default "240";
    }
    leaf tag {
      description
        "User defined tag";
      type string;
    }
    leaf threshold {
      description
        "Operation threshold in milliseconds";
      type uint16 {
        range "1..60000";
      }
      default "5000";
    }
    leaf timeout {
      description
        "Timeout of an operation";
      type uint32 {
        range "0..604800000";
      }
      default "5000";
    }
  }

  grouping mpls-lsp-monitor-type-echo-grouping {
    uses mpls-lsp-monitor-type-common-grouping;
    leaf force-explicit-null {
      description
        "force an explicit null label to be added";
      type boolean;
    }
    leaf reply-dscp-bits {
      description
        "DSCP bits in reply IP header";
      type union {
        type uint8 {
          range "0..63";
        }
        type reply-dscp-bits-type;
      }
    }
    container reply-mode {
      description
        "Reply for LSP echo request";
      leaf ipv4 {
        description
          "Send reply via IPv4";
        type boolean;
      }
      leaf router-alert {
        description
          "Send reply via IPv4 UDP with router alert";
        type boolean;
      }
    }
    leaf request-data-size {
      description
        "Request data size";
      type uint16 {
        range "100..1500";
      }
    }
    container secondary-frequency {
      description
        "Frequency to be used if there is any violation condition happens";
      leaf both {
        description
          "Enable secondary freq for timeout and connection loss";
        type uint32 {
          range "1..604800";
        }
      }
      leaf connection-loss {
        description
          "Enable secondary freq for connection loss";
        type uint32 {
          range "1..604800";
        }
      }
      leaf timeout {
        description
          "Enable secondary freq for timeout";
        type uint32 {
          range "1..604800";
        }
      }
    }
    leaf ttl {
      description
        "Time to live";
      type uint8 {
        range "1..255";
      }
      default "255";
    }
    container path-discover {
      description
        "IP SLAs LSP path discover configuration";
      presence "true";
      leaf force-explicit-null {
        description
          "Force an explicit null label to be added";
        type empty;
      }
      leaf hours-of-statistics-kept {
        description
          "Maximum number of statistics hour groups to capture";
        type uint8 {
          range "0..2";
        }
        default "2";
      }
      leaf interval {
        description
          "Interval in milliseconds";
        type uint32 {
          range "0..3600000";
        }
        units "microseconds";
        default "0";
      }
      leaf lsp-selector-base {
        description
          "Base 127/8 address to start the tree trace";
        type inet:ipv4-address;
        default "127.0.0.0";
      }
      leaf maximum-sessions {
        description
          "Number of concurrent active tree trace requests which can be submit at one time";
        type uint8 {
          range "0..15";
        }
        default "1";
      }
      leaf scan-period {
        description
          "Time period for finishing tree trace discovery in minutes";
        type uint16 {
          range "0..7200";
        }
        units "minutes";
        default "60";
      }
      leaf session-timeout {
        description
          "Timeout value for the tree trace requests in seconds";
        type uint16 {
          range "1..900";
        }
        units "seconds";
        default "120";
      }
      leaf timeout {
        description
          "Timeout for an MPLS Echo Request in seconds";
        type uint32 {
          range "1..604800000";
        }
        units "seconds";
        default "5";
      }
    }
  }

  grouping mpls-lsp-monitor-type-jitter-grouping {
    leaf access-list {
      status obsolete;
      description
        "Apply Access-List";
      type uint16 {
        range "1..9";
      }
    }
    leaf delete-scan-factor {
      status obsolete;
      description
        "Scan Factor for automatic deletion";
      type uint32 {
        range "0..2147483647";
      }
    }
    leaf exp {
      status obsolete;
      description
        "EXP value";
      type uint8 {
        range "0..7";
      }
    }
    leaf lsp-selector {
      status obsolete;
      description
        "Local-Host address used to select the LSP";
      type inet:ipv4-address;
    }
    leaf scan-interval {
      status obsolete;
      description
        "Scan Interval for automatic discovery in minutes";
      type uint32 {
        range "1..70560";
      }
    }
    leaf tag {
      status obsolete;
      description
        "User defined tag";
      type string;
    }
    leaf threshold {
      status obsolete;
      description
        "Operation threshold in milliseconds";
      type uint16 {
        range "1..60000";
      }
    }
    leaf timeout {
      status obsolete;
      description
        "Timeout of an operation";
      type uint32 {
        range "0..604800000";
      }
    }
    leaf dest-port {
      status obsolete;
      description
        "Destination Port";
      type uint16 {
        range "1..65535";
      }
    }
    leaf interval {
      status obsolete;
      description
        "Inter Packet Interval";
      type uint16 {
        range "4..60000";
      }
    }
    leaf num-packets {
      status obsolete;
      description
        "Number of Packets to be transmitted";
      type uint16 {
        range "1..60000";
      }
    }
    leaf request-data-size {
      status obsolete;
      description
        "Request data size";
      type uint16 {
        range "100..1500";
      }
    }
    container secondary-frequency {
      status obsolete;
      description
        "Frequency to be used if there is any violation condition happens";
      leaf both {
        status obsolete;
        description
          "Enable secondary freq for timeout and connection loss";
        type uint32 {
          range "1..604800";
        }
      }
      leaf connection-loss {
        status obsolete;
        description
          "Enable secondary freq for connection loss";
        type uint32 {
          range "1..604800";
        }
      }
      leaf timeout {
        status obsolete;
        description
          "Enable secondary freq for timeout";
        type uint32 {
          range "1..604800";
        }
      }
    }
    leaf verify-data {
      status obsolete;
      description
        "Verify data";
      type boolean;
    }
  }

  grouping mpls-lsp-monitor-type-pathEcho-grouping {
    uses mpls-lsp-monitor-type-common-grouping;
    leaf force-explicit-null {
      description
        "force an explicit null label to be added";
      type boolean;
    }
    leaf reply-dscp-bits {
      description
        "DSCP bits in reply IP header";
      type union {
        type uint8 {
          range "0..63";
        }
        type reply-dscp-bits-type;
      }
    }
    container reply-mode {
      description
        "Reply for LSP echo request";
      leaf ipv4 {
        description
          "Send reply via IPv4";
        type boolean;
      }
      leaf router-alert {
        description
          "Send reply via IPv4 UDP with router alert";
        type boolean;
      }
    }
    leaf ttl {
      description
        "Time to live";
      type uint8 {
        range "1..30";
      }
      default "30";
    }
  }

  grouping config-auto-ip-sla-react-action-type-grouping {
    leaf action-type {
      description
        "IP SLAs Reaction Action Type";
      type enumeration {
        enum none;
        enum trapOnly;
      }
      default "none";
    }
  }

  grouping config-auto-ip-sla-react-threshold-type-grouping {
    container threshold-type {
      description
        "Threshold Type";
      choice threshold-type-param {
        case consecutive-type {
          container consecutive {
            description
              "Consecutive Occurrences";
            presence "true";
            leaf consecutive-value {
              description
                "Number of Occurrences";
              type uint8 {
                range "1..16";
              }
              default "5";
            }
          }
        }
        case immediate-type {
          leaf immediate {
            description
              "React Immediately";
            type empty;
          }
        }
        case never-type {
          leaf never {
            description
              "Never React";
            type empty;
          }
        }
      }
    }
  }

  grouping config-auto-ip-sla-grouping {
    container auto {
      description
        "Configure Automation";
      container ip {
        description
          "Configure Auto IP Service Level Agreement";
        container sla {
          description
            "IP Service Level Agreement";
          container mpls-lsp-monitor {
            description
              "IP SLAs MPLS LSP Monitor Configuration";
            list entry {
              key "number";
              leaf number {
                type uint32;
              }
              container type {
                description
                  "Type of entry";
                choice type {
                  case echo-case {
                    container echo {
                      description
                        "Perform MPLS LSP Ping operation";
                      choice vrf {
                        case ipsla-vrf-all-case {
                          container ipsla-vrf-all {
                            description
                              "Configure IP SLAs MPLS LSP Monitor for all Virtual Private Networks";
                            presence "true";
                            uses mpls-lsp-monitor-type-echo-grouping;
                          }
                        }
                        case vrf_container-case {
                          container vrf_container {
                            leaf vrf {
                              description
                                "vrf Name";
                              mandatory true;
                              must '/ios:native/ios:vrf/ios:definition[ios:name=current()] or /ios:native/ios:ip/ios:vrf[ios:name=current()]' {
                                error-message "VRF must be created 1st, deleted last";
                              }
                              type string;
                            }
                            uses mpls-lsp-monitor-type-echo-grouping;
                          }
                        }
                      }
                    }
                  }
                  case jitter-case {
                    container jitter {
                      status obsolete;
                      description
                        "Perform MPLS Jitter operation";
                      choice vrf {
                        status obsolete;
                        case ipsla-vrf-all-case {
                          status obsolete;
                          container ipsla-vrf-all {
                            status obsolete;
                            description
                              "Configure IP SLAs MPLS LSP Monitor for all Virtual Private Networks";
                            presence "true";
                            uses mpls-lsp-monitor-type-jitter-grouping;
                          }
                        }
                        case vrf_container-case {
                          status obsolete;
                          container vrf_container {
                            status obsolete;
                            leaf vrf {
                              status obsolete;
                              description
                                "vrf Name";
                              must '/ios:native/ios:vrf/ios:definition[ios:name=current()] or /ios:native/ios:ip/ios:vrf[ios:name=current()]' {
                                error-message "VRF must be created 1st, deleted last";
                              }
                              type string;
                            }
                            uses mpls-lsp-monitor-type-jitter-grouping;
                          }
                        }
                      }
                    }
                  }
                  case pathEcho-case {
                    container pathEcho {
                      description
                        "Perform MPLS LSP Trace operation";
                      choice vrf {
                        case ipsla-vrf-all-case {
                          container ipsla-vrf-all {
                            description
                              "Configure IP SLAs MPLS LSP Monitor for all Virtual Private Networks";
                            presence "true";
                            uses mpls-lsp-monitor-type-pathEcho-grouping;
                          }
                        }
                        case vrf_container-case {
                          container vrf_container {
                            leaf vrf {
                              description
                                "vrf Name";
                              mandatory true;
                              must '/ios:native/ios:vrf/ios:definition[ios:name=current()] or /ios:native/ios:ip/ios:vrf[ios:name=current()]' {
                                error-message "VRF must be created 1st, deleted last";
                              }
                              type string;
                            }
                            uses mpls-lsp-monitor-type-pathEcho-grouping;
                          }
                        }
                      }
                    }
                  }
                }
              }
              container modification-configuration {
                status obsolete;
                leaf access-list {
                  status obsolete;
                  description
                    "Apply Access-List";
                  when "../../type/echo or
                        ../../type/jitter or
                        ../../type/pathEcho";
                  type uint16 {
                    range "1..9";
                  }
                }
                leaf delete-scan-factor {
                  status obsolete;
                  description
                    "Scan Factor for automatic deletion";
                  when "../../type/echo or
                        ../../type/jitter or
                        ../../type/pathEcho";
                  type uint32 {
                    range "0..2147483647";
                  }
                }
                leaf exp {
                  status obsolete;
                  description
                    "EXP value";
                  when "../../type/echo or
                        ../../type/jitter or
                        ../../type/pathEcho";
                  type uint8 {
                    range "0..7";
                  }
                }
                leaf lsp-selector {
                  status obsolete;
                  description
                    "Local-Host address used to select the LSP";
                  when "../../type/echo or
                        ../../type/jitter or
                        ../../type/pathEcho";
                  type inet:ipv4-address;
                }
                leaf scan-interval {
                  status obsolete;
                  description
                    "Scan Interval for automatic discovery in minutes";
                  when "../../type/echo or
                        ../../type/jitter or
                        ../../type/pathEcho";
                  type uint32 {
                    range "1..70560";
                  }
                }
                leaf tag {
                  status obsolete;
                  description
                    "User defined tag";
                  when "../../type/echo or
                        ../../type/jitter or
                        ../../type/pathEcho";
                  type string;
                }
                leaf threshold {
                  status obsolete;
                  description
                    "Operation threshold in milliseconds";
                  when "../../type/echo or
                        ../../type/jitter or
                        ../../type/pathEcho";
                  type uint16 {
                    range "1..60000";
                  }
                }
                leaf timeout {
                  status obsolete;
                  description
                    "Timeout of an operation";
                  when "../../type/echo or
                        ../../type/jitter or
                        ../../type/pathEcho";
                  type uint32 {
                    range "0..604800000";
                  }
                }
                leaf force-explicit-null {
                  status obsolete;
                  description
                    "force an explicit null label to be added";
                  when "../../type/echo or
                        ../../type/pathEcho";
                  type boolean;
                }
                leaf reply-dscp-bits {
                  status obsolete;
                  description
                    "DSCP bits in reply IP header";
                  when "../../type/echo or
                        ../../type/pathEcho";
                  type union {
                    type uint8 {
                      range "0..63";
                    }
                    type reply-dscp-bits-type;
                  }
                }
                container reply-mode {
                  status obsolete;
                  description
                    "Reply for LSP echo request";
                  when "../../type/echo or
                        ../../type/pathEcho";
                  leaf ipv4 {
                    status obsolete;
                    description
                      "Send reply via IPv4";
                    type boolean;
                  }
                  leaf router-alert {
                    status obsolete;
                    description
                      "Send reply via IPv4 UDP with router alert";
                    type boolean;
                  }
                }
                leaf request-data-size {
                  status obsolete;
                  description
                    "Request data size";
                  when "../../type/echo or
                        ../../type/jitter";
                  type uint16 {
                    range "100..1500";
                  }
                }
                container secondary-frequency {
                  status obsolete;
                  description
                    "Frequency to be used if there is any violation condition happens";
                  when "../../type/echo or
                        ../../type/jitter";
                  leaf both {
                    status obsolete;
                    description
                      "Enable secondary freq for timeout and connection loss";
                    type uint32 {
                      range "1..604800";
                    }
                  }
                  leaf connection-loss {
                    status obsolete;
                    description
                      "Enable secondary freq for connection loss";
                    type uint32 {
                      range "1..604800";
                    }
                  }
                  leaf timeout {
                    status obsolete;
                    description
                      "Enable secondary freq for timeout";
                    type uint32 {
                      range "1..604800";
                    }
                  }
                }
                leaf ttl {
                  status obsolete;
                  description
                    "Time to live";
                  when "../../type/echo or
                        ../../type/pathEcho";
                  type uint8 {
                    range "1..255";
                  }
                }
                leaf dest-port {
                  status obsolete;
                  description
                    "Destination Port";
                  when '../../type/jitter';
                  type uint16 {
                    range "1..65535";
                  }
                }
                leaf interval {
                  status obsolete;
                  description
                    "Inter Packet Interval";
                  when '../../type/jitter';
                  type uint16 {
                    range "4..60000";
                  }
                }
                leaf num-packets {
                  status obsolete;
                  description
                    "Number of Packets to be transmitted";
                  when '../../type/jitter';
                  type uint16 {
                    range "1..60000";
                  }
                }
                leaf verify-data {
                  status obsolete;
                  description
                    "Verify data";
                  when '../../type/jitter';
                  type boolean;
                }
              }
            }
            list reaction-configuration {
              description
                "IP SLAs MPLS LSP Monitor Reaction Configuration";
              key "entry-number";
              leaf entry-number {
                description
                  "Entry number";
                type leafref {
                  path "/ios:native/ios-sla:auto/ios-sla:ip/ios-sla:sla/ios-sla:mpls-lsp-monitor/ios-sla:entry/ios-sla:number";
                }
              }
              container react {
                description
                  "Reaction Variable To Be Configured";
                container connectionLoss {
                  description
                    "Connection Loss";
                  presence "true";
                  uses config-auto-ip-sla-react-action-type-grouping;
                  uses config-auto-ip-sla-react-threshold-type-grouping;
                }
                container lpd {
                  description
                    "IP SLAs LSP Path Discover";
                  container lpd-group {
                    description
                      "LSP Path Discover Group";
                    presence "true";
                    leaf retry {
                      description
                        "Retry Count";
                      type uint8 {
                        range "1..16";
                      }
                    }
                    leaf action-type {
                      description
                        "LSP Path Discover Reaction Action Type";
                      type enumeration {
                        enum trapOnly;
                      }
                    }
                  }
                  container tree-trace {
                    description
                      "Tree Trace";
                    presence "true";
                    leaf action-type {
                      description
                        "LSP Path Discover Reaction Action Type";
                      type enumeration {
                        enum trapOnly;
                      }
                    }
                  }
                }
                container timeout {
                  description
                    "Timeout";
                  presence "true";
                  uses config-auto-ip-sla-react-action-type-grouping;
                  uses config-auto-ip-sla-react-threshold-type-grouping;
                }
              }
            }
            list schedule {
              description
                "IP SLAs MPLS LSP Monitor Schedule";
              key "entry";
              leaf entry {
                description
                  "Entry Number";
                type leafref {
                  path "/ios:native/ios-sla:auto/ios-sla:ip/ios-sla:sla/ios-sla:mpls-lsp-monitor/ios-sla:entry/ios-sla:number";
                }
              }
              leaf schedule-period {
                description
                  "Group schedule period range";
                type uint32 {
                  range "1..604800";
                }
              }
              leaf frequency {
                description
                  "Group operation frequency";
                type uint32 {
                  range "1..604800";
                }
              }
              container start-time {
                description
                  "When to start this entry";
                choice start-time-param {
                  case after-type {
                    leaf after {
                      description
                        "Start after a certain amount of time from now";
                      type ios-sla:hour-min-sec;
                    }
                  }
                  case hour-min-type {
                    container hour-min {
                      leaf hour-min {
                        description
                          "Start time (hh:mm)";
                        type ios-sla:hour-min;
                      }
                      leaf date-of-month {
                        description
                          "Day of the month";
                        type uint8 {
                          range "1..31";
                        }
                      }
                      leaf month {
                        description
                          "Month of the year";
                        type string {
                          pattern '(Jan|Feb|Mar|Apr|May|Jun|Jul|Aug|Sep|Oct|Nov|Dec)';
                        }
                      }
                    }
                  }
                  case hour-min-sec-type {
                    container hour-min-sec {
                      leaf hour-min-sec {
                        description
                          "Start time (hh:mm)";
                        type ios-sla:hour-min-sec;
                      }
                      leaf date-of-month {
                        description
                          "Day of the month";
                        type uint8 {
                          range "1..31";
                        }
                      }
                      leaf month {
                        description
                          "Month of the year";
                        type string {
                          pattern '(Jan|Feb|Mar|Apr|May|Jun|Jul|Aug|Sep|Oct|Nov|Dec)';
                        }
                      }
                    }
                  }
                  case now-type {
                    leaf now {
                      description
                        "Start now";
                      type empty;
                    }
                  }
                  case pending-type {
                    leaf pending {
                      description
                        "Start pending";
                      type empty;
                    }
                  }
                }
              }
            }
          }
        }
      }
    }
  }

  grouping config-ip-sla-mpls-ping-trace-grouping {
    leaf target-fec-address {
      description
        "Target FEC address (broadcast disallowed)";
      mandatory true;
      type inet:ip-address;
    }
    leaf ip-prefix-mask {
      description
        "IP prefix mask";
      mandatory true;
      type inet:ip-address;
    }
    leaf lsp-selector {
      description
        "Local Host IP Address, broadcast disallowed";
      type union {
        type inet:ip-address;
        type string;
      }
    }
    container reply-mode {
      description
        "Reply mode for LSP echo request";
      container reply {
        description
          "Reply for LSP echo request";
        leaf mode {
          description
            "Reply mode";
          type enumeration {
            enum ipv4;
            enum router-alert;
          }
          default "ipv4";
        }
      }
    }
    container reply {
      description
        "Reply for LSP echo request";
      leaf dscp {
        description
          "DSCP bits in reply IP header";
        type reply-dscp-bits-type;
      }
    }
    leaf force-explicit-null {
      description
        "force an explicit null label to be added";
      type empty;
    }
    leaf source-ipaddr {
      description
        "Source specified as an IP address";
      type inet:ip-address;
    }
  }

  grouping config-ip-sla-mpls-lsp-submode-grouping {
    leaf exp {
      description
        "EXP value";
      type uint8 {
        range "0..7";
      }
      default "0";
    }
    leaf owner {
      description
        "Owner of Entry";
      type string;
    }
    leaf tag {
      description
        "User defined tag";
      type string;
    }
    leaf frequency {
      description
        "Frequency of an operation";
      units "seconds";
      type uint32 {
        range "1..604800";
      }
      default "60";
    }
    leaf timeout {
      description
        "Timeout of an operation";
      units "miliseconds";
      type uint32 {
        range "0..604800000";
      }
      default "5000";
    }
    leaf threshold {
      description
        "Operation threshold in milliseconds";
      units "miliseconds";
      type uint32 {
        range "0..60000";
      }
      default "5000";
    }
    container history {
      description
        "History and Distribution Data";
    }
  }

  grouping config-ip-sla-mpls-enhanced-history-grouping {
    container enhanced {
      description
        "Enable enhanced history collection";
      leaf interval {
        description
          "Aggregation interval";
        type uint16 {
          range "1..3600";
        }
      }
      leaf buckets {
        description
          "Number of buckets to collect data";
        type uint8 {
          range "1..100";
        }
      }
    }
  }

  grouping config-ip-sla-mpls-history-grouping {
    leaf buckets-kept {
      description
        "Maximum number of history buckets to collect";
      type uint8 {
        range "1..60";
      }
      default "15";
    }
    leaf distributions-of-statistics-kept {
      description
        "Maximum number of statistics distribution buckets to capture";
      type uint8 {
        range "1..20";
      }
      default "1";
    }
    leaf filter {
      description
        "Add operation to History when...";
      type enumeration {
        enum all;
        enum failures;
        enum none;
        enum overThreshold;
      }
      default "none";
    }
    leaf hours-of-statistics-kept {
      description
        "Maximum number of statistics hour groups to capture";
      type uint8 {
        range "0..25";
      }
      default "2";
    }
    leaf lives-kept {
      description
        "Maximum number of history lives to collect";
      type uint8 {
        range "0..2";
      }
      default "0";
    }
    leaf statistics-distribution-interval {
      description
        "Statistics distribution interval size";
      type uint8 {
        range "1..100";
      }
      default "20";
    }
  }

  grouping config-ip-sla-mpls-ping-secondary-frequency-grouping {
    container secondary-frequency {
      description
        "Frequency to be used if there is any violation condition happens";
      choice type-params {
        case connection-loss-type {
          leaf connection-loss {
            description
              "Enable secondary frequency for connection loss";
            units "seconds";
            type uint32 {
              range "1..604800";
            }
          }
        }
        case timeout-type {
          leaf timeout {
            description
              "Enable secondary frequency for timeout";
            units "seconds";
            type uint32 {
              range "1..604800";
            }
          }
        }
      }
    }
  }

  grouping config-ip-sla-group-schedule-grouping {
    container frequency {
      description
        "Group operation frequency";
      choice frequency-choice {
        case frequency-value {
          leaf frequency-val {
            description
              "Specify frequency in seconds";
            type uint32;
          }
        }
        case frequency-range {
          leaf range {
            description
              "Group operation frequency-range for random scheduling";
            type string;
          }
        }
      }
    }
    container start-time {
      description
        "When to start this entry";
      choice start-time-param {
        case after-type {
          leaf after {
            description
              "Start after a certain amount of time from now";
            type ios-sla:hour-min-sec;
          }
        }
        case hour-min-type {
          container hour-min {
            leaf hour-min {
              description
                "Start time (hh:mm)";
              type ios-sla:hour-min;
            }
            leaf date-of-month {
              description
                "Day of the month";
              type uint8 {
                range "1..31";
              }
            }
            leaf month {
              description
                "Month of the year";
              type string {
                pattern '(Jan|Feb|Mar|Apr|May|Jun|Jul|Aug|Sep|Oct|Nov|Dec)';
              }
            }
          }
        }
        case hour-min-sec-type {
          container hour-min-sec {
            leaf hour-min-sec {
              description
                "Start time (hh:mm)";
              type ios-sla:hour-min-sec;
            }
            leaf date-of-month {
              description
                "Day of the month";
              type uint8 {
                range "1..31";
              }
            }
            leaf month {
              description
                "Month of the year";
              type string {
                pattern '(Jan|Feb|Mar|Apr|May|Jun|Jul|Aug|Sep|Oct|Nov|Dec)';
              }
            }
          }
        }
        case now-type {
          leaf now {
            description
              "Start now";
            type empty;
          }
        }
        case pending-type {
          leaf pending {
            description
              "Start pending";
            type empty;
          }
        }
        case random {
          leaf random {
            description
              "Start after random time (range)";
            units "miliseconds";
            type uint16 {
              range "500..10000";
            }
          }
        }
      }
    }
    leaf life {
      description
        "Length of time to execute in seconds";
      type union {
        type uint32 {
          range "0..2147483647";
        }
        type enumeration {
          enum forever;
        }
      }
      default "3600";
    }
    leaf ageout {
      description
        "How long to keep this Entry when inactive";
      type uint32 {
        range "0..2073600";
      }
    }
  }

  grouping config-ip-sla-ethernet-monitor-submode-grouping {
    leaf cos {
      description
        "Class of Service";
      type uint8 {
        range "0..7";
      }
    }
    leaf owner {
      description
        "Owner of Entry";
      type string;
    }
    leaf tag {
      description
        "User defined tag";
      type string;
    }
    leaf threshold {
      description
        "Operation threshold in milliseconds";
      units "miliseconds";
      type uint32 {
        range "0..60000";
      }
      default "5000";
    }
    leaf timeout {
      description
        "Timeout of an operation";
      units "miliseconds";
      type uint32 {
        range "0..604800000";
      }
      default "5000";
    }
  }

  grouping config-ip-sla-ethernet-monitor-schedule-grouping {
    leaf date-of-month {
      description
        "Day of the month";
      type uint8 {
        range "1..31";
      }
    }
    leaf month {
      description
        "Month of the year";
      type string {
        pattern '(Jan|Feb|Mar|Apr|May|Jun|Jul|Aug|Sep|Oct|Nov|Dec)';
      }
    }
  }

  grouping config-ip-sla-grouping {
    container sla {
      description
        "IP Service Level Agreement";
      list entry {
        key "number";
        leaf number {
          description
            "Entry Number";
          type uint32 {
            range "1..2147483647";
          }
        }
        choice sla-param {
          case icmp-echo-case {
            container icmp-echo {
              description
                "ICMP Echo Operation";
              leaf destination {
                description
                  "Destination IP address or hostname, broadcast disallowed";
                mandatory true;
                type union {
                  type string;
                  type inet:ip-address;
                }
              }
              choice source-param {
                case source-interface {
                  leaf source-interface {
                    description
                      "Source Interface (ingress icmp packet interface)";
                    type string;
                  }
                }
                case source-ip {
                  leaf source-ip {
                    description
                      "Source Address";
                    type union {
                      type string;
                      type inet:ip-address;
                    }
                  }
                }
              }
              leaf data-pattern {
                description
                  "Data Pattern";
                type string;
              }
              uses ip-sla-sub-mode-commands-grouping;
              uses ip-sla-full-history-grouping;
              leaf request-data-size {
                description
                  "Request data size";
                type uint32 {
                  range "0..16384";
                }
                default "28";
              }
              choice tos-param {
                case tos {
                  leaf tos {
                    description
                      "Type Of Service";
                    type uint8 {
                      range "0..255";
                    }
                  }
                }
                case traffic-class {
                  leaf traffic-class {
                    description
                      "Traffic class";
                    type uint8 {
                      range "0..255";
                    }
                  }
                }
              }
              leaf verify-data {
                description
                  "Verify data";
                type boolean;
              }
              leaf vrf {
                description
                  "Configure IP SLAs for a VPN Routing/Forwarding instance";
                type string;
              }
            }
          }
          case icmp-jitter-case {
            container icmp-jitter {
              description
                "ICMP-jitter Operations";
              leaf dst-ip {
                description
                  "Destination IP address or hostname, broadcast disallowed";
                mandatory true;
                type union {
                  type string;
                  type inet:ipv4-address;
                }
              }
              leaf interval {
                description
                  "Inter Packet Interval";
                units "milliseconds";
                type uint16 {
                  range "4..60000";
                }
                default "20";
              }
              leaf num-packets {
                description
                  "Number of Packets to be transmitted";
                units "packets";
                type uint16 {
                  range "1..60000";
                }
                default "10";
              }
              leaf source-ip {
                description
                  "IP address or hostname, broadcast disallowed";
                type union {
                  type string;
                  type inet:ipv4-address;
                }
              }
              uses ip-sla-sub-mode-commands-grouping;
              container history {
                description
                  "History and Distribution Data";
                leaf distributions-of-statistics-kept {
                  description
                    "Maximum number of statistics distribution buckets to capture";
                  type uint8 {
                    range "1..20";
                  }
                  default "1";
                }
                container enhanced {
                  description
                    "Enable enhanced history collection";
                  leaf interval {
                    description
                      "Aggregation interval";
                    type uint16 {
                      range "1..3600";
                    }
                  }
                  leaf buckets {
                    description
                      "Number of buckets to collect data";
                    type uint8 {
                      range "1..100";
                    }
                  }
                }
                leaf hours-of-statistics-kept {
                  description
                    "Maximum number of statistics hour groups to capture";
                  type uint8 {
                    range "0..25";
                  }
                  default "2";
                }
                leaf statistics-distribution-interval {
                  description
                    "Statistics distribution interval value in msec";
                  units "milliseconds";
                  type uint8 {
                    range "1..100";
                  }
                  default "20";
                }
              }
              leaf tos {
                description
                  "Type Of Service";
                type uint8 {
                  range "0..255";
                }
              }
              leaf vrf {
                description
                  "Configure IP SLAs for a VPN Routing/Forwarding instance";
                type string;
              }
            }
          }
          case path-echo-case {
            container path-echo {
              description
                "Path Discovered ICMP Echo Operation";
              leaf dst-ip {
                description
                  "Destination IP address or hostname, broadcast disallowed";
                mandatory true;
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-path-echo-grouping;
            }
          }
          case path-jitter-case {
            container path-jitter {
              description
                "Path Discovered ICMP Jitter Operation";
              leaf dst-ip {
                mandatory true;
                type union {
                  type string;
                  type inet:ipv4-address;
                  type inet:ipv6-address;
                }
              }
              leaf source-ip {
                description
                  "Source IP Address";
                type union {
                  type string;
                  type inet:ipv4-address;
                }
              }
              container default {
                description
                  "Set a command to its defaults";
                uses ip-sla-default-path-jitter-grouping;
              }
              uses ip-sla-sub-mode-commands-grouping;
              uses ip-sla-path-jitter-grouping;
            }
          }
          case udp-echo-case {
            container udp-echo {
              description
                "UDP echo operation";
              leaf dest-addr {
                description
                  "Hostname or A.B.C.D  Destination IP address or hostname, broadcast disallowed";
                mandatory true;
                type union {
                  type inet:ip-address;
                  type string;
                }
              }
              leaf dest-port {
                description
                  "Port Number (Recommended ports greater than 1023)";
                mandatory true;
                type uint16 {
                  range "1..65535";
                }
              }
              leaf source-ip {
                description
                  "Source address: Hostname or A.B.C.D IP address or hostname, broadcast disallowed";
                type union {
                  type inet:ip-address;
                  type string;
                }
              }
              leaf source-port {
                description
                  "Source Port: Port Number (Recommended ports greater than 1023)";
                type uint16 {
                  range "1..65535";
                }
              }
              leaf control {
                description
                  "Enable or disable control packets";
                type enumeration {
                  enum disable;
                  enum enable;
                }
                default "enable";
              }
              uses ip-sla-sub-mode-commands-grouping;
              uses ip-sla-udp-echo-grouping;
            }
          }
          case udp-jitter-case {
            container udp-jitter {
              description
                "UDP jitter operation";
              leaf dest-addr {
                description
                  "Hostname or A.B.C.D/X:X:X:X::X  Destination IP/IPv6 address";
                mandatory true;
                type union {
                  type inet:ip-address;
                  type inet:ipv6-address;
                  type string;
                }
              }
              leaf portno {
                description
                  "Port Number";
                mandatory true;
                type uint16 {
                  range "1..65535";
                }
              }
              leaf endpoint-list {
                description
                  "Endpoint list configuration. Applicable only when the
                   destination address is multicast address";
                type leafref {
                  path "/ios:native/ios:ip/ios-sla:sla/ios-sla:endpoint-list/ios-sla:type/ios-sla:ip/ios-sla:name";
                }
              }
              choice type-param {
                case codec {
                  leaf codec {
                    description
                      "codec type to be configured";
                    type enumeration {
                      enum g711alaw;
                      enum g711ulaw;
                      enum g729a;
                    }
                  }
                  leaf advantage-factor {
                    description
                      "Advantage Factor";
                    type uint16 {
                      range "0..20";
                    }
                    default "0";
                  }
                  leaf codec-interval {
                    description
                      "Inter Packet Interval";
                    type uint32 {
                      range "4..60000";
                    }
                    default "20";
                  }
                  leaf codec-numpackets {
                    description
                      "Number of Packets";
                    type uint32 {
                      range "1..60000";
                    }
                    default "1000";
                  }
                  leaf codec-size {
                    description
                      "Number of Packets";
                    type uint16 {
                      range "16..16384";
                    }
                  }
                }
                case non-codec {
                  leaf num-packets {
                    description
                      "Number of Packets (default 10)";
                    type uint16 {
                      range "1..60000";
                    }
                    default "10";
                  }
                  leaf interval {
                    description
                      "Delay (default 20)";
                    type uint16 {
                      range "4..60000";
                    }
                    default "20";
                  }
                }
              }
              leaf ssm {
                description
                  "Source Specific multicast configuration. Applicable only
                   when the destination address is multicast address";
                type empty;
              }
              leaf source-ip {
                description
                  "Hostname or A.B.C.D/X:X:X:X::X Source IP/IPv6 address";
                type union {
                  type inet:ip-address;
                  type inet:ipv6-address;
                  type string;
                }
              }
              leaf source-port {
                description
                  "Source port";
                type uint16 {
                  range "1..65535";
                }
              }
              leaf control {
                description
                  "Enable or disable control packets";
                type enumeration {
                  enum enable;
                  enum disable;
                }
                default "enable";
              }
              uses ip-sla-sub-mode-commands-grouping;
              uses ip-sla-udp-jitter-grouping;
              uses ip-sla-jitter-percentile;
            }
          }
          case http-case {
            container http {
              description
                "HTTP Operation";
              choice http-choice {
                case http-get {
                  container get {
                    description
                      "HTTP get operation";
                    leaf url {
                      description
                        "URL";
                      mandatory true;
                      type string;
                    }
                    leaf cache {
                      description
                        "Enable or Disable download of cached HTTP page";
                      type enumeration {
                        enum enable;
                        enum disable;
                      }
                      default "enable";
                    }
                    leaf source-ip {
                      description
                        "Source Hostname or A.B.C.D/X:X:X:X::X  IPv4/IPv6 address";
                      type union {
                        type inet:ipv6-address;
                        type inet:ip-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description
                        "Proxy information string";
                      type string;
                    }
                    leaf version {
                      description
                        "Http Version";
                      type enumeration {
                        enum 1.0;
                        enum 1.1;
                      }
                      default "1.0";
                    }
                  }
                }
                case http-raw {
                  container raw {
                    description
                      "HTTP raw operation";
                    leaf url {
                      mandatory true;
                      type string;
                    }
                    leaf cache {
                      description
                        "Enable or Disable download of cached HTTP page";
                      type enumeration {
                        enum enable;
                        enum disable;
                      }
                      default "enable";
                    }
                    leaf source-ip {
                      description
                        "Source Hostname or A.B.C.D/X:X:X:X::X  IPv4/IPv6 address";
                      type union {
                        type inet:ip-address;
                        type inet:ipv6-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description
                        "Proxy information string";
                      type string;
                    }
                    leaf version {
                      description
                        "Http Version";
                      type enumeration {
                        enum 1.0;
                        enum 1.1;
                      }
                      default "1.0";
                    }
                  }
                }
              }
              uses ip-sla-sub-mode-commands-grouping;
              container history {
                description
                  "History and Distribution Data";
                leaf distributions-of-statistics-kept {
                  description
                    "Maximum number of statistics distribution buckets to capture";
                  type uint8 {
                    range "1..20";
                  }
                  default "1";
                }
                leaf hours-of-statistics-kept {
                  description
                    "Maximum number of statistics hour groups to capture";
                  type uint8 {
                    range "0..25";
                  }
                  default "2";
                }
                leaf statistics-distribution-interval {
                  description
                    "Statistics distribution interval size";
                  type uint8 {
                    range "1..100";
                  }
                  default "20";
                }
              }
              leaf http-status-code-ignore {
                description
                  "HTTP Status Code Check Disable";
                type boolean;
              }
              leaf vrf {
                description
                  "Configure IP SLAs for a new VPN Routing/Forwarding instance";
                type string;
              }
              choice tos-param {
                case tos {
                  leaf tos {
                    description
                      "Type Of Service";
                    type uint8 {
                      range "0..255";
                    }
                  }
                }
                case traffic-class {
                  leaf traffic-class {
                    description
                      "Traffic class";
                    type uint8 {
                      range "0..255";
                    }
                  }
                }
              }
              container http-raw-request {
                description
                  "HTTP Raw Request configuration";
                leaf raw-request-string {
                  description
                    "HTTP Raw string";
                  type string;
                }
              }
            }
          }
          case dhcp-case {
            container dhcp {
              description
                "DHCP Operation";
              leaf dst-ip {
                description
                  "Destination IP address or hostname, broadcast disallowed";
                mandatory true;
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-history-without-enhanced-grouping;
            }
          }
          case tcp-connect-case {
            container tcp-connect {
              description
                "TCP connect operation";
              leaf dest-addr {
                description
                  "Destination IPv6/IP address or hostname";
                mandatory true;
                type union {
                  type inet:ip-address;
                  type inet:ipv6-address;
                  type string;
                }
              }
              leaf dest-port {
                description
                  "Port Number (Recommended ports greater than 1023)";
                mandatory true;
                type uint16 {
                  range "1..65535";
                }
              }
              leaf source-ip {
                description
                  "Source IPv6/IP address or hostname";
                type union {
                  type inet:ip-address;
                  type inet:ipv6-address;
                  type string;
                }
              }
              leaf source-port {
                description
                  "Source Port: Port Number (Recommended ports greater than 1023)";
                type uint16 {
                  range "1..65535";
                }
              }
              leaf control {
                description
                  "Enable or disable control packets";
                type enumeration {
                  enum enable;
                  enum disable;
                }
                default "enable";
              }
              uses ip-sla-sub-mode-commands-grouping;
              uses ip-sla-full-history-grouping;
              choice tos-param {
                case tos {
                  leaf tos {
                    description
                      "Type Of Service";
                    type uint8 {
                      range "0..255";
                    }
                  }
                }
                case traffic-class {
                  leaf traffic-class {
                    description
                      "Traffic class";
                    type uint8 {
                      range "0..255";
                    }
                  }
                }
              }
              leaf vrf {
                description
                  "Configure IP SLAs for a VPN Routing/Forwarding instance";
                type string;
              }
            }
          }
          case dns-case {
            container dns {
              description
                "DNS operation";
              leaf dest-addr {
                description
                  "Destination IPv6/IP address or hostname";
                mandatory true;
                type union {
                  type inet:ip-address;
                  type inet:ipv6-address;
                  type string;
                }
              }
              leaf name-server {
                description
                  "Name Server: IPv6/IP address or hostname";
                mandatory true;
                type union {
                  type inet:ip-address;
                  type inet:ipv6-address;
                  type string;
                }
              }
              leaf source-ip {
                description
                  "Source IPv6/IP address or hostname";
                type union {
                  type inet:ip-address;
                  type inet:ipv6-address;
                  type string;
                }
              }
              leaf source-port {
                description
                  "Source Port: Port Number (Recommended ports greater than 1023)";
                type uint16 {
                  range "1..65535";
                }
              }
              uses ip-sla-sub-mode-commands-grouping;
              uses ip-sla-history-without-enhanced-grouping;
              leaf vrf {
                description
                  "Configure IP SLAs for a VPN Routing/Forwarding instance";
                type string;
              }
            }
          }
          case ftp-case {
            container ftp {
              description
                "DNS operation";
              container get {
                presence "true";
                description
                  "FTP get operation";
                leaf url {
                  description
                    "URL";
                  mandatory true;
                  type union {
                    type string;
                  }
                }
                leaf mode {
                  description
                    "Specify mode to be used";
                  type enumeration {
                    enum active;
                    enum passive;
                  }
                }
                leaf source-ip {
                  description
                    "Source IPv6/IP address or hostname";
                  type union {
                    type inet:ip-address;
                    type inet:ipv6-address;
                    type string;
                  }
                }
                leaf owner {
                  description
                    "Owner of Entry";
                  status obsolete;
                  type string;
                }
                leaf tag {
                  description
                    "User defined tag";
                  status obsolete;
                  type string;
                }
                leaf frequency {
                  description
                    "Frequency of an operation";
                  status obsolete;
                  units "seconds";
                  type uint32 {
                    range "1..604800";
                  }
                  default "60";
                }
                leaf timeout {
                  description
                    "Timeout of an operation";
                  status obsolete;
                  units "miliseconds";
                  type uint32 {
                    range "0..604800000";
                  }
                  default "5000";
                }
                leaf threshold {
                  description
                    "Operation threshold in milliseconds";
                  status obsolete;
                  units "miliseconds";
                  type uint32 {
                    range "0..60000";
                  }
                  default "5000";
                }
                container history {
                  description
                    "History and Distribution Data";
                  status obsolete;
                  container enhanced {
                    status obsolete;
                    description
                      "Enable enhanced history collection";
                    leaf interval {
                      status obsolete;
                      description
                        "Aggregation interval";
                      type uint16 {
                        range "1..3600";
                      }
                      default "900";
                    }
                    leaf buckets {
                      status obsolete;
                      description
                        "Number of buckets to collect data";
                      type uint8 {
                        range "1..100";
                      }
                      default "100";
                    }
                  }
                  leaf buckets-kept {
                    status obsolete;
                    description
                      "Maximum number of history buckets to collect";
                    type uint8;
                    default "50";
                  }
                  leaf distributions-of-statistics-kept {
                    status obsolete;
                    description
                      "Maximum number of statistics distribution buckets to capture";
                    type uint8;
                    default "1";
                  }
                  leaf filter {
                    status obsolete;
                    description
                      "Add operation to History when...";
                    type enumeration {
                      enum all;
                      enum failures;
                      enum none;
                      enum overThreshold;
                    }
                    default "none";
                  }
                  leaf hours-of-statistics-kept {
                    status obsolete;
                    description
                      "Maximum number of statistics hour groups to capture";
                    type uint8 {
                      range "0..25";
                    }
                    default "2";
                  }
                  leaf lives-kept {
                    status obsolete;
                    description
                      "Maximum number of history lives to collect";
                    type uint8 {
                      range "0..2";
                    }
                    default "0";
                  }
                  leaf statistics-distribution-interval {
                    status obsolete;
                    description
                      "Statistics distribution interval size";
                    type uint8 {
                      range "1..100";
                    }
                    default "20";
                  }
                }
              }
              uses ip-sla-sub-mode-commands-grouping;
              uses ip-sla-history-without-enhanced-grouping;
            }
          }
          case ethernet-case {
            container ethernet {
              description
                "Ethernet Operations";
              choice ethernet-probe-type {
                case echo-case {
                  container echo {
                    description
                      "Ethernet Echo Operation 802.11 ag Loopback";
                    leaf mpid {
                      description
                        "Maintenance Point ID";
                      mandatory true;
                      type uint16 {
                        range "1..8191";
                      }
                    }
                    leaf domain {
                      description
                        "Domain Name";
                      mandatory true;
                      type string;
                    }
                    choice param {
                      mandatory true;
                      case evc-case {
                        leaf evc {
                          description
                            "EVC ID";
                          type string;
                        }
                      }
                      case port {
                        leaf port {
                          description
                            "DOWN service direction with no vlan association";
                          type empty;
                        }
                      }
                      case vlan {
                        leaf vlan {
                          description
                            "VLAN ID";
                          type uint16 {
                            range "1..4094";
                          }
                        }
                      }
                    }
                    leaf cos {
                      description
                        "Class Of Service";
                      type uint8 {
                        range "0..7";
                      }
                    }
                    leaf request-data-size {
                      description
                        "Request data size";
                      type uint16 {
                        range "0..1400";
                      }
                    }
                    leaf owner {
                      description
                        "Owner of Entry";
                      type string;
                    }
                    leaf tag {
                      description
                        "User defined tag";
                      type string;
                    }
                    leaf threshold {
                      description
                        "Operation threshold in milliseconds";
                      units "miliseconds";
                      type uint32 {
                        range "0..60000";
                      }
                      default "5000";
                    }
                    leaf timeout {
                      description
                        "Timeout of an operation";
                      units "miliseconds";
                      type uint32 {
                        range "0..604800000";
                      }
                      default "5000";
                    }
                    leaf frequency {
                      description
                        "Frequency of an operation";
                      units "seconds";
                      type uint32 {
                        range "1..604800";
                      }
                      default "60";
                    }
                    container history {
                      description
                        "History and Distribution Data";
                      container enhanced {
                        description
                          "Enable enhanced history collection";
                        leaf interval {
                          description
                            "Aggregation interval";
                          type uint16 {
                            range "1..3600";
                          }
                          default "900";
                        }
                        leaf buckets {
                          description
                            "Number of buckets to collect data";
                          type uint8 {
                            range "1..100";
                          }
                          default "100";
                        }
                      }
                      leaf buckets-kept {
                        description
                          "Maximum number of history buckets to collect";
                        type uint8 {
                          range "1..60";
                        }
                        default "50";
                      }
                      leaf distributions-of-statistics-kept {
                        description
                          "Maximum number of statistics distribution buckets to capture";
                        type uint8 {
                          range "1..20";
                        }
                        default "1";
                      }
                      leaf filter {
                        description
                          "Add operation to History when...";
                        type enumeration {
                          enum all;
                          enum failures;
                          enum none;
                          enum overThreshold;
                        }
                        default "none";
                      }
                      leaf hours-of-statistics-kept {
                        description
                          "Maximum number of statistics hour groups to capture";
                        type uint8 {
                          range "0..25";
                        }
                        default "2";
                      }
                      leaf lives-kept {
                        description
                          "Maximum number of history lives to collect";
                        type uint8 {
                          range "0..2";
                        }
                        default "0";
                      }
                      leaf statistics-distribution-interval {
                        description
                          "Statistics distribution interval size";
                        type uint8 {
                          range "1..100";
                        }
                        default "20";
                      }
                    }
                  }
                }
                case jitter-case {
                  container jitter {
                    description
                      "Ethernet Jitter Operation";
                    leaf mpid {
                      description
                        "Maintenance Point ID";
                      mandatory true;
                      type uint16 {
                        range "1..8191";
                      }
                    }
                    leaf domain {
                      description
                        "Domain Name";
                      mandatory true;
                      type string;
                    }
                    choice param {
                      mandatory true;
                      case evc-case {
                        leaf evc {
                          description
                            "EVC ID";
                          type string;
                        }
                      }
                      case port {
                        leaf port {
                          description
                            "DOWN service direction with no vlan association";
                          type empty;
                        }
                      }
                      case vlan {
                        leaf vlan {
                          description
                            "VLAN ID";
                          type uint16 {
                            range "1..4094";
                          }
                        }
                      }
                    }
                    container jitter-params {
                      leaf interval {
                        description
                          "Inter Packet Interval";
                        type uint16 {
                          range "4..60000";
                        }
                      }
                      leaf num-frames {
                        description
                          "Number of Frames to be transmitted";
                        type uint16 {
                          range "1..60000";
                        }
                      }
                    }
                    leaf cos {
                      description
                        "Class Of Service";
                      type uint8 {
                        range "0..7";
                      }
                    }
                    leaf request-data-size {
                      description
                        "Request data size";
                      type uint16 {
                        range "0..1400";
                      }
                    }
                    container percentile {
                      description
                        "Set percentile statistics levels";
                      leaf jitteravg {
                        description
                          "% of Average Jitter values to use (default 100%)";
                        type uint8 {
                          range "90..100";
                        }
                      }
                      leaf jitterds {
                        description
                          "% of Destination to source jitter value to use (default 100%)";
                        type uint8 {
                          range "90..100";
                        }
                      }
                      leaf jittersd {
                        description
                          "% of Source to destination jitter value to use (default 100%)";
                        type uint8 {
                          range "90..100";
                        }
                      }
                      leaf owds {
                        description
                          "% of One way destination to source value to use (default 100%)";
                        type uint8 {
                          range "90..100";
                        }
                      }
                      leaf owsd {
                        description
                          "% of One way source to destination value to use (default 100%)";
                        type uint8 {
                          range "90..100";
                        }
                      }
                      leaf rtt {
                        description
                          "% of Round Trip Time value to use (default 100%)";
                        type uint8 {
                          range "90..100";
                        }
                      }
                    }
                    leaf owner {
                      description
                        "Owner of Entry";
                      type string;
                    }
                    leaf tag {
                      description
                        "User defined tag";
                      type string;
                    }
                    leaf threshold {
                      description
                        "Operation threshold in milliseconds";
                      units "miliseconds";
                      type uint32 {
                        range "0..60000";
                      }
                      default "5000";
                    }
                    leaf timeout {
                      description
                        "Timeout of an operation";
                      units "miliseconds";
                      type uint32 {
                        range "0..604800000";
                      }
                      default "6000";
                    }
                    leaf frequency {
                      description
                        "Frequency of an operation";
                      units "seconds";
                      type uint32 {
                        range "1..604800";
                      }
                      default "60";
                    }
                    container history {
                      description
                        "History and Distribution Data";
                      container enhanced {
                        description
                          "Enable enhanced history collection";
                        leaf interval {
                          description
                            "Aggregation interval";
                          type uint16 {
                            range "1..3600";
                          }
                          default "900";
                        }
                        leaf buckets {
                          description
                            "Number of buckets to collect data";
                          type uint8 {
                            range "1..100";
                          }
                          default "100";
                        }
                      }
                      leaf distributions-of-statistics-kept {
                        description
                          "Maximum number of statistics distribution buckets to capture";
                        type uint8 {
                          range "1..20";
                        }
                        default "1";
                      }
                      leaf hours-of-statistics-kept {
                        description
                          "Maximum number of statistics hour groups to capture";
                        type uint8 {
                          range "0..25";
                        }
                        default "2";
                      }
                      leaf statistics-distribution-interval {
                        description
                          "Statistics distribution interval size";
                        type uint8 {
                          range "1..100";
                        }
                        default "20";
                      }
                    }
                  }
                }
                case y1731-case {
                  container y1731-config {
                    description
                      "Y1731 Ethernet OAM Performance Measurement Operations";
                    uses ip-sla-ethernet-y1731-grouping;
                  }
                }
              }
              container y1731 {
                status deprecated;
                description
                  "Y1731 Ethernet OAM Performance Measurement Operations (DEPRECATED, use y1731-config container inside the choice statement)";
                container delay {
                  status deprecated;
                  description
                    "Y1731 Delay and Delay Variation Operation";
                  leaf name {
                    status deprecated;
                    description
                      "Y1731 Delay option";
                    type enumeration {
                      enum 1DM;
                      enum DMM;
                      enum DMMv1;
                    }
                  }
                  leaf burst {
                    status deprecated;
                    description
                      "Enable bursting of delay frames";
                    type empty;
                  }
                  leaf domain {
                    status deprecated;
                    description
                      "Specify the Ethernet OAM domain";
                    type string;
                  }
                  choice evc-or-vlan {
                    status deprecated;
                    leaf evc {
                      status deprecated;
                      description
                        "Specify the Ethernet Virtual Circuit Identifier";
                      type string;
                    }
                    leaf vlan {
                      status deprecated;
                      description
                        "Specify the VLAN";
                      type uint16 {
                        range "1..4096";
                      }
                    }
                  }
                  choice mac-or-mpid {
                    status deprecated;
                    leaf mac-address {
                      status deprecated;
                      description
                        "Specify the remote mac-address";
                      type ios-types:cisco-mac-address-type;
                    }
                    leaf mpid {
                      status deprecated;
                      description
                        "Specify the remote MPID";
                      type uint16 {
                        range "1..8191";
                      }
                    }
                  }
                  leaf cos {
                    status deprecated;
                    description
                      "Specify the Class of Service";
                    type uint8 {
                      range "0..7";
                    }
                  }
                  container source {
                    status deprecated;
                    description
                      "Specify the local MPID or MAC-Address";
                    choice mac-or-mpid {
                      status deprecated;
                      leaf mac-address {
                        status deprecated;
                        description
                          "Specify the local mac-address";
                        type ios-types:cisco-mac-address-type;
                      }
                      leaf mpid {
                        status deprecated;
                        description
                          "Specify the local MPID";
                        type uint16 {
                          range "1..8191";
                        }
                      }
                    }
                  }
                }
                container loss {
                  status deprecated;
                  description
                    "Y1731 Loss Operation";
                  leaf name {
                    status deprecated;
                    description
                      "Y1731 Delay option";
                    type enumeration {
                      enum LMM;
                      enum SLM;
                    }
                  }
                  leaf burst {
                    status deprecated;
                    description
                      "Enable bursting of delay frames. Applicable only to SLM option";
                    type empty;
                  }
                  leaf domain {
                    status deprecated;
                    description
                      "Specify the Ethernet OAM domain";
                    type string;
                  }
                  choice evc-or-vlan {
                    status deprecated;
                    leaf evc {
                      status deprecated;
                      description
                        "Specify the Ethernet Virtual Circuit Identifier";
                      type string;
                    }
                    leaf vlan {
                      status deprecated;
                      description
                        "Specify the VLAN";
                      type uint16 {
                        range "1..4096";
                      }
                    }
                  }
                  choice mac-or-mpid {
                    status deprecated;
                    leaf mac-address {
                      status deprecated;
                      description
                        "Specify the remote mac-address";
                      type ios-types:cisco-mac-address-type;
                    }
                    leaf mpid {
                      status deprecated;
                      description
                        "Specify the remote MPID";
                      type uint16 {
                        range "1..8191";
                      }
                    }
                  }
                  leaf cos {
                    status deprecated;
                    description
                      "Specify the Class of Service";
                    type uint8 {
                      range "0..7";
                    }
                  }
                  container source {
                    status deprecated;
                    description
                      "Specify the local MPID or MAC-Address";
                    choice mac-or-mpid {
                      status deprecated;
                      leaf mac-address {
                        status deprecated;
                        description
                          "Specify the local mac-address";
                        type ios-types:cisco-mac-address-type;
                      }
                      leaf mpid {
                        status deprecated;
                        description
                          "Specify the local MPID";
                        type uint16 {
                          range "1..8191";
                        }
                      }
                    }
                  }
                }
              }
              uses ip-sla-ethernet-delay-grouping {
                status obsolete;
                refine "aggregate" {
                  description
                    "Aggregate parameters (OBSOLETE)";
                }
                refine "history" {
                  description
                    "History parameters (OBSOLETE)";
                }
              }
            }
          }
          case service-performance-case {
            container service-performance {
              if-feature "ios-features:service-performance";
              description
                "Service Performance Operation";
              container type {
                description
                  "Server Performance identifier";
                choice service-type {
                  case ethernet-case {
                    container ethernet {
                      description
                        "Service Performance Ethernet";
                      leaf dest-mac-addr {
                        description
                          "Specify the remote mac-address";
                        mandatory true;
                        type ios-types:cisco-mac-address-type;
                      }
                      leaf bridge-domain {
                        description
                          "Specify the Bridge Domain";
                        type uint16 {
                          range "1..65535";
                        }
                      }
                      leaf interface {
                        description
                          "Interface Name";
                        type string;
                      }
                      leaf service {
                        description
                          "Specify the Service Instance";
                        type empty;
                      }
                      leaf instance {
                        description
                          "Specify the Service Instance";
                        type uint16 {
                          range "1..16000";
                        }
                      }
                      leaf ethernet {
                        description
                          "Configure an Ethernet Instance";
                        type string;
                      }
                      uses ip-sla-service-performance-sub-command-grouping {
                        augment "profile" {
                          uses ip-sla-service-performance-packet-direction-sub-command-grouping {
                            augment "packet" {
                              leaf dscp {
                                description
                                  "Configure DSCP";
                                type union {
                                  type uint8 {
                                    range "0..63";
                                  }
                                  type reply-dscp-bits-type;
                                }
                              }
                              leaf ethertype {
                                description
                                  "Frame type";
                                type enumeration {
                                  enum ipv4;
                                  enum ipv6;
                                }
                              }
                              leaf inner-cos {
                                description
                                  "Inner COS";
                                type uint8 {
                                  range "0..7";
                                }
                              }
                              leaf inner-vlan {
                                description
                                  "Specify Inner VLAN";
                                type uint16 {
                                  range "0..4095";
                                }
                              }
                              leaf outer-cos {
                                description
                                  "Outer COS";
                                type uint8 {
                                  range "0..7";
                                }
                              }
                              leaf src-mac-addr {
                                description
                                  "The source mac-address";
                                type ios-types:cisco-mac-address-type;
                              }
                            }
                          }
                          uses ip-sla-service-performance-traffic-direction-sub-command-grouping;
                        }
                        augment "measurement-type" {
                          uses ip-sla-service-performance-measurement-type-sub-command-grouping {
                            augment "conform-color" {
                              leaf cos {
                                description
                                  "configure conform COS";
                                type uint8 {
                                  range "0..7";
                                }
                              }
                            }
                            augment "exceed-color" {
                              leaf cos {
                                description
                                  "configure conform COS";
                                type uint8 {
                                  range "0..7";
                                }
                              }
                            }
                          }
                        }
                      }
                    }
                  }
                  case ip-case {
                    container ip {
                      description
                        "Service Performance IP";
                      leaf dest-ip-addr {
                        description
                          "Specify the target ip";
                        mandatory true;
                        type union {
                          type string;
                          type inet:ip-address;
                        }
                      }
                      leaf bridge-domain {
                        description
                          "Specify the Bridge Domain";
                        type uint16 {
                          range "1..65535";
                        }
                      }
                      choice option {
                        case interface-case {
                          leaf interface {
                            description
                              "Interface Name";
                            type string;
                          }
                          leaf service {
                            description
                              "Specify the Service Instance";
                            type empty;
                          }
                          leaf instance {
                            description
                              "Specify the Service Instance";
                            type uint16 {
                              range "1..16000";
                            }
                          }
                          leaf ethernet {
                            description
                              "Configure an Ethernet Instance";
                            type string;
                          }
                        }
                        case vrf-case {
                          leaf vrf {
                            description
                              "Configure an VRF";
                            type uint16 {
                              range "1..4096";
                            }
                          }
                        }
                      }
                      uses ip-sla-service-performance-sub-command-grouping {
                        augment "profile" {
                          uses ip-sla-service-performance-packet-direction-sub-command-grouping {
                            augment "packet" {
                              container tunnel {
                                description
                                  "Tunnel type";
                                leaf exp {
                                  description
                                    "Exp value";
                                  type uint8 {
                                    range "0..7";
                                  }
                                }
                              }
                              leaf source-ip-addr {
                                description
                                  "ip address";
                                type union {
                                  type string;
                                  type inet:ip-address;
                                }
                              }
                            }
                          }
                          uses ip-sla-service-performance-traffic-direction-sub-command-grouping;
                        }
                        augment "measurement-type" {
                          uses ip-sla-service-performance-measurement-type-sub-command-grouping {
                            augment "conform-color" {
                              leaf dscp {
                                description
                                  "configure conform DSCP";
                                type union {
                                  type uint8 {
                                    range "0..63";
                                  }
                                  type reply-dscp-bits-type;
                                }
                              }
                            }
                            augment "exceed-color" {
                              leaf dscp {
                                description
                                  "configure conform DSCP";
                                type union {
                                  type uint8 {
                                    range "0..63";
                                  }
                                  type reply-dscp-bits-type;
                                }
                              }
                            }
                          }
                        }
                      }
                    }
                  }
                }
              }
            }
          }
          case mpls {
            container mpls {
              description
                "MPLS Operation";
              container lsp {
                description
                  "Based on LSP echo Request/Reply";
                choice mpls-lsp-param {
                  case lsp-ping {
                    container ping {
                      description
                        "MPLS lsp ping operation";
                      choice ping-choice {
                        case ping-ipv4 {
                          container ipv4 {
                            description
                              "Target specified as an IPv4 address";
                            uses config-ip-sla-mpls-ping-trace-grouping;
                            uses config-ip-sla-mpls-lsp-submode-grouping {
                              augment "history" {
                                uses config-ip-sla-mpls-history-grouping;
                                uses config-ip-sla-mpls-enhanced-history-grouping;
                              }
                            }
                            uses config-ip-sla-mpls-ping-secondary-frequency-grouping;
                            leaf ttl {
                              description
                                "Time to live";
                              type uint8 {
                                range "1..255";
                              }
                              default "255";
                            }
                            leaf request-data-size {
                              description
                                "Request data size";
                              type uint16 {
                                range "100..1500";
                              }
                            }
                          }
                        }
                        case ping-psuedowire {
                          container pseudowire {
                            description
                              "Pseudowire Virtual Circuit";
                            leaf ipv4-address {
                              description
                                "Hostname or IPv4 address of peer";
                              mandatory true;
                              type union {
                                type inet:ip-address;
                                type string;
                              }
                            }
                            leaf vc-id {
                              description
                                "VC ID value";
                              mandatory true;
                              type uint32 {
                                range "1..4294967295";
                              }
                            }
                            leaf source-ipaddr {
                              description
                                "Source specified as an IP address";
                              type inet:ip-address;
                            }
                            uses config-ip-sla-mpls-lsp-submode-grouping {
                              augment "history" {
                                uses config-ip-sla-mpls-history-grouping;
                                uses config-ip-sla-mpls-enhanced-history-grouping;
                              }
                            }
                            uses config-ip-sla-mpls-ping-secondary-frequency-grouping;
                            leaf request-data-size {
                              description
                                "Request data size";
                              type uint16 {
                                range "100..1500";
                              }
                            }
                          }
                        }
                      }
                    }
                  }
                  case lsp-trace {
                    container trace {
                      description
                        "MPLS lsp trace operation";
                      container ipv4 {
                        description
                          "Target FEC address(broadcast disallowed)";
                        uses config-ip-sla-mpls-ping-trace-grouping;
                        uses config-ip-sla-mpls-lsp-submode-grouping {
                          augment "history" {
                            uses config-ip-sla-mpls-history-grouping;
                          }
                        }
                        leaf ttl {
                          description
                            "Time to live";
                          type uint8 {
                            range "1..30";
                          }
                          default "30";
                        }
                        leaf paths-of-statistics-kept {
                          description
                            "Maximum number of statistics paths to capture";
                          type uint8 {
                            range "1..128";
                          }
                          default "5";
                        }
                        leaf samples-of-history-kept {
                          description
                            "Maximum number of history samples to collect";
                          type uint8 {
                            range "1..30";
                          }
                          default "16";
                        }
                        leaf hops-of-statistics-kept {
                          description
                            "Maximum number of statistics hops to capture";
                          type uint8 {
                            range "1..30";
                          }
                          default "16";
                        }
                      }
                    }
                  }
                }
              }
            }
          }
          case http-secure-case {
            container http-secure {
              description
                "Secure HTTP Operation";
              container http {
                description
                  "Secure HTTP Operation";
                container secure {
                  description
                    "Secure HTTP Operation";
                  leaf https-method {
                    description
                      "HTTP get operation";
                    mandatory true;
                    type enumeration {
                      enum get;
                      enum head;
                    }
                  }
                  leaf url {
                    description
                      "URL";
                    mandatory true;
                    type string;
                  }
                  leaf name-server {
                    description
                      "Hostname or A.B.C.D/X:X:X:X::X  IPv4/IPv6 address";
                    type union {
                      type string;
                      type inet:ip-address;
                      type inet:ipv6-address;
                    }
                  }
                  leaf version {
                    description
                      "Http Version";
                    type enumeration {
                      enum 1.0;
                      enum 1.1;
                    }
                    default "1.0";
                  }
                  leaf source-interface {
                    description
                      "Source Interface";
                    type string;
                  }
                  leaf http-status-code-ignore {
                    description
                      "HTTP Status Code Check Disable";
                    type empty;
                  }
                  uses ip-sla-sub-mode-commands-grouping {
                    refine "timeout" {
                      default "60000";
                    }
                  }
                  container history {
                    description
                      "History and Distribution Data";
                    leaf distributions-of-statistics-kept {
                      description
                        "Maximum number of statistics distribution buckets to capture";
                      type uint8 {
                        range "1..20";
                      }
                      default "1";
                    }
                    leaf hours-of-statistics-kept {
                      description
                        "Maximum number of statistics hour groups to capture";
                      type uint8 {
                        range "0..25";
                      }
                      default "2";
                    }
                    leaf statistics-distribution-interval {
                      description
                        "Statistics distribution interval size";
                      type uint8 {
                        range "1..100";
                      }
                      units "miliseconds";
                      default "20";
                    }
                  }
                  leaf vrf {
                    description
                      "Configure IP SLAs for a new VPN Routing/Forwarding instance";
                    must '/ios:native/ios:vrf/ios:definition[ios:name=current()] or /ios:native/ios:ip/ios:vrf[ios:name=current()]' {
                      error-message "VRF must be created 1st, deleted last";
                    }
                    type string;
                  }
                }
              }
            }
          }
        }
        container modification-configuration {
          status obsolete;
          leaf owner {
            status obsolete;
            description
              "Owner of Entry";
            when "../../icmp-echo or
                  ../../icmp-jitter or
                  ../../path-echo or
                  ../../path-jitter or
                  ../../udp-echo or
                  ../../udp-jitter or
                  ../../http or
                  ../../dhcp or
                  ../../tcp-connect or
                  ../../dns or
                  ../../ftp or
                  ../../ethernet/echo or
                  ../../ethernet/jitter or
                  ../../ethernet/y1731-config or
                  ../../mpls";
            type string;
          }
          leaf tag {
            status obsolete;
            description
              "User defined tag";
            when "../../icmp-echo or
                  ../../icmp-jitter or
                  ../../path-echo or
                  ../../path-jitter or
                  ../../udp-echo or
                  ../../udp-jitter or
                  ../../http or
                  ../../dhcp or
                  ../../tcp-connect or
                  ../../dns or
                  ../../ftp or
                  ../../ethernet/echo or
                  ../../ethernet/jitter or
                  ../../mpls";
            type string;
          }
          leaf threshold {
            status obsolete;
            description
              "Operation threshold in milliseconds";
            when "../../icmp-echo or
                  ../../icmp-jitter or
                  ../../path-echo or
                  ../../path-jitter or
                  ../../udp-echo or
                  ../../udp-jitter or
                  ../../http or
                  ../../dhcp or
                  ../../tcp-connect or
                  ../../dns or
                  ../../ftp or
                  ../../ethernet/echo or
                  ../../ethernet/jitter or
                  ../../mpls";
            units "miliseconds";
            type uint32 {
              range "0..60000";
            }
            default "5000";
          }
          leaf timeout {
            status obsolete;
            description
              "Timeout of an operation";
            when "../../icmp-echo or
                  ../../icmp-jitter or
                  ../../path-echo or
                  ../../path-jitter or
                  ../../udp-echo or
                  ../../udp-jitter or
                  ../../http or
                  ../../dhcp or
                  ../../tcp-connect or
                  ../../dns or
                  ../../ftp or
                  ../../ethernet/echo or
                  ../../ethernet/jitter or
                  ../../mpls";
            units "miliseconds";
            type uint32 {
              range "0..604800000";
            }
            default "5000";
          }
          leaf frequency {
            status obsolete;
            description
              "Frequency of an operation";
            when "../../icmp-echo or
                  ../../icmp-jitter or
                  ../../path-echo or
                  ../../path-jitter or
                  ../../udp-echo or
                  ../../udp-jitter or
                  ../../http or
                  ../../dhcp or
                  ../../tcp-connect or
                  ../../dns or
                  ../../ftp or
                  ../../ethernet/echo or
                  ../../ethernet/jitter or
                  ../../ethernet/y1731-config/delay/sender/burst or
                  ../../ethernet/y1731-config/loss/wrapper-container/burst or
                  ../../mpls";
            units "seconds";
            type uint32 {
              range "1..604800";
            }
            default "60";
          }
          container history {
            status obsolete;
            description
              "History and Distribution Data";
            container enhanced {
              status obsolete;
              description
                "Enable enhanced history collection";
              when "../../../icmp-echo or
                    ../../../icmp-jitter or
                    ../../../udp-echo or
                    ../../../udp-jitter or
                    ../../../tcp-connect or
                    ../../../ethernet/echo or
                    ../../../ethernet/jitter or
                    ../../../mpls/lsp/ping";
              leaf interval {
                status obsolete;
                description
                  "Aggregation interval";
                type uint16 {
                  range "1..3600";
                }
              }
              leaf buckets {
                status obsolete;
                description
                  "Number of buckets to collect data";
                type uint8 {
                  range "1..100";
                }
              }
            }
            leaf buckets-kept {
              status obsolete;
              description
                "Maximum number of history buckets to collect";
              when "../../../icmp-echo or
                    ../../../path-echo or
                    ../../../udp-echo or
                    ../../../dhcp or
                    ../../../tcp-connect or
                    ../../../dns or
                    ../../../ftp or
                    ../../../ethernet/echo or
                    ../../../mpls";
              type uint8 {
                range "1..60";
              }
              default "15";
            }
            leaf distributions-of-statistics-kept {
              status obsolete;
              description
                "Maximum number of statistics distribution buckets to capture";
              when "../../../icmp-echo or
                    ../../../icmp-jitter or
                    ../../../path-echo or
                    ../../../udp-echo or
                    ../../../udp-jitter or
                    ../../../dhcp or
                    ../../../http or
                    ../../../tcp-connect or
                    ../../../dns or
                    ../../../ftp or
                    ../../../ethernet/echo or
                    ../../../ethernet/jitter or
                    ../../../mpls";
              type uint8 {
                range "1..20";
              }
              default "1";
            }
            leaf filter {
              status obsolete;
              description
                "Add operation to History when...";
              when "../../../icmp-echo or
                    ../../../path-echo or
                    ../../../udp-echo or
                    ../../../dhcp or
                    ../../../tcp-connect or
                    ../../../dns or
                    ../../../ftp or
                    ../../../ethernet/echo or
                    ../../../mpls";
              type enumeration {
                enum all;
                enum failures;
                enum none;
                enum overThreshold;
              }
              default "none";
            }
            leaf hours-of-statistics-kept {
              status obsolete;
              description
                "Maximum number of statistics hour groups to capture";
              when "../../../icmp-echo or
                    ../../../icmp-jitter or
                    ../../../path-echo or
                    ../../../udp-echo or
                    ../../../udp-jitter or
                    ../../../dhcp or
                    ../../../http or
                    ../../../tcp-connect or
                    ../../../dns or
                    ../../../ftp or
                    ../../../ethernet/echo or
                    ../../../ethernet/jitter or
                    ../../../mpls";
              type uint8 {
                range "0..25";
              }
              default "2";
            }
            leaf lives-kept {
              status obsolete;
              description
                "Maximum number of history lives to collect";
              when "../../../icmp-echo or
                    ../../../path-echo or
                    ../../../udp-echo or
                    ../../../dhcp or
                    ../../../tcp-connect or
                    ../../../dns or
                    ../../../ftp or
                    ../../../ethernet/echo or
                    ../../../mpls";
              type uint8 {
                range "0..2";
              }
              default "0";
            }
            leaf statistics-distribution-interval {
              status obsolete;
              description
                "Statistics distribution interval size";
              when "../../../icmp-echo or
                    ../../../icmp-jitter or
                    ../../../path-echo or
                    ../../../udp-echo or
                    ../../../udp-jitter or
                    ../../../dhcp or
                    ../../../http or
                    ../../../tcp-connect or
                    ../../../dns or
                    ../../../ftp or
                    ../../../ethernet/echo or
                    ../../../ethernet/jitter or
                    ../../../mpls";
              type uint8 {
                range "1..100";
              }
              default "20";
            }
            leaf interval {
              status obsolete;
              description
                "Specify number of intervals";
              when '../../../ethernet/y1731-config';
              type uint8 {
                range "1..10";
              }
            }
          }
          leaf paths-of-statistics-kept {
            status obsolete;
            description
              "Maximum number of statistics paths to capture";
            when "../../path-echo or
                  ../../mpls/lsp/trace";
            type uint8 {
              range "1..128";
            }
            default "5";
          }
          leaf samples-of-history-kept {
            status obsolete;
            description
              "Maximum number of history samples to collect";
            when "../../path-echo or
                  ../../mpls/lsp/trace";
            type uint8 {
              range "1..30";
            }
            default "16";
          }
          leaf hops-of-statistics-kept {
            status obsolete;
            description
              "Maximum number of statistics hops to capture";
            when "../../path-echo or
                  ../../mpls/lsp/trace";
            type uint8 {
              range "1..30";
            }
            default "16";
          }
          leaf-list lsr-path {
            status obsolete;
            description
              "Loose Source Routing Path";
            when "../../path-echo or
                  ../../path-jitter";
            type union {
              type string;
              type inet:ipv4-address;
            }
          }
          leaf request-data-size {
            status obsolete;
            description
              "Request data size";
            when "../../icmp-echo or
                  ../../path-echo or
                  ../../path-jitter or
                  ../../udp-echo or
                  ../../udp-jitter or
                  ../../ethernet/echo or
                  ../../ethernet/jitter or
                  ../../mpls/lsp/ping";
            type uint32 {
              range "0..16384";
            }
            default "28";
          }
          choice tos-param {
            status obsolete;
            case tos {
              status obsolete;
              leaf tos {
                status obsolete;
                description
                  "Type Of Service";
                when "../../icmp-echo or
                      ../../icmp-jitter or
                      ../../path-echo or
                      ../../path-jitter or
                      ../../udp-echo or
                      ../../udp-jitter or
                      ../../http or
                      ../../tcp-connect";
                type uint8 {
                  range "0..255";
                }
              }
            }
            case traffic-class {
              status obsolete;
              leaf traffic-class {
                status obsolete;
                description
                  "Traffic class";
                when "../../icmp-echo or
                      ../../path-echo or
                      ../../path-jitter or
                      ../../udp-echo or
                      ../../udp-jitter or
                      ../../http or
                      ../../tcp-connect";
                type uint8 {
                  range "0..255";
                }
              }
            }
          }
          leaf verify-data {
            status obsolete;
            description
              "Verify data";
            when "../../icmp-echo or
                  ../../path-echo or
                  ../../path-jitter or
                  ../../udp-echo or
                  ../../udp-jitter";
            type boolean;
          }
          leaf vrf {
            status obsolete;
            description
              "Configure IP SLAs for a VPN Routing/Forwarding instance";
            when "../../icmp-echo or
                  ../../icmp-jitter or
                  ../../path-echo or
                  ../../path-jitter or
                  ../../udp-echo or
                  ../../udp-jitter or
                  ../../http or
                  ../../tcp-connect or
                  ../../dns";
            must '/ios:native/ios:vrf/ios:definition[ios:name=current()] or /ios:native/ios:ip/ios:vrf[ios:name=current()]' {
              error-message "VRF must be created 1st, deleted last";
            }
            type string;
          }
          leaf flow-label {
            status obsolete;
            description
              "Flow Label Value for IPv6 destination";
            when '../../path-jitter';
            type uint64 {
              range "0..1048575";
            }
          }
          leaf data-pattern {
            status obsolete;
            description
              "Data Pattern in Hex 0-FFFFFFFF";
            when "../../icmp-echo or
                  ../../udp-echo or
                  ../../udp-jitter";
            type string;
          }
          leaf response-data-size {
            status obsolete;
            description
              "Number of bytes in response payload";
            when '../../udp-jitter';
            type uint16 {
              range "20..17512";
            }
          }
          leaf precision {
            status obsolete;
            description
              "Set precision of measurement";
            when '../../udp-jitter';
            type enumeration {
              enum microseconds;
              enum milliseconds;
            }
            default "milliseconds";
          }
          leaf optimize {
            status obsolete;
            description
              "Optimize timestamp of measurement";
            when '../../udp-jitter';
            type enumeration {
              enum timestamp;
            }
          }
          leaf enhanced {
            status obsolete;
            description
              "Improve the accuracy of measurement";
            when '../../udp-jitter';
            type enumeration {
              enum timestamp;
            }
          }
          leaf operation-packet-priority {
            status obsolete;
            description
              "Set operation packet properties";
            when '../../udp-jitter';
            type enumeration {
              enum high;
              enum normal;
            }
          }
          container clock-tolerance {
            status obsolete;
            description
              "Set acceptable clock synchronization error";
            when '../../udp-jitter';
            container ntp {
              status obsolete;
              description
                "Acceptable clock synchronization error due to NTP";
              container oneway {
                status obsolete;
                description
                  "Acceptable clock synchronization error in one-way measurement";
                choice clock-tolerance-param {
                  status obsolete;
                  case absolute-type {
                    status obsolete;
                    leaf absolute {
                      status obsolete;
                      description
                        "Acceptable error in microseconds";
                      type uint32 {
                        range "0..100000";
                      }
                    }
                  }
                  case percent-type {
                    status obsolete;
                    leaf percent {
                      status obsolete;
                      description
                        "Acceptable error as percent of value measured";
                      type uint8 {
                        range "0..100";
                      }
                    }
                  }
                }
              }
            }
          }
          container percentile {
            status obsolete;
            description
              "Set percentile statistics levels";
            when "../../udp-jitter or
                  ../../ethernet/jitter";
            leaf jitteravg {
              status obsolete;
              description
                "% of Average Jitter values to use (default 100%)";
              type uint8 {
                range "90..100";
              }
            }
            leaf jitterds {
              status obsolete;
              description
                "% of Destination to source jitter value to use (default 100%)";
              type uint8 {
                range "90..100";
              }
            }
            leaf jittersd {
              status obsolete;
              description
                "% of Source to destination jitter value to use (default 100%)";
              type uint8 {
                range "90..100";
              }
            }
            leaf owds {
              status obsolete;
              description
                "% of One way destination to source value to use (default 100%)";
              type uint8 {
                range "90..100";
              }
            }
            leaf owsd {
              status obsolete;
              description
                "% of One way source to destination value to use (default 100%)";
              type uint8 {
                range "90..100";
              }
            }
            leaf rtt {
              status obsolete;
              description
                "% of Round Trip Time value to use (default 100%)";
              type uint8 {
                range "90..100";
              }
            }
          }
          container http-raw-request {
            status obsolete;
            description
              "HTTP Raw Request configuration";
            when '../../http';
            leaf raw-request-string {
              status obsolete;
              description
                "HTTP Raw string";
              type string;
            }
          }
          leaf http-status-code-ignore {
            status obsolete;
            description
              "HTTP Status Code Check Disable";
            when '../../http';
            type boolean;
          }
          leaf cos {
            status obsolete;
            description
              "Class Of Service";
            when "../../ethernet/echo or
                  ../../ethernet/jitter ";
            type uint8 {
              range "0..7";
            }
          }
          container aggregate {
            status obsolete;
            description
              "Aggregate parameters";
            when '../../ethernet/y1731-config';
            leaf interval_leaf {
              status obsolete;
              description
                "Specify interval period";
              when '../../../ethernet/y1731-config/delay/receive';
              type uint16 {
                range "1..65535";
              }
            }
            container interval {
              status obsolete;
              description
                "Specify interval period";
              when "../../../ethernet/y1731-config/delay/sender or
                    ../../../ethernet/y1731-config/loss";
              leaf interval-period {
                description
                  "Specify interval period";
                status obsolete;
                when "not (../../../../ethernet/y1731-config/delay/sender/burst) and
                      not (../../../../ethernet/y1731-config/loss/wrapper-container/burst)";
                type uint32 {
                  range "1..65535";
                }
              }
              leaf burst-cycles {
                status obsolete;
                description
                  "Specify number of burst cycles";
                when "(../../../../ethernet/y1731-config/delay/sender/burst) or
                      (../../../../ethernet/y1731-config/loss/wrapper-container/burst)";
                type uint16 {
                  range "1..900";
                }
              }
            }
          }
          container clock {
            status obsolete;
            description
              "Specify clock parameters";
            when "../../ethernet/y1731-config/delay/sender/name='DMM' or
                  ../../ethernet/y1731-config/delay/sender/name='DMMv1'";
            leaf sync {
              status obsolete;
              description
                "Clocks are in sync on sender and responder";
              type boolean;
            }
          }
          container distribution {
            status obsolete;
            description
              "Specify the distribution statistics parameters";
            when '../../ethernet/y1731-config';
            container delay {
              status obsolete;
              description
                "Specify delay distribution parameters";
              container one-way {
                status obsolete;
                leaf one-way {
                  status obsolete;
                  description
                    "Specify one-way distribution parameters";
                  type uint8 {
                    range "1..10";
                  }
                }
                leaf bin-upper-boundry {
                  status obsolete;
                  description
                    "Specify a comma separated list of bin upper boundaries in micro-second";
                  type string;
                }
              }
              container two-way {
                status obsolete;
                when "../../../../ethernet/y1731-config/delay/sender/name='DMM' or
                      ../../../../ethernet/y1731-config/delay/sender/name='DMMv1'";
                leaf two-way {
                  status obsolete;
                  description
                    "Specify two-way distribution parameters";
                  type uint8 {
                    range "1..10";
                  }
                }
                leaf bin-upper-boundry {
                  status obsolete;
                  description
                    "Specify a comma separated list of bin upper boundaries in micro-second";
                  type string;
                }
              }
            }
            container delay-variation {
              status obsolete;
              description
                "Specify delay-variation distribution parameters";
              container one-way {
                status obsolete;
                leaf one-way {
                  status obsolete;
                  description
                    "Specify one-way distribution parameters";
                  type uint8 {
                    range "1..10";
                  }
                }
                leaf bin-upper-boundry {
                  status obsolete;
                  description
                    "Specify a comma separated list of bin upper boundaries in micro-second";
                  type string;
                }
              }
              container two-way {
                status obsolete;
                when "../../../../ethernet/y1731-config/delay/sender/name='DMM' or
                      ../../../../ethernet/y1731-config/delay/sender/name='DMMv1'";
                leaf two-way {
                  status obsolete;
                  description
                    "Specify two-way distribution parameters";
                  type uint8 {
                    range "1..10";
                  }
                }
                leaf bin-upper-boundry {
                  status obsolete;
                  description
                    "Specify a comma separated list of bin upper boundaries in micro-second";
                  type string;
                }
              }
            }
          }
          container frame {
            status obsolete;
            description
              "Specify frame parameters";
            when '../../ethernet/y1731-config';
            leaf interval {
              status obsolete;
              description
                "Specify inter-frame period";
              when "../../../ethernet/y1731-config/delay/sender or
                    ../../../ethernet/y1731-config/loss";
              type frame-interval-type;
            }
            leaf size {
              status obsolete;
              description
                "Specify payload size in 4 octet increments";
              when "../../../ethernet/y1731-config/delay/sender or
                    ../../../ethernet/y1731-config/loss/wrapper-container/name='SLM'";
              type uint16 {
                range "64..384";
              }
            }
            leaf offset {
              status obsolete;
              description
                "Specify the frame offset to be used for calculations";
              when "(../../../ethernet/y1731-config/delay/receive or
                    ../../../ethernet/y1731-config/delay/sender/name = 'DMM' or
                    ../../../ethernet/y1731-config/delay/sender/name = 'DMMv1')";
              type uint8 {
                range "1..10";
              }
            }
            leaf consecutive {
              status obsolete;
              description
                "Specify the consecutive frames to be used for calculations";
              when '../../../ethernet/y1731-config/loss';
              type uint16 {
                range "1..10";
              }
            }
            leaf burst {
              status obsolete;
              description
                "Number of frames to send per burst";
              when "(../../../ethernet/y1731-config/delay/sender/burst) or
                    (../../../ethernet/y1731-config/loss/wrapper-container/burst)";
              type uint16 {
                range "1..65535";
              }
            }
          }
          container availability {
            status obsolete;
            description
              "Specify the availability parameters";
            when '../../ethernet/y1731-config/loss';
            container algorithm {
              status obsolete;
              description
                "Specify the algorithm to use";
              leaf sliding-window {
                status obsolete;
                description
                  "Use a sliding window";
                type boolean;
              }
              leaf static-window {
                status obsolete;
                description
                  "Use a static window";
                type boolean;
              }
            }
          }
          leaf max-delay {
            status obsolete;
            description
              "Specify the max delay";
            when "../../ethernet/y1731-config/loss/wrapper-container/name='LMM' or
                  ../../ethernet/y1731-config/delay/receive/name='1DM' or
                  ../../ethernet/y1731-config/delay/sender/name='DMM' or
                  ../../ethernet/y1731-config/delay/sender/name='DMMv1' or
                  ../../ethernet/y1731-config/delay/sender/name='1DM'";
            type uint16 {
              range "1..65535";
            }
          }
          container aggregation {
            status obsolete;
            description
              "Statistics aggregation";
            if-feature "ios-features:service-performance";
            when '../../service-performance';
            container interval {
              status obsolete;
              description
                "Statistics aggregation period";
              leaf buckets {
                status obsolete;
                description
                  "interval statistic buckets";
                type uint8 {
                  range "1..30";
                }
              }
            }
          }
          leaf description {
            status obsolete;
            description
              "Operation Description";
            if-feature "ios-features:service-performance";
            when '../../service-performance';
            type string;
          }
          container duration {
            status obsolete;
            description
              "Service Performance duration configuration";
            if-feature "ios-features:service-performance";
            when '../../service-performance';
            leaf time {
              status obsolete;
              description
                "Time based duration";
              type uint16 {
                range "10..40950";
              }
            }
          }
          container frequency_serv_perf {
            status obsolete;
            description
              "Scheduled frequency";
            if-feature "ios-features:service-performance";
            when '../../service-performance';
            leaf time {
              status obsolete;
              description
                "Frequency period";
              type uint32 {
                range "20..604800";
              }
            }
            container frequency-iteration {
              status obsolete;
              description
                "Frequency iteration configuration";
              leaf iteration {
                status obsolete;
                description
                  "Iteration number";
                type uint8 {
                  range "1..100";
                }
              }
              leaf delay {
                status obsolete;
                description
                  "Delay between interactions";
                type uint8 {
                  range "0..10";
                }
              }
            }
          }
          container loopback {
            status obsolete;
            description
              "loopback";
            if-feature "ios-features:service-performance";
            when '../../service-performance';
            container direction {
              status obsolete;
              description
                "loopback direction";
              leaf internal {
                status obsolete;
                description
                  "internal direction";
                type boolean;
              }
              leaf external {
                status obsolete;
                description
                  "external direction";
                type boolean;
              }
            }
          }
          container measurement-type {
            status obsolete;
            description
              "Measurement";
            if-feature "ios-features:service-performance";
            when '../../service-performance';
            leaf direction {
              status obsolete;
              description
                "Measurement direction";
              type enumeration {
                enum external {
                  description
                    "external direction";
                }
                enum internal {
                  description
                    "internal direction";
                }
              }
            }
            container conform-color {
              status obsolete;
              description
                "conform-color";
              leaf cos {
                status obsolete;
                description
                  "configure conform COS";
                if-feature "ios-features:service-performance";
                when '../../../../service-performance/type/ethernet';
                type uint8 {
                  range "0..7";
                }
              }
              leaf dscp {
                status obsolete;
                description
                  "configure conform DSCP";
                if-feature "ios-features:service-performance";
                when '../../../../service-performance/type/ip';
                type union {
                  type uint8 {
                    range "0..63";
                  }
                  type reply-dscp-bits-type;
                }
              }
            }
            container exceed-color {
              status obsolete;
              description
                "exceed-color";
              leaf cos {
                status obsolete;
                description
                  "configure conform COS";
                if-feature "ios-features:service-performance";
                when '../../../../service-performance/type/ethernet';
                type uint8 {
                  range "0..7";
                }
              }
              leaf dscp {
                status obsolete;
                description
                  "configure conform DSCP";
                if-feature "ios-features:service-performance";
                when '../../../../service-performance/type/ip';
                type union {
                  type uint8 {
                    range "0..63";
                  }
                  type reply-dscp-bits-type;
                }
              }
            }
            leaf delay {
              status obsolete;
              description
                "Delay measurement";
              type empty;
            }
            leaf jitter {
              status obsolete;
              description
                "Jitter measurement";
              type empty;
            }
            leaf loss {
              status obsolete;
              description
                "loss measurement";
              type empty;
            }
            leaf receive {
              status obsolete;
              description
                "Received bytes/packets measurement";
              type empty;
            }
            leaf throughput {
              status obsolete;
              description
                "Throughput measurement";
              type empty;
            }
          }
          container profile {
            status obsolete;
            when '../../service-performance';
            if-feature "ios-features:service-performance";
            description
              "Service Performance Profile";
            container packet {
              status obsolete;
              description
                "Packet Profiles";
              leaf dscp {
                status obsolete;
                description
                  "Configure DSCP";
                type union {
                  type uint8 {
                    range "0..63";
                  }
                  type reply-dscp-bits-type;
                }
              }
              leaf ethertype {
                status obsolete;
                description
                  "Frame type";
                type enumeration {
                  enum ipv4;
                  enum ipv6;
                }
              }
              leaf inner-cos {
                status obsolete;
                description
                  "Inner COS";
                type uint8 {
                  range "0..7";
                }
              }
              leaf inner-vlan {
                status obsolete;
                description
                  "Specify Inner VLAN";
                type uint16 {
                  range "0..4095";
                }
              }
              leaf outer-cos {
                status obsolete;
                description
                  "Outer COS";
                type uint8 {
                  range "0..7";
                }
              }
              leaf outer-vlan {
                status obsolete;
                description
                  "Specify the Outer VLAN";
                type uint16 {
                  range "0..4095";
                }
              }
              leaf packet-size {
                status obsolete;
                description
                  "Packet Size";
                type packet-size-type;
              }
              leaf src-mac-addr {
                status obsolete;
                description
                  "The source mac-address";
                if-feature "ios-features:service-performance";
                when '../../../../service-performance/type/ethernet';
                type ios-types:cisco-mac-address-type;
              }
              leaf source-ip-addr {
                status obsolete;
                description
                  "ip address";
                if-feature "ios-features:service-performance";
                when '../../../../service-performance/type/ip';
                type union {
                  type string;
                  type inet:ip-address;
                }
              }
              container tunnel {
                status obsolete;
                description
                  "Tunnel type";
                leaf exp {
                  status obsolete;
                  description
                    "Exp value";
                  type uint8 {
                    range "0..7";
                  }
                }
              }
            }
            container traffic {
              status obsolete;
              description
                "Service Performance traffic profile";
              leaf direction {
                status obsolete;
                description
                  "Traffic direction";
                type enumeration {
                  enum external {
                    description
                      "external direction";
                  }
                  enum internal {
                    description
                      "internal direction";
                  }
                }
              }
              leaf cbs {
                status obsolete;
                description
                  "Committed Burst Size";
                type uint32 {
                  range "0..16000000";
                }
                units "Kbps";
              }
              leaf cir {
                status obsolete;
                description
                  "Committed Information Rate. The range mentioned is for 10G interface. For 1G interface, the range is 0..1000000";
                type uint32 {
                  range "0..10000000";
                }
                units "Kbps";
              }
              leaf ebs {
                status obsolete;
                description
                  "Excess Burst Size";
                type uint32 {
                  range "0..16000000";
                }
                units "Kbps";
              }
              leaf eir {
                status obsolete;
                description
                  "Excess Information Rate. The range mentioned is for 10G interface. For 1G interface, the range is 0..1000000";
                type uint32 {
                  range "0..10000000";
                }
                units "Kbps";
              }
              container rate-step {
                status obsolete;
                description
                  "Rate Step";
                choice Kbps_or_pps {
                  status obsolete;
                  container Kbps {
                    status obsolete;
                    description
                      "Kilobits per second rate. The range mentioned is for 10G interface. For 1G interface, the range is 0..1000000";
                    leaf step1 {
                      status obsolete;
                      description
                        "Step 1 (Kbps/pps)";
                      type uint32 {
                        range "1..10000000";
                      }
                      units "Kbps/pps";
                    }
                    leaf step2 {
                      status obsolete;
                      description
                        "Step 2 (Kbps/pps), Step 2 >= Step 1";
                      must '../step2 >= ../step1';
                      type uint32 {
                        range "1..10000000";
                      }
                      units "Kbps/pps";
                    }
                    leaf step3 {
                      status obsolete;
                      description
                        "Step 3 (Kbps/pps), Step 3 >= Step 2";
                      must '../step3 >= ../step2';
                      type uint32 {
                        range "1..10000000";
                      }
                      units "Kbps/pps";
                    }
                    leaf step4 {
                      status obsolete;
                      description
                        "Step 4 (Kbps/pps), Step 4 >= Step 3";
                      must '../step4 >= ../step3';
                      type uint32 {
                        range "1..10000000";
                      }
                      units "Kbps/pps";
                    }
                    leaf step5 {
                      status obsolete;
                      description
                        "Step 5 (Kbps/pps), Step 5 >= Step 4";
                      must '../step5 >= ../step4';
                      type uint32 {
                        range "1..10000000";
                      }
                      units "Kbps/pps";
                    }
                    leaf step6 {
                      status obsolete;
                      description
                        "Step 6 (Kbps/pps), Step 6 >= Step 5";
                      must '../step6 >= ../step5';
                      type uint32 {
                        range "1..10000000";
                      }
                      units "Kbps/pps";
                    }
                    leaf step7 {
                      status obsolete;
                      description
                        "Step 7 (Kbps/pps), Step 7 >= Step 6";
                      must '../step7 >= ../step6';
                      type uint32 {
                        range "1..10000000";
                      }
                      units "Kbps/pps";
                    }
                    leaf step8 {
                      status obsolete;
                      description
                        "Step 8 (Kbps/pps), Step 8 >= Step 7";
                      must '../step8 >= ../step7';
                      type uint32 {
                        range "1..10000000";
                      }
                      units "Kbps/pps";
                    }
                    leaf step9 {
                      status obsolete;
                      description
                        "Step 9 (Kbps/pps), Step 9 >= Step 8";
                      must '../step9 >= ../step8';
                      type uint32 {
                        range "1..10000000";
                      }
                      units "Kbps/pps";
                    }
                    leaf step10 {
                      status obsolete;
                      description
                        "Step 10 (Kbps/pps), Step 10 >= Step 9";
                      must '../step10 >= ../step9';
                      type uint32 {
                        range "1..10000000";
                      }
                      units "Kbps/pps";
                    }
                  }
                  container pps {
                    status obsolete;
                    description
                      "Packet per second rate";
                    leaf step1 {
                      status obsolete;
                      description
                        "Step 1 (Kbps/pps)";
                      type uint32 {
                        range "1..15000000";
                      }
                      units "Kbps/pps";
                    }
                    leaf step2 {
                      status obsolete;
                      description
                        "Step 2 (Kbps/pps), Step 2 >= Step 1";
                      must '../step2 >= ../step1';
                      type uint32 {
                        range "1..15000000";
                      }
                      units "Kbps/pps";
                    }
                    leaf step3 {
                      status obsolete;
                      description
                        "Step 3 (Kbps/pps), Step 3 >= Step 2";
                      must '../step3 >= ../step2';
                      type uint32 {
                        range "1..15000000";
                      }
                      units "Kbps/pps";
                    }
                    leaf step4 {
                      status obsolete;
                      description
                        "Step 4 (Kbps/pps), Step 4 >= Step 3";
                      must '../step4 >= ../step3';
                      type uint32 {
                        range "1..15000000";
                      }
                      units "Kbps/pps";
                    }
                    leaf step5 {
                      status obsolete;
                      description
                        "Step 5 (Kbps/pps), Step 5 >= Step 4";
                      must '../step5 >= ../step4';
                      type uint32 {
                        range "1..15000000";
                      }
                      units "Kbps/pps";
                    }
                    leaf step6 {
                      status obsolete;
                      description
                        "Step 6 (Kbps/pps), Step 6 >= Step 5";
                      must '../step6 >= ../step5';
                      type uint32 {
                        range "1..15000000";
                      }
                      units "Kbps/pps";
                    }
                    leaf step7 {
                      status obsolete;
                      description
                        "Step 7 (Kbps/pps), Step 7 >= Step 6";
                      must '../step7 >= ../step6';
                      type uint32 {
                        range "1..15000000";
                      }
                      units "Kbps/pps";
                    }
                    leaf step8 {
                      status obsolete;
                      description
                        "Step 8 (Kbps/pps), Step 8 >= Step 7";
                      must '../step8 >= ../step7';
                      type uint32 {
                        range "1..15000000";
                      }
                      units "Kbps/pps";
                    }
                    leaf step9 {
                      status obsolete;
                      description
                        "Step 9 (Kbps/pps), Step 9 >= Step 8";
                      must '../step9 >= ../step8';
                      type uint32 {
                        range "1..15000000";
                      }
                      units "Kbps/pps";
                    }
                    leaf step10 {
                      status obsolete;
                      description
                        "Step 10 (Kbps/pps), Step 10 >= Step 9";
                      must '../step10 >= ../step9';
                      type uint32 {
                        range "1..15000000";
                      }
                      units "Kbps/pps";
                    }
                  }
                }
              }
            }
          }
          leaf signature {
            status obsolete;
            description
              "Payload Contents";
            if-feature "ios-features:service-performance";
            when '../../service-performance';
            type string;
          }
          container control {
            status obsolete;
            description
              "Set control protocol parameters";
            leaf retry {
              status obsolete;
              description
                "How often the control message should do a retry (default 3 times)";
              when '../../../udp-jitter';
              type uint8 {
                range "1..5";
              }
              default "3";
            }
            leaf timeout {
              status obsolete;
              description
                "How long to wait for control message timeout (default 5 seconds)";
              when '../../../udp-jitter';
              type uint16 {
                range "1..10000";
              }
              default "5000";
            }
          }
          leaf exp {
            status obsolete;
            description
              "EXP bits in MPLS header";
            when "../../mpls/lsp/ping or
                  ../../mpls/lsp/trace";
            type uint8 {
              range "0..7";
            }
            default "0";
          }
          leaf ttl {
            status obsolete;
            description
              "Time to live.
               For MPLS LSP trace probe, ttl range is 1-30";
            when "../../mpls/lsp/ping/ipv4 or
                  ../../mpls/lsp/trace";
            type uint8 {
              range "1..255";
            }
            default "255";
          }
          container secondary-frequency {
            status obsolete;
            description
              "Frequency to be used if there is any violation condition happens";
            choice type-params {
              status obsolete;
              case connection-loss-type {
                status obsolete;
                leaf connection-loss {
                  status obsolete;
                  description
                    "Enable secondary frequency for connection loss";
                  units "seconds";
                  type uint32 {
                    range "1..604800";
                  }
                }
              }
              case timeout-type {
                status obsolete;
                leaf timeout {
                  status obsolete;
                  description
                    "Enable secondary frequency for timeout";
                  units "seconds";
                  type uint32 {
                    range "1..604800";
                  }
                }
              }
            }
          }
        }
      }
      container enable {
        leaf reaction-alerts {
          type empty;
        }
      }
      container responder-config {
        description
          "Enable IP SLAs Responder configuration";
        leaf enable {
          description
            "Enable IP SLAs general Responder";
          type empty;
        }
        container udp-echo {
          description
            "Setup udp-echo responder";
          list port-config {
            description
              "Permanent port list";
            key "port";
            leaf port {
              description
                "Permanent port";
              type uint16 {
                range "1..65535";
              }
            }
          }
          list port-vrf {
            description
              "Permanent port and vrf list";
            key "port vrf";
            leaf port {
              description
                "Permanent port";
              type uint16 {
                range "1..65535";
              }
            }
            leaf vrf {
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          list ipaddress-port {
            description
              "Permanent address and port list";
            key "ipaddress port";
            leaf ipaddress {
              description
                "IPv4/IPv6 address of the permanent port responder";
              type union {
                type inet:ipv4-address;
                type inet:ipv6-address;
              }
            }
            leaf port {
              description
                "Permanent port";
              type uint16 {
                range "1..65535";
              }
            }
          }
          list ipaddress-port-vrf {
            description
              "Permanent address, port and VPN routing/forwarding instance.";
            key "ipaddress port vrf";
            leaf ipaddress {
              description
                "IPv4/IPv6 address of the permanent port responder";
              type union {
                type inet:ipv4-address;
                type inet:ipv6-address;
              }
            }
            leaf port {
              description
                "Permanent port";
              type uint16 {
                range "1..65535";
              }
            }
            leaf vrf {
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
        }
        container tcp-connect {
          description
            "Setup tcp-connect responder";
          list port-config {
            description
              "Permanent port list";
            key "port";
            leaf port {
              description
                "Permanent port";
              type uint16 {
                range "1..65535";
              }
            }
          }
          list port-vrf {
            description
              "Permanent port and vrf list";
            key "port vrf";
            leaf port {
              description
                "Permanent port";
              type uint16 {
                range "1..65535";
              }
            }
            leaf vrf {
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          list ipaddress-port {
            description
              "Permanent address and port list";
            key "ipaddress port";
            leaf ipaddress {
              description
                "IPv4/IPv6 address of the permanent port responder";
              type union {
                type inet:ipv4-address;
                type inet:ipv6-address;
              }
            }
            leaf port {
              description
                "Permanent port";
              type uint16 {
                range "1..65535";
              }
            }
          }
          list ipaddress-port-vrf {
            description
              "Permanent address, port and VPN routing/forwarding instance.";
            key "ipaddress port vrf";
            leaf ipaddress {
              description
                "IPv4/IPv6 address of the permanent port responder";
              type union {
                type inet:ipv4-address;
                type inet:ipv6-address;
              }
            }
            leaf port {
              description
                "Permanent port";
              type uint16 {
                range "1..65535";
              }
            }
            leaf vrf {
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
        }
        container twamp {
          description
            "Setup TWAMP responder";
          presence "true";
          leaf timeout {
            description
              "Inactivity timeout period";
            type uint32 {
              range "1..604800";
            }
            default "900";
          }
        }
        container twamp-light {
          description
            "Setup TWAMP Light responder";
          list test-session {
            description
              "TWAMP Light test session";
            key "session-number";
            leaf session-number {
              description
                "TWAMP Light test session identifier";
              type uint8 {
                range "1..100";
              }
            }
            container local-ip {
              choice local-ip-param {
                mandatory true;
                case address {
                  leaf address {
                    description
                      "Local IP/IPv6 address";
                    type inet:ip-address;
                  }
                }
                case any-address {
                  leaf any {
                    description
                      "Any local address";
                    type enumeration {
                      enum ipv4;
                      enum ipv6;
                    }
                  }
                }
              }
            }
            leaf local-port {
              description
                "Local port number";
              mandatory true;
              type uint16 {
                range "1..65535";
              }
            }
            container remote-ip {
              choice remote-ip-param {
                mandatory true;
                case address {
                  leaf address {
                    description
                      "Remote IP/IPv6 address";
                    type inet:ip-address;
                  }
                }
                case any-address {
                  leaf any {
                    description
                      "Any address";
                    type enumeration {
                      enum ipv4;
                      enum ipv6;
                    }
                  }
                }
              }
            }
            container remote-port {
              choice remote-port-param {
                mandatory true;
                case port-number {
                  leaf port {
                    description
                      "Local port number";
                    type uint16 {
                      range "1..65535";
                    }
                  }
                }
                case port-any {
                  leaf any {
                    description
                      "Any port number";
                    type empty;
                  }
                }
              }
            }
            leaf vrf {
              description
                "VPN Routing/Forwarding instance";
              must '/ios:native/ios:vrf/ios:definition[ios:name=current()] or /ios:native/ios:ip/ios:vrf[ios:name=current()]' {
                error-message "VRF must be created 1st, deleted last";
              }
              type string;
            }
            leaf timeout {
              description
                "TWAMP Light test session timeout";
              units "seconds";
              type uint32 {
                range "1..604800";
              }
            }
          }
        }
      }
      container responder {
        description
          "Enable IP SLAs Responder";
        status deprecated;
        presence "true";
        container udp-echo {
          status deprecated;
          description
            "Setup udp-echo responder";
          list port-config {
            status deprecated;
            description
              "Permanent port list";
            key "port";
            leaf port {
              status deprecated;
              description
                "Permanent port";
              type uint16 {
                range "1..65535";
              }
            }
          }
          list port-vrf {
            status deprecated;
            description
              "Permanent port and vrf list";
            key "port vrf";
            leaf port {
              status deprecated;
              description
                "Permanent port";
              type uint16 {
                range "1..65535";
              }
            }
            leaf vrf {
              status deprecated;
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          list ipaddress-port {
            status deprecated;
            description
              "Permanent address and port list";
            key "ipaddress port";
            leaf ipaddress {
              status deprecated;
              description
                "IPv4/IPv6 address of the permanent port responder";
              type union {
                type inet:ipv4-address;
                type inet:ipv6-address;
              }
            }
            leaf port {
              status deprecated;
              description
                "Permanent port";
              type uint16 {
                range "1..65535";
              }
            }
          }
          list ipaddress-port-vrf {
            status deprecated;
            description
              "Permanent address, port and VPN routing/forwarding instance.";
            key "ipaddress port vrf";
            leaf ipaddress {
              status deprecated;
              description
                "IPv4/IPv6 address of the permanent port responder";
              type union {
                type inet:ipv4-address;
                type inet:ipv6-address;
              }
            }
            leaf port {
              status deprecated;
              description
                "Permanent port";
              type uint16 {
                range "1..65535";
              }
            }
            leaf vrf {
              status deprecated;
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          leaf port {
            status deprecated;
            description
              "Permanent port (DEPRECATED, use port-config container)";
            type uint16 {
              range "1..65535";
            }
          }
          list ipaddress {
            status deprecated;
            description
              "Permanent address (DEPRECATED, use ipaddress-port list)";
            key "host";
            leaf host {
              status deprecated;
              type union {
                type inet:ipv4-address;
                type inet:ipv6-address;
              }
            }
            leaf port {
              status deprecated;
              description
                "Permanent port";
              type uint16 {
                range "1..65535";
              }
            }
          }
        }
        container tcp-connect {
          status deprecated;
          description
            "Setup tcp-connect responder";
          list port-config {
            status deprecated;
            description
              "Permanent port list";
            key "port";
            leaf port {
              status deprecated;
              description
                "Permanent port";
              type uint16 {
                range "1..65535";
              }
            }
          }
          list port-vrf {
            status deprecated;
            description
              "Permanent port and vrf list";
            key "port vrf";
            leaf port {
              status deprecated;
              description
                "Permanent port";
              type uint16 {
                range "1..65535";
              }
            }
            leaf vrf {
              status deprecated;
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          list ipaddress-port {
            status deprecated;
            description
              "Permanent address and port list";
            key "ipaddress port";
            leaf ipaddress {
              status deprecated;
              description
                "IPv4/IPv6 address of the permanent port responder";
              type union {
                type inet:ipv4-address;
                type inet:ipv6-address;
              }
            }
            leaf port {
              status deprecated;
              description
                "Permanent port";
              type uint16 {
                range "1..65535";
              }
            }
          }
          list ipaddress-port-vrf {
            status deprecated;
            description
              "Permanent address, port and VPN routing/forwarding instance.";
            key "ipaddress port vrf";
            leaf ipaddress {
              status deprecated;
              description
                "IPv4/IPv6 address of the permanent port responder";
              type union {
                type inet:ipv4-address;
                type inet:ipv6-address;
              }
            }
            leaf port {
              status deprecated;
              description
                "Permanent port";
              type uint16 {
                range "1..65535";
              }
            }
            leaf vrf {
              status deprecated;
              description
                "Configure permanent port for a VPN Routing/Forwarding instance";
              must '/ios:native/ios:vrf/ios:definition[ios:name=current()] or /ios:native/ios:ip/ios:vrf[ios:name=current()]' {
                error-message "VRF must be created 1st, deleted last";
              }
              type string;
            }
          }
          leaf port {
            status deprecated;
            description
              "Permanent port (DEPRECATED, use port-config container)";
            type uint16 {
              range "1..65535";
            }
          }
          list ipaddress {
            status deprecated;
            description
              "Permanent address (DEPRECATED, use ipaddress-port list)";
            key "host";
            leaf host {
              status deprecated;
              type union {
                type inet:ipv4-address;
                type inet:ipv6-address;
              }
            }
            leaf port {
              status deprecated;
              description
                "Permanent port";
              type uint16 {
                range "1..65535";
              }
            }
          }
        }
        container twamp {
          status deprecated;
          description
            "Setup TWAMP responder";
          presence "true";
          leaf timeout {
            status deprecated;
            description
              "Inactivity timeout period";
            type uint32 {
              range "1..604800";
            }
            default "900";
          }
        }
        container twamp-light {
          status deprecated;
          description
            "Setup TWAMP Light responder";
          list test-session {
            status deprecated;
            description
              "TWAMP Light test session";
            key "session-number";
            leaf session-number {
              status deprecated;
              description
                "TWAMP Light test session identifier";
              type uint8 {
                range "1..100";
              }
            }
            container local-ip {
              status deprecated;
              choice local-ip-param {
                mandatory true;
                case address {
                  status deprecated;
                  leaf address {
                    status deprecated;
                    description
                      "Local IP/IPv6 address";
                    type inet:ip-address;
                  }
                }
                case any-address {
                  status deprecated;
                  leaf any {
                    status deprecated;
                    description
                      "Any local address";
                    type enumeration {
                      enum ipv4;
                      enum ipv6;
                    }
                  }
                }
              }
            }
            leaf local-port {
              status deprecated;
              description
                "Local port number";
              mandatory true;
              type uint16 {
                range "1..65535";
              }
            }
            container remote-ip {
              status deprecated;
              choice remote-ip-param {
                mandatory true;
                case address {
                  status deprecated;
                  leaf address {
                    status deprecated;
                    description
                      "Remote IP/IPv6 address";
                    type inet:ip-address;
                  }
                }
                case any-address {
                  status deprecated;
                  leaf any {
                    status deprecated;
                    description
                      "Any address";
                    type enumeration {
                      enum ipv4;
                      enum ipv6;
                    }
                  }
                }
              }
            }
            container remote-port {
              status deprecated;
              choice remote-port-param {
                mandatory true;
                case port-number {
                  status deprecated;
                  leaf port {
                    status deprecated;
                    description
                      "Local port number";
                    type uint16 {
                      range "1..65535";
                    }
                  }
                }
                case port-any {
                  status deprecated;
                  leaf any {
                    status deprecated;
                    description
                      "Any port number";
                    type empty;
                  }
                }
              }
            }
            leaf vrf {
              status deprecated;
              description
                "VPN Routing/Forwarding instance";
              must '/ios:native/ios:vrf/ios:definition[ios:name=current()] or /ios:native/ios:ip/ios:vrf[ios:name=current()]' {
                error-message "VRF must be created 1st, deleted last";
              }
              type string;
            }
            leaf timeout {
              status deprecated;
              description
                "TWAMP Light test session timeout";
              units "seconds";
              type uint32 {
                range "1..604800";
              }
            }
          }
        }
      }
      container logging {
        description
          "Enable Syslog";
        leaf traps {
          description
            "Enable syslog traps";
          type empty;
        }
      }
      container group {
        description
          "Group Configuration or Group Scheduling";
        list schedule {
          description
            "Group scheduling";
          key "entry-number";
          leaf entry-number {
            description
              "Group schedule entry number";
            type uint32 {
              range "1..2147483647";
            }
          }
          list probe-ids {
            key "word";
            leaf word {
              description
                "Probe ids which are part of the group schedule";
              type string;
            }
            choice group-schedule-type {
              case schedule-period-type {
                container schedule-period-config {
                  description
                    "Group schedule period range";
                  leaf seconds {
                    description
                      "seconds";
                    type uint32;
                  }
                  uses config-ip-sla-group-schedule-grouping;
                }
              }
              case schedule-together-type {
                container schedule-together {
                  description
                    "Group schedule together";
                  uses config-ip-sla-group-schedule-grouping;
                }
              }
            }
            container schedule-period {
              status deprecated;
              description
                "Group schedule period range (DEPRECATED, use schedule-period-config container)";
              leaf seconds {
                status deprecated;
                description
                  "seconds";
                type uint32;
              }
              container frequency {
                status deprecated;
                description
                  "Group operation frequency";
                choice frequency-choice {
                  status deprecated;
                  case frequency-value {
                    status deprecated;
                    leaf frequency-val {
                      status deprecated;
                      description
                        "Specify frequency in seconds";
                      type uint32;
                    }
                  }
                  case frequency-range {
                    status deprecated;
                    leaf range {
                      status deprecated;
                      description
                        "Group operation frequency-range for random scheduling";
                      type string;
                    }
                  }
                }
              }
              container start-time {
                status deprecated;
                description
                  "When to start this entry";
                leaf now {
                  status deprecated;
                  description
                    "Start now";
                  type empty;
                }
              }
              leaf life {
                status deprecated;
                description
                  "Length of time to execute in seconds";
                type union {
                  type uint32;
                  type enumeration {
                    enum forever;
                  }
                }
              }
            }
          }
        }
      }
      list schedule {
        description
          "Entry Scheduling";
        key "entry-number";
        leaf entry-number {
          type leafref {
            path "/ios:native/ios:ip/ios-sla:sla/ios-sla:entry/ios-sla:number";
          }
        }
        leaf ageout {
          description
            "How long to keep this Entry when inactive";
          type uint32 {
            range "0..2073600";
          }
          default "0";
        }
        leaf life {
          description
            "Length of time to execute in seconds";
          type union {
            type uint32 {
              range "0..2147483647";
            }
            type enumeration {
              enum forever;
            }
          }
          default "3600";
        }
        leaf recurring {
          description
            "Probe to be scheduled automatically every day";
          type empty;
        }
        container start-time {
          description
            "When to start this entry.";
          choice start-time-param {
            default "pending-type";
            case after-type {
              leaf after-config {
                description
                  "Start after a certain amount of time from now";
                type ios-sla:hour-min-sec;
              }
            }
            case hour-min-type {
              container hour-min-config {
                leaf hour-min {
                  description
                    "Start time (hh:mm)";
                  type ios-sla:hour-min;
                }
                leaf date-of-month {
                  description
                    "Day of the month";
                  type uint8 {
                    range "1..31";
                  }
                }
                leaf month {
                  description
                    "Month of the year";
                  type string {
                    pattern '(Jan|Feb|Mar|Apr|May|Jun|Jul|Aug|Sep|Oct|Nov|Dec)';
                  }
                }
              }
            }
            case hour-min-sec-type {
              container hour-min-sec-config {
                leaf hour-min-sec {
                  description
                    "Start time (hh:mm)";
                  type ios-sla:hour-min-sec;
                }
                leaf date-of-month {
                  description
                    "Day of the month";
                  type uint8 {
                    range "1..31";
                  }
                }
                leaf month {
                  description
                    "Month of the year";
                  type string {
                    pattern '(Jan|Feb|Mar|Apr|May|Jun|Jul|Aug|Sep|Oct|Nov|Dec)';
                  }
                }
              }
            }
            case now-type {
              leaf now-config {
                description
                  "Start now";
                type empty;
              }
            }
            case pending-type {
              leaf pending-config {
                description
                  "Start pending";
                type empty;
              }
            }
            case random-type {
              leaf random-config {
                description
                  "Start after random time (range)";
                type uint32 {
                  range "500..10000";
                }
              }
            }
          }
          leaf after {
            description
              "Start after a certain amount of time from now. (DEPRECATED, use after-config)";
            status deprecated;
            type string;
          }
          leaf hour-min {
            status deprecated;
            type string;
          }
          leaf hour-min-sec {
            status deprecated;
            type string;
          }
          leaf now {
            description
              "Start now. (DEPRECATED, use now-config)";
            status deprecated;
            type empty;
          }
          leaf pending {
            description
              "Start pending. (DEPRECATED, use pending-config)";
            status deprecated;
            type empty;
          }
          leaf random {
            description
              "Start after random time (range).  (DEPRECATED, use random-config)";
            status deprecated;
            type uint32 {
              range "500..10000";
            }
          }
        }
      }
      list reaction-configuration {
        description
          "IP SLA's reaction configuration";
        key "entry-number";
        leaf entry-number {
          description
            "Entry number";
          type leafref {
            path "/ios:native/ios:ip/ios-sla:sla/ios-sla:entry/ios-sla:number";
          }
        }
        container react {
          description
            "Reaction variable to be configured";
          container connectionLoss {
            description
              "Connection Loss";
            presence "true";
            uses config-ip-sla-react-threshold-type-grouping;
            leaf action-type {
              description
                "Action type of the reaction-configuration";
              type enumeration {
                enum none;
                enum trapAndTrigger;
                enum trapOnly;
                enum triggerOnly;
              }
              default "none";
            }
          }
          container rtt {
            description
              "Round Trip Time";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container timeout {
            description
              "Timeout";
            presence "true";
            uses config-ip-sla-react-threshold-type-grouping;
            leaf action-type {
              description
                "Action type of the reaction-configuration";
              type enumeration {
                enum none;
                enum trapAndTrigger;
                enum trapOnly;
                enum triggerOnly;
              }
              default "none";
            }
          }
          container protocolSpecificError {
            description
              "Protocol Specific Error";
            presence "true";
            uses config-ip-sla-react-threshold-type-grouping;
            leaf action-type {
              description
                "Action type of the reaction-configuration";
              type enumeration {
                enum none;
                enum trapAndTrigger;
                enum trapOnly;
                enum triggerOnly;
              }
              default "none";
            }
          }
          container verifyError {
            description
              "Verify error";
            presence "true";
            uses config-ip-sla-react-threshold-type-grouping;
            leaf action-type {
              description
                "Action type of the reaction-configuration";
              type enumeration {
                enum none;
                enum trapAndTrigger;
                enum trapOnly;
                enum triggerOnly;
              }
              default "none";
            }
          }
          container icpif {
            description
              "Calculated Planning Impairment Factor";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterAvg {
            description
              "Jitter Average in both the directions";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterAvgPct {
            description
              "Percentile Jitter Average in both the directions";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterDSAvg {
            description
              "Jitter Average in the direction from Destination
               to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterDSAvgPct {
            description
              "Percentile Jitter Average in the direction from
               Destination to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterSDAvg {
            description
              "Jitter Average in the direction from Source
               to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container jitterSDAvgPct {
            description
              "Percentile jitter Average in the direction from
               Source to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOfNegativeDS {
            description
              "Maximum negative jitter from Destination to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOfNegativeSD {
            description
              "Maximum negative jitter from Source to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOfPositiveDS {
            description
              "Maximum positive jitter from Destination to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOfPositiveSD {
            description
              "Maximum positive jitter from Source to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container mos {
            description
              "MOS Score";
            presence "true";
            uses config-ip-sla-react-threshold-type-grouping;
            container threshold-value {
              description
                "Threshold value";
              leaf upper-limit-val {
                description
                  "Upper limit";
                type uint32 {
                  range "100..500";
                }
              }
              leaf lower-limit-val {
                description
                  "Lower limit";
                type uint32 {
                  range "100..500";
                }
              }
            }
            leaf action-type {
              description
                "Action type of the reaction-configuration";
              type enumeration {
                enum none;
                enum trapAndTrigger;
                enum trapOnly;
                enum triggerOnly;
              }
              default "none";
            }
          }
          container overThreshold {
            description
              "Percent of Round Trip Times over threshold";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container packetLateArrival {
            description
              "Packets arriving Late";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container packetLossDS {
            description
              "Packet Loss in the direction from Destination
               to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container packetLossSD {
            description
              "Packet Loss in the direction from Source
               to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container packetMIA {
            description
              "Missing in Action";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container packetOutOfSequence {
            description
              "Packet arriving out of sequence";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container rttPct {
            description
              "Percentile Round Trip Time";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container latencyDSAvg {
            description
              "Latency Average from Destination to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container latencyDSAvgPct {
            description
              "Percentile Latency Average from Destination
               to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container latencySDAvg {
            description
              "Latency Average from Source to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container latencySDAvgPct {
            description
              "Percentile Latency Average from Source
               to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOflatencySD {
            description
              "Maximum Latency from Source to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOflatencySDPct {
            description
              "Percentile Maximum Latency from Source
               to Destination";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOflatencyDS {
            description
              "Maximum Latency from Destination to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container maxOflatencyDSPct {
            description
              "Percentile Maximum Latency from Destination
               to Source";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container successivePacketLoss {
            description
              "Successive Packet Loss";
            presence "true";
            uses config-ip-sla-react-threshold-type-grouping;
            uses config-ip-sla-react-threshold-value-grouping;
            leaf action-type {
              description
                "Action type of the reaction-configuration";
              type enumeration {
                enum none;
                enum trapAndTrigger;
                enum trapOnly;
                enum triggerOnly;
              }
              default "none";
            }
          }
          container loss-ratioDS {
            description
              "FLR % Destination to Source";
            presence "true";
            uses config-ip-sla-react-threshold-type-grouping;
            container threshold-value {
              description
                "Threshold value";
              leaf upper-limit-val {
                description
                  "Upper limit";
                type uint32 {
                  range "0..100";
                }
                default "50";
              }
              leaf lower-limit-val {
                description
                  "Lower limit";
                type uint32 {
                  range "0..100";
                }
                default "50";
              }
            }
          }
          container loss-ratioSD {
            description
              "FLR % Source to Destination";
            presence "true";
            uses config-ip-sla-react-threshold-type-grouping;
            container threshold-value {
              description
                "Threshold value";
              leaf upper-limit-val {
                description
                  "Upper limit";
                type uint32 {
                  range "0..100";
                }
                default "50";
              }
              leaf lower-limit-val {
                description
                  "Lower limit";
                type uint32 {
                  range "0..100";
                }
                default "50";
              }
            }
          }
          container unavailableDS {
            description
              "Unavailability % used for FLR Destination to
               Source";
            presence "true";
            uses config-ip-sla-react-threshold-type-grouping;
            container threshold-value {
              description
                "Threshold value";
              leaf upper-limit-val {
                description
                  "Upper limit";
                type uint32 {
                  range "0..100";
                }
                default "50";
              }
              leaf lower-limit-val {
                description
                  "Lower limit";
                type uint32 {
                  range "0..100";
                }
                default "50";
              }
            }
          }
          container unavailableSD {
            description
              "Unavailability % used for FLR Source to
               Destination";
            presence "true";
            uses config-ip-sla-react-threshold-type-grouping;
            container threshold-value {
              description
                "Threshold value";
              leaf upper-limit-val {
                description
                  "Upper limit";
                type uint32 {
                  range "0..100";
                }
                default "50";
              }
              leaf lower-limit-val {
                description
                  "Lower limit";
                type uint32 {
                  range "0..100";
                }
                default "50";
              }
            }
          }
        }
      }
      list reaction-trigger {
        description
          "IP SLAs Trigger Assignment";
        key "react-number target-number";
        leaf react-number {
          description
            "IPSLA operation number configured with action-type as trigger";
          type leafref {
            path "/ios:native/ios:ip/ios-sla:sla/ios-sla:reaction-configuration/ios-sla:entry-number";
          }
        }
        leaf target-number {
          description
            "IPSLA operation number which need to be trigger when reaction occurred";
          type leafref {
            path "/ios:native/ios:ip/ios-sla:sla/ios-sla:entry/ios-sla:number";
          }
        }
      }
      container server {
        description
          "IPPM server configuration";
        container twamp {
          description
            "IPPM TWAMP server configuration";
          presence "true";
          leaf port {
            description
              "Port on which to listen";
            type uint16 {
              range "1..65535";
            }
            default "862";
          }
          container timer {
            description
              "Timer configurations";
            leaf inactivity {
              description
                "Inactivity timer";
              units "seconds";
              type uint16 {
                range "1..6000";
              }
              default "900";
            }
          }
        }
      }
      container ethernet-monitor {
        description
          "IP SLAs Auto Ethernet Configuration";
        list entry {
          description
            "IP SLAs auto ethernet entry";
          key "number";
          leaf number {
            description
              "IP SLAs auto ethernet number";
            type uint32 {
              range "0..2147483647";
            }
          }
          container type {
            description
              "Type of entry";
            choice type {
              case echo-case {
                container echo {
                  description
                    "Perform Ethernet Echo operation";
                  leaf domain {
                    description
                      "Domain Name";
                    mandatory true;
                    type string;
                  }
                  choice type-param {
                    mandatory true;
                    case evc-case {
                      leaf evc {
                        description
                          "EVC ID";
                        type string;
                      }
                    }
                    case vlan {
                      leaf vlan {
                        description
                          "VLAN ID";
                        type uint16 {
                          range "1..4094";
                        }
                      }
                    }
                  }
                  leaf exclude-mpids {
                    description
                      "List of Maintenance Point ID to be excluded";
                    type string;
                  }
                  uses config-ip-sla-ethernet-monitor-submode-grouping;
                  leaf request-data-size {
                    description
                      "Request data size";
                    type uint16 {
                      range "0..1400";
                    }
                    default "66";
                  }
                }
              }
              case jitter-case {
                container jitter {
                  description
                    "Perform Ethernet Jitter operation";
                  leaf domain {
                    description
                      "Domain Name";
                    mandatory true;
                    type string;
                  }
                  choice type-param {
                    mandatory true;
                    case evc-case {
                      leaf evc {
                        description
                          "EVC ID";
                        type string;
                      }
                    }
                    case vlan {
                      leaf vlan {
                        description
                          "VLAN ID";
                        type uint16 {
                          range "1..4094";
                        }
                      }
                    }
                  }
                  leaf exclude-mpids {
                    description
                      "List of Maintenance Point ID to be excluded";
                    type string;
                  }
                  leaf num-frames {
                    description
                      "Number of frames";
                    type uint16 {
                      range "1..60000";
                    }
                    default "10";
                  }
                  leaf interval {
                    description
                      "Inter Packet Interval";
                    units "milliseconds";
                    type uint16 {
                      range "4..60000";
                    }
                    default "20";
                  }
                  uses config-ip-sla-ethernet-monitor-submode-grouping;
                  leaf request-data-size {
                    description
                      "Request data size";
                    type uint16 {
                      range "0..1400";
                    }
                    default "51";
                  }
                }
              }
            }
          }
          container ethernet-monitor-modification-configuration {
            status obsolete;
            leaf cos {
              status obsolete;
              description
                "Class of Service";
              type uint8 {
                range "0..7";
              }
            }
            leaf owner {
              status obsolete;
              description
                "Owner of Entry";
              type string;
            }
            leaf request-data-size-type-echo {
              status obsolete;
              description
                "Request data size for ethernet-monitor type echo.";
              when '../../type/echo';
              type uint16 {
                range "0..1400";
              }
              default "66";
            }
            leaf request-data-size-type-jitter {
              status obsolete;
              description
                "Request data size for ethernet-monitor type jitter.";
              when '../../type/jitter';
              type uint16 {
                range "0..1400";
              }
              default "51";
            }
            leaf tag {
              status obsolete;
              description
                "User defined tag";
              type string;
            }
            leaf threshold {
              status obsolete;
              description
                "Operation threshold in milliseconds";
              units "miliseconds";
              type uint32 {
                range "0..60000";
              }
              default "5000";
            }
            leaf timeout {
              status obsolete;
              description
                "Timeout of an operation";
              units "miliseconds";
              type uint32 {
                range "0..604800000";
              }
              default "6000";
            }
          }
        }
        list schedule {
          description
            "Entry Scheduling";
          key "entry-number";
          leaf entry-number {
            description
              "IP SLAs auto ethernet number";
            type leafref {
              path "/ios:native/ios:ip/ios-sla:sla/ios-sla:ethernet-monitor/ios-sla:entry/ios-sla:number";
            }
          }
          leaf schedule-period {
            description
              "Group schedule period range";
            type uint32 {
              range "1..604800";
            }
          }
          leaf frequency {
            description
              "Group operation frequency";
            type uint32 {
              range "1..604800";
            }
          }
          container start-time {
            description
              "When to start this entry";
            choice start-time-param {
              case after-type {
                leaf after {
                  description
                    "Start after a certain amount of time from now";
                  type ios-sla:hour-min-sec;
                }
              }
              case hour-min-type {
                container hour-min {
                  leaf hour-min {
                    description
                      "Start time (hh:mm)";
                    type ios-sla:hour-min;
                  }
                  uses config-ip-sla-ethernet-monitor-schedule-grouping;
                }
              }
              case hour-min-sec-type {
                container hour-min-sec {
                  leaf hour-min-sec {
                    description
                      "Start time (hh:mm)";
                    type ios-sla:hour-min-sec;
                  }
                  uses config-ip-sla-ethernet-monitor-schedule-grouping;
                }
              }
              case now-type {
                leaf now {
                  description
                    "Start now";
                  type empty;
                }
              }
              case pending-type {
                leaf pending {
                  description
                    "Start pending";
                  type empty;
                }
              }
            }
          }
        }
        list reaction-configuration {
          description
            "IP SLA's reaction configuration";
          key "entry-number";
          leaf entry-number {
            description
              "Entry number";
            type leafref {
              path "/ios:native/ios:ip/ios-sla:sla/ios-sla:ethernet-monitor/ios-sla:entry/ios-sla:number";
            }
          }
          container react {
            description
              "Reaction variable to be configured";
            container connectionLoss {
              description
                "Connection Loss";
              presence "true";
              uses config-ip-sla-react-threshold-type-grouping;
              leaf action-type {
                description
                  "Action type of the reaction configuration";
                type enumeration {
                  enum none;
                  enum trapOnly;
                }
                default "none";
              }
            }
            container rtt {
              description
                "Round Trip Time";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container timeout {
              description
                "Timeout";
              presence "true";
              uses config-ip-sla-react-threshold-type-grouping;
              leaf action-type {
                description
                  "Action type of the reaction configuration";
                type enumeration {
                  enum none;
                  enum trapOnly;
                }
                default "none";
              }
            }
            container jitterAvg {
              description
                "Jitter Average in both the directions";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container jitterDSAvg {
              description
                "Jitter Average in the direction from Destination to Source";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container jitterSDAvg {
              description
                "Jitter Average in the direction from Source to Destination";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container maxOfNegativeDS {
              description
                "Maximum negative jitter from Destination to Source";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container maxOfNegativeSD {
              description
                "Maximum negative jitter from Source to Destination";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container maxOfPositiveDS {
              description
                "Maximum positive jitter from Destination to Source";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container maxOfPositiveSD {
              description
                "Maximum positive jitter from Source to Destination";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container packetLateArrival {
              description
                "Packets which are arrived late";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container packetLossDS {
              description
                "Packet Loss in the direction from Destination to Source";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container packetLossSD {
              description
                "Packet Loss in the direction from Source to Destination";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container packetMIA {
              description
                "Missing in Action";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
            container packetOutOfSequence {
              description
                "Packet arriving out of sequence";
              presence "true";
              uses config-ip-sla-react-threshold-type-grouping;
              uses config-ip-sla-react-threshold-value-grouping;
              leaf action-type {
                description
                  "Action type of the reaction configuration";
                type enumeration {
                  enum none;
                  enum trapOnly;
                }
                default "none";
              }
            }
          }
        }
      }
      container endpoint-list {
        description
          "Endpoint list configuration";
        container type {
          description
            "Endpoint list type";
          list ip {
            description
              "IP type Endpoint list";
            key "name";
            leaf name {
              description
                "Endpoint list name";
              type string;
            }
            list address {
              description
                "List of IP address and port";
              key "ip-address port";
              leaf ip-address {
                description
                  "IP-Addresses(range)/hostname list, ',' delimited, max 5,
                   may contain range denoted by '-', Example: 1.1.1.1-224,
                   cannot mix with individual addresses";
                type union {
                  type string;
                  type inet:ipv4-address;
                }
              }
              leaf port {
                description
                  "Port Number (Recommended ports greater than 1023)";
                type uint16 {
                  range "1..65535";
                }
              }
            }
            leaf description {
              description
                "Customer specific description of endpoint list";
              type string;
            }
          }
          list ipv6 {
            description
              "IP type Endpoint list";
            key "name";
            leaf name {
              description
                "Endpoint list name";
              type string;
            }
            list address {
              description
                "List of IPv6 address and port";
              key "ip-address port";
              leaf ip-address {
                description
                  "IPv6 address";
                type union {
                  type inet:ipv6-address;
                }
              }
              leaf port {
                description
                  "Port Number (Recommended ports greater than 1023)";
                type uint16 {
                  range "1..65535";
                }
              }
            }
            leaf description {
              description
                "Customer specific description of the endpoint list";
              type string;
            }
          }
        }
      }
      container snmp {
        description
          "Set SNMP extensions";
        container extend {
          description
            "Extend SNMP Object length";
          leaf tag {
            description
              "Extend the length of rttMonCtrlAdminTag object";
            type empty;
          }
        }
      }
      container periodic {
        description
          "Enable Periodic Resolution of the IPSLA hostname";
        container hostname {
          description
            "IPSLA hostname configured in the probe";
          leaf resolution {
            description
              "Enable IPSLA Hostname Resolution";
            type empty;
          }
        }
      }
      container profile {
        description
          "IP SLA Profile configuration";
        container packet {
          description
            "Create/Modify Packet Profiles";
          container type {
            description
              "Type of the profile";
            list ip {
              description
                "IP profile list";
              key "profile-name";
              leaf profile-name {
                description
                  "Name of Packet Profile";
                type string;
              }
              leaf dest-ip-addr {
                description
                  "destination ip address";
                type inet:ip-address;
              }
              leaf packet-size {
                description
                  "Packet Size";
                type packet-size-type;
              }
              leaf source-ip-addr {
                description
                  "source ip address";
                type inet:ip-address;
              }
              container tunnel {
                description
                  "Tunnel type";
                leaf exp {
                  description
                    "Exp value";
                  type uint8 {
                    range "0..7";
                  }
                }
              }
            }
            list ethernet {
              description
                "Ethernet profile list";
              key "profile-name";
              leaf profile-name {
                description
                  "Name of Packet Profile";
                type string;
              }
              leaf dest-mac-addr {
                description
                  "Specify the destination mac-address";
                type ios-types:cisco-mac-address-type;
              }
              leaf ethertype {
                description
                  "Frame type";
                type enumeration {
                  enum ipv4;
                  enum ipv6;
                }
              }
              leaf inner-cos {
                description
                  "Inner COS";
                type uint8 {
                  range "0..7";
                }
              }
              leaf inner-vlan {
                description
                  "Specify Inner VLAN";
                type uint16 {
                  range "0..4095";
                }
              }
              leaf outer-cos {
                description
                  "Outer COS";
                type uint8 {
                  range "0..7";
                }
              }
              leaf outer-vlan {
                description
                  "Specify the Outer VLAN";
                type uint16 {
                  range "0..4095";
                }
              }
              leaf packet-size {
                description
                  "Packet Size";
                type packet-size-type;
              }
              leaf src-mac-addr {
                description
                  "Specify the source mac-address";
                type ios-types:cisco-mac-address-type;
              }
            }
          }
        }
      }
      container key-chain {
        leaf key-chain-name {
          description
            "Use MD5 Authentication for IP SLAs Control Messages";
          type string;
        }
      }
      leaf low-memory {
        description
          "Configure Low Water Memory Mark";
        type uint32 {
          range "0..2147483647";
        }
      }
    }
  }

  augment "/ios:native/ios:ip" {
    uses config-ip-sla-grouping;
  }

  augment "/ios:native" {
    uses config-auto-ip-sla-grouping;
  }
}
