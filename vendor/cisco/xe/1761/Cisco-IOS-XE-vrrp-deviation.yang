module Cisco-IOS-XE-vrrp-deviation {
  namespace "http://cisco.com/ns/yang/Cisco-IOS-XE-vrrp-deviation";
  prefix vrrp-d;

  import Cisco-IOS-XE-native {
    prefix ios;
  }
  import cisco-semver {
    prefix cisco-semver;
  }

  organization
    "Cisco Systems";
  description
    "Cisco XE Native Deviation YANG module for IOS
     Copyright (c) 2020 by Cisco Systems, Inc.
     All rights reserved.";

  revision 2020-07-01 {
    description
      "Removing default value in vrrp leaf";
    cisco-semver:module-version "1.0.0";
  }

  deviation "/ios:native/ios:fhrp/ios:version/ios:vrrp" {
    deviate delete {
      default "v2";
    }
  }

  deviation "/ios:native/ios:fhrp/ios:version/ios:vrrp" {
    deviate replace {
      type enumeration {
        enum v3;
      }
    }
  }
}
