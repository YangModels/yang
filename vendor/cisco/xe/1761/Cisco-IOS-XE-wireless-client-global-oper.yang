module Cisco-IOS-XE-wireless-client-global-oper {
  yang-version 1;
  namespace "http://cisco.com/ns/yang/Cisco-IOS-XE-wireless-client-global-oper";
  prefix wireless-client-global-oper;

  import Cisco-IOS-XE-wireless-client-types {
    prefix wireless-client-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains client operational data aggregated across wireless processes.
     Copyright (c) 2021 by Cisco Systems, Inc.
     All rights reserved.";

  revision 2021-07-01 {
    description
      "Initial revision";
    reference
      "1.0.0";
    cisco-semver:module-version "1.0.0";
  }

  grouping client-statistics {
    description
      "Client statistics";
    container co-client-del-reason {
      description
        "Client delete reason statistics";
      uses wireless-client-types:co-delete-reason;
    }
  }

  grouping client-live-stats {
    description
      "Statistics of clients/mobile stations current state";
    leaf auth-state-clients {
      type uint32;
      description
        "Number of clients in authenticating state";
    }
    leaf mobility-state-clients {
      type uint32;
      description
        "Number of clients in mobility state";
    }
    leaf iplearn-state-clients {
      type uint32;
      description
        "Number of clients in IP learn state";
    }
    leaf webauth-state-clients {
      type uint32;
      description
        "Number of clients in web authenticating state";
    }
    leaf run-state-clients {
      type uint32;
      description
        "Number of clients in run state";
    }
    leaf delete-state-clients {
      type uint32;
      description
        "Number of clients in deletion state";
    }
    leaf random-mac-clients {
      type uint32;
      description
        "Number of clients using random MAC address";
    }
  }

  container client-global-oper-data {
    config false;
    description
      "Root container for client operational data aggregated across wireless processes";
    container client-live-stats {
      presence "client-live-stats";
      description
        "Snapshot of statistics of current state of wireless clients";
      uses wireless-client-global-oper:client-live-stats;
    }
    container client-stats {
      presence "client-stats";
      description
        "Summary of client statistics";
      uses wireless-client-global-oper:client-statistics;
    }
  }
}
