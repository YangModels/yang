module Cisco-IOS-XE-l3vpn {
  namespace "http://cisco.com/ns/yang/Cisco-IOS-XE-l3vpn";
  prefix ios-l3vpn;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Layer 3 Virtual Private Network (L2VPN) Yang model.
     Copyright (c) 2016, 2017, 2019 by Cisco Systems, Inc.
     All rights reserved.";

  revision 2019-11-01 {
    description
      "- Add description to leaf profile-name";
    cisco-semver:module-version "1.0.1";
  }
  revision 2019-07-01 {
    description
      "Establish semantic version baseline";
    cisco-semver:module-version "1.0.0";
  }
  revision 2017-02-07 {
    description
      "Initial revision";
  }

  grouping config-l3vpn-grouping {
    container encapsulation {
      description
        "l3vpn encapsulation ip";
      list ip {
        description
          "l3vpn encapsulation ip";
        key "profile-name";
        leaf profile-name {
          description
            "profile name";
          type string;
        }
        container transport {
          description
            "transport mode";
          container ipv4 {
            description
              "transport ipv4 mode";
            presence "true";
            leaf source {
              description
                "transport source";
              type string;
            }
          }
        }
        container protocol {
          description
            "protocol mode";
          container gre {
            description
              "protocol gre";
            presence "true";
            leaf key {
              description
                "gre key";
              type uint32 {
                range "0..4294967295";
              }
            }
          }
        }
        container mpls {
          description
            "Configure MPLS interface parameters";
          leaf mtu {
            description
              "Set MPLS Maximum Transmission Unit";
            type union {
              type uint32 {
                range "64..17916";
              }
              type enumeration {
                enum max;
              }
            }
          }
        }
      }
    }
  }

  augment "/ios:native/ios:l3vpn" {
    uses config-l3vpn-grouping;
  }
}
