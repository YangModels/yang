module cisco-xe-switching-openconfig-interfaces-deviation {
  namespace "http://openconfig.net/yang/cisco-xe-switching-openconfig-interfaces-deviation";
  prefix cisco-xe-switching-oc-if-devs;

  import openconfig-interfaces {
    prefix oc-if;
  }
  import ietf-yang-types {
    prefix yang;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-interfaces module for IOS XE Switching platforms.
     Copyright (c) 2018 by Cisco Systems, Inc.
     All rights reserved.";

  revision 2018-12-12 {
    description
      "Initial revision";
  }

  deviation "/oc-if:interfaces/oc-if:interface/oc-if:config/oc-if:mtu" {
    deviate not-supported;
    description
      "Top level mtu not supported on switching platforms";
  }
}
