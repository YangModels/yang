module Cisco-IOS-XE-nam {
  namespace "http://cisco.com/ns/yang/Cisco-IOS-XE-nam";
  prefix ios-nam;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco IOS XE Native Network Analysis Module (NAM) monitoring YANG module.
     Copyright (c) 2018 by Cisco Systems, Inc.
     All rights reserved.";

  revision 2019-07-01 {
    description
      "Establish semantic version baseline";
    cisco-semver:module-version "1.0.0";
  }
  revision 2019-01-22 {
    description
      "Added leaf for App-hosting Gigabit Ethernet interface";
  }
  revision 2017-12-28 {
    description
      "Initial revision";
  }

  grouping config-interface-analysis-module-grouping {
    container analysis-module {
      description
        "Configure NAM on the interface";
      container monitoring {
        description
          "Configure NAM monitoring on the interface";
        leaf interface-name {
          description
            "The name of the output interface.  E.g., 'ucse 1/0/0'";
          type string;
        }
      }
    }
  }

  augment "/ios:native/ios:interface/ios:FastEthernet" {
    uses config-interface-analysis-module-grouping;
  }

  augment "/ios:native/ios:interface/ios:GigabitEthernet" {
    uses config-interface-analysis-module-grouping;
  }

  augment "/ios:native/ios:interface/ios:TenGigabitEthernet" {
    uses config-interface-analysis-module-grouping;
  }

  augment "/ios:native/ios:interface/ios:FiveGigabitEthernet" {
    uses config-interface-analysis-module-grouping;
  }

  augment "/ios:native/ios:interface/ios:AppGigabitEthernet" {
    uses config-interface-analysis-module-grouping;
  }

  augment "/ios:native/ios:interface/ios:TwentyFiveGigE" {
    uses config-interface-analysis-module-grouping;
  }

  augment "/ios:native/ios:interface/ios:TwoGigabitEthernet" {
    uses config-interface-analysis-module-grouping;
  }

  augment "/ios:native/ios:interface/ios:FortyGigabitEthernet" {
    uses config-interface-analysis-module-grouping;
  }

  augment "/ios:native/ios:interface/ios:HundredGigE" {
    uses config-interface-analysis-module-grouping;
  }

  augment "/ios:native/ios:interface/ios:Tunnel" {
    uses config-interface-analysis-module-grouping;
  }

  augment "/ios:native/ios:interface/ios:Port-channel" {
    uses config-interface-analysis-module-grouping;
  }

  augment "/ios:native/ios:ppp" {
    uses config-interface-analysis-module-grouping;
  }

  augment "/ios:native/ios:interface/ios:Serial" {
    uses config-interface-analysis-module-grouping;
  }
}
