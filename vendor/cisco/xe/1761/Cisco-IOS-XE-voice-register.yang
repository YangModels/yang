submodule Cisco-IOS-XE-voice-register {
  belongs-to Cisco-IOS-XE-voice {
    prefix ios-voice;
  }

  import Cisco-IOS-XE-native {
    prefix ios;
  }
  import cisco-semver {
    prefix cisco-semver;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Register Yang model.
     Copyright (c) 2019-2020 by Cisco Systems, Inc.
     All rights reserved.";

  revision 2021-07-01 {
    description
      "- Modified noan leaf to handle the no form properly
       - Added cor incoming/outgoing under voice register pool";
    cisco-semver:module-version "3.1.0";
  }
  revision 2020-07-01 {
    description
      "- Added dependency of pool configuration on global and max-pool configurations
       - Adding tailf flag to the global container to avoid removing its configuration before pool list
       - Increasing the range for configuring max-pool to 2500";
    cisco-semver:module-version "3.0.0";
  }
  revision 2020-03-01 {
    description
      "- Removed statement mandatory for leaves";
    cisco-semver:module-version "2.1.0";
  }
  revision 2019-11-01 {
    description
      "- Added call-forward All, Busy, Mailbox and noan
       - Added statement mandatory for leaves";
    cisco-semver:module-version "2.0.0";
  }
  revision 2019-07-01 {
    description
      "Establish semantic version baseline";
    cisco-semver:module-version "1.0.0";
  }

  typedef config-voice-register-corlist-tag {
    type union {
      type uint8 {
        range "1..20";
      }
      type enumeration {
        enum default;
      }
    }
  }

  typedef config-e164-number {
    type string {
      length "1..32";
      pattern '((((\^)(\+))?([0-9,#*A-F])*T?)($)?)' {
        error-message
          "Incorrect format for E.164 Number: regular expression
           must be of the form (((\\^)(\\+))?([0-9,#*A-F])*T?)($)?";
      }
    }
  }

  grouping config-voice-register-pool-cor {
    leaf name {
      description
        "cor list name";
      type leafref {
        path "/ios:native/ios-voice:dial-peer/ios-voice:cor/ios-voice:list/id";
      }
    }
    leaf lowerbound {
      description
        "cor list matched number or lower bound number";
      when "../id != 'default'";
      type config-e164-number;
    }
    leaf hyphen {
      description
        "number range";
      when '../lowerbound';
      type enumeration {
        enum -;
      }
    }
    leaf upperbound {
      description
        "cor list matched number or lower bound number";
      when '../hyphen';
      type config-e164-number;
    }
  }

  grouping config-voice-register-grouping {
    container register {
      description
        "voice register commands";
      container global {
        description
          "Define global commands";
        presence "true";
        leaf max-dn {
          description
            "Maximum directory numbers supported";
          type uint32 {
            range "1..3500";
          }
        }
        leaf max-pool {
          description
            "Maximum pools to support";
          type uint16 {
            range "1..2500";
          }
        }
        container system {
          description
            "Define system message";
          leaf message {
            description
              "Define system message";
            type string {
              length "1..32";
            }
          }
        }
      }
      list pool {
        description
          "voice-register-pool tag";
        when '../global and ../global/max-pool';
        key "pool-tag";
        leaf pool-tag {
          description
            "voice register pool commands";
          must '. <= ../../global/max-pool' {
            error-message "pool-tag cannot exceed max-pool value set under voice register global";
          }
          type uint16 {
            range "1..2500";
          }
        }
        container call-forward {
          description
            "Define E.164 telephone number for call forward";
          container b2bua {
            description
              "Define call forward for B2BUA (back-to-back user agent)";
            leaf all {
              description
                "forward all calls";
              type string {
                pattern '([0-9,A-F#*.?+%()-]*T?)' {
                  error-message "Incorrect format for E.164 Number: regular expression must be of the form  [0-9,A-F#*.?+%()-]*T?";
                }
              }
            }
            leaf busy {
              description
                "forward call on busy";
              type string {
                pattern '([0-9,A-F#*.?+%()-]*T?)' {
                  error-message "Incorrect format for E.164 Number: regular expression must be of the form  [0-9,A-F#*.?+%()-]*T?";
                }
              }
            }
            leaf mailbox {
              description
                "mailbox number";
              type string {
                pattern '([0-9,A-F#*.?+%()-]*T?)' {
                  error-message "Incorrect format for E.164 Number: regular expression must be of the form  [0-9,A-F#*.?+%()-]*T?";
                }
              }
            }
            container noan-config {
              leaf noan {
                description
                  "forward call on no-answer";
                type string {
                  pattern '([0-9,A-F#*.?+%()-]*T?)' {
                    error-message "Incorrect format for E.164 Number: regular expression must be of the form  [0-9,A-F#*.?+%()-]*T?";
                  }
                }
              }
              leaf timeout {
                description
                  "Ringing no answer timeout duration";
                type uint32 {
                  range "3..60000";
                }
              }
            }
          }
        }
        container id {
          description
            "define phone or device id";
          container network {
            description
              "define phone or device network address";
            choice ipaddress {
              case ipv4 {
                container ipv4address {
                  leaf address {
                    description
                      "IPv4 Address";
                    type inet:ipv4-address;
                  }
                  leaf mask {
                    description
                      "IPv4 Address Mask";
                    type inet:ipv4-address;
                  }
                }
              }
              case ipv6 {
                leaf ippv6 {
                  description
                    "IPv6 network and mask";
                  type ios-types:ipv6-prefix;
                }
              }
            }
          }
        }
        container voice-class {
          description
            "Set voice class parameters";
          leaf codec {
            description
              "Set Global Codec parameters";
            type leafref {
              path "../../../../ios-voice:class/ios-voice:codec/codec-tag";
            }
          }
        }
        container dtmf-relay {
          description
            "Transport DTMF digits across IP link";
          leaf rtp-nte {
            description
              "RTP Named Telephone Event RFC 2833";
            type empty;
          }
          leaf sip-kpml {
            description
              "DTMF Relay via KPML messages";
            type empty;
          }
          leaf sip-notify {
            description
              "DTMF Relay via SIP NOTIFY messages";
            type empty;
          }
        }
        container cor {
          description
            "Class of Restriction on dial-peer for this dn";
          list incoming {
            description
              "incoming class of restriction list";
            key "id";
            leaf id {
              description
                "corlist tag";
              type config-voice-register-corlist-tag;
            }
            uses config-voice-register-pool-cor;
          }
          list outgoing {
            description
              "outgoing class of restriction list";
            key "id";
            leaf id {
              description
                "cor list tag";
              type config-voice-register-corlist-tag;
            }
            uses config-voice-register-pool-cor;
          }
        }
      }
    }
  }

  grouping config-voice-moh-file-location-grouping {
    leaf filename {
      description
        "Example: bootflash:MOH filename";
      type string {
        pattern '(((bootflash:)|(flash:)|(nvram:)|(webui:)).*)';
      }
    }
  }

  grouping config-voice-call-manager-fallback-grouping {
    container call-manager-fallback {
      description
        "SRST for Cisco Call Manager fallback";
      presence "true";
      container moh {
        description
          "Define music-on-hold filename";
        container g729 {
          description
            "File for G.729/G.729A";
          uses config-voice-moh-file-location-grouping;
        }
        uses config-voice-moh-file-location-grouping;
      }
    }
  }
}
