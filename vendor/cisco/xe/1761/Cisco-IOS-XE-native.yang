module Cisco-IOS-XE-native {
  namespace "http://cisco.com/ns/yang/Cisco-IOS-XE-native";
  prefix ios;

  import cisco-semver {
    prefix cisco-semver;
  }
  import ietf-inet-types {
    prefix inet;
  }
  import Cisco-IOS-XE-types {
    prefix ios-types;
  }
  import Cisco-IOS-XE-features {
    prefix ios-features;
  }
  import Cisco-IOS-XE-interface-common {
    prefix ios-ifc;
  }
  include Cisco-IOS-XE-parser;
  include Cisco-IOS-XE-license;
  include Cisco-IOS-XE-line;
  include Cisco-IOS-XE-logging;
  include Cisco-IOS-XE-ip;
  include Cisco-IOS-XE-ipv6;
  include Cisco-IOS-XE-interfaces;

  organization
    "Cisco Systems, Inc.";
  contact
    "Cisco Systems, Inc.
     Customer Service

     Postal: 170 W Tasman Drive
     San Jose, CA 95134

     Tel: +1 1800 553-NETS

     E-mail: cs-yang@cisco.com";
  description
    "NED YANG module for IOS-XE
     Copyright (c) 2016-2020 by Cisco Systems, Inc.
     All rights reserved.";

  revision 2021-07-01 {
    description
      "- Added support for LACP System priority
       - Updated default value for fhrp bfd/sso to false
       - Added private-config-encryption leaf to service
       - Obsolete monitor-event-trace-enable-disable-grouping";
    cisco-semver:module-version "7.0.0";
  }
  revision 2021-03-01 {
    description
      "- Add support for VRRPv3 BFD
       - Add support for fhrp-sso
       - Added common-criteria-policy leaf
       - Replaced cli-diff-dependency";
    cisco-semver:module-version "6.0.0";
  }
  revision 2020-11-01 {
    description
      "- Initial revision for 17.4.1
       - Added logging console/logging monitor new models
       - Added logging console/logging monitor new models";
    cisco-semver:module-version "5.0.0";
  }
  revision 2020-07-02 {
    description
      "- Interval addition for gateway-failover";
    cisco-semver:module-version "4.0.1";
  }
  revision 2020-07-01 {
    description
      "- Change ipv6 prefixlist obsolete nodes to deprecated
       - Added model for quiet-mode and access-class
       - Added model for block-for attempts and within
       - Obsolete clock offset
       - modified range of mab username attribute format to support size 6
       - Added yang model for: hw-module subslot x/y ethernet mode XX
       - Added model for breakout CLI";
    cisco-semver:module-version "4.0.0";
  }
  revision 2020-03-01 {
    description
      "- Added Endpoint Tracker
       - Updated Cisco-IOS-XE-(ip/ipv6).yang
       - Added range and default value for leaf distance of ipv6 route
       - Updated Cisco-IOS-XE-ip.yang(route-replicate)
       - Updated global-address-family";
    cisco-semver:module-version "3.0.0";
  }
  revision 2019-11-01 {
    description
      "- Added new management container
       - Deprecating child nodes in case of deprecated parent";
    cisco-semver:module-version "2.0.0";
  }
  revision 2019-07-01 {
    description
      "- Establish semantic version baseline
       - Corrected failover threshold command inside RG group command
       - Change call-home to non-presence container
       - Add support for network-clock revertive
       - Add support for allowing spaces in passwords";
    cisco-semver:module-version "1.0.0";
  }
  revision 2019-01-30 {
    description
      "enum types updated for username/user-name/enable config models";
  }
  revision 2019-01-21 {
    description
      "Add support for hw-module subslot x/y mode 10|40|100 Gig CLI";
  }
  revision 2018-12-14 {
    description
      "Support type6 password enum for username configuration model";
  }
  revision 2018-12-11 {
    description
      "Add model for enable secret 9";
  }
  revision 2018-11-30 {
    description
      "Corrections for user-name configuration model";
  }
  revision 2018-11-22 {
    description
      "Cleanup spelling errors in description statements";
  }
  revision 2018-11-14 {
    description
      "Model for tftp-server load configuration";
  }
  revision 2018-11-06 {
    description
      "Add md-list configuration";
  }
  revision 2018-10-26 {
    description
      "Modelled transport-map type related configuration";
  }
  revision 2018-10-25 {
    description
      "Added application redundancy command inside redundancy";
  }
  revision 2018-10-24 {
    description
      "Added model for the user-name configuration";
  }
  revision 2018-10-18 {
    description
      "Add module vxlan";
  }
  revision 2018-10-16 {
    description
      "Added l2tp-class list";
  }
  revision 2018-10-11 {
    description
      "Add description to clock time zone";
  }
  revision 2018-10-09 {
    description
      "Delete 'enable secret' container when empty or when secret deleted";
  }
  revision 2018-08-10 {
    description
      "Modelled breakout ports related configuration";
  }
  revision 2018-08-03 {
    description
      "Make mac address-table static to be list";
  }
  revision 2018-07-30 {
    description
      "Add usbflash1-password for hw-module";
  }
  revision 2018-07-27 {
    description
      "Add default value 'v2' for fhrp version vrrp";
  }
  revision 2018-06-27 {
    description
      "Remove 'presence true' from top level 'native / qos'";
  }
  revision 2018-06-06 {
    description
      "Change 'alias' to be a list instead of a single leaf";
  }
  revision 2018-05-23 {
    description
      "Removed vrf option from erspan-dst, added dscp,vrf options under erspan-src";
  }
  revision 2018-05-22 {
    description
      "Remove wireless model";
  }
  revision 2018-04-24 {
    description
      "Make card type list";
  }
  revision 2018-03-27 {
    description
      "Move top level card to native before controller to keep the sequence.";
  }
  revision 2018-02-26 {
    description
      "Add model for username secret 9 SCRYPT";
  }
  revision 2018-02-06 {
    description
      "Refactor parameter-map";
  }
  revision 2018-02-01 {
    description
      "fix banner issue";
  }
  revision 2018-01-15 {
    description
      "Add monitor session type local and options";
  }
  revision 2018-01-07 {
    description
      "Add monitor session type erspan-dst and options under erspan-src";
  }
  revision 2017-10-24 {
    description
      "Add banner support back for login and motd";
  }
  revision 2017-10-23 {
    description
      "Support for AVB,PTP,MVRP";
  }
  revision 2017-10-16 {
    description
      "Add diff-dependency on VirtualPortGroup for virtual-service";
  }
  revision 2017-09-26 {
    description
      "Add username view";
  }
  revision 2017-08-30 {
    description
      "Add 'umbrella' to parameter-map enum";
  }
  revision 2017-08-14 {
    description
      "Model for monitor event-trace";
  }
  revision 2017-07-13 {
    description
      "Support for AVC";
  }
  revision 2017-07-08 {
    description
      "Model for identity policy additional support";
  }
  revision 2017-06-26 {
    description
      "Model for identity policy";
  }
  revision 2017-06-23 {
    description
      "add options under monitor session type erspan-src";
  }
  revision 2017-06-21 {
    description
      "add some model in domain";
  }
  revision 2017-06-15 {
    description
      "Removed native/access-list";
  }
  revision 2017-06-01 {
    description
      "add default crypto ikev2 policy and proposal";
  }
  revision 2017-03-24 {
    description
      "Removed banner";
  }
  revision 2017-02-07 {
    description
      "Initial revision";
  }

  typedef monitor-event-type {
    type enumeration {
      enum error;
      enum detail;
      enum major;
    }
  }

  container native {
    container default {
      description
        "Set a command to its defaults";
      container crypto {
        description
          "Encryption module";
        container ikev2 {
          description
            "Configure IKEv2 Options";
          leaf proposal {
            description
              "Define IKEV2 proposals";
            type empty;
          }
          leaf policy {
            description
              "Define IKEV2 policies";
            type empty;
          }
        }
      }
    }
    container bfd {
      description
        "BFD configuration commands";
    }
    leaf version {
      description
        "Version";
      type string;
    }
    container stackwise-virtual {
      description
        "Enter stackwise-virtual configuration mode";
      presence "true";
    }
    leaf boot-start-marker {
      type empty;
    }
    container boot {
      description
        "Modify boot system parameters";
      container system {
        description
          "System Image";
        leaf tftp-path {
          description
            "Example: 192.x.x.x/<path to image>";
          type string;
        }
        leaf tftp {
          description
            "Example 192.168.x.x/<image-path>";
          type string;
        }
        container bootfile {
          description
            "WORD - boot filename";
          list filename-list {
            key "filename";
            leaf filename {
              description
                "WORD - TFTP filename or URL";
              type string;
            }
          }
        }
        container flash {
          description
            "flash - Boot from flash memory";
          list flash-list {
            key "flash-leaf";
            leaf flash-leaf {
              type string;
            }
          }
        }
      }
    }
    leaf boot-end-marker {
      type empty;
    }
    grouping banner-grouping {
      leaf banner {
        description
          "Banner message";
        type string;
      }
    }

    container banner {
      description
        "Define a login banner";
      container exec {
        description
          "Set EXEC process creation banner";
        uses banner-grouping;
      }
      container login {
        description
          "Set login banner";
        uses banner-grouping;
      }
      container prompt-timeout {
        description
          "Set Message for login authentication timeout";
        uses banner-grouping;
      }
      container motd {
        description
          "Set Message of the Day banner";
        uses banner-grouping;
      }
    }
    leaf captive-portal-bypass {
      description
        "Enable Captive portal bypass for apple devices";
      type empty;
    }
    container memory {
      description
        "Configure memory management";
      container statistics {
        description
          "Configure statistics history table";
        container history {
          description
            "Configure statistics history table";
          leaf table {
            description
              "Configure statistics history table";
            type uint8 {
              range "12..72";
            }
          }
        }
      }
      container chunk {
        description
          "chunk related configuration";
        container siblings {
          description
            "chunk siblings related configuration";
          leaf threshold {
            description
              "Default is platform dependent";
            type uint32 {
              range "2..4294967295";
            }
          }
        }
      }
      container free {
        description
          "free memory low water mark";
        container low-watermark {
          description
            "low water mark for notifications";
          leaf IO {
            description
              "low water mark of memory in KB";
            type uint32 {
              range "1..3994575";
            }
          }
          leaf processor {
            description
              "low water mark of memory in KB";
            type uint32 {
              range "1..3994575";
            }
          }
        }
      }
      leaf lite {
        description
          "Enable/disable memory lite";
        type empty;
      }
      container reserve {
        description
          "reserve memory";
        container critical {
          description
            "Reserve Critical Memory";
          presence "true";
          leaf memory-range {
            description
              "total amount of memory to be reserved in kilobytes";
            type uint32 {
              range "1..4294967295";
            }
          }
        }
      }
      container sanity {
        description
          "Enable memory sanity";
        presence "true";
        leaf all {
          description
            "Enable memory sanity all";
          type empty;
        }
        leaf buffer {
          description
            "Enable memory sanity buffer";
          type empty;
        }
        leaf queue {
          type empty;
        }
      }
    }
    container location {
      description
        "Global location configuration commands";
      container civic-location {
        description
          "Civic location information";
        list identifier {
          description
            "Set the identifier";
          key "identifier";
          leaf identifier {
            type string;
          }
          leaf building {
            description
              "Building information";
            type string;
          }
          leaf floor {
            description
              "Floor number";
            type string;
          }
          leaf landmark {
            description
              "Landmark";
            type string;
          }
          leaf name {
            description
              "Resident name";
            type string;
          }
          leaf number {
            description
              "Street number";
            type string;
          }
        }
      }
    }
    container call-home {
      description
        "Enter call-home configuration mode";
    }
    container hw-module {
      description
        "Control of individual components in the system";
      container uplink {
        description
          "Uplink control";
        leaf select {
          description
            "Select uplink interface";
          type string;
        }
        leaf mode {
          description
            "Uplink mode";
          type enumeration {
            enum shared-backplane;
          }
        }
      }
      list breakout {
        description
          "Configure a native port into four breakout ports";
        key "port-number";
        leaf port-number {
          description
            "Port Number to be converted in to breakout ports";
          type uint8 {
            range "1..32";
          }
        }
      }
      list switch {
        description
          "Switch in the system";
        key "switch-number";
        leaf switch-number {
          description
            "Switch number in the Stack (Refer to show switch CLI)";
          type uint8 {
            range "1..8";
          }
        }
        leaf usbflash1-password1 {
          description
            "USB SSD Security";
          type string;
        }
        list usbflash1-password {
          status deprecated;
          description
            "USB SSD Security";
          key "usbflash1-password-string";
          leaf usbflash1-password-string {
            status deprecated;
            description
              "USB SSD Security";
            type string;
          }
        }
      }
      list slot {
        description
          "Control a component in a slot";
        key "name";
        leaf name {
          description
            "Slot of LC";
          type string;
        }
        leaf shutdown {
          description
            "Shutdown a fru";
          type empty;
        }
      }
      list subslot {
        description
          "Control a component in a subslot";
        key "subslot-number";
        leaf subslot-number {
          description
            "Line card subslot number in the range of <0-1>/<0-2> for mode change";
          type string {
            length "1..3";
            pattern '[0-2/0-2]*';
          }
        }
        leaf mode {
          description
            "subslot mode value, for which valid mode values are 10, 40 & 100 Gig";
          type enumeration {
            enum 10G {
              value 10;
            }
            enum 40G {
              value 40;
            }
            enum 100G {
              value 100;
            }
          }
          must "not((../subslot-number = '0/2') and (current() = '10G'))" {
            error-message "10G mode is not supported on bay2";
          }
        }
        container breakout {
          description
            "configure breakout mode";
          choice breakout-choice {
            default "none";
            case mode-case {
              list breakout-mode {
                description
                  "Breakout mode for native ports";
                key "id";
                leaf id {
                  type enumeration {
                    enum 10g;
                  }
                  must "not(current() and (current()/../../../mode = '100G'))" {
                    error-app-tag "Invalid-mode";
                    error-message "Either EPA is in 100G mode or it has some native ports with active breakout configurations before switching to 100G mode. Please note 10G Breakout is supported only in 40G mode";
                  }
                }
                container port {
                  description
                    "Native port";
                  choice port-mode {
                    case all {
                      leaf all {
                        description
                          "Configure all native ports in breakout mode";
                        type empty;
                      }
                    }
                    case native_port {
                      leaf native_port_0 {
                        description
                          "Configure native port 0 in breakout mode";
                        type empty;
                      }
                      leaf native_port_4 {
                        description
                          "Configure native port 4 in breakout mode";
                        type empty;
                      }
                      leaf native_port_8 {
                        description
                          "Configure native port 8 in breakout mode";
                        type empty;
                      }
                    }
                  }
                }
              }
            }
            case none {
              container none {
                description
                  "Remove breakout configuration from all native ports";
                container port {
                  description
                    "Native port";
                  leaf all {
                    description
                      "Remove breakout configuration from all native ports";
                    type enumeration {
                      enum all;
                    }
                    default "all";
                  }
                }
              }
            }
          }
        }
        container shutdown {
          description
            "Shutdown the target subslot";
          leaf unpowered {
            description
              "Power-off the target subslot";
            type empty;
          }
        }
        container ethernet {
          description
            "Configure ethernet";
          leaf mode {
            description
              "configure mode for front-panel module ports 0/0/<4-5>";
            type enumeration {
              enum GE;
              enum TE;
            }
            default "TE";
          }
        }
      }
      leaf sm {
        type uint8;
      }
      leaf pvdm {
        type string;
      }
    }
    container cisp {
      description
        "Set CISP parameters";
      leaf enable {
        description
          "Enable CISP";
        type empty;
      }
    }
    container module {
      description
        "Module";
    }
    list domain {
      description
        "Domain Configuration Commands";
      key "name";
      leaf name {
        type string;
      }
      list vrf {
        description
          "Specify vrf for domain";
        key "name";
        leaf name {
          type string;
        }
        container border {
          description
            "Enter border router configuration submode";
          container advanced {
            description
              "Enter border router advanced configuration submode";
            leaf monitor-cache-percent {
              description
                "cache usage (%), border instance will AUTOMATICALLY go through SHUT/NO SHUT any ACTIVE traffic on this border will be affected";
              type uint8 {
                range "1..100";
              }
            }
          }
          container source-interface {
            description
              "Source Interface for border";
            leaf Loopback {
              description
                "Loopback interface";
              type uint32;
            }
          }
          leaf master {
            description
              "Specify IP address of Domain master controller";
            type union {
              type inet:ipv4-address;
              type enumeration {
                enum local;
              }
            }
          }
          container password {
            description
              "MD5 password to be used with MC";
            leaf encryption {
              type enumeration {
                enum 0;
                enum 7;
              }
            }
            leaf clear-key {
              type string;
            }
          }
        }
        container master {
          description
            "Enter master controller configuration submode";
          choice master-type {
            case branch {
              leaf branch {
                description
                  "Set master type as branch hub";
                type empty;
              }
            }
            case hub {
              leaf hub {
                description
                  "Set master type as hub";
                type empty;
              }
            }
            case transit {
              leaf transit {
                description
                  "Set master type as transit";
                type uint8 {
                  range "1..64";
                }
              }
            }
          }
          container advanced {
            description
              "Advanced configuration submode";
            leaf byte-loss-threshold {
              description
                "Specify minimum byte loss calculation threshold";
              type uint16 {
                range "0..5600";
              }
            }
            leaf channel-unreachable-timer {
              description
                "Unreach interval detection";
              type uint16 {
                range "1..65535";
              }
            }
            leaf load-sharing {
              description
                "Enable load-sharing";
              type empty;
            }
            leaf minimum-mask-length {
              description
                "Specify minimum mask length";
              type uint8 {
                range "1..32";
              }
            }
            leaf mitigation-mode {
              description
                "Enable brown out detection in domain";
              type enumeration {
                enum aggressive;
              }
            }
            leaf packet-loss-threshold {
              description
                "Specify minimum packet loss calculation threshold";
              type uint8 {
                range "1..100";
              }
            }
            container smart-probes {
              description
                "Smart probes configuration";
              leaf destination-port {
                description
                  "Specify smart probes destination port number";
                type uint16 {
                  range "1..65535";
                }
              }
              leaf source-port {
                description
                  "Specify smart probes source port number";
                type uint16 {
                  range "1..65535";
                }
              }
            }
            container syslog {
              description
                "Specify syslog minimum time between tca";
              leaf tca-time-min {
                description
                  "Specify time between syslog tcas in seconds";
                type uint32 {
                  range "30..36000";
                }
              }
            }
            container tcp {
              description
                "Specify tcp port numbers for mc-br communication";
              leaf mc-port {
                description
                  "Specify tcp MC self port for mc-br communication";
                type uint16 {
                  range "1..65535";
                }
              }
            }
            leaf threshold-variance {
              description
                "Policy decision Threshold variance";
              type uint8 {
                range "0..100";
              }
            }
            container traffic-class-ageout-timer {
              description
                "Traffic-class DB age timer";
              leaf interval {
                description
                  "Specify new timer interval value mins/hours";
                type uint16 {
                  range "5..65535";
                }
              }
              leaf interval-unit {
                type enumeration {
                  enum hours;
                  enum minutes;
                }
              }
            }
            leaf transit-site-affinity {
              description
                "Enable Transit Site Affinity";
              type empty;
            }
          }
          container collector {
            description
              "NMS/v9 collector configuration";
            leaf ip {
              type inet:ipv4-address;
            }
            leaf port {
              description
                "Specify collector port number";
              type uint16;
            }
          }
          container enterprise-prefix {
            description
              "Enterprise prefix configuration";
            leaf prefix-list {
              description
                "Specify prefix-list with static site targets";
              type string;
            }
          }
          container load-balance {
            description
              "load balance non-policy traffic";
            presence "true";
            container advanced {
              description
                "Load balancing configuration mode";
              uses domain-vrf-master-hub-class-grouping;
            }
          }
          container password {
            description
              "MD5 password to be used with BRs";
            leaf encryption {
              type enumeration {
                enum 0;
                enum 7;
              }
            }
            leaf clear-key {
              type string;
            }
          }
          container site-prefixes {
            description
              "site-prefixes configuration";
            leaf prefix-list {
              description
                "Specify prefix-list with static site targets";
              type string;
            }
          }
          container source-interface {
            description
              "Source Interface for master controller";
            leaf Loopback {
              description
                "Loopback interface";
              type uint32;
            }
          }
          list class {
            description
              "Create domain class and enter domain class command mode";
            key "name sequence";
            leaf name {
              type string;
            }
            leaf sequence {
              description
                "Set the Sequence for the class";
              type uint16;
            }
            uses domain-vrf-master-hub-class-grouping;
          }
          leaf hub-ip {
            type inet:ipv4-address;
          }
        }
      }
    }
    grouping domain-vrf-master-hub-class-grouping {
      container match {
        description
          "Specify the applications the policy applies to";
        list dscp {
          description
            "specify DSCP";
          key "value";
          leaf value {
            type ios-types:dscp-type;
          }
          leaf policy {
            description
              "Specify the policy (user defined/predefined)";
            type enumeration {
              enum best-effort;
              enum bulk-data;
              enum custom;
              enum low-latency-data;
              enum real-time-video;
              enum scavenger;
              enum voice;
            }
          }
        }
      }
      container path-preference {
        description
          "Specify the preferred provider";
        leaf primary {
          description
            "Primary service provider";
          type string;
        }
        leaf primary2 {
          description
            "Primary service provider";
          type string;
        }
        leaf primary3 {
          description
            "Primary service provider";
          type string;
        }
        leaf fallback {
          description
            "Specify the fallback provider";
          type union {
            type enumeration {
              enum routing;
              enum blackhole;
            }
            type string;
          }
        }
        leaf fallback2 {
          description
            "Fallback service provider";
          type string;
        }
        leaf fallback3 {
          description
            "Fallback service provider";
          type string;
        }
      }
      leaf path-last-resort {
        description
          "Specify path of last resort provider";
        type string;
      }
    }

    grouping identity-policy-grouping {
      leaf absolute-timer {
        description
          "Absolute timeout value in seconds";
        type uint16 {
          range "1..65535";
        }
      }
      leaf access-group {
        description
          "Access list to be applied";
        type string;
      }
      leaf description {
        description
          "Enter a description";
        type string;
      }
      leaf inactivity-timer {
        description
          "Inactivity timeout value in seconds";
        type uint16 {
          range "0..65535";
        }
      }
      leaf interface-template {
        description
          "Interface template to be applied";
        type string;
      }
      container linksec {
        description
          "Configure link security parameters";
        leaf policy {
          description
            "Set the link security policy";
          type enumeration {
            enum must-not-secure;
            enum must-secure;
            enum should-secure;
          }
        }
      }
      container redirect {
        description
          "Redirect clients to a particular location";
        leaf url {
          description
            "URL where clients should be redirected";
          type string;
        }
      }
      container service-policy {
        description
          "Configure service policy";
        list qos {
          description
            "Configure qos policies for client";
          key "direction";
          leaf direction {
            type enumeration {
              enum input;
              enum output;
            }
          }
          leaf name {
            type string;
          }
        }
      }
      leaf sgt {
        description
          "SGT tag";
        type uint16 {
          range "2..65519";
        }
      }
      leaf tag {
        description
          "tag name";
        type string;
      }
      container tunnel {
        description
          "tunnel for wired client access";
        container type {
          description
            "tunnel type";
          container capwap {
            description
              "capwap tunnel type";
            leaf name {
              description
                "tunnel profile name";
              type string;
            }
          }
        }
      }
      leaf vlan {
        description
          "Enter a VlanId";
        type uint16 {
          range "1..4094";
        }
      }
      container voice {
        description
          "Voice feature";
        leaf vlan {
          description
            "Critical voice vlan";
          type empty;
        }
      }
    }

    uses config-parser-grouping;
    container service {
      description
        "Modify use of network based services";
      leaf internal {
        description
          "Enable/Disable Internal commands";
        type empty;
      }
      container pad-conf {
        leaf pad {
          description
            "Enable PAD commands";
          type boolean;
          default "false";
        }
      }
      container pad-config-more {
        container pad-config {
          description
            "Enable PAD commands";
          leaf cmns {
            description
              "Enable PAD over CMNS connections";
            type empty;
          }
          leaf from-xot {
            description
              "Accept XOT to PAD connections";
            type empty;
          }
          leaf to-xot {
            description
              "Allow outgoing PAD over XOT connections";
            type empty;
          }
        }
      }
      container pad {
        description
          "Enable PAD commands";
        status deprecated;
        presence "true";
        leaf cmns {
          description
            "Enable PAD over CMNS connections";
          status deprecated;
          type empty;
        }
        leaf from-xot {
          description
            "Accept XOT to PAD connections";
          status deprecated;
          type empty;
        }
        leaf to-xot {
          description
            "Allow outgoing PAD over XOT connections";
          status deprecated;
          type empty;
        }
      }
      leaf password-encryption {
        description
          "Encrypt system passwords";
        type empty;
      }
      leaf password-recovery {
        description
          "Enable password recovery";
        type boolean;
      }
      leaf private-config-encryption {
        description
          "Enable private config file encryption";
        type empty;
      }
      grouping service-timestamps-debug-log-options {
        container datetime {
          description
            "Timestamp with date and time";
          presence "true";
          leaf msec {
            description
              "Include milliseconds in timestamp";
            type empty;
          }
          leaf localtime {
            description
              "Use local time zone for timestamps";
            type empty;
          }
          leaf show-timezone {
            description
              "Add time zone information to timestamp";
            type empty;
          }
          leaf year {
            description
              "Include year in timestamp";
            type empty;
          }
        }
        leaf uptime {
          description
            "Timestamp with system uptime";
          type empty;
        }
      }

      container timestamps {
        description
          "Timestamp debug/log messages";
        presence "true";
        container debug-config {
          description
            "Timestamp debug messages";
          presence "true";
          uses service-timestamps-debug-log-options;
        }
        container log-config {
          description
            "Timestamp log messages";
          presence "true";
          uses service-timestamps-debug-log-options;
        }
        container debug {
          description
            "Timestamp debug messages";
          status obsolete;
          container datetime {
            description
              "Timestamp with date and time";
            status obsolete;
            presence "true";
            container localtime {
              description
                "Use local time zone for timestamps";
              status obsolete;
              presence "true";
              container msec {
                description
                  "Include milliseconds in timestamp";
                status obsolete;
                presence "true";
                uses service-timestamp-show-timezone-and-year;
              }
              container show-timezone {
                description
                  "Add time zone information to timestamp";
                status obsolete;
                presence "true";
                uses service-timestamp-msec-and-year;
              }
              container year {
                description
                  "Include year in timestamp";
                status obsolete;
                presence "true";
                uses service-timestamp-msec-and-show-timezone;
              }
            }
            container msec {
              description
                "Include milliseconds in timestamp";
              status obsolete;
              presence "true";
              container localtime {
                description
                  "Use local time zone for timestamps";
                status obsolete;
                presence "true";
                uses service-timestamp-show-timezone-and-year;
              }
              container show-timezone {
                description
                  "Add time zone information to timestamp";
                status obsolete;
                presence "true";
                uses service-timestamp-local-time-and-year;
              }
              container year {
                description
                  "Include year in timestamp";
                status obsolete;
                presence "true";
                uses service-timestamp-local-time-and-show-timezone;
              }
            }
            container show-timezone {
              description
                "Add time zone information to timestamp";
              status obsolete;
              presence "true";
              container localtime {
                description
                  "Use local time zone for timestamps";
                status obsolete;
                presence "true";
                uses service-timestamp-msec-and-year;
              }
              container msec {
                description
                  "Include milliseconds in timestamp";
                status obsolete;
                presence "true";
                uses service-timestamp-local-time-and-year;
              }
              container year {
                description
                  "Include year in timestamp";
                status obsolete;
                presence "true";
                uses service-timestamp-local-time-and-msec;
              }
            }
            container year {
              description
                "Include year in timestamp";
              status obsolete;
              presence "true";
              container localtime {
                description
                  "Use local time zone for timestamps";
                status obsolete;
                presence "true";
                uses service-timestamp-msec-and-show-timezone;
              }
              container msec {
                description
                  "Include milliseconds in timestamp";
                status obsolete;
                presence "true";
                uses service-timestamp-local-time-and-show-timezone;
              }
              container show-timezone {
                description
                  "Add time zone information to timestamp";
                status obsolete;
                presence "true";
                uses service-timestamp-local-time-and-msec;
              }
            }
          }
          leaf uptime {
            description
              "Timestamp with system uptime";
            status obsolete;
            type empty;
          }
        }
        container log {
          description
            "Timestamp log messages";
          status obsolete;
          container datetime {
            description
              "Timestamp with date and time";
            status obsolete;
            presence "true";
            leaf msec {
              description
                "Include milliseconds in timestamp";
              status obsolete;
              type empty;
            }
            leaf localtime {
              description
                "Use local time zone for timestamps";
              status obsolete;
              type empty;
            }
            leaf show-timezone {
              description
                "Add time zone information to timestamp";
              status obsolete;
              type empty;
            }
            leaf year {
              description
                "Include year in timestamp";
              status obsolete;
              type empty;
            }
          }
          leaf uptime {
            description
              "Timestamp with system uptime";
            status obsolete;
            type empty;
          }
        }
      }
      container alignment {
        description
          "Control alignment correction and logging";
        leaf detection {
          description
            "Enable detection of alignment issues";
          type empty;
        }
        leaf logging {
          description
            "Enable logging of alignment issues";
          type empty;
        }
      }
      leaf call-home {
        description
          "Enable call-home service";
        type empty;
      }
      leaf compress-config {
        description
          "Compress the configuration file";
        type empty;
      }
      leaf config {
        description
          "TFTP load config files";
        type empty;
      }
      container counters {
        description
          "Control aging of interface counters";
        container max {
          description
            "Maximum counter aging threshold";
          leaf age {
            description
              "Aging threshold";
            type uint8 {
              range "0..60";
            }
          }
        }
      }
      leaf dhcp {
        description
          "Enable DHCP server and relay agent";
        type empty;
      }
      leaf disable-ip-fast-frag {
        description
          "Disable IP particle-based fast fragmentation";
        type empty;
      }
      leaf exec-callback {
        description
          "Enable exec callback";
        type empty;
      }
      leaf exec-wait {
        description
          "Delay EXEC startup on noisy lines";
        type empty;
      }
      leaf finger {
        description
          "Allow responses to finger requests";
        type empty;
      }
      container heartbeat {
        description
          "Enable heartbeat processing";
        leaf fatal-count {
          description
            "Set heartbeat fatal count";
          type uint8 {
            range "1..60";
          }
        }
        leaf interrupt-interval {
          description
            "Set heartbeat interrupt test interval";
          type uint8 {
            range "0..60";
          }
        }
        leaf interrupt-max {
          description
            "Set maximum message count from interrupt test";
          type uint8 {
            range "0..60";
          }
        }
        leaf transmit-interval {
          description
            "Set heartbeat transmit interval";
          type uint8 {
            range "1..30";
          }
        }
        leaf warning-timeout {
          description
            "Set heartbeat warning timeout interval";
          type uint8 {
            range "5..60";
          }
        }
      }
      leaf hide-telnet-addresses {
        description
          "Hide destination addresses in telnet command";
        type empty;
      }
      leaf linenumber {
        description
          "enable line number banner for each exec";
        type empty;
      }
      leaf log-hidden {
        description
          "Enable syslog msgs for hidden/internal commands";
        type empty;
      }
      leaf nagle {
        description
          "Enable Nagle's congestion control algorithm";
        type empty;
      }
      leaf old-slip-prompts {
        description
          "Allow old scripts to operate with slip/ppp";
        type empty;
      }
      container prompt {
        description
          "Enable mode specific prompt";
        leaf config {
          description
            "Enable configuration mode prompt";
          type empty;
        }
      }
      leaf pt-vty-logging {
        description
          "Log significant VTY-Async events";
        type empty;
      }
      leaf sequence-numbers {
        description
          "Stamp logger messages with a sequence number";
        type empty;
      }
      leaf slave-log {
        description
          "Enable log capability of slave IPs";
        type empty;
      }
      leaf tcp-keepalives-in {
        description
          "Generate keepalives on idle incoming network connections";
        type empty;
      }
      leaf tcp-keepalives-out {
        description
          "Generate keepalives on idle outgoing network connections";
        type empty;
      }
      leaf telnet-zeroidle {
        description
          "Set TCP window 0 when connection is idle";
        type empty;
      }
      leaf tcp-small-servers {
        description
          "Enable small TCP servers (e.g., ECHO)";
        type empty;
      }
      leaf udp-small-servers {
        description
          "Enable small UDP servers (e.g., ECHO)";
        type empty;
      }
      leaf unsupported-transceiver {
        description
          "Enable support for third-party transceivers";
        type empty;
      }
    }
    container platform {
      description
        "platform specific configuration";
    }
    leaf hostname {
      description
        "Set system's network name";
      type string;
    }
    container enable {
      description
        "Modify enable password parameters";
      container password {
        description
          "Assign the privileged level password (MAX of 25 characters)";
        uses password-07-grouping;
      }
      leaf last-resort {
        description
          "Define enable action if no TACACS servers respond";
        type enumeration {
          enum password;
          enum succeed;
        }
      }
      container secret {
        description
          "Assign the privileged level secret";
        leaf level {
          description
            "Set exec level password";
          type uint8;
        }
        leaf type {
          type enumeration {
            enum 0;
            enum 4;
            enum 5;
            enum 8;
            enum 9;
          }
        }
        leaf secret {
          type string;
        }
      }
      leaf use-tacacs {
        description
          "Use TACACS to check enable passwords";
        type empty;
      }
    }
    container password {
      description
        "Configure encryption password (key)";
      container encryption {
        description
          "Encrypt system passwords";
        leaf aes {
          description
            "Enable stronger (AES) password encryption";
          type empty;
        }
      }
    }
    container eap {
      description
        "Configure EAP authenticator parameters";
      container key-name {
        description
          "EAP Key-name";
        leaf compliance {
          description
            "Turn on compliance for EAP key-name";
          type empty;
        }
      }
      container method {
        description
          "Configure EAP authentication method profiles";
        container fast {
          description
            "EAP-FAST method configuration";
          list profile {
            description
              "Set the authentication method profile name";
            key "name";
            leaf name {
              description
                "Specify the name of the method profile
                 (max 63 characters)";
              type string;
            }
            leaf accept-on-auth-prov {
              description
                "Accept client on authenticated provisioning,
                 default: on";
              type boolean;
              default "true";
            }
            leaf allow-anon-prov {
              description
                "Allow anonymous provisioning, default: on";
              type boolean;
              default "true";
            }
            leaf allow-auth-prov {
              description
                "Allow authenticated provisioning,default: on";
              type boolean;
              default "true";
            }
            container authority-id {
              description
                "Configure the authority ID";
              leaf identity {
                description
                  "Specify the authority ID identity";
                type string;
              }
              leaf information {
                description
                  "Specify the authority ID information";
                type string;
              }
            }
            leaf client-cert-required {
              description
                "Use a client certificate if present,
                 default: on";
              type boolean;
              default "true";
            }
            leaf description {
              description
                "Description for this EAP-FAST profile";
              type string;
            }
            leaf local-cert-required {
              description
                "Use a local (server) certificate if present,
                 default: on";
              type boolean;
              default "true";
            }
            container local-key {
              description
                "Configure the local (server) key";
              leaf type {
                description
                  "type of local-key";
                type enumeration {
                  enum 0;
                  enum 7;
                }
              }
              leaf secret {
                description
                  "define local-key";
                type string {
                  pattern '.*';
                }
              }
            }
            container pac-password {
              description
                "Default password for manual PAC provisioning";
              leaf type {
                description
                  "type of pac-password";
                type enumeration {
                  enum 0;
                  enum 7;
                }
              }
              leaf secret {
                description
                  "define pac-password";
                type string {
                  pattern '.*';
                }
              }
            }
            leaf pac-ttl {
              description
                "PAC Time to live in seconds, default: 86400";
              type uint32 {
                range "1..700000000";
              }
              default "86400";
            }
          }
        }
      }
      list profile {
        description
          "Configure EAP profiles";
        key "name";
        leaf name {
          description
            "Specify a profile name (max 63 characters)";
          type string;
        }
        leaf description {
          description
            "Provide a description for the EAP profile";
          type string;
        }
        container method {
          description
            "Add an allowed method";
          container fast-config {
            description
              "EAP-FAST method allowed";
            presence "true";
            leaf profile {
              description
                "Set the authenticator profile for this method";
              type string;
            }
          }
          leaf fast {
            status deprecated;
            description
              "Deprecated: Use fast-config";
            type empty;
          }
          leaf gtc {
            description
              "EAP-GTC method allowed";
            type empty;
          }
          leaf leap {
            description
              "EAP-LEAP method allowed";
            type empty;
          }
          leaf mschapv2 {
            description
              "EAP-MSCHAPV2 method allowed";
            type empty;
          }
          leaf peap {
            description
              "EAP-PEAP method allowed";
            type empty;
          }
          leaf md5 {
            description
              "EAP-MD5 method allowed";
            type empty;
          }
          leaf tls {
            description
              "EAP-TLS method allowed";
            type empty;
          }
        }
        leaf pki-trustpoint {
          description
            "Set the default pki trustpoint";
          type string;
        }
      }
    }
    container archive {
      description
        "Archive the configuration";
      container log {
        description
          "Logging commands";
        container config {
          description
            "Logging changes to the running configuration";
          leaf hidekeys {
            description
              "suppress output (e.g. passwords) when displaying logged commands";
            type empty;
          }
          container logging {
            description
              "Modify config logging parameters";
            leaf enable {
              description
                "Enable the config logger";
              type empty;
            }
            leaf size {
              description
                "Maximum number of logged commands that will be kept by the config log";
              type uint16 {
                range "1..1000";
              }
            }
            container persistent {
              description
                "Log configuration persistent";
              presence "true";
              leaf auto {
                description
                  "Log configuration commands automatically";
                type empty;
              }
              leaf reload {
                description
                  "Apply persisted commands on reload";
                type empty;
              }
            }
          }
          container notify {
            description
              "Send logged commands to target applications";
            container syslog {
              description
                "Send logged commands as syslog messages";
              presence "true";
              leaf contenttype {
                description
                  "Type of the syslog message content";
                type enumeration {
                  enum plaintext;
                  enum xml;
                }
              }
            }
          }
        }
      }
      leaf path {
        description
          "path for backups";
        type union {
          type enumeration {
            enum bootflash:;
            enum flash:;
            enum ftp:;
            enum harddisk:;
            enum http:;
            enum https:;
            enum pram:;
            enum rcp:;
            enum scp:;
            enum tftp:;
          }
          type string;
        }
      }
      leaf maximum {
        description
          "maximum number of backup copies";
        type uint8 {
          range "1..14";
        }
      }
      leaf write-memory {
        description
          "Enable automatic backup generation during write memory";
        type empty;
      }
      leaf time-period {
        description
          "Period of time in minutes to automatically archive the running-config";
        type uint32 {
          range "1..525600";
        }
      }
    }
    list username {
      description
        "Establish User Name Authentication";
      key "name";
      leaf name {
        type string;
      }
      leaf privilege {
        description
          "Set user privilege level";
        type uint8 {
          range "0..15";
        }
      }
      leaf view {
        description
          "Set view name";
        type string;
      }
      leaf one-time {
        description
          "Specify that the username/password is valid for only one time";
        type empty;
      }
      leaf mac {
        description
          "Entry is for MAC Filtering";
        type empty;
      }
      leaf serial-number {
        description
          "Entry is for serial number";
        type empty;
      }
      leaf description {
        description
          "description string with max 128 characters";
        type string;
      }
      leaf wlan-profile-name {
        description
          "wlan-profile-name string with max 32 characters";
        type string;
      }
      container password {
        description
          "Specify the password for the user";
        leaf encryption {
          type enumeration {
            enum 0;
            enum 7;
            enum 6;
          }
        }
        leaf password {
          type string {
            pattern '.*';
          }
        }
      }
      container secret {
        description
          "Specify the secret for the user";
        leaf encryption {
          type enumeration {
            enum 0;
            enum 5;
            enum 8;
            enum 9;
          }
        }
        leaf secret {
          type string;
        }
      }
    }
    list user-name {
      description
        "Establish User-Name Authentication";
      key "name";
      leaf name {
        type string;
      }
      leaf privilege {
        description
          "User Privilege level";
        type uint8 {
          range "0..15";
        }
      }
      leaf view {
        description
          "Set User View name";
        type string;
      }
      leaf mac {
        description
          "Entry is for MAC Filtering";
        type empty;
      }
      leaf description {
        description
          "description string with max 128 characters";
        type string;
      }
      container type {
        description
          "Specify the type of the user";
        choice user-type {
          case default-user-type {
            leaf default {
              description
                "Default user type";
              type empty;
            }
          }
          case lobby-admin-user-type {
            leaf lobby-admin {
              description
                "Lobby Admin User";
              type empty;
            }
          }
          case mgmt-user-type {
            leaf mgmt-user {
              description
                "Mgmt user type";
              type empty;
            }
          }
          case network-user-type {
            container network-user {
              description
                "Network user type";
              leaf description {
                description
                  "User Description";
                type string;
              }
              container guest-user {
                description
                  "Guest user type";
                leaf max-login-limit {
                  description
                    "Maximum login limits per guest user credentials";
                  type uint8 {
                    range "0..64";
                  }
                }
                container lifetime {
                  description
                    "Lifetime of user";
                  leaf year {
                    description
                      "Number of Years";
                    type uint8 {
                      range "0..1";
                    }
                  }
                  leaf month {
                    description
                      "Number of months";
                    type uint8 {
                      range "0..11";
                    }
                  }
                  leaf day {
                    description
                      "Number of days";
                    type uint8 {
                      range "0..30";
                    }
                  }
                  leaf hour {
                    description
                      "Number of hours";
                    type uint8 {
                      range "0..23";
                    }
                  }
                  leaf minute {
                    description
                      "Number of minutes";
                    type uint8 {
                      range "0..59";
                    }
                  }
                  leaf second {
                    description
                      "Number of seconds";
                    type uint8 {
                      range "0..59";
                    }
                  }
                }
              }
            }
          }
        }
      }
      leaf wlan-profile-name {
        description
          "wlan-profile-name string with max 32 characters";
        type string;
      }
      container password {
        description
          "Password for the user";
        leaf encryption {
          type enumeration {
            enum 0;
            enum 7;
            enum 6;
          }
        }
        leaf password {
          type string {
            pattern '.*';
          }
        }
      }
      container secret {
        description
          "Secret for the user";
        leaf encryption {
          type enumeration {
            enum 0;
            enum 5;
            enum 8;
            enum 9;
          }
        }
        leaf secret {
          type string;
        }
      }
    }
    container card {
      description
        "Configure T1/E1 SPA";
    }
    container controller {
      description
        "Configure controller";
    }
    container frame-relay {
      description
        "global frame relay configuration commands";
    }
    leaf aqm-register-fnf {
      description
        "Export audio/video stats to flow record";
      type empty;
    }
    uses config-vrf-definition-grouping;
    uses config-global-address-family;
    container rmon {
      description
        "Remote Monitoring";
      list alarm {
        description
          "Configure an RMON alarm";
        key "number";
        leaf number {
          type uint16;
        }
        leaf mib-object {
          type string;
        }
        leaf sample-interval {
          type uint32;
        }
        leaf test-mode {
          type enumeration {
            enum absolute;
            enum delta;
          }
        }
        leaf rising-threshold {
          description
            "Configure the rising threshold";
          type int32;
        }
        leaf rising-event {
          type uint16;
        }
        leaf falling-threshold {
          description
            "Configure the falling threshold";
          type int32;
        }
        leaf falling-event {
          type uint16;
        }
        leaf owner {
          description
            "Specify an owner for the alarm";
          type string;
        }
      }
      list event {
        description
          "Configure an RMON event";
        key "number";
        leaf number {
          type uint16;
        }
        container log {
          description
            "Generate RMON log when the event fires";
          presence "true";
          leaf trap {
            description
              "Generate SNMP trap when the event fires";
            type string;
          }
          leaf description {
            description
              "Specify a description of the event";
            type string;
          }
          leaf owner {
            description
              "Specify an owner for the event";
            type string;
          }
        }
      }
    }
    list sampler {
      description
        "Define a Sampler";
      key "name";
      leaf name {
        type string;
      }
    }
    container flow {
      description
        "Global Flow configuration subcommands";
    }
    uses config-ip-grouping;
    container mka {
      description
        "MACsec Key Agreement (MKA) configuration";
    }
    container macro {
      description
        "Macro configuration";
      container global {
        description
          "Enter global macro configuration";
        leaf description {
          description
            "Macro description of this device";
          type string;
        }
      }
      container auto {
        description
          "Macro autoexecution settings";
      }
    }
    uses config-ipv6-grouping;
    container vlan {
      description
        "Global vlan configuration";
    }
    container mvrp {
      description
        "Global MVRP";
    }
    container avb {
      description
        "Global AVB";
      presence "true";
    }
    container ptp {
      description
        "Global PTP";
    }
    container cdp {
      description
        "Global CDP configuration subcommands";
    }
    container avc {
      description
        "Application visibility and control";
    }
    container policy;
    uses config-interface-grouping;
    list route-map {
      description
        "Route map tag";
      key "name";
      leaf name {
        description
          "WORD;;Route map tag";
        type string;
      }
    }
    container route-tag;
    list table-map {
      description
        "Configure Table Map";
      key "name";
      leaf name {
        type string;
      }
    }
    container sdm {
      description
        "Switch database management";
    }
    container mls {
      description
        "mls global commands";
    }
    container object-group {
      description
        "Configure Object group";
    }
    list pseudowire-class {
      description
        "Pseudowire-class configuration";
      key "name";
      leaf name {
        type string;
      }
    }
    list l2tp-class {
      description
        "l2tp-class configuration";
      key "name";
      leaf name {
        description
          "l2tp-class name";
        type string;
      }
    }
    container control-plane {
      description
        "Configure control plane services";
      presence "true";
    }
    container control-plane-host {
      container control-plane {
        description
          "Configure control plane services";
        container host {
          presence "true";
          list management-interface {
            description
              "Configure interface for receiving network management traffic";
            key "interface-name";
            leaf interface-name {
              type string;
            }
            container allow {
              description
                "Allowed network management protocols on selected interface";
              leaf beep {
                description
                  "Beep Protocol";
                type empty;
              }
              leaf ftp {
                description
                  "File Transfer Protocol";
                type empty;
              }
              leaf http {
                description
                  "HTTP Protocol";
                type empty;
              }
              leaf https {
                description
                  "HTTPS Protocol";
                type empty;
              }
              leaf snmp {
                description
                  "Simple Network Management Protocol";
                type empty;
              }
              leaf ssh {
                description
                  "Secure Shell Protocol";
                type empty;
              }
              leaf telnet {
                description
                  "Telnet Protocol";
                type empty;
              }
              leaf tftp {
                description
                  "Trivial File Transfer Protocol";
                type empty;
              }
              leaf tl1 {
                description
                  "Transaction Language Session Protocol";
                type empty;
              }
            }
          }
        }
      }
    }
    leaf config-register {
      description
        "Define the configuration register";
      type string {
        pattern '[0-9xXa-fA-F].*';
      }
    }
    container clock {
      description
        "Configure time-of-day clock";
      container calendar-valid {
        description
          "Calendar time is authoritative";
        presence "true";
      }
      container summer-time {
        description
          "Configure summer (daylight savings) time";
        leaf zone {
          description
            "Name of time zone in summer";
          type string;
        }
        choice summer-choice {
          case date-case {
            leaf date {
              description
                "Configure absolute summer time";
              type empty;
            }
            leaf start-day {
              type uint8 {
                range "1..31";
              }
            }
            leaf start-month {
              type ios-types:month-type;
            }
            leaf start-year {
              type uint32 {
                range "1993..2035";
              }
            }
            leaf start-time {
              type ios-types:hhmm-type;
            }
            leaf date-end-day {
              type uint8 {
                range "1..31";
              }
            }
            leaf date-end-month {
              type ios-types:month-type;
            }
            leaf date-end-year {
              type uint32 {
                range "1993..2035";
              }
            }
            leaf date-end-time {
              type ios-types:hhmm-type;
            }
            leaf offset {
              type uint16 {
                range "1..1440";
              }
            }
          }
          case recurring-case {
            leaf recurring {
              description
                "Configure recurring summer time";
              type empty;
            }
            leaf recurring-start {
              type union {
                type uint8 {
                  range "1..4";
                }
                type enumeration {
                  enum first;
                  enum last;
                }
              }
            }
            leaf recurring-start-day {
              type ios-types:weekday-type;
            }
            leaf recurring-start-month {
              type ios-types:month-type;
            }
            leaf recurring-start-time {
              type ios-types:hhmm-type;
            }
            leaf recurring-end {
              type union {
                type uint8 {
                  range "1..4";
                }
                type enumeration {
                  enum first;
                  enum last;
                }
              }
            }
            leaf recurring-end-day {
              type ios-types:weekday-type;
            }
            leaf recurring-end-month {
              type ios-types:month-type;
            }
            leaf recurring-end-time {
              type ios-types:hhmm-type;
            }
            leaf recurring-offset {
              type uint16 {
                range "1..1440";
              }
            }
          }
        }
      }
      container timezone {
        description
          "Configure time zone";
        leaf zone {
          description
            "Name of time zone";
          type string;
        }
        leaf offset {
          status obsolete;
          type enumeration {
            enum +;
            enum -;
          }
        }
        leaf hours {
          type int8 {
            range "-23..23";
          }
        }
        leaf minutes {
          type int8 {
            range "0..59";
          }
        }
      }
    }
    uses config-logging-grouping;
    container aaa {
      description
        "Authentication, Authorization and Accounting.";
    }
    uses config-privilege-grouping;
    container login {
      description
        "Enable secure login checking";
      leaf delay {
        description
          "Set delay between successive fail login";
        type uint8 {
          range "1..10";
        }
      }
      container on-failure {
        description
          "Set options for failed login attempt";
        presence "true";
        container log {
          description
            "Generate syslogs on failure logins";
          presence "true";
          leaf every {
            description
              "Periodicity for logs generated";
            type uint16 {
              range "1..65535";
            }
          }
        }
      }
      container on-success {
        description
          "Set options for successful login attempt";
        presence "true";
        container log {
          description
            "Generate syslogs on successful logins";
          presence "true";
          leaf every {
            description
              "Periodicity for logs generated";
            type uint16 {
              range "1..65535";
            }
          }
        }
      }
      container quiet-mode {
        description
          "Set quiet-mode options";
        leaf access-class {
          description
            "Set access class";
          type union {
            type uint16 {
              range "1..199|1300..2699";
            }
            type string {
              length "1..223";
              pattern '[a-zA-Z].*';
            }
          }
        }
      }
      container block-config {
        leaf block-for {
          description
            "Set quiet-mode active time period";
          type uint16 {
            range "1..65535";
          }
        }
        leaf attempts {
          description
            "Fail attempts max value";
          type uint16 {
            range "1..65535";
          }
        }
        leaf within {
          description
            "Watch period for fail attempts";
          type uint16 {
            range "1..65535";
          }
        }
      }
    }
    container multilink {
      description
        "PPP multilink global configuration";
    }
    container mac-address-table {
      description
        "Configure the MAC address table";
      container evc-xconnect {
        description
          "All ethernet virtual connections xconnect";
        leaf l2pt-forward-all {
          description
            "Layer 2 Protocol Forward All";
          type empty;
        }
      }
      container limit {
        description
          "Enter parameters for mac limit feature";
        list bdomain {
          description
            "bdomain number for  mac limit feature";
          key "number";
          leaf number {
            type uint16 {
              range "1..4095";
            }
          }
          leaf action {
            description
              "Enter action";
            type enumeration {
              enum warning;
              enum limit;
              enum shutdown;
            }
          }
          leaf maximum {
            description
              "Enter max allowed entries";
            type uint32 {
              range "0..16000";
            }
          }
        }
      }
      container learning {
        description
          "Enable a MAC table learning feature";
        list vlan {
          description
            "Layer 2 table learning per VLAN";
          key "id";
          leaf id {
            type uint16 {
              range "1..4094";
            }
          }
          leaf module {
            description
              "Layer 2 table learning per VLAN per module";
            type uint8 {
              range "1..9";
            }
          }
        }
      }
    }
    container redundancy {
      description
        "Enter redundancy mode";
      presence "true";
      container application {
        description
          "Enter application redundancy group mode";
        container redundancy {
          description
            "Enter application redundancy group mode";
          presence "true";
          list group {
            description
              "Enter rg group mode";
            key "id";
            leaf id {
              description
                "rg group id";
              type uint8 {
                range "1..2";
              }
            }
            container name {
              description
                "RG group name string";
              leaf group-name {
                description
                  "name string (25 chars. max)";
                type string {
                  length "1..25";
                }
              }
            }
            container control {
              description
                "RG group control interface";
              leaf interface {
                description
                  "Interface to be used as RG control interface";
                type string;
              }
              leaf protocol {
                description
                  "RG group protocol media";
                when '../interface';
                type uint8 {
                  range "1..8";
                }
              }
            }
            leaf data {
              description
                "RG group data interface";
              type string;
            }
            leaf preempt {
              description
                "RG group preempt";
              type empty;
            }
            container timers {
              description
                "RG group timers";
              leaf delay {
                description
                  "RG group delay timer. value in seconds";
                type uint16 {
                  range "0..10000";
                }
              }
              leaf reload {
                description
                  "RG group reload timer. Value in seconds";
                when '../delay';
                type uint16 {
                  range "0..10000";
                }
              }
            }
            container priority {
              description
                "RG group Priority";
              leaf value {
                description
                  "Priority value";
                type uint8 {
                  range "1..255";
                }
              }
              container failover {
                description
                  "Failover Threshold";
                when '../value';
                leaf threshold {
                  description
                    "Failover Threshold";
                  type uint8 {
                    range "1..255";
                  }
                }
              }
              leaf failover-threshold {
                status deprecated;
                description
                  "Failover Threshold";
                when '../value';
                type uint8 {
                  range "1..255";
                }
              }
            }
          }
        }
      }
      leaf maintenance-mode {
        description
          "Enable/Disable maintenance mode ";
        type empty;
      }
      container main-cpu {
        description
          "Enter main-cpu mode";
        presence "true";
        container auto-sync {
          leaf running-config {
            type empty;
          }
          leaf config-register {
            type empty;
          }
          leaf bootvar {
            type empty;
          }
          leaf standard {
            type empty;
          }
        }
        container standby {
          description
            "Standby";
          container console {
            description
              "Console";
            leaf enable {
              description
                "Enable";
              type empty;
            }
          }
          container initialization {
            description
              "Initialization";
            container delay {
              description
                "Delay";
              leaf second {
                description
                  "Delay value in seconds";
                type uint16 {
                  range "30..1800";
                }
              }
              leaf boot-only {
                description
                  "Delay effective only on system boot";
                type empty;
              }
            }
          }
        }
      }
      leaf mode {
        description
          "redundancy mode for this chassis";
        type enumeration {
          enum rpr;
          enum rpr-plus;
          enum sso;
          enum none;
        }
      }
      container policy {
        description
          "redundancy policy enforcement";
        container config-sync {
          description
            "config sync parameters";
          container bulk {
            description
              "bulk configuration mode";
            container prc {
              description
                "prc policy enforcement";
              leaf reload {
                description
                  "reload standby";
                type boolean;
              }
            }
          }
          container lbl {
            description
              "line-by-line configuration mode";
            container prc {
              description
                "prc policy enforcement";
              leaf reload {
                description
                  "reload standby";
                type boolean;
              }
            }
          }
        }
      }
      container timer {
        description
          "Select a timer to configure";
        leaf rpso {
          description
            "Delay value in seconds";
          type uint16 {
            range "120..1200";
          }
        }
      }
      container interchassis {
        description
          "Enter interchassis mode";
        list group {
          description
            "Enter the redundancy group number";
          key "group-number";
          leaf group-number {
            type uint64 {
              range "1..4294967295";
            }
          }
          container monitor {
            description
              "define the peer monitoring method";
            leaf peer {
              description
                "the peer method";
              type empty;
            }
            leaf bfd {
              description
                "set peer monitoring method to bfd";
              type empty;
            }
          }
          container member {
            description
              "specify a redundancy group member";
            leaf ip {
              description
                "specify the redundancy group member using an ip address";
              type inet:ipv4-address;
            }
          }
          container backbone {
            description
              "specify a redundancy group member";
            container interface {
              uses ios-ifc:interface-grouping;
            }
          }
        }
      }
    }
    container scheduler {
      description
        "Scheduler parameters";
      container runtime {
        description
          "Process runtime controls";
        leaf netinput {
          description
            "Process-switching run time (in milliseconds)";
          type uint16 {
            range "100..40000";
          }
        }
      }
      container allocate {
        description
          "Guarantee CPU time for processes";
        leaf interrupt-time {
          type uint16 {
            range "400..60000";
          }
        }
        leaf process-time {
          type uint16 {
            range "100..4000";
          }
        }
      }
    }
    container epm {
      description
        "EPM Global Configuration Commands";
      leaf logging {
        description
          "Enable EPM logging";
        type empty;
      }
    }
    container spanning-tree {
      description
        "Spanning Tree Subsystem";
    }
    container subscriber {
      description
        "Subscriber configuration";
      leaf templating {
        description
          "Configure subscriber templating";
        type empty;
      }
    }
    container track {
      description
        "Object tracking configuration commands";
    }
    container dot1x {
      description
        "IEEE 802.1X Global Configuration Commands";
    }
    container mab {
      description
        "mab Configuration Commands";
      container logging {
        description
          "Set logging parameters";
        leaf verbose {
          description
            "Show verbose messages in system logs";
          type empty;
        }
      }
      container request {
        description
          "Customize MAB request";
        container format {
          description
            "Configure the customized MAB request format";
          container attribute {
            description
              "Format selected attributes";
            container one {
              description
                "Username format used for MAB requests";
              container groupsize {
                description
                  "Specify how may hex digits per group";
                leaf size {
                  description
                    "specify how many digits per group";
                  type uint8 {
                    range "1|2|4|6|12";
                  }
                }
                leaf separator {
                  description
                    "Specify how to separate groups";
                  type enumeration {
                    enum -;
                    enum .;
                    enum :;
                  }
                }
                leaf case {
                  description
                    "Username will be sent in lower-case/upper-case format";
                  type enumeration {
                    enum lowercase;
                    enum uppercase;
                  }
                }
              }
            }
            container two {
              description
                "Global Password used for all MAB requests";
              leaf type {
                description
                  "0 Specifies an UNENCRYPTED password will follow 
                   7 Specifies a HIDDEN password will follow";
                type enumeration {
                  enum 0;
                  enum 7;
                }
              }
              leaf LINE {
                description
                  "The UNENCRYPTED (cleartext) password";
                type string;
              }
            }
            container thirty-two {
              description
                "NAS-Identifier attribute";
              container vlan {
                description
                  "Add the vlan";
                leaf access-vlan {
                  description
                    "Add the configured access vlan";
                  type empty;
                }
              }
            }
          }
        }
      }
    }
    container fallback {
      description
        "Fallback configuration commands";
    }
    container parameter-map {
      description
        "parameter map";
      container type {
        description
          "parameter map type";
      }
    }
    container ppp {
      description
        "PPP global configuration";
    }
    container mac {
      description
        "Global MAC configuration subcommands";
      container address-table {
        description
          "Configure the MAC address table";
        container aging-time {
          description
            "Set MAC address table entry maximum age";
          leaf val {
            type uint32 {
              range "0 | 10..1000000";
            }
          }
          leaf routed-mac {
            description
              "Set RM Aging interval";
            type empty;
          }
          leaf vlan {
            description
              "VLAN Keyword";
            type uint16 {
              range "1..4094";
            }
          }
        }
        leaf control-packet-learn {
          description
            "Enable/Disable learning from Control Packets";
          type empty;
        }
        container learning {
          description
            "Enable MAC table learning feature";
          leaf vlan {
            description
              "<1-4094>,VLAN id to enable MAC Address learning";
            type uint16 {
              range "1..4094";
            }
          }
        }
        container notification {
          description
            "Enable/Disable MAC Notification on the switch";
          container change {
            description
              "Enable/Disable MAC Notification feature on the switch";
            presence "true";
            leaf history-size {
              description
                "Number of entries in history table (0-500)";
              type uint16 {
                range "0..500";
              }
            }
            leaf interval {
              description
                "Notification interval in seconds (0-2147483647)";
              type uint32 {
                range "0..2147483647";
              }
            }
          }
          leaf mac-move {
            description
              "Enable Mac Move Notification";
            type empty;
          }
          container threshold {
            description
              "Configure L2 Table monitoring";
            presence "true";
            leaf interval {
              description
                "<120-1000000> Interval time in seconds";
              type uint32 {
                range "120..1000000";
              }
            }
            container limit {
              description
                "Limit percentage";
              leaf percentage {
                description
                  "Percentage (0-100)";
                type uint8 {
                  range "0..100";
                }
              }
              leaf interval {
                description
                  "<120-1000000> Interval time in seconds";
                type uint32 {
                  range "120..1000000";
                }
              }
            }
          }
        }
        list static {
          description
            "Static MAC entry";
          key "mac-address vlan";
          leaf mac-address {
            description
              "xxxx.xxxx.xxxx 48 bit mac address";
            type ios-types:cisco-mac-address-type;
          }
          leaf vlan {
            description
              "<1-4094> VLAN id of mac address table (1-4094)";
            type uint16 {
              range "1..4094";
            }
          }
          choice static-mac-choice {
            case drop-case {
              leaf drop {
                description
                  "drop frames";
                type empty;
              }
            }
            case interface-case {
              leaf-list interface {
                description
                  "Output interface exact long name";
                type string;
              }
            }
          }
        }
      }
    }
    container tacacs {
      description
        "TACACS server configuration command";
    }
    container tacacs-server {
      description
        "Modify TACACS query parameters";
    }
    container scada-gw {
      if-feature "ios-features:scada-gw";
      description
        "SCADA Gateway configuration commands";
    }
    container software {
      description
        "Configure software installation parameters";
      container auto-upgrade {
        description
          "Configure software auto upgrade parameters";
        leaf enable {
          description
            "Enable the auto upgrade installation feature";
          type empty;
        }
      }
    }
    container upgrade {
      description
        "Global upgrade configuration subcommands";
      container fpd {
        description
          "Configure field programmable devices upgrade options";
        leaf auto {
          description
            "Auto upgrade all FPD images";
          type empty;
        }
        leaf path {
          description
            "Set path to locate the FPD image package file for auto upgrade";
          type string;
        }
      }
    }
    container vtp {
      description
        "Configure global VTP state";
    }
    container xconnect;
    container fabric {
      description
        "Catalyst 6000 crossbar fabric configuration commands";
      container switching-mode {
        description
          "Switching mode settings";
        container allow {
          description
            "Allow settings";
          choice allow-choice {
            leaf bus-mode {
              description
                "Allow switching in bus mode for modules";
              type empty;
            }
            container truncated {
              description
                "Truncated switching mode";
              presence "true";
              leaf threshold {
                description
                  "Number of SFM-capable modules for truncated switching mode. Switch applies the threshold only when the mode is disallowed. Switch ignores the threshold when the truncated mode is allowed";
                type uint8 {
                  range "1..9";
                }
              }
            }
          }
        }
        container force {
          description
            "Force modules to different switching modes";
          leaf bus-mode {
            description
              "Switching mode of service modules will be forced to bus-mode by powercycling it.";
            type empty;
          }
        }
      }
    }
    container lacp {
      description
        "LACP interface subcommands";
      leaf system-priority {
        description
          "LACP priority for the System ";
        default "32768";
        type uint16;
      }
    }
    container port-channel {
      description
        "EtherChannel configuration";
    }
    container key {
      description
        "Key management";
    }
    container l2 {
      description
        "Layer 2 configuration";
      leaf router-id {
        description
          "Configure a layer 2 identifier";
        type inet:ipv4-address;
      }
    }
    container system {
      description
        "Set the system configuration";
    }
    container errdisable {
      description
        "Error disable";
      container detect {
        description
          "Error disable detection";
        container cause {
          description
            "Enable error disable detection for application";
          leaf all {
            description
              "Enable error detection on all cases";
            type empty;
          }
          leaf arp-inspection {
            description
              "Enable error detection for arp inspection";
            type empty;
          }
          leaf bpduguard {
            description
              "Enable error detection on bpdu-guard";
            type empty;
          }
          leaf dhcp-rate-limit {
            description
              "Enable error detection on dhcp-rate-limit";
            type empty;
          }
          leaf dtp-flap {
            description
              "Enable error detection on dtp-flapping";
            type empty;
          }
          leaf gbic-invalid {
            description
              "Enable error detection on gbic-invalid";
            type empty;
          }
          leaf inline-power {
            description
              "Enable error detection for inline-power";
            type empty;
          }
          leaf l2ptguard {
            description
              "Enable timer to recover from l2protocol-tunnel error disable state";
            type empty;
          }
          leaf link-flap {
            description
              "Enable error detection on linkstate-flapping";
            type empty;
          }
          leaf loopback {
            description
              "Enable error detection on loopback";
            type empty;
          }
          leaf mlacp-minlink {
            type empty;
          }
          leaf pagp-flap {
            description
              "Enable error detection on pagp-flapping";
            type empty;
          }
          leaf pppoe-ia-rate-limit {
            description
              "Enable error detection on PPPoE IA rate-limit";
            type empty;
          }
          container security-violation {
            description
              "Enable error detection on 802.1x-guard";
            container shutdown {
              description
                "Specify error disable shutdown mode for 802.1x-guard";
              leaf vlan {
                description
                  "Shutdown vlan on 802.1x-guard violation";
                type empty;
              }
            }
          }
          leaf sfp-config-mismatch {
            description
              "Enable error detection on SFP config mismatch";
            type empty;
          }
          leaf small-frame {
            description
              "Enable error detection on small_frame";
            type empty;
          }
        }
      }
      container flap-setting {
        description
          "Error disable flap detection setting";
        container cause {
          description
            "Set error disable flap parameters for application";
          container dtp-flap {
            description
              "Set the variables related to detection of dtp flaps";
            leaf max-flaps {
              description
                "maximum flaps allowed before setting to errdisable";
              type uint8 {
                range "1..100";
              }
            }
            leaf time {
              description
                "time period the flaps are counted";
              type uint8 {
                range "1..120";
              }
            }
          }
          container link-flap {
            description
              "Set the variables related to detection of link flaps";
            leaf max-flaps {
              description
                "maximum flaps allowed before setting to errdisable";
              type uint8 {
                range "1..100";
              }
            }
            leaf time {
              description
                "time period the flaps are counted";
              type uint8 {
                range "1..120";
              }
            }
          }
          container pagp-flap {
            description
              "Set the variables related to detection of pagp flaps";
            leaf max-flaps {
              description
                "maximum flaps allowed before setting to errdisable";
              type uint8 {
                range "1..100";
              }
            }
            leaf time {
              description
                "time period the flaps are counted";
              type uint8 {
                range "1..120";
              }
            }
          }
        }
      }
      container recovery {
        description
          "Error disable recovery";
        container cause {
          description
            "Enable error disable recovery for application";
          leaf all {
            description
              "Enable timer to recover from all error causes";
            type empty;
          }
          leaf arp-inspection {
            description
              "Enable timer to recover from arp inspection error disable state";
            type empty;
          }
          leaf bpduguard {
            description
              "Enable timer to recover from BPDU Guard error";
            type empty;
          }
          leaf channel-misconfig {
            description
              "(STP)  Enable timer to recover from channel misconfiguration error";
            type empty;
          }
          leaf dhcp-rate-limit {
            description
              "Enable timer to recover from dhcp-rate-limit error";
            type empty;
          }
          leaf dtp-flap {
            description
              "Enable timer to recover from dtp-flap error";
            type empty;
          }
          leaf gbic-invalid {
            description
              "Enable timer to recover from invalid GBIC error";
            type empty;
          }
          leaf inline-power {
            description
              "Enable timer to recover from inline-power error";
            type empty;
          }
          leaf l2ptguard {
            description
              "Enable timer to recover from l2protocol-tunnel error disable state";
            type empty;
          }
          leaf link-flap {
            description
              "Enable timer to recover from link-flap error";
            type empty;
          }
          leaf link-monitor-failure {
            type empty;
          }
          leaf loopback {
            description
              "Enable timer to recover from loopback error";
            type empty;
          }
          leaf mac-limit {
            description
              "Enable timer to recover from mac limit disable state";
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            description
              "Enable timer to recover from pagp-flap error";
            type empty;
          }
          leaf port-mode-failure {
            description
              "Enable timer to recover from port mode change failure";
            type empty;
          }
          leaf pppoe-ia-rate-limit {
            description
              "Enable timer to recover from PPPoE IA rate-limit error";
            type empty;
          }
          leaf psp {
            type empty;
          }
          leaf psecure-violation {
            description
              "Enable timer to recover from psecure violation error";
            type empty;
          }
          leaf security-violation {
            description
              "Enable timer to recover from 802.1x violation error";
            type empty;
          }
          leaf sfp-config-mismatch {
            description
              "Enable timer to recover from SFP config mismatch error";
            type empty;
          }
          leaf small-frame {
            description
              "Enable timer to recover from small frame error";
            type empty;
          }
          leaf storm-control {
            description
              "Enable timer to recover from storm-control error";
            type empty;
          }
          leaf udld {
            description
              "Enable timer to recover from udld error";
            type empty;
          }
          leaf unicast-flood {
            type empty;
          }
          leaf vmps {
            description
              "Enable timer to recover from vmps shutdown error";
            type empty;
          }
        }
        leaf interval {
          description
            "Error disable recovery timer value";
          type uint32 {
            range "30..86400";
          }
        }
      }
    }
    container nat {
      description
        "nat scale support";
      leaf scale {
        description
          "enable nat scale";
        type boolean;
      }
    }
    container identity {
      description
        "Identity Configuration Commands";
      list policy {
        description
          "Create an Identity policy";
        key "name";
        leaf name {
          description
            "Specify a policy name";
          type string;
        }
        container no {
          description
            "Negate a command or set its defaults";
          uses identity-policy-grouping;
        }
        uses identity-policy-grouping;
      }
      container profile {
        description
          "Create an Identity profile";
        leaf dot1x {
          description
            "Service type for 802.1x";
          type empty;
        }
        leaf default {
          description
            "Service type default";
          type empty;
        }
      }
    }
    grouping monitor-event-trace-enable-disable-grouping {
      leaf enable {
        status obsolete;
        type empty;
      }
      leaf disable {
        status obsolete;
        type empty;
      }
    }

    container monitor {
      description
        "Monitoring different system events";
      container event-trace {
        description
          "Tracing of system events";
        container timestamps {
          presence "true";
          description
            "Format of event trace timestamps";
          leaf uptime {
            description
              "Timestamp with system uptime";
            type empty;
          }
        }
        container atom {
          description
            "AToM traces";
          container error {
            description
              "This buffer stores only error logs by default.";
            uses monitor-event-trace-enable-disable-grouping;
            leaf-list include {
              description
                "Include a subset of debug types";
              type monitor-event-type;
            }
          }
          container event {
            description
              "This buffer stores all logs by default.";
            uses monitor-event-trace-enable-disable-grouping;
            leaf size {
              type uint32;
            }
            leaf-list exclude {
              description
                "Include a subset of debug types";
              type monitor-event-type;
            }
          }
          container major {
            description
              "This buffer stores only major logs and error logs by default.";
            uses monitor-event-trace-enable-disable-grouping;
            leaf-list include {
              description
                "Include a subset of debug types";
              type monitor-event-type;
            }
          }
        }
        leaf sequence-number {
          description
            "Display event trace entries with sequence number";
          type empty;
        }
      }
      list session {
        description
          "Configure a SPAN session";
        key "id";
        leaf id {
          type uint8 {
            range "1..66";
          }
        }
        container destination {
          description
            "SPAN destination interface or VLAN";
          list interface {
            description
              "SPAN destination interface";
            key "name";
            leaf name {
              description
                "Interface Name";
              type string;
            }
            leaf encapsulation {
              description
                "Set encapsulation for destination interface";
              type enumeration {
                enum dot1q;
                enum isl;
                enum replicate;
              }
            }
            leaf ingress {
              description
                "Enable ingress traffic forwarding";
              type empty;
            }
            leaf ingress-encap {
              when '../ingress';
              type enumeration {
                enum dot1q;
                enum isl;
                enum untagged;
              }
            }
            leaf vlan {
              description
                "Set default VLAN for untagged ingress traffic";
              when '../ingress';
              type uint16 {
                range "1..4094";
              }
            }
          }
          container remote {
            description
              "SPAN destination Remote";
            leaf vlan {
              description
                "Remote SPAN destination RSPAN VLAN";
              type uint16 {
                range "1006..4094";
              }
            }
          }
        }
        container filter {
          description
            "SPAN filter VLAN";
          container packet-type {
            leaf status {
              type enumeration {
                enum good;
                enum bad;
              }
            }
            leaf direction {
              type enumeration {
                enum rx;
                enum tx;
              }
            }
          }
          container ip {
            description
              "Specify IP Access control rules";
            container access-group {
              description
                "Specify access control group";
              leaf acl-name {
                description
                  "Access-list name";
                type string;
              }
            }
          }
        }
        container source {
          description
            "SPAN source interface, VLAN ";
          list interface {
            description
              "SPAN source interface";
            key "name";
            leaf name {
              description
                "Interface Name";
              type string;
            }
            leaf direction {
              type enumeration {
                enum both;
                enum rx;
                enum tx;
              }
            }
          }
          container vlan {
            description
              "SPAN source VLAN";
            leaf vlan {
              type uint16 {
                range "1..4094";
              }
            }
            leaf direction {
              type enumeration {
                enum both;
                enum rx;
                enum tx;
              }
            }
          }
          container remote {
            description
              "SPAN source Remote";
            leaf vlan {
              description
                "Remote SPAN source RSPAN VLAN <1-1001>|<1006-4094>";
              type uint16 {
                range "1..1001 | 1006..4094";
              }
            }
          }
        }
        container type {
          description
            "Type of monitor session";
          container erspan-source {
            description
              "Encapsulated RSPAN Source Session";
            presence "true";
            leaf description {
              description
                "Description for this session";
              type string;
            }
            container source {
              description
                "SPAN source interface, VLAN ";
              list interface {
                description
                  "SPAN source interface";
                key "name";
                leaf name {
                  description
                    "Interface Name";
                  type string;
                }
                leaf direction {
                  type enumeration {
                    enum both;
                    enum rx;
                    enum tx;
                  }
                }
              }
              list vlan {
                description
                  "SPAN source VLAN";
                key "vlan1";
                leaf vlan1 {
                  type uint16 {
                    range "1..4094";
                  }
                }
                leaf direction {
                  type enumeration {
                    enum both;
                    enum rx;
                    enum tx;
                  }
                }
              }
            }
            container filter {
              description
                "SPAN filter VLAN";
              list vlan {
                key "vlan1";
                leaf vlan1 {
                  type uint16 {
                    range "1..4094";
                  }
                }
              }
              container ip {
                description
                  "Specify IP Access control rules";
                container access-group {
                  description
                    "Specify access control group";
                  leaf acl-name {
                    description
                      "Access-list name";
                    type string;
                  }
                }
              }
              container ipv6 {
                description
                  "Specify IPv6 Access control rules";
                container access-group {
                  description
                    "Specify access control group";
                  leaf acl-name {
                    description
                      "Access-list name";
                    type string;
                  }
                }
              }
              container mac {
                description
                  "Specify MAC Access control rules";
                container access-group {
                  description
                    "Specify access control group";
                  leaf acl-name {
                    description
                      "Access-list name";
                    type string;
                  }
                }
              }
              leaf sgt {
                description
                  "SPAN source SGT";
                type uint16 {
                  range "0..65535";
                }
              }
            }
            leaf header-type {
              description
                "ERSPAN header-type for encapsulation. Default is type 2";
              type uint8 {
                range "2..3";
              }
            }
            leaf shutdown-source {
              description
                "Take the Service Instance out of Service";
              type boolean;
              default "true";
            }
            leaf shutdown {
              description
                "Take the Service Instance out of Service";
              status obsolete;
              type empty;
            }
            container destination {
              description
                "Specify Destination and their properties";
              presence "true";
              container ip {
                description
                  "IP Properties";
                leaf address {
                  description
                    "Enter IP Address";
                  type inet:ipv4-address;
                }
                leaf ttl {
                  description
                    "IP TTL";
                  type uint16 {
                    range "2..255";
                  }
                }
                leaf dscp {
                  description
                    "IP QOS DSCP";
                  type uint16 {
                    range "0..63";
                  }
                }
              }
              leaf erspan-id {
                description
                  "Enter ERSPAN Identifier";
                type uint16 {
                  range "1..1023";
                }
              }
              leaf mtu {
                description
                  "ERSpan MTU";
                type uint16 {
                  range "176..9000";
                }
              }
              leaf vrf {
                description
                  "Enter VRF number";
                type string;
              }
              container origin {
                description
                  "Origin IP Properties";
                container ip {
                  description
                    "origin IP Properties";
                  leaf address {
                    description
                      "Enter IP Address";
                    type inet:ipv4-address;
                  }
                }
              }
            }
          }
          container erspan-destination {
            description
              "Encapsulated RSPAN Destination Session";
            presence "true";
            leaf description {
              description
                "Properties for this session";
              type string;
            }
            container destination {
              description
                "SPAN destination interface, VLAN ";
              list interface {
                description
                  "SPAN destination interface";
                key "name";
                leaf name {
                  description
                    "Interface Name";
                  type string;
                }
              }
              leaf vlan {
                description
                  "Remote SPAN destination RSPAN VLAN <1-1001>|<1006-4094>";
                type uint16 {
                  range "1..1001 | 1006..4094";
                }
              }
            }
            leaf shutdown-destination {
              description
                "Shutdown this session";
              type boolean;
              default "true";
            }
            leaf shutdown {
              description
                "Shutdown this session";
              status obsolete;
              type empty;
            }
            container source {
              description
                "Specify Source and their properties";
              presence "true";
              container ip {
                description
                  "IP Address";
                leaf address {
                  description
                    "Enter IP Address";
                  type inet:ipv4-address;
                }
              }
              leaf erspan-id {
                description
                  "Enter ERSPAN Identifier";
                type uint16 {
                  range "1..1023";
                }
              }
            }
          }
          container local {
            description
              "Local SPAN Session";
            presence "true";
            leaf description {
              description
                "Description for this session";
              type string;
            }
            container source {
              description
                "SPAN source Interface/VLAN/CPU";
              list interface {
                description
                  "SPAN source interface";
                key "name";
                leaf name {
                  description
                    "Interface Name";
                  type string;
                }
                leaf direction {
                  type enumeration {
                    enum both;
                    enum rx;
                    enum tx;
                  }
                }
              }
              list vlan {
                description
                  "SPAN source VLAN";
                key "vlan1";
                leaf vlan1 {
                  type uint16 {
                    range "1..4094";
                  }
                }
                leaf direction {
                  type enumeration {
                    enum both;
                    enum rx;
                    enum tx;
                  }
                }
              }
            }
            container destination {
              description
                "SPAN destination interface or VLAN";
              list interface {
                description
                  "SPAN destination interface";
                key "name";
                leaf name {
                  description
                    "Interface Name";
                  type string;
                }
              }
            }
            container filter {
              description
                "SPAN filter VLAN";
              list vlan {
                key "vlan1";
                leaf vlan1 {
                  type uint16 {
                    range "1..4094";
                  }
                }
              }
            }
            leaf shutdown {
              description
                "Take the Service Instance out of Service";
              type empty;
            }
          }
        }
      }
    }
    list md-list {
      description
        "Provide md list";
      key "ipaddr mask";
      leaf ipaddr {
        type inet:ipv4-address;
      }
      leaf mask {
        type inet:ipv4-address;
      }
    }
    grouping tftp-alias-acl-number-grouping {
      leaf alias {
        description
          "file alias";
        type string;
      }
      leaf acl-number {
        description
          "IP access list of requesting hosts";
        type ios-types:default-access-list-standard-id-type;
      }
    }

    container tftp-server-config {
      description
        "Provide TFTP service for netload requests";
      list flash {
        description
          "Allow URL file TFTP load requests";
        key "flash-name";
        leaf flash-name {
          type string;
        }
        uses tftp-alias-acl-number-grouping;
      }
      container rom {
        description
          "Allow ROM image TFTP load requests";
        list alias {
          description
            "file alias";
          key "alias-name";
          leaf alias-name {
            type string;
          }
          leaf acl-number {
            type ios-types:default-access-list-standard-id-type;
          }
        }
      }
      list bootflash {
        description
          "Allow URL file TFTP load requests";
        key "bootflash-name";
        leaf bootflash-name {
          type string;
        }
        uses tftp-alias-acl-number-grouping;
      }
      list null {
        description
          "Allow URL file TFTP load requests";
        key "null-name";
        leaf null-name {
          type string;
        }
        uses tftp-alias-acl-number-grouping;
      }
      list system {
        description
          "Allow URL file TFTP load requests";
        key "system-name";
        leaf system-name {
          type string;
        }
        uses tftp-alias-acl-number-grouping;
      }
      list tmpsys {
        description
          "Allow URL file TFTP load requests";
        key "tmpsys-name";
        leaf tmpsys-name {
          type string;
        }
        uses tftp-alias-acl-number-grouping;
      }
      list nvram {
        description
          "Allow URL file TFTP load requests";
        key "nvram-name";
        leaf nvram-name {
          type string;
        }
        uses tftp-alias-acl-number-grouping;
      }
    }
    list tftp-server {
      status deprecated;
      description
        "Provide TFTP service for netload requests";
      key "name";
      leaf name {
        type string;
      }
      uses tftp-alias-acl-number-grouping;
    }
    container radius-server {
      description
        "Modify RADIUS query parameters";
    }
    container radius {
      description
        "RADIUS server configuration command";
    }
    container ldap {
      description
        "LDAP server configuration command";
    }
    container endpoint-tracker {
      description
        "Endpoint Tracker";
    }
    container zone {
      description
        "FW with zoning";
    }
    container zone-pair {
      description
        "Zone pair command";
    }
    list alarm-contact {
      key "name";
      leaf name {
        type uint8 {
          range "1..4";
        }
      }
      leaf description {
        type string {
          length "1..80";
        }
      }
      leaf severity {
        type enumeration {
          enum critical;
          enum major;
          enum minor;
        }
      }
      leaf trigger {
        type enumeration {
          enum open;
          enum closed;
        }
      }
    }
    container ethernet {
      description
        "Ethernet configuration";
    }
    container bridge-domain {
      description
        "Bridge-domain global configuration commands";
    }
    container crypto {
      description
        "Encryption module";
    }
    container cts {
      description
        "Configures Cisco TrustSec";
    }
    container bfd-template {
      description
        "BFD-template";
    }
    container pfr {
      description
        "Performance Routing configuration submodes";
    }
    list pfr-map {
      description
        "Create pfr-map and enter pfr-map command mode";
      key "pfr-tg";
      leaf pfr-tg {
        description
          "pfr-map tag";
        type string;
      }
    }
    container facility-alarm {
      description
        "Configure facility alarms";
      leaf severity {
        type enumeration {
          enum critical;
        }
      }
      leaf exceed-action {
        description
          "Behavior on critical threshold exceed";
        type enumeration {
          enum shutdown;
        }
      }
    }
    container setup {
      description
        "Configure setup options";
    }
    container tod-clock {
      description
        "Tod clock config commands";
      container input-source {
        description
          "Synchronization Input Source";
        status deprecated;
        leaf priority {
          status deprecated;
          type uint8 {
            range "1..250";
          }
        }
        container ptp {
          status deprecated;
          leaf domain {
            type uint8;
          }
        }
      }
    }
    container network-clock {
      description
        "Network clock config commands";
      container synchronization {
        description
          "Network clock synchronization selection process";
        status deprecated;
        leaf automatic {
          description
            "ITU-T G.781/Telcordia standard based";
          status deprecated;
          type empty;
        }
        leaf mode {
          description
            "synchronization networking mode";
          status deprecated;
          type enumeration {
            enum QL-enabled;
          }
        }
        leaf-list participate {
          description
            "network clock participate, input line card slot number";
          status deprecated;
          type string;
        }
      }
      leaf revertive {
        description
          "Network clock revertive mode";
        status deprecated;
        type empty;
      }
      container wait-to-restore {
        description
          "Wait-to-Restore timer";
        status deprecated;
        leaf time {
          description
            "Wait-to-Restore time";
          status deprecated;
          type uint32 {
            range "0..86400";
          }
          default "300";
        }
        leaf global {
          description
            "Global";
          status obsolete;
          type empty;
        }
      }
      list input-source-list {
        description
          "Synchronization Input Source";
        status deprecated;
        key "priority";
        leaf priority {
          status deprecated;
          type uint8 {
            range "1..250";
          }
        }
        container interface {
          status deprecated;
          uses ios-ifc:interface-grouping;
        }
        container ptp {
          status deprecated;
          leaf domain {
            type uint8;
          }
        }
        container controller {
          description
            "T1/E1 controller";
          status deprecated;
          leaf name {
            status deprecated;
            type enumeration {
              enum T1;
              enum E1;
              enum t1;
              enum e1;
            }
          }
          leaf number {
            status deprecated;
            type string;
          }
        }
      }
      container input-source {
        description
          "Synchronization Input Source";
        status deprecated;
        leaf priority {
          status deprecated;
          type uint8 {
            range "1..250";
          }
        }
        container interface {
          status deprecated;
          uses ios-ifc:interface-grouping;
        }
        container ptp {
          status deprecated;
          leaf domain {
            status deprecated;
            type uint8;
          }
        }
      }
    }
    container l2vpn {
      description
        "Layer2 VPN commands";
    }
    container l2vpn-config;
    container l3vpn {
      description
        "l3vpn encapsulation ip commands";
    }
    container mpls {
      description
        "Configure MPLS parameters";
    }
    container router;
    container service-chain {
      description
        "Service Chain mode";
    }
    container performance {
      description
        "Global Performance monitor configuration";
    }
    container otv {
      description
        "Configure OTV information";
    }
    container remote-management {
      description
        "Enable the remote managment";
      leaf dmi {
        description
          "data-model-interface";
        type empty;
      }
      leaf restful-api {
        description
          "RESTful API";
        type boolean;
      }
    }
    list virtual-service {
      description
        "Configure virtual service";
      key "name";
      leaf name {
        type string {
          length "1..63";
        }
      }
    }
    container vxlan {
      description
        "VXLAN configuration commands";
    }
    container snmp {
      description
        "Modify SNMP interface parameters";
    }
    container snmp-server {
      description
        "Modify SNMP engine parameters";
    }
    container segment-routing {
      description
        "Enter Segment Routing Mode";
    }
    container performance-measurement {
      description
        "Enter Performance Measurement Mode";
      presence "true";
    }
    uses config-license-grouping;
    leaf disable-eadi {
      type empty;
    }
    container memory-size {
      if-feature "ios-features:mem-size";
      description
        "Adjust memory size by percentage";
      leaf iomem {
        description
          "I/O memory";
        type uint8 {
          range "5..25";
        }
      }
    }
    container transceiver {
      if-feature "ios-features:transceiver";
      description
        "Select from transceiver configuration commands";
      container type {
        description
          "type keyword";
        container all {
          container monitoring {
            description
              "Enable/disable monitoring";
            presence "true";
            leaf interval {
              description
                "Set interval for monitoring";
              type uint16 {
                range "300..3600";
              }
            }
          }
        }
      }
    }
    container service-insertion {
      description
        "Service Insertion mode";
    }
    container udld {
      description
        "Configure global UDLD setting";
    }
    container qos {
      description
        "Global QoS configuration commands";
    }
    list time-range {
      description
        "Define time range entries";
      key "word";
      leaf word {
        type string;
      }
      container absolute {
        description
          "absolute time and date";
        container start {
          description
            "starting time and date";
          leaf start-time {
            description
              "Starting time";
            type string;
          }
          leaf day-of-month {
            description
              "<1-31>  Day of the month";
            type uint8;
          }
          leaf month {
            description
              "Month of the year [eg: Jan for January, Jun for June]";
            type string;
          }
          leaf year {
            description
              "Year";
            type uint16 {
              range "1993..2035";
            }
          }
        }
      }
    }
    container device-tracking {
      description
        "Device tracking configuration commands";
    }
    container fhrp {
      description
        "Configure First Hop Redundancy Protocols";
      container version {
        description
          "Configure which FHRP version is allowed to run";
        leaf vrrp {
          description
            "Configure Virtual Router Redundancy Protocol";
          type enumeration {
            enum v2;
            enum v3;
          }
          default "v2";
        }
      }
      leaf bfd {
        description
          "Allows VRRPv3 BFD configuration";
        default "false";
        type boolean;
      }
      leaf sso {
        if-feature "ios-features:fhrp-sso";
        description
          "Enable VRRPv3 Stateful switchover";
        default "false";
        type boolean;
      }
    }
    container standby {
      description
        "Configure Hot Standby Redundancy Protocol";
      container bfd {
        description
          "Configure HSRP BFD";
        leaf all-interfaces {
          description
            "Enable HSRP BFD on all interfaces";
          default "true";
          type boolean;
        }
      }
      container redirects-config {
        description
          "Configure sending ICMP Redirects with HSRP VIP as gateway IP";
        choice redirect_choice {
          default "redirects";
          leaf redirects {
            type boolean;
            default "true";
          }
          container redirect-enable-disable {
            leaf redirects {
              type enumeration {
                enum enable;
                enum disable;
              }
            }
          }
        }
      }
      leaf redirects {
        status deprecated;
        description
          "Configure sending ICMP Redirects with HSRP VIP as gateway IP";
        default "true";
        type boolean;
      }
      leaf sso {
        description
          "Enable Stateful switchover";
        default "true";
        type boolean;
      }
    }
    container metadata {
      description
        "Metadata Application";
      container flow {
        description
          "Enable Metadata Flow Handling";
        presence "true";
        leaf transmit {
          description
            "Enable Metadata Flow Transmit ";
          type empty;
        }
      }
    }
    container profile {
      description
        "MSP Profile";
      leaf flow {
        description
          "MSP Profile Flow";
        type empty;
      }
    }
    container alias {
      description
        "Create command alias";
      list exec {
        description
          "Exec mode";
        key "alias-name";
        leaf alias-name {
          type string;
        }
        leaf new-alias-name {
          type string;
        }
      }
      list configure {
        description
          "Global configuration mode";
        key "alias-name";
        leaf alias-name {
          type string;
        }
        leaf new-alias-name {
          type string;
        }
      }
    }
    uses config-line-grouping;
    container ntp {
      description
        "Configure NTP";
    }
    container wsma {
      description
        "Configure Web Services Management Agents";
    }
    container event {
      description
        "Event related configuration commands";
    }
    container template {
      description
        "template";
    }
    grouping service-timestamp-show-timezone-and-year {
      leaf show-timezone {
        description
          "Add time zone information to timestamp";
        status obsolete;
        type empty;
      }
      leaf year {
        description
          "Include year in timestamp";
        status obsolete;
        type empty;
      }
    }

    grouping service-timestamp-msec-and-year {
      leaf msec {
        description
          "Include milliseconds in timestamp";
        status obsolete;
        type empty;
      }
      leaf year {
        description
          "Include year in timestamp";
        status obsolete;
        type empty;
      }
    }

    grouping service-timestamp-msec-and-show-timezone {
      leaf msec {
        description
          "Include milliseconds in timestamp";
        status obsolete;
        type empty;
      }
      leaf show-timezone {
        description
          "Add time zone information to timestamp";
        status obsolete;
        type empty;
      }
    }

    grouping service-timestamp-local-time-and-year {
      leaf localtime {
        description
          "Use local time zone for timestamps";
        status obsolete;
        type empty;
      }
      leaf year {
        description
          "Include year in timestamp";
        status obsolete;
        type empty;
      }
    }

    grouping service-timestamp-local-time-and-show-timezone {
      leaf localtime {
        description
          "Use local time zone for timestamps";
        status obsolete;
        type empty;
      }
      leaf show-timezone {
        description
          "Add time zone information to timestamp";
        status obsolete;
        type empty;
      }
    }

    grouping service-timestamp-local-time-and-msec {
      leaf localtime {
        description
          "Use local time zone for timestamps";
        status obsolete;
        type empty;
      }
      leaf msec {
        description
          "Include milliseconds in timestamp";
        status obsolete;
        type empty;
      }
    }

    grouping process-rising-grouping {
      container rising {
        description
          "rising threshold";
        list cpu-range {
          key "cpu-range";
          leaf cpu-range {
            type uint8 {
              range "1..100";
            }
          }
          container interval {
            description
              "observation interval";
            list cpu-range {
              key "cpu-range";
              leaf cpu-range {
                type uint32 {
                  range "5..86400";
                }
              }
              container falling {
                description
                  "falling threshold";
                list cpu-range {
                  key "cpu-range";
                  leaf cpu-range {
                    type uint8 {
                      range "1..100";
                    }
                  }
                  leaf interval {
                    description
                      "observation interval";
                    type uint32 {
                      range "5..86400";
                    }
                  }
                }
              }
            }
          }
        }
      }
    }

    container process {
      description
        "Configure process";
      container cpu {
        description
          "Configure cpu parameters";
        container threshold {
          description
            "cpu threshold parameters";
          container type {
            description
              "cpu threshold type";
            container interrupt {
              description
                "interrupt level utilization";
              uses process-rising-grouping;
            }
            container process {
              description
                "process level utilization";
              uses process-rising-grouping;
            }
            container total {
              description
                "total cpu utilization";
              uses process-rising-grouping;
            }
          }
        }
      }
    }
    container exception {
      description
        "help";
      container crashinfo {
        description
          "Crash info collection";
        presence "true";
        leaf buffersize {
          description
            "buffer size in Kbytes 256K or less (default is 32K)";
          type uint16 {
            range "32..256";
          }
        }
      }
    }
    container iox {
      description
        "Configure IOx services";
      presence "true";
      leaf switch {
        description
          "Configure switch number for IOx media";
        type uint8 {
          range "1..16";
        }
      }
    }
    grouping transport-map-type-persistent-webui-list {
      leaf secure-server {
        description
          "Enable HTTP secure server";
        type empty;
      }
      leaf server {
        description
          "Enable HTTP server";
        type empty;
      }
    }

    container transport-map {
      description
        "Configure transport map";
      container type {
        description
          "Specify transport map type";
        container persistent {
          description
            "Persistent transport types";
          list persistent-type-name {
            key "tm-name";
            leaf tm-name {
              type string;
            }
            leaf persistent-type {
              type enumeration {
                enum webui {
                  description
                    "Persistent webui transport type";
                }
              }
            }
            uses transport-map-type-persistent-webui-list;
          }
        }
      }
    }
    container redun-management {
      description
        "Redundancy Management Interface configuration";
    }
    container management {
      description
        "Management Gateway-failover configuration";
    }
  }
}
