module Cisco-IOS-XE-switch-dp-punt-inject-oper {
  yang-version 1;
  namespace "http://cisco.com/ns/yang/Cisco-IOS-XE-switch-dp-punt-inject-oper";
  prefix switch-dp-punt-inject-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for switching device datapath punt and inject operational data.
     Copyright (c) 2019-2020 by Cisco Systems, Inc.
     All rights reserved.";

  revision 2020-07-01 {
    description
      "Initial revision";
    reference
      "1.0.0";
    cisco-semver:module-version "1.0.0";
  }

  grouping brief-punt-cpuq-statistics {
    description
      "Brief punt CPU queue statistics";
    leaf cpuq-id {
      type uint8;
      description
        "CPU queue identification";
    }
    leaf rx-recv-prev {
      type uint64;
      description
        "Previous count of packets received from ASIC";
    }
    leaf rx-recv-cur {
      type uint64;
      description
        "Current count of packets received from ASIC";
    }
    leaf rx-recv-delta {
      type uint64;
      description
        "Delta of counts of packets received from ASIC";
    }
    leaf rx-dropped-prev {
      type uint64;
      description
        "Previous count of dropped RX packets";
    }
    leaf rx-dropped-cur {
      type uint64;
      description
        "Current count of dropped RX packets";
    }
    leaf rx-dropped-delta {
      type uint64;
      description
        "Delta of counts of dropped RX packets";
    }
    leaf cpu-punt-queue-name {
      type string;
      description
        "Name of CPU punt queue";
    }
  }

  container switch-dp-punt-inject-oper-data {
    config false;
    description
      "Switching device datapath punt and inject operational data";
    list location {
      key "fru slot bay chassis node";
      description
        "A list of data provider locations";
      uses common-types-ios-xe:extended-location;
      list punt-inject-cpuq-brief-stats {
        key "cpuq-id";
        description
          "This list contains brief punt CPU queue statistics";
        uses switch-dp-punt-inject-oper:brief-punt-cpuq-statistics;
      }
    }
  }
}
