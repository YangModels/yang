module ietf-restconf-monitoring-ann {
  namespace "urn:dummy";
  prefix dummy;

  import tailf-common {
    prefix tailf;
  }
  import ietf-restconf-monitoring {
    prefix rcm;
  }

  organization "Tail-f Systems";

  description
    "Annotation module for ietf-restconf-monitoring.

     Adds tailf:info statements for a better CLI / WebUI experience,
     and adds the callpoints necessary for using this module with
     ConfD.

     Copyright 2019 Cisco Systems, Inc.
     All rights reserved.
     Permission is hereby granted to redistribute this file without
     modification.";

  tailf:annotate "/rcm:restconf-state" {
    tailf:callpoint "rcagent" {
      tailf:internal;
    }
    tailf:info "Statistics about RESTCONF";

    tailf:annotate "rcm:capabilities" {
      tailf:info "Capabilities supported by the RESTCONF server";

      tailf:annotate "rcm:capability" {
        tailf:info "Capabilities supported by the RESTCONF server";
        tailf:cli-list-syntax;
      }
    }
    tailf:annotate "rcm:streams" {
      tailf:info "Notification event streams supported by the server";
      tailf:cli-suppress-show-path;
    }
  }
}
