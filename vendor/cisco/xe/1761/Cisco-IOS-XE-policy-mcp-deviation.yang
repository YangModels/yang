module Cisco-IOS-XE-policy-mcp-deviation {
  namespace "http://cisco.com/ns/yang/Cisco-IOS-XE-policy-mcp-deviation";
  prefix ios-policy-mcp-deviate;

  import Cisco-IOS-XE-native {
    prefix ios;
  }
  import Cisco-IOS-XE-policy {
    prefix ios-policy;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Deviation Policy Map Yang model for ASR platform.
     Copyright (c) 2019-2021 by Cisco Systems, Inc.
     All rights reserved.";

  revision 2021-07-01 {
    description
      "- Added priority range value";
  }
  revision 2020-07-01 {
    description
      "Initial Revision";
  }

  deviation "/ios:native/ios:policy/ios-policy:policy-map/ios-policy:class/ios-policy:action-list/ios-policy:action-param/ios-policy:police-case/ios-policy:police-choice/ios-policy:police-policy-map-case/ios-policy:police-policy-map/ios-policy:police/ios-policy:cir-bc-choice/ios-policy:cir-bc/ios-policy:cir" {
    deviate replace {
      type uint64 {
        range "8000..67104768000";
      }
    }
  }

  deviation "/ios:native/ios:policy/ios-policy:policy-map/ios-policy:class/ios-policy:action-list/ios-policy:action-param/ios-policy:priority-case/ios-policy:priority/ios-policy:priority-type/ios-policy:kilo-bits/ios-policy:kilo-bits" {
    deviate replace {
      type uint32 {
        range "1..10000000";
      }
    }
  }
}
