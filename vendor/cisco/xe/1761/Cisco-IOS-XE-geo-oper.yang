module Cisco-IOS-XE-geo-oper {
  yang-version 1;
  namespace "http://cisco.com/ns/yang/Cisco-IOS-XE-geo-oper";
  prefix geo-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring the Geo-Location database feature.
     Copyright (c) 2020 by Cisco Systems, Inc.
     All rights reserved.";

  revision 2021-03-01 {
    description
      "Initial revision";
    reference
      "1.0.0";
    cisco-semver:module-version "1.0.0";
  }

  grouping geo-db-status {
    description
      "Geo-location database status";
    leaf geo-enabled {
      type boolean;
      description
        "Geo-location database feature enablement status";
    }
    leaf db-file-name {
      when "(../geo-enabled = 'true')";
      type string;
      description
        "Geo-location database file name";
    }
    leaf db-version {
      when "(../geo-enabled = 'true')";
      type string;
      description
        "Geo-location database version";
    }
  }

  container geo-oper-data {
    config false;
    description
      "Geo-Location database operational data";
    container geo-db-status {
      presence "geo-db-status";
      description
        "Geo-location database status";
      uses geo-ios-xe-oper:geo-db-status;
    }
  }
}
