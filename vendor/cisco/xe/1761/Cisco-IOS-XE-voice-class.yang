submodule Cisco-IOS-XE-voice-class {
  belongs-to Cisco-IOS-XE-voice {
    prefix ios-voice;
  }

  import cisco-semver {
    prefix cisco-semver;
  }
  import Cisco-IOS-XE-native {
    prefix ios;
  }
  import Cisco-IOS-XE-interface-common {
    prefix ios-ifc;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Class Tenant Yang model.
     Copyright (c) 2020 by Cisco Systems, Inc.
     All rights reserved.";

  revision 2021-03-01 {
    description
      "- Added voice class server-group and sip-options-keepalive";
    cisco-semver:module-version "2.0.0";
  }
  revision 2020-07-01 {
    description
      "- Added voice class tenant";
    cisco-semver:module-version "1.0.0";
  }

  grouping config-source-interface-grouping {
    container source-interface {
      description
        "Specify interface for source address of SIP packets";
      container source-interface-std {
        when '/ios:native/sip-ua';
        uses ios-ifc:interface-grouping;
      }
      leaf source-interface-string {
        when 'not (/ios:native/sip-ua)';
        type string;
      }
    }
  }

  grouping config-session-transport-grouping {
    container transport {
      description
        "SIP session transport config";
      choice transport-choice {
        leaf udp {
          description
            "Transport Layer Protocol - UDP";
          type empty;
        }
        container tcp {
          description
            "Transport Layer Protocol - TCP";
          presence "true";
          leaf tls {
            description
              "Transport Layer Protocol - TLS over TCP";
            type empty;
          }
        }
      }
    }
  }

  grouping config-sip-bind-grouping {
    container bind {
      description
        "SIP bind command";
      container control {
        description
          "bind only SIP control packets";
        uses config-source-interface-grouping;
      }
      container media {
        description
          "bind only SIP media packets";
        uses config-source-interface-grouping;
      }
    }
  }

  grouping pass-thru-grouping {
    container pass-thru {
      description
        "SIP pass-through global config";
      container content {
        description
          "SIP content pass-through config";
        container sdp {
          description
            "Pass-through sdp content";
          presence "true";
          leaf mode {
            description
              "Set Pass-through sdp mode";
            type enumeration {
              enum non-rtp {
                description
                  "Set Pass-through sdp mode to non-rtp";
              }
            }
          }
        }
        leaf unsupp {
          description
            "Pass-through all unsupported content";
          type empty;
        }
      }
      container headers {
        description
          "SIP header pass-through config";
        choice headers-choice {
          case unsupp-case {
            leaf unsupp {
              description
                "Pass-through all unsupported headers";
              type empty;
            }
          }
        }
      }
      container subscribe-notify-events {
        description
          "Subscribe/Notify event passthrough config";
        choice subscribe-notify-events-choice {
          case sip-event-list-all-case {
            leaf all {
              description
                "Pass-through all subscribe/notify events";
              type empty;
            }
          }
        }
      }
    }
  }

  grouping config-voice-class-tenant-grouping {
    list tenant {
      description
        "Tenant group";
      max-elements 10000;
      key "id";
      leaf id {
        description
          "Voice class tenant tag";
        type uint16 {
          range "1..10000";
        }
      }
      container connection-reuse {
        description
          "Use listener port for sending requests over UDP";
        presence "true";
        leaf via-port {
          description
            "Send responses to port present in Via header";
          type empty;
        }
      }
      container early-offer {
        description
          "Configure sending Early-Offer";
        must "/ios:native/voice/service[type='voip']/allow-connections/sip/to/sip" {
          error-message "Config allow-connections sip to sip";
        }
        container forced {
          description
            "Forcefully Send Early-Offer";
          presence "true";
          container re-negotiate {
            description
              "Enables end-to-end re-negotiation for variable quality codecs";
            presence "true";
            leaf always {
              description
                "Enables end-to-end re-negotiation for all codecs";
              type empty;
            }
          }
        }
      }
      leaf header-passing {
        description
          "SIP Headers need to be passed to Applications";
        type empty;
      }
      leaf error-passthru {
        description
          "SIP error response pass-thru functionality";
        type empty;
      }
      uses pass-thru-grouping;
      uses config-sip-bind-grouping;
      container session {
        description
          "SIP Voice Protocol session config";
        uses config-session-transport-grouping;
      }
      leaf sip-server {
        description
          "Configure a SIP Server Interface";
        type string {
          pattern '(ipv4:[0-255]+\.[0-255]+\.[0-255]+\.[0-255]+(:[0-65535]+)?)|(ipv6:\[([0-9A-Fa-f.:])+\](:[0-9]+)?)|(dns:.*)' {
            error-message
              "Ill-formed SIP Server address. Valid formats are:
                   ipv4:[0-255].[0-255].[0-255].[0-255],
                   ipv4:[0-255].[0-255].[0-255].[0-255]:[0-65535],
                   ipv6:[X:X:X:X::X],
                   ipv6:[X:X:X:X::X]:[0-65535],
                   dns:host.domain";
          }
        }
      }
    }
  }

  grouping config-voice-class-server-group-grouping {
    list server-group {
      description
        "IP Server Group";
      must '(count(ipv4-address/ipv4/address) + count(ipv4-address/ipv4-addr-port/ipv4/address) + count(ipv6-address/ipv6/address) + count(ipv6-address/ipv6-addr-port/ipv6/address)) < 6' {
        error-message "Maximum 5 addresses allowed";
      }
      max-elements 10000;
      key "id";
      leaf id {
        description
          "Voice class server group tag";
        type uint16 {
          range "1..10000";
        }
      }
      leaf description {
        description
          "Description of a dialpeer group";
        type string {
          length "1..80";
        }
      }
      leaf shutdown {
        description
          "Put server group to inactive state";
        type boolean;
        default "false";
      }
      container hunt-scheme {
        description
          "List of IP targets hunt method";
        leaf round-robin {
          description
            "Servers are sorted in round robin";
          type empty;
        }
      }
      container ipv4-address {
        list ipv4 {
          key "address";
          leaf address {
            description
              "set the Call Manager configuration download TFTP server address/name";
            type inet:ipv4-address;
          }
          leaf preference {
            description
              "Preference order of this server in a group";
            type uint8 {
              range "0..5";
            }
          }
        }
        container ipv4-addr-port {
          list ipv4 {
            key "address port";
            leaf address {
              description
                "set the Call Manager configuration download TFTP server address/name";
              type inet:ipv4-address;
            }
            leaf port {
              description
                "IP Address Port";
              type uint16 {
                range "1..65535";
              }
            }
            leaf preference {
              description
                "Preference order of this server in a group";
              type uint8 {
                range "0..5";
              }
            }
          }
        }
      }
      container ipv6-address {
        list ipv6 {
          key "address";
          leaf address {
            description
              "set the Call Manager configuration download TFTP server address/name";
            type inet:ipv6-address;
          }
          leaf preference {
            description
              "Preference order of this server in a group";
            type uint8 {
              range "0..5";
            }
          }
        }
        container ipv6-addr-port {
          list ipv6 {
            key "address port";
            leaf address {
              description
                "set the Call Manager configuration download TFTP server address/name";
              type inet:ipv6-address;
            }
            leaf port {
              description
                "IP Address Port";
              type uint16 {
                range "1..65535";
              }
            }
            leaf preference {
              description
                "Preference order of this server in a group";
              type uint8 {
                range "0..5";
              }
            }
          }
        }
      }
    }
  }

  grouping config-voice-class-sip-options-keepalive-grouping {
    list sip-options-keepalive {
      description
        "SIP Options Keepalive Profile setup";
      max-elements 10000;
      key "id";
      leaf id {
        description
          "Voice class sip-options-keepalive tag";
        type uint16 {
          range "1..10000";
        }
      }
      leaf description {
        description
          "Description of a options-keepalive profile";
        type string {
          length "1..80";
        }
      }
      leaf shutdown {
        description
          "Put sip-options-keepalive to inactive state";
        type boolean;
        default "false";
      }
      leaf down-interval {
        description
          "OPTIONS keepalive timer interval for DOWN endpoint";
        type uint16 {
          range "5..1200";
        }
        default "30";
      }
      leaf up-interval {
        description
          "OPTIONS keepalive timer interval for UP endpoint";
        type uint16 {
          range "5..1200";
        }
        default "60";
      }
      leaf retry {
        description
          "Retry count for OPTIONS keepalive retransmission";
        type uint8 {
          range "1..10";
        }
        default "5";
      }
      uses config-session-transport-grouping;
    }
  }
}
