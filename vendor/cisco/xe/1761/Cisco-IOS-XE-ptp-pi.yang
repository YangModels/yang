module Cisco-IOS-XE-ptp-pi {
  namespace "http://cisco.com/ns/yang/Cisco-IOS-XE-ptp-pi";
  prefix ios-ptp-pi;

  import cisco-semver {
    prefix cisco-semver;
  }
  import ietf-inet-types {
    prefix inet;
  }
  import Cisco-IOS-XE-native {
    prefix ios;
  }
  import Cisco-IOS-XE-interface-common {
    prefix ios-ifc;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Precision Time Protocol (PTP) Yang Model.
     Copyright (c) 2019 by Cisco Systems, Inc.
     All rights reserved.";

  revision 2019-11-01 {
    description
      "- Fixing some of the missed models";
    cisco-semver:module-version "1.1.0";
  }
  revision 2019-07-01 {
    description
      "- Establish semantic version baseline
       - Add fix for ptp clock deletion";
    cisco-semver:module-version "1.0.0";
  }
  revision 2019-01-23 {
    description
      "Initial revision";
  }

  grouping config-clock-src-dest-grouping {
    container src-dest-grp {
      leaf interface {
        description
          "Interface";
        type string;
      }
      leaf bridge-domain {
        description
          "Bridge Domain";
        type uint32 {
          range "1..4294967295";
        }
      }
      leaf priority {
        description
          "Local priority";
        type uint8 {
          range "1..2";
        }
      }
      leaf delay-asymmetry {
        description
          "Delay asymmetry";
        type int32 {
          range "-500000000..500000000";
        }
        default "0";
      }
      leaf units {
        type enumeration {
          enum nanoseconds;
          enum picoseconds;
        }
      }
    }
  }

  grouping config-address-grouping {
    container address {
      choice ipormac {
        container ip {
          leaf ipaddress {
            description
              "IPv4 Address";
            type inet:ipv4-address;
          }
          uses config-clock-src-dest-grouping;
        }
        container mac {
          leaf macaddress {
            description
              "Mac Address";
            type ios-types:cisco-mac-address-type;
          }
          uses config-clock-src-dest-grouping;
        }
      }
    }
  }

  grouping config-ptp-grouping {
    container clock {
      description
        "Configure PTP clock";
      container ordinary {
        description
          "Configure PTP Ordinary clock";
        list domain {
          description
            "PTP domain";
          key "domain-num";
          leaf domain-num {
            type int8 {
              range "0..127";
            }
          }
          leaf hybrid {
            description
              "PTP hybrid mode";
            type empty;
          }
          leaf profile {
            description
              "Change PTP clock profile";
            type enumeration {
              enum g8265.1;
              enum g8275.1;
              enum g8275.2;
            }
          }
          uses config-ptp-clock-port-grouping;
        }
      }
      container boundary {
        description
          "Configure PTP Boundary clock";
        list domain {
          description
            "PTP domain";
          key "domain-num";
          leaf domain-num {
            type int8 {
              range "0..127";
            }
          }
          leaf hybrid {
            description
              "PTP hybrid mode";
            type empty;
          }
          leaf profile {
            description
              "Change PTP clock profile";
            type enumeration {
              enum g8265.1;
              enum g8275.1;
              enum g8275.2;
            }
          }
          uses config-ptp-clock-port-grouping;
        }
      }
      container e2e-transparent {
        description
          "Configure PTP transparent clock";
        leaf domain {
          description
            "PTP domain";
          type int8 {
            range "0..127";
          }
        }
      }
    }
    grouping config-ptp-clock-port-grouping {
      list clock-port {
        description
          "Configure clock port";
        key "name";
        leaf name {
          description
            "Port name";
          type string;
        }
        leaf slave {
          description
            "Configure as Slave";
          type empty;
        }
        container inter-op-port {
          description
            "Configure as Inter-op Multi-Profile";
          list domain {
            description
              "domain";
            key "value";
            leaf value {
              description
                "PTP domain";
              type uint8 {
                range "0..127";
              }
            }
            container inter-op-profile {
              description
                "Inter-op profile";
              choice interop-profile-choice {
                leaf p1588 {
                  description
                    "Telecom Default Profile ITU-T 1588";
                  type empty;
                }
                container g8275.2 {
                  description
                    "Telecom Profile ITU-T G.8275.2";
                  presence "true";
                  leaf local-priority {
                    type uint8 {
                      range "1..255";
                    }
                  }
                }
              }
            }
          }
        }
        leaf master {
          description
            "Configure as Master";
          type empty;
        }
        leaf profile {
          description
            "Change PTP clock profile";
          type enumeration {
            enum g8265.1;
            enum g8275.1;
            enum g8275.2;
          }
        }
        leaf local-priority {
          description
            "Set virtual port local priority";
          type uint8 {
            range "1..255";
          }
        }
        container announce {
          description
            "announcement packet parameters";
          leaf interval {
            description
              "PTP announce interval";
            type int8 {
              range "-3..3";
            }
            default "1";
          }
          leaf timeout {
            description
              "PTP announce timeout";
            type int8 {
              range "1..10";
            }
            default "3";
          }
        }
        container delay-req {
          leaf interval {
            description
              "PTP delay request interval";
            type int8 {
              range "-7..4";
            }
            default "-4";
          }
        }
        container sync {
          leaf interval {
            description
              "PTP delay request interval";
            type int8 {
              range "-7..4";
            }
            default "-5";
          }
          leaf one-step {
            type empty;
          }
        }
        container transport {
          description
            "Set port transport parameters";
          container ethernet {
            description
              "Use Ethernet encapsulation";
            container multicast {
              description
                "Use multicast communication channel";
              leaf bridge-domain {
                description
                  "Bridge domain id";
                type uint64 {
                  range "1..4294967295";
                }
              }
              container interface {
                uses ios-ifc:interface-grouping;
              }
            }
            leaf unicast {
              description
                "Use unicast communication channel";
              type empty;
            }
            leaf negotiation {
              description
                "Enable unicast negotiation";
              type empty;
            }
          }
          container ipv4 {
            description
              "Use Ipv4 encapsulation";
            container unicast {
              description
                "Use unicast communication channel";
              container interface {
                uses ios-ifc:interface-grouping;
                leaf negotiation {
                  description
                    "Enable unicast negotiation";
                  type empty;
                }
                leaf single-hop {
                  description
                    "Enable single hop transport";
                  type empty;
                }
              }
            }
          }
        }
        container clock {
          list source {
            key "address";
            leaf ip {
              type empty;
            }
            leaf address {
              type inet:ipv4-address;
            }
            leaf priority {
              description
                "Local priority";
              type uint8 {
                range "1..2";
              }
            }
            leaf delay-asymmetry {
              description
                "Delay asymmetry";
              type int64 {
                range "-500000000..500000000";
              }
              default "0";
            }
            leaf units {
              type enumeration {
                enum nanoseconds;
                enum picoseconds;
              }
            }
          }
          container destination {
            description
              "Destination options";
            uses config-address-grouping;
          }
        }
        container unicast {
          leaf grant-duration {
            type enumeration {
              enum 0;
            }
            default "0";
          }
        }
        leaf wait-to-restore {
          type enumeration {
            enum 0;
          }
          default "0";
        }
      }
      container time-properties {
        description
          "Time for which BC need to set UtcOffsetValid as true";
        leaf persist {
          description
            "Persist Time Interval for which BC need to set UtcOffsetValid as true";
          type uint16;
        }
      }
      leaf default-clock-class {
        type uint8 {
          range "0..255";
        }
      }
      leaf local-priority {
        type uint8 {
          range "1..255";
        }
      }
      leaf min-clock-class {
        type uint8 {
          range "0..255";
        }
      }
      container input {
        leaf input_1pps {
          type empty;
        }
        leaf slot-port {
          description
            "1PPS slot/port";
          type string;
        }
        leaf port_1pps {
          type enumeration {
            enum R0;
            enum R1;
          }
        }
      }
      container offset-msg-threshold {
        container warning {
          leaf value {
            type uint8 {
              range "0..200";
            }
          }
          leaf units {
            type enumeration {
              enum ms;
              enum us;
              enum ns;
            }
          }
        }
        container critical {
          leaf value {
            type uint16 {
              range "201..400";
            }
          }
          leaf units {
            type enumeration {
              enum ms;
              enum us;
              enum ns;
            }
          }
        }
      }
      container output {
        leaf out_1pps {
          type empty;
        }
        leaf slot-port {
          description
            "1PPS slot/port";
          type string;
        }
        leaf port_1pps {
          type enumeration {
            enum R0;
            enum R1;
          }
        }
        leaf offset {
          type uint64 {
            range "0..500000000";
          }
        }
        leaf negative {
          type empty;
        }
        leaf pulse-width {
          type uint16 {
            range "1..4096";
          }
        }
        leaf units {
          type enumeration {
            enum ms;
            enum us;
            enum ns;
          }
        }
      }
      leaf priority1 {
        type uint8 {
          range "1..255";
        }
        default "128";
      }
      leaf priority2 {
        type uint8 {
          range "1..255";
        }
        default "128";
      }
      leaf ref-clock-class-trap-clear {
        type uint8 {
          range "0..255";
        }
      }
      leaf ref-clock-state-trap-clear {
        type enumeration {
          enum ACQUIRING;
          enum FREERUN;
          enum FREQ_LOCKED;
          enum HOLDOVER;
          enum INITIALIZING;
          enum PHASE_ALIGNED;
          enum UNKNOWN;
        }
      }
      leaf ref-time-source-trap-clear {
        type enumeration {
          enum Atomic;
          enum GPS;
          enum "Hand Set";
          enum "Internal Oscillator";
          enum NTP;
          enum Other;
          enum PTP;
          enum "Terrestrial Radio";
        }
      }
      container servo {
        leaf network-type {
          type enumeration {
            enum High-Jitter;
            enum XDSL;
          }
        }
        leaf tracking-type {
          type enumeration {
            enum Frequency;
            enum High-Jitter;
          }
        }
      }
      container tod {
        leaf tod_port {
          type enumeration {
            enum R0;
            enum R1;
          }
        }
        leaf tod_format {
          type enumeration {
            enum cisco;
            enum nmea;
            enum ntp;
            enum ubx;
            enum cmcc;
          }
        }
        leaf delay {
          type uint16 {
            range "1..999";
          }
        }
        leaf slot-card {
          description
            "slot/card input";
          type string;
        }
      }
      container utc-offset {
        leaf value {
          type uint32 {
            range "0..65535";
          }
        }
        leaf leap-second {
          type string;
        }
        leaf offset {
          type int8 {
            range "-1..1";
          }
        }
      }
      list virtual-port {
        key "name";
        leaf name {
          type string;
        }
        leaf profile {
          type enumeration {
            enum g8275.1;
            enum g8275.2;
          }
        }
        leaf local-priority {
          description
            "Set virtual port local priority";
          type uint8 {
            range "1..255";
          }
        }
      }
    }
  }

  augment "/ios:native/ios:ptp" {
    uses config-ptp-grouping;
  }
}
