module Cisco-IOS-XE-wireless-rrm-types {
  yang-version 1;
  namespace "http://cisco.com/ns/yang/Cisco-IOS-XE-wireless-rrm-types";
  prefix wireless-rrm-types;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless rrm data types.
     Copyright (c) 2016-2021 by Cisco Systems, Inc.
     All rights reserved.";

  revision 2021-07-01 {
    description
      "- Added 6 GHz radio band enum for 802.11 interface type
       - Added DTLS connection status for RF group member";
    reference
      "4.3.0";
    cisco-semver:module-version "4.3.0";
  }
  revision 2019-11-01 {
    description
      "Added class type enum for cleanair device class-type.";
    reference
      "4.2.0";
    cisco-semver:module-version "4.2.0";
  }
  revision 2019-05-01 {
    description
      "Added semantic version";
    reference
      "4.1.0";
    cisco-semver:module-version "4.1.0";
  }
  revision 2018-11-15 {
    description
      "- Removed rrm channel list static array
       - Cleaned up spelling errors in descriptions.";
    reference
      "4.0.0";
    cisco-semver:module-version "4.0.0";
  }
  revision 2018-06-18 {
    description
      "Remove of grouping. List of Channel Numbers";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enm-rrm-phy-type {
    type enumeration {
      enum rrm-phy-80211b {
        value 1;
        description
          "Represents the 802.11b/g interface type for this entry.";
      }
      enum rrm-phy-80211a {
        value 2;
        description
          "Represents the 802.11a/c interface type for this entry.";
      }
      enum rrm-phy-80211xor {
        value 3;
        description
          "Represents the 802.11abgn interface type for this entry.";
      }
      enum rrm-phy-80211-6ghz {
        value 4;
        description
          "802.11 6 GHz band interface type.";
      }
    }
    description
      "This object uniquely represents the 802.11 interface type for this entry.";
  }

  typedef enm-rrm-ctrl-mode {
    type enumeration {
      enum rrm-automatic-mode {
        value 0;
        description
          "Represents group mode as Auto selection mode";
      }
      enum rrm-run-once-mode {
        value 1;
        description
          "Represents group mode as Run once selection mode";
      }
      enum rrm-static-mode {
        value 2;
        description
          "Represents group mode as Static selection mode";
      }
      enum rrm-leader-mode {
        value 3;
        description
          "Represents group mode as rf static leader";
      }
      enum rrm-restart-mode {
        value 4;
        description
          "Represents group mode as restart";
      }
    }
    description
      "This object represents current rf group mode";
  }

  typedef enm-ca-si-capable {
    type enumeration {
      enum spectrum-mode-ca {
        value 1;
        description
          "Represents the Access point is CA type for this entry.";
      }
      enum spectrum-mode-si {
        value 2;
        description
          "Represents the Access point is SI type for this entry.";
      }
      enum spectrum-mode-invalid {
        value 3;
        description
          "Represents the Access point is CA type for this entry.";
      }
    }
    description
      "This object uniquely represents the 802.11 interface type for this entry.";
  }

  typedef enm-cleanair-class-type {
    type enumeration {
      enum pmac-dev-unknown {
        value 0;
        description
          "Cleanair device class type unknown";
      }
      enum pmac-dev-id-bt {
        value 1;
        description
          "Cleanair device class type bluetooth pico-net";
      }
      enum pmac-dev-id-mwave {
        value 8;
        description
          "Cleanair device class type microwaves";
      }
      enum pmac-dev-id-fh {
        value 10;
        description
          "Cleanair device class type 802.11 - frequency hopping version";
      }
      enum pmac-dev-id-bti {
        value 17;
        description
          "Cleanair device class type bluetooth inquiry and paging";
      }
      enum pmac-dev-id-gtdd {
        value 18;
        description
          "Cleanair device class type generic periodic fixed frequency";
      }
      enum pmac-dev-id-jam {
        value 19;
        description
          "Cleanair device class type jammer";
      }
      enum pmac-dev-id-wform {
        value 25;
        description
          "Cleanair device class type generic continuous";
      }
      enum pmac-dev-id-dect {
        value 26;
        description
          "Cleanair device class type DECT like phone networks";
      }
      enum pmac-dev-id-video {
        value 27;
        description
          "Cleanair device class type video (sub-case of generic continuous class type)";
      }
      enum pmac-dev-id-zigbee {
        value 28;
        description
          "Cleanair device class type 802.15.4 e.g. ZigBee, HART, etc.";
      }
      enum pmac-dev-id-wifi-norm {
        value 29;
        description
          "Cleanair device class type standard 802.11 a/b/g/n/j";
      }
      enum pmac-dev-id-wifi-iq {
        value 30;
        description
          "Cleanair device class type spectrally inverted 802.11";
      }
      enum pmac-dev-id-wifi-chan {
        value 31;
        description
          "Cleanair device class type 802.11 on non standard channels";
      }
      enum pmac-dev-id-wifi-sup-g {
        value 32;
        description
          "Cleanair device class type Super G variant of WiFi";
      }
      enum pmac-dev-id-radar {
        value 33;
        description
          "Cleanair device class type radar";
      }
      enum pmac-dev-id-canopy {
        value 34;
        description
          "Cleanair device class type Motorola canopy";
      }
      enum pmac-dev-id-xbox {
        value 35;
        description
          "Cleanair device class type XBOX wireless controller";
      }
      enum pmac-dev-id-wmxm {
        value 36;
        description
          "Cleanair device class type 802.16 e mobile WiMAX";
      }
      enum pmac-dev-id-wmxf {
        value 37;
        description
          "Cleanair device class type 802.16 d fixed WiMAX";
      }
      enum pmac-dev-id-exalt {
        value 38;
        description
          "Cleanair device class type Exalt Bridge";
      }
      enum pmac-dev-id-ibeacon {
        value 41;
        description
          "Cleanair device class type iBeacon";
      }
      enum pmac-dev-id-max {
        value 42;
        description
          "Cleanair device class type maximum value";
      }
      enum pmac-dev-id-aci {
        value 254;
        description
          "Cleanair device class type Wi-Fi adjacent channel interference";
      }
      enum pmac-dev-id-undef {
        value 255;
        description
          "Cleanair device undefined class type";
      }
    }
    description
      "Cleanair device class type";
  }

  typedef enm-rrm-dtls-status {
    type enumeration {
      enum rrm-dtls-invalid {
        value 0;
        description
          "Invalid DTLS state.";
      }
      enum rrm-dtls-disabled {
        value 1;
        description
          "DTLS connection is disabled for RF group member.";
      }
      enum rrm-dtls-init {
        value 2;
        description
          "DTLS connection initiated for RF group member.";
      }
      enum rrm-dtls-in-handshake {
        value 3;
        description
          "DTLS connection is in handshake phase for RF group member.";
      }
      enum rrm-dtls-in-cert-verify {
        value 4;
        description
          "DTLS connection is in certificate verification state for RF group member.";
      }
      enum rrm-dtls-sess-established {
        value 5;
        description
          "DTLS connection is in session established state for RF group member.";
      }
      enum rrm-dtls-in-key-plumbing {
        value 6;
        description
          "DTLS connection is in key plumbing state for RF group member.";
      }
      enum rrm-dtls-key-plumbed {
        value 7;
        description
          "DTLS connection has plumbed the key for RF group member.";
      }
    }
    description
      "DTLS connection status for RF group member.";
  }

  grouping st-member-id {
    description
      "This object represents the rf group member identifier";
    leaf-list byte-var {
      type uint8;
      max-elements 6;
      ordered-by user;
      description
        "This value contains the ip address of member in the first four bytes and the last two bytes contains  the maximum number of Radios handled by the rf group leader";
    }
  }

  grouping st-group-id {
    description
      "This object represents the rf group identifier";
    leaf wlc-mac {
      type yang:mac-address;
      description
        "This value contains the rf group leader's ip address in the first four bytes and the last two bytes contains  the maximum number of Radios handled by the rf group leader";
    }
    leaf cnt {
      type uint16;
      description
        "This value contains a random counter that is created every time the rf group initializes";
    }
  }

  grouping st-rrm-msg-seq {
    description
      "Field is used in rrm message retry mechanism";
    leaf seq-num {
      type uint32;
      description
        "Indicates rrm message sequence number";
    }
    leaf duplicate {
      type uint32;
      description
        "Indicates if the message received is duplicate of previously received message";
    }
  }

  grouping st-rrm-channels-list {
    description
      "List of Channel Numbers";
    leaf-list channel {
      type uint16;
      max-elements 64;
      ordered-by user;
      description
        "Channel Number";
    }
  }

  grouping st-rrm-common-ctrl-confg {
    description
      "This object represents rrm common control config for various algorithms";
    leaf mode {
      type wireless-rrm-types:enm-rrm-ctrl-mode;
      description
        "Represents algorithms current mode";
    }
    leaf update-counter {
      type uint32;
      description
        "Indicates the number of times the corresponding algorithm has run";
    }
    leaf update-interval-sec {
      type uint32;
      description
        "Time interval before which the algorithm was run";
    }
    leaf contribution {
      type uint8;
      description
        "Contributing factors to the algorithm";
    }
  }

  grouping st-rrm-dpc-config {
    description
      "Represents rrm tpc algorithm related configuration";
    container rf {
      description
        "Contains general configuration that is applicable to all the algorithms";
      uses wireless-rrm-types:st-rrm-common-ctrl-confg;
    }
    leaf dpc-min-tx-power-limit {
      type int8;
      description
        "Minimum tx power that the tpc algorithm can assign to any radio";
    }
    leaf dpc-max-tx-power-limit {
      type int8;
      description
        "Maximum tx power that the tpc algorithm can assign to any radio";
    }
    leaf tx-power-control-threshold {
      type int8;
      description
        "Indicates tx power threshold for tpc algorithm";
    }
  }
}
