module Cisco-IOS-XE-device-tracking {
  namespace "http://cisco.com/ns/yang/Cisco-IOS-XE-device-tracking";
  prefix ios-dt;

  import cisco-semver {
    prefix cisco-semver;
  }
  import Cisco-IOS-XE-types {
    prefix ios-types;
  }
  import Cisco-IOS-XE-native {
    prefix ios;
  }
  import ietf-inet-types {
    prefix inet;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Device Tracking Yang model.
     Copyright (c) 2016-2020 by Cisco Systems, Inc.
     All rights reserved.";

  revision 2021-03-01 {
    description
      "- Fixing the issue with protocol container
       - Fixing the issue with Tracking container
       - Adding the support for attaching policy under vlan for device-tracking
       - Added the missing commands to fill the gap between CLI and Yang for SISF";
    cisco-semver:module-version "2.2.0";
  }
  revision 2020-03-01 {
    description
      "- Updated the must constraints in the device tracking container";
    cisco-semver:module-version "2.1.0";
  }
  revision 2019-11-01 {
    description
      "- Obsolete ip device-tracking hierarchy";
    cisco-semver:module-version "2.0.0";
  }
  revision 2019-07-01 {
    description
      "- Establish semantic version baseline
       - Add new containers (prefix-glean, destination-glean and trusted port)in device-tracking policy list
       - Assign default value for protocol options";
    cisco-semver:module-version "1.0.0";
  }
  revision 2018-01-29 {
    description
      "Add device-tracking tracking reachable-lifetime";
  }
  revision 2017-06-07 {
    description
      "Add device-tracking tracking support";
  }
  revision 2017-02-07 {
    description
      "Initial revision";
  }

  grouping config-interface-device-tracking-vlan-grouping {
    container vlan {
      description
        "Configure the vlan list for which this policy applies (default: all)";
      leaf vlan-name {
        description
          "VLAN IDs of the VLANs for which this policy applies";
        type string;
      }
      leaf add {
        description
          "add VLANs to the current list";
        type string;
      }
      leaf all {
        description
          "all VLANs";
        type empty;
      }
      leaf except {
        description
          "VLAN IDs of disallowed VLANS for this policy on this port";
        type string;
      }
      leaf none {
        description
          "no VLANs";
        type empty;
      }
      leaf remove {
        description
          "Remove VLANs from the current list";
        type string;
      }
    }
  }

  grouping config-interface-device-tracking-grouping {
    container device-tracking {
      description
        "Configure device-tracking on the interface";
      presence "Attach default device-tracking on interface";
      if-feature "ios-features:switching-platform";
      must "not (../ios:switchport-conf/ios:switchport = 'false') or (../ios:switchport-conf/ios:switchport = 'true')" {
        error-message "To configure attach device-tracking policy, set switchport-conf to true; To detach a policy, set switchport to false";
      }
      list attached-policies {
        key "attach-policy";
        leaf attach-policy {
          description
            "Apply a policy for feature device-tracking";
          type string;
          must '(/ios:native/ios:device-tracking/ios-dt:policy[ios-dt:word=current()])' {
            error-message "Create policy first, then attach policy; Detach policy first then remove policy";
          }
        }
        uses config-interface-device-tracking-vlan-grouping;
      }
      container default-policy {
        uses config-interface-device-tracking-vlan-grouping;
      }
      leaf attach-policy {
        status deprecated;
        description
          "Apply a policy for feature device-tracking";
        type string;
        must '(/ios:native/ios:device-tracking/ios-dt:policy[ios-dt:word=current()])' {
          error-message "Create policy first, then attach policy; Detach policy first then remove policy";
        }
      }
    }
  }

  grouping config-interface-switchport-device-tracking-grouping {
    container device-tracking {
      description
        "Obsolete - Configure device-tracking on the interface";
      presence "Attach default device-tracking on interface";
      status obsolete;
      leaf attach-policy {
        description
          "Obsolete - Apply a policy for feature device-tracking";
        status obsolete;
        type string;
        must '(/ios:native/ios:device-tracking/ios-dt:policy[ios-dt:word=current()])' {
          error-message "Create policy first, then attach policy; Detach policy first then remove policy";
        }
      }
    }
  }

  grouping config-binding-reachable-lifetime-grouping {
    container reachable-lifetime {
      description
        "Default maximum time in REACHABLE without activity";
      choice time-choice {
        leaf seconds {
          description
            "Seconds to keep in reachable state";
          type uint32 {
            range "1..86400";
          }
        }
        leaf default {
          description
            "Use default binding table value";
          type empty;
        }
        leaf infinite {
          description
            "Keep in REACHABLE forever";
          type empty;
        }
      }
    }
  }

  grouping config-vlan-device-tracking-grouping {
    container device-tracking {
      description
        "Obsolete - Configure device-tracking on the interface";
      presence "Attach default device-tracking on interface";
      status obsolete;
      leaf attach-policy {
        description
          "Obsolete - Apply a policy for feature device-tracking";
        status obsolete;
        type string;
        must '(/ios:native/ios:device-tracking/ios-dt:policy[ios-dt:word=current()])' {
          error-message "Create policy first, then attach policy; Detach policy first then remove policy";
        }
      }
    }
  }

  grouping config-device-tracking-grouping {
    list policy {
      description
        "Configure a policy for feature device-tracking";
      key "word";
      leaf word {
        type string;
      }
      container device-role {
        description
          "Sets the role of the device attached to the port";
        choice device-role-choice {
          case node {
            leaf node {
              type boolean;
              default "true";
            }
          }
          case switch {
            leaf switch {
              type empty;
            }
          }
        }
      }
      container data-glean {
        description
          "binding recovery by data traffic source address gleaning";
        leaf log-only {
          description
            "only generate a syslog upon data packet notification";
          type empty;
        }
        container recovery {
          description
            "recovery protocol to use";
          leaf dhcp {
            description
              "use DHCP as the recovery protocol";
            type empty;
          }
          leaf ndp {
            description
              "use NDP as the recovery protocol";
            type empty;
          }
        }
      }
      container prefix-glean {
        presence "Enable prefix-glean";
        description
          "Glean prefixes in RA and DHCP-PD traffic";
        leaf only {
          type empty;
          description
            "Glean only prefixes i.e. do not glean host addresses";
        }
      }
      container destination-glean {
        description
          "binding recovery by data traffic destination address gleaning";
        leaf log-only {
          type empty;
        }
        container recovery {
          description
            "recovery protocol to use";
          leaf dhcp {
            description
              "use DHCP as the recovery protocol";
            type empty;
          }
        }
      }
      container protocol {
        description
          "Set the protocol to glean (default all)";
        container proto-udp {
          leaf udp {
            description
              "Glean addresses in UDP packets";
            type boolean;
          }
          leaf prefix-list {
            description
              "Name of the prefix-list to be matched";
            type string;
          }
        }
        container proto-arp {
          leaf arp {
            description
              "Glean addresses in ARP packets";
            type boolean;
            default "true";
          }
          leaf prefix-list {
            description
              "Name of the prefix-list to be matched";
            type string;
          }
        }
        container proto-dhcp4 {
          leaf dhcp4 {
            description
              "Glean addresses in DHCPv4 packets";
            type boolean;
            default "true";
          }
          leaf prefix-list {
            description
              "Name of the prefix-list to be matched";
            type string;
          }
        }
        container proto-dhcp6 {
          leaf dhcp6 {
            description
              "Glean addresses in DHCPv6 packets";
            type boolean;
            default "true";
          }
          leaf prefix-list {
            description
              "Name of the prefix-list to be matched";
            type string;
          }
        }
        container proto-ndp {
          leaf ndp {
            description
              "Glean addresses in NDP packets";
            type boolean;
            default "true";
          }
          leaf prefix-list {
            description
              "Name of the prefix-list to be matched";
            type string;
          }
        }
        leaf udp {
          description
            "Deprecated, use other leaf to set the protocol";
          status deprecated;
          type boolean;
        }
        leaf arp {
          status deprecated;
          description
            "Deprecated, use other leaf to set the protocol. Glean addresses in ARP packets";
          type boolean;
          default "true";
        }
        leaf dhcp4 {
          status deprecated;
          description
            "Deprecated, use other leaf to set the protocol. Glean addresses in DHCPv4 packets";
          type boolean;
          default "true";
        }
        leaf dhcp6 {
          status deprecated;
          description
            "Deprecated, use other leaf to set the protocol. Glean addresses in DHCPv6 packets";
          type boolean;
          default "true";
        }
        leaf ndp {
          status deprecated;
          description
            "Deprecated, use other leaf to set the protocol. Glean addresses in NDP packets";
          type boolean;
          default "true";
        }
      }
      container tracking {
        description
          "Override default tracking behavior";
        choice tracking-enable-disable {
          container enable-tracking {
            presence "true";
            container reachable-lifetime {
              description
                "Time entry is kept REACHABLE";
              choice tracking-enable {
                leaf seconds {
                  description
                    "Seconds";
                  type uint32 {
                    range "1..86400";
                  }
                }
                leaf infinite {
                  description
                    "Keep in REACHABLE forever";
                  type empty;
                }
              }
            }
          }
          container disable-tracking {
            description
              "Tracking on or off";
            presence "true";
            leaf stale-lifetime {
              description
                "Default maximum time in STALE";
              type union {
                type uint32 {
                  range "1..86400";
                }
                type enumeration {
                  enum infinite;
                }
              }
            }
          }
        }
        container enable {
          status deprecated;
          presence "true";
          container reachable-lifetime {
            status deprecated;
            description
              "Time entry is kept REACHABLE";
            leaf seconds {
              status deprecated;
              description
                "Seconds";
              type uint32 {
                range "1..86400";
              }
            }
            leaf infinite {
              status deprecated;
              description
                "Keep in REACHABLE forever";
              type empty;
            }
          }
        }
        leaf disable {
          status deprecated;
          description
            "Tracking on or off";
          type empty;
        }
      }
      container limit {
        description
          "Specifies a limit";
        leaf address-count {
          description
            "Configure maximum address per port";
          type uint16 {
            range "1..32000";
          }
        }
      }
      container security-level {
        description
          "setup security level";
        leaf glean {
          description
            "glean addresses passively";
          type empty;
        }
        leaf guard {
          description
            "inspect and drop un-authorized messages (default)";
          type empty;
        }
        leaf inspect {
          description
            "glean and Validate message";
          type empty;
        }
      }
      leaf medium-type-wireless {
        description
          "Force medium type to wireless";
        type empty;
      }
      leaf trusted-port {
        description
          "setup trusted port";
        type empty;
      }
    }
    container tracking {
      presence "true";
      container auto-source {
        presence "true";
        container fallback {
          description
            "Specify IP and MASK to use as last resort";
          choice ip-subnet-choice {
            case ip-addr-and-mask {
              description
                "IPv4 and MASK of fallback source";
              container ipv4-subnet-type1 {
                leaf ipv4 {
                  description
                    "IPv4 address";
                  type inet:ipv4-address;
                }
                leaf mask {
                  description
                    "IP prefix mask";
                  type inet:ipv4-address;
                }
                leaf override {
                  description
                    "Do not select source address from device track table";
                  type empty;
                }
              }
            }
            case ip-addr-and-prefix-len {
              description
                "IPv4 and MASK of fallback source";
              container ipv4-subnet-type2 {
                leaf ipv4-prefix-name {
                  description
                    "ip address/length <network>/<length>, e.g., 192.168.12.12/16";
                  type ios-types:ipv4-address-slash-prefix-len;
                }
                leaf override {
                  description
                    "Do not select source address from device track table";
                  type empty;
                }
              }
            }
          }
        }
        leaf override {
          description
            "Do not select source address from device track table";
          type empty;
        }
      }
      leaf retry-interval {
        description
          "Interval time  between two probing";
        type uint16 {
          range "1..3600";
        }
      }
    }
    container binding {
      description
        "Configure device tracking binding table";
      list static-device-tracking-binding {
        description
          "Binding a static entry";
        if-feature "ios-features:routing-platform";
        key "addr";
        leaf addr {
          type union {
            type inet:ipv4-address;
            type inet:ipv6-address;
            type ios-types:ipv6-prefix;
          }
        }
        leaf interface {
          description
            "Interface name";
          mandatory true;
          type string;
        }
        leaf hardware-address {
          description
            "48-bit hardware address";
          type string;
        }
        container binding-choices {
          when '(../hardware-address)';
          choice binding-choice {
            case reachable-lifetime-choice {
              uses config-binding-reachable-lifetime-grouping;
            }
            case tracking-choice {
              container tracking {
                description
                  "Override default tracking behavior";
                choice binding-tracking-choice {
                  container default-tracking {
                    leaf default {
                      description
                        "Default tracking";
                      type empty;
                    }
                    uses config-binding-reachable-lifetime-grouping;
                  }
                  container enable-tracking {
                    leaf enable {
                      description
                        "Enable tracking";
                      type empty;
                    }
                    choice time-type-choice {
                      case reachable-lifetime-choice {
                        uses config-binding-reachable-lifetime-grouping;
                      }
                      case retry-interval-choice {
                        container retry-interval {
                          description
                            "Retry interval between two probings";
                          choice retry-time {
                            leaf seconds {
                              description
                                "Seconds";
                              type uint32 {
                                range "1..86400";
                              }
                            }
                            leaf default {
                              description
                                "Use default";
                              type empty;
                            }
                          }
                        }
                      }
                    }
                  }
                  container disable-tracking {
                    leaf disable {
                      description
                        "Disable tracking";
                      type empty;
                    }
                    uses config-binding-reachable-lifetime-grouping;
                  }
                }
              }
            }
          }
        }
      }
      container down-lifetime {
        choice time-choice {
          leaf seconds {
            description
              "Seconds..";
            type uint32 {
              range "1..86400";
            }
          }
          leaf infinite {
            description
              "Never delete from DOWN";
            type empty;
          }
        }
      }
      leaf logging {
        description
          "Enable syslog logging of binding table events";
        type empty;
      }
      container reachable-lifetime {
        description
          "Default maximum time in REACHABLE without activity";
        choice time-choice {
          leaf seconds {
            description
              "Seconds..";
            type uint32 {
              range "1..86400";
            }
          }
          leaf infinite {
            description
              "Keep in REACHABLE forever";
            type empty;
          }
        }
        container stale-lifetime {
          description
            "Default maximum time in STALE before deletion";
          choice time-choice {
            leaf seconds {
              description
                "Seconds..";
              type uint32 {
                range "1..86400";
              }
            }
            leaf infinite {
              description
                "Keep in REACHABLE forever";
              type empty;
            }
          }
        }
        container down-lifetime {
          description
            "Default maximum time in DOWN before removal";
          choice time-choice {
            leaf seconds {
              description
                "Seconds..";
              type uint32 {
                range "1..86400";
              }
            }
            leaf infinite {
              description
                "Keep in REACHABLE forever";
              type empty;
            }
          }
        }
      }
      container stale-lifetime {
        description
          "Default maximum time in STALE before deletion";
        choice time-choice {
          leaf seconds {
            description
              "Seconds..";
            type uint32 {
              range "1..86400";
            }
          }
          leaf infinite {
            description
              "Never delete from STALE";
            type empty;
          }
        }
        container down-lifetime {
          description
            "Default maximum time in DOWN before removal";
          choice time-choice {
            leaf seconds {
              description
                "Seconds..";
              type uint32 {
                range "1..86400";
              }
            }
            leaf infinite {
              description
                "Never delete from DOWN";
              type empty;
            }
          }
        }
      }
      list vlan {
        description
          "Vlan identifier";
        key "numbers addr";
        leaf numbers {
          description
            "Vlan numbers";
          type uint16 {
            range "1..4096";
          }
        }
        leaf addr {
          mandatory true;
          type union {
            type inet:ipv4-address;
            type inet:ipv6-address;
            type ios-types:ipv6-prefix;
          }
        }
        leaf interface {
          description
            "Interface name";
          type string;
        }
        leaf hardware-address {
          description
            "48-bit hardware address";
          type string;
        }
      }
      container max-entries {
        description
          "Define maximum number of entries in the Binding table";
        leaf entry {
          description
            "Number of entries";
          type uint32 {
            range "1..1000000";
          }
        }
        leaf vlan-limit {
          description
            "Define maximum number of entries allowed per vlan";
          type uint32 {
            range "1..200000";
          }
        }
        leaf port-limit {
          description
            "Define maximum number of entries allowed per interface";
          type uint32 {
            range "1..100000";
          }
        }
        leaf mac-limit {
          description
            "Define maximum number of entries allowed per mac";
          type uint32 {
            range "1..100000";
          }
        }
      }
    }
    container logging {
      description
        "Configure snooping Security logging";
      presence "true";
      container packet {
        description
          "Packet events";
        leaf drop {
          description
            "packets drop events";
          type empty;
        }
      }
      leaf resolution-veto {
        description
          "Resolution veto events";
        type empty;
      }
      leaf theft {
        description
          "IP or MAC theft events";
        type empty;
      }
    }
  }

  grouping config-ip-device-grouping {
    container tracking {
      status obsolete;
      description
        "Obsolete - Device tracking";
      presence "true";
      container probe {
        status obsolete;
        description
          "Obsolete - Probe";
        container auto-source {
          status obsolete;
          description
            "Obsolete - Probe source selection algorithm";
          presence "true";
          container fallback {
            status obsolete;
            description
              "Obsolete -  Specify IP and MASK to use as last resort";
            leaf src-ip {
              status obsolete;
              description
                "Obsolete - IP and MASK of fallback source";
              type inet:ipv4-address;
            }
            leaf mask {
              status obsolete;
              description
                "Obsolete - IP prefix mask";
              type inet:ipv4-address;
            }
          }
          leaf override {
            status obsolete;
            description
              "Obsolete - Do not select source address from device track table";
            type empty;
          }
        }
        leaf count {
          status obsolete;
          description
            "Obsolete - Probe count";
          type uint8;
        }
        leaf delay {
          status obsolete;
          description
            "Obsolete - Probe delay";
          type uint8 {
            range "1..120";
          }
        }
        leaf interval {
          status obsolete;
          description
            "Obsolete - Probe interval";
          type uint32 {
            range "30..1814400";
          }
        }
      }
      leaf trace-buffer {
        status obsolete;
        description
          "Obsolete - Enable Tracing Support";
        type empty;
      }
    }
  }

  augment "/ios:native/ios:device-tracking" {
    uses config-device-tracking-grouping;
  }

  augment "/ios:native/ios:ip/ios:device" {
    uses config-ip-device-grouping {
      if-feature "ios-features:device-tracking";
    }
  }
}
