module Cisco-IOS-XE-netconf-diag-rpc {
  yang-version 1;
  namespace "http://cisco.com/ns/yang/Cisco-IOS-XE-netconf-diag-rpc";
  prefix ios-xe-netconf-diag-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NETCONF Message Diagnostics RPC.
     Copyright (c) 2020 by Cisco Systems, Inc.
     All rights reserved.";

  revision 2021-03-01 {
    description
      "Initial revision";
    reference
      "1.0.0";
    cisco-semver:module-version "1.0.0";
  }

  typedef diagnostic-level {
    type enumeration {
      enum diag-disabled {
        value 0;
        description
          "No diagnostic data collection (default).";
      }
      enum diag-basic {
        value 1;
        description
          "Include IOS CLI parser command logs, developer logs,
           running-config change, and last rollback contents.";
      }
      enum diag-maximum {
        value 2;
        description
          "Include the basic diagnostics plus before and after
           running-config snapshots.";
      }
    }
    description
      "Levels of diagnostic reporting.";
  }

  grouping enable-netconf-diag {
    description
      "NETCONF Message Diagnostics data.";
    leaf diag-level {
      type ios-xe-netconf-diag-rpc:diagnostic-level;
      mandatory true;
      description
        "Choose diagnostic level.";
    }
  }

  grouping archive-netconf-diag-logs-output {
    description
      "Output of the RPC.";
    leaf log-file {
      type string;
      description
        "The path and file name of the log file in
         archived and compressed format (.tar.gz).
         It contains all the latest diagnostics logs.";
    }
  }

  rpc enable-netconf-diag {
    description
      "Enable NETCONF Message Diagnostics for providing
       easy access to all information required to diagnose
       NETCONF transaction failures on NED models.";
    input {
      uses ios-xe-netconf-diag-rpc:enable-netconf-diag;
    }
  }

  rpc archive-netconf-diag-logs {
    description
      "Archive and compress the NETCONF Message Diagnostics logs
       into a file that is stored on the network device's persistent storage.
       The log file including path and file name is returned
       with the RPC reply.";
    output {
      uses ios-xe-netconf-diag-rpc:archive-netconf-diag-logs-output;
    }
  }
}
