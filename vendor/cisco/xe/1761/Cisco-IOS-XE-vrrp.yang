module Cisco-IOS-XE-vrrp {
  namespace "http://cisco.com/ns/yang/Cisco-IOS-XE-vrrp";
  prefix ios-vrrp;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native VRRP Yang model.
     Copyright (c) 2017-2021 by Cisco Systems, Inc.
     All rights reserved.";

  revision 2021-07-01 {
    description
      "- Moved vrrp-group when condition to annotation file
       - CLI configuration for VRRP on 2 Gigabit Ethernet interface
       - CLI configuration for VRRP enabled on Port-Channel sub-interface
       - Added tailf:cli-delete-when-empty in list secondary of container address";
    cisco-semver:module-version "1.3.0";
  }
  revision 2020-11-01 {
    description
      "Added container for bfd peer.(for 17.5.1)";
    cisco-semver:module-version "1.2.0";
  }
  revision 2019-11-01 {
    description
      "Removed presence from some containers";
    cisco-semver:module-version "1.0.1";
  }
  revision 2019-07-01 {
    description
      "Establish semantic version baseline";
    cisco-semver:module-version "1.0.0";
  }
  revision 2019-01-22 {
    description
      "Added leaf for App-hosting Gigabit Ethernet interface";
  }
  revision 2018-08-15 {
    description
      "Revise the model for vrrp ip primary/secondary in vrrp-group-v2";
  }
  revision 2018-08-07 {
    description
      "Remove tailf:cli-incomplete-no in list vrrp-group-v2";
  }
  revision 2018-07-27 {
    description
      "Modify container preempt for both version";
  }
  revision 2018-06-28 {
    description
      "Add support for VRRP version 2";
  }
  revision 2018-05-30 {
    description
      "Add cli-delete-when-empty for track omp";
  }
  revision 2018-05-16 {
    description
      "Support match-address and preempt with no form of the command only
       included in the CLI show output when explicitly disabled";
  }
  revision 2018-05-09 {
    description
      "Remove tailf:cli-show-no from match-address and preempt";
  }
  revision 2018-04-11 {
    description
      "Add mandatory true for track interface choice action.";
  }
  revision 2018-02-15 {
    description
      "Add primary leaf for IPv4 VRRP group address.";
  }
  revision 2018-01-02 {
    description
      "Initial version";
  }

  grouping config-interface-vrrp-grouping {
    container vrrp {
      description
        "Configure VRRP";
      list vrrp-group {
        key "group-id";
        leaf group-id {
          description
            "VRRP group number";
          type uint8 {
            range "1..255";
          }
        }
        container address-family {
          description
            "Address family of the group";
          container ipv4 {
            description
              "IPv4 Address family";
            presence "Enable IPv4 address-family for this VRRP group";
            uses config-ipv4-address-grouping;
            uses config-common-vrrp-grouping;
          }
          container ipv6 {
            description
              "IPv6 Address family";
            presence "Enable IPv6 address-family for this VRRP group";
            uses config-ipv6-address-grouping;
            uses config-common-vrrp-grouping;
          }
        }
      }
      list vrrp-group-v2 {
        description
          "vrrp version 2";
        when "/ios:native/ios:fhrp/ios:version/ios:vrrp = 'v2'";
        key "group-id";
        leaf group-id {
          description
            "VRRP group number";
          type uint8 {
            range "1..255";
          }
        }
        container authentication {
          leaf text {
            description
              "authentication string";
            type string {
              length "1..8";
            }
          }
        }
        leaf description {
          description
            "Up to 80 characters describing this group";
          type string;
        }
        container ip {
          container primary {
            leaf address {
              type inet:ipv4-address;
            }
          }
          list secondary {
            key "address";
            leaf address {
              type inet:ipv4-address;
            }
            leaf secondary {
              description
                "Make this IPv4 address a secondary address";
              mandatory true;
              type empty;
            }
          }
        }
        leaf name {
          description
            "Unique VRRS identifier (max 48 characters)";
          type string;
        }
        container preempt-config {
          leaf preempt {
            description
              "Enable preemption of lower priority Master";
            type boolean;
            default "true";
          }
        }
        container preempt {
          description
            "Enable preemption of lower priority Master";
          container delay {
            description
              "Set time delay before preempting";
            leaf minimum {
              description
                "Seconds to delay";
              type uint16 {
                range "0..3600";
              }
              units "seconds";
            }
          }
        }
        leaf priority {
          description
            "Priority level";
          type uint8 {
            range "1..254";
          }
          default "100";
        }
        leaf shutdown {
          type empty;
        }
        container timers {
          container advertise {
            choice interval-setting {
              description
                "Specify the advertise time interval.";
              case second {
                leaf interval {
                  type uint8 {
                    range "1..255";
                  }
                }
              }
              case milisecond {
                leaf msec {
                  description
                    "Advertisement interval in milliseconds";
                  type uint16 {
                    range "50..999";
                  }
                }
              }
            }
          }
          leaf learn {
            type empty;
          }
        }
        container track {
          list event {
            key "object-id";
            leaf object-id {
              type uint16 {
                range "1..1000";
              }
            }
            leaf decrement {
              description
                "Decrement value";
              type uint8 {
                range "1..255";
              }
            }
          }
        }
      }
      container delay {
        when "/ios:native/ios:fhrp/ios:version/ios:vrrp = 'v2'";
        leaf reload {
          description
            "Seconds to delay after reload";
          type uint16 {
            range "0..10000";
          }
        }
        leaf minimum {
          description
            "Seconds to delay after interface up";
          type uint16 {
            range "0..10000";
          }
        }
      }
    }
  }

  grouping config-ipv4-address-grouping {
    leaf vrrpv2 {
      description
        "Set VRRPv2 compatibility mode";
      type empty;
    }
    container address {
      description
        "Set the IPv4 address of VRRP group";
      container primary {
        leaf address {
          type inet:ipv4-address;
        }
        leaf primary {
          description
            "IPv4 primary address";
          type empty;
        }
      }
      list secondary {
        key "address";
        leaf address {
          type inet:ipv4-address;
        }
        leaf secondary {
          description
            "Make this IPv4 address a secondary address";
          mandatory true;
          type empty;
        }
      }
    }
    container bfd {
      description
        "Configure HSRP BFD peer";
      container peer {
        leaf address {
          type inet:ipv4-address;
        }
      }
    }
  }

  grouping config-ipv6-address-grouping {
    container address {
      description
        "Set the IPv6 address of VRRP group";
      container primary {
        leaf ipv6-link-local {
          description
            "IPv6 link-local address";
          type inet:ipv6-address;
        }
        leaf primary {
          description
            "IPv6 primary address";
          type empty;
        }
      }
      list ipv6-prefix {
        key "prefix";
        leaf prefix {
          type ios-types:ipv6-prefix;
        }
      }
    }
    container bfd {
      description
        "Configure HSRP BFD peer";
      container peer {
        choice address-setting {
          description
            "Specify the IPv6 address.";
          case link-local {
            leaf ipv6-address {
              type inet:ipv6-address;
            }
          }
          case prefix {
            leaf ipv6-prefix {
              type ios-types:ipv6-prefix;
            }
          }
        }
      }
    }
  }

  grouping config-common-vrrp-grouping {
    leaf description {
      description
        "Group description";
      type string {
        length "1..80";
      }
    }
    leaf match-address {
      description
        "Match addresses in advertisement packet";
      type boolean;
    }
    container preempt-config {
      leaf preempt {
        description
          "Enable preemption of lower priority Master";
        type boolean;
        default "true";
      }
    }
    container preempt {
      description
        "Enable preemption of lower priority Master";
      container delay {
        description
          "Set time delay before preempting";
        leaf minimum {
          description
            "Seconds to delay";
          type uint16 {
            range "0..3600";
          }
          units "seconds";
        }
      }
    }
    leaf priority {
      description
        "Priority level";
      type uint8 {
        range "1..254";
      }
      default "100";
    }
    leaf shutdown {
      description
        "Shutdown the group";
      type empty;
    }
    container timers {
      description
        "Set the VRRP timers";
      leaf advertise {
        description
          "Advertisement interval in milliseconds";
        type uint16 {
          range "100..40950";
        }
        units "milliseconds";
      }
    }
    container track {
      list event {
        key "object-id";
        leaf object-id {
          description
            "Specify the tracked object-id";
          type union {
            type uint16 {
              range "1..1000";
            }
            type enumeration {
              enum omp;
            }
          }
        }
        choice action {
          description
            "Specify the taken action.";
          mandatory true;
          case priority {
            leaf decrement {
              description
                "Specify the decrement value from current priority";
              type uint8 {
                range "1..255";
              }
            }
          }
          case other {
            leaf shutdown {
              description
                "Shutdown the group";
              type empty;
            }
          }
        }
      }
    }
    container vrrs {
      description
        "VRRS related commands";
      leaf leader {
        description
          "Name of VRRS Tag for which this group is the leader";
        type string;
      }
    }
  }

  augment "/ios:native/ios:interface/ios:FastEthernet" {
    uses config-interface-vrrp-grouping;
  }

  augment "/ios:native/ios:interface/ios:GigabitEthernet" {
    uses config-interface-vrrp-grouping;
  }

  augment "/ios:native/ios:interface/ios:TwoGigabitEthernet" {
    uses config-interface-vrrp-grouping;
  }

  augment "/ios:native/ios:interface/ios:FiveGigabitEthernet" {
    uses config-interface-vrrp-grouping;
  }

  augment "/ios:native/ios:interface/ios:AppGigabitEthernet" {
    uses config-interface-vrrp-grouping;
  }

  augment "/ios:native/ios:interface/ios:TenGigabitEthernet" {
    uses config-interface-vrrp-grouping;
  }

  augment "/ios:native/ios:interface/ios:FortyGigabitEthernet" {
    uses config-interface-vrrp-grouping;
  }

  augment "/ios:native/ios:interface/ios:HundredGigE" {
    uses config-interface-vrrp-grouping;
  }

  augment "/ios:native/ios:interface/ios:Vlan" {
    uses config-interface-vrrp-grouping;
  }

  augment "/ios:native/ios:interface/ios:Port-channel" {
    uses config-interface-vrrp-grouping;
  }

  augment "/ios:native/ios:interface/ios:BDI" {
    uses config-interface-vrrp-grouping;
  }

  augment "/ios:native/ios:interface/ios:Port-channel-subinterface/ios:Port-channel" {
    uses config-interface-vrrp-grouping;
  }
}
