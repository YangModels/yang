module Cisco-IOS-XE-wireless-mcast-oper {
  yang-version 1;
  namespace "http://cisco.com/ns/yang/Cisco-IOS-XE-wireless-mcast-oper";
  prefix wireless-mcast-oper;

  import Cisco-IOS-XE-wireless-enum-types {
    prefix wireless-enum-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for wireless multicast operational data.
     Copyright (c) 2018-2019 by Cisco Systems, Inc.
     All rights reserved.";

  revision 2019-05-01 {
    description
      "Added semantic version";
    reference
      "3.1.0";
    cisco-semver:module-version "3.1.0";
  }
  revision 2018-12-10 {
    description
      "- Removal of unused leaves and container
       - Cleaned up spelling errors in descriptions.
       - Cleaned renaming";
    reference
      "3.0.0";
    cisco-semver:module-version "3.0.0";
  }
  revision 2018-08-15 {
    description
      "- Add Fabric multicast operational yang
       - Change Multicast over Multicast to ipv4 and ipv6 specific";
    reference
      "2.0.0";
    cisco-semver:module-version "2.0.0";
  }
  revision 2018-01-29 {
    description
      "Initial revision";
    reference
      "1.0.0";
    cisco-semver:module-version "1.0.0";
  }

  grouping mcast-client-entry {
    description
      "Multicast client entries";
    leaf vlan {
      type uint16;
      description
        "Client's vlan for Multicast";
    }
    leaf mgid {
      type uint16;
      description
        "Mgid for Multicast group";
    }
    leaf group {
      type inet:ip-address;
      description
        "Multicast group IP address";
    }
    leaf client-status {
      type wireless-enum-types:enm-mcast-client-status;
      description
        "Client status of Multicast group";
    }
    leaf qos {
      type wireless-enum-types:media-stream-qos;
      description
        "QOS value for Multicast group";
    }
    leaf used {
      type boolean;
      description
        "Multicast client entry is in use or not";
    }
  }

  grouping ewlc-multicast-oper-data {
    description
      "Multicast operational data";
    leaf ms-mac-address {
      type yang:mac-address;
      description
        "Client MAC address";
    }
    leaf num-entries {
      type uint8;
      description
        "Number of currently filled entries";
    }
    list entry {
      max-elements 16;
      description
        "Multicast client entry";
      uses wireless-mcast-oper:mcast-client-entry;
    }
    leaf client-ipv6 {
      type inet:ipv6-address;
      description
        "Multicast client IPv6 address";
    }
    leaf capwap-iif-id {
      type uint64;
      description
        "Client capwap IIF ID";
    }
    leaf client-ip {
      type inet:ipv4-address;
      description
        "Client IPv4 address";
    }
  }

  grouping mcast-mgid-client-entry {
    description
      "multicast MGID client entry";
    leaf client-mac-addr {
      type yang:mac-address;
      description
        "client MAC address";
    }
    leaf client-ip-addr {
      type inet:ip-address;
      description
        "Client IPv4 address";
    }
    leaf client-status {
      type wireless-enum-types:enm-mcast-client-status;
      description
        "Client's multicast status";
    }
  }

  grouping mcast-mgid-entry {
    description
      "Multicast MGID entries";
    leaf mgid {
      type uint16;
      description
        "MGID for Multicast group";
    }
    leaf vlan {
      type uint16;
      description
        "VLAN used for MGID";
    }
    leaf mc-only-num-clients {
      type uint32;
      description
        "Number of MC-only clients for MGID";
    }
    leaf mc2uc-num-clients {
      type uint32;
      description
        "Number of MC-UC clients for MGID";
    }
    leaf mc2uc-num-deny-clients {
      type uint32;
      description
        "Number of MC-UC deny clients for MGID";
    }
    leaf mc2uc-num-pending-clients {
      type uint32;
      description
        "Number of MC-UC pending client for MGID";
    }
    leaf group {
      type inet:ip-address;
      description
        "Multicast group IP address";
    }
    list mcast-mgid-client-list {
      key "client-mac-addr";
      description
        "Multicast MGID client list";
      uses wireless-mcast-oper:mcast-mgid-client-entry;
    }
  }

  grouping mcast-flex-client-grp-info {
    description
      "Multicast flex client group information";
    leaf mcast-ip {
      type inet:ip-address;
      description
        "Multicast group IP";
    }
    leaf stream-name {
      type string;
      description
        "Stream name associated with multicast group";
    }
    leaf ap-mac {
      type yang:mac-address;
      description
        "AP MAC on which Multicast group is reported";
    }
    leaf is-direct {
      type boolean;
      description
        "Stream is Multicast-Direct or Multicast";
    }
  }

  grouping mcast-flex-client-info {
    description
      "Multicast flex client information";
    leaf client-mac {
      type yang:mac-address;
      description
        "Multicast flex client MAC address";
    }
    leaf vlan-id {
      type uint16;
      description
        "Multicast client's VLAN";
    }
    list flex-mcast-client-group {
      key "mcast-ip";
      description
        "Flex multicast client group";
      uses wireless-mcast-oper:mcast-flex-client-grp-info;
    }
  }

  grouping mcast-fabric-client-grp-info {
    description
      "Multicast fabric client group information";
    leaf mcast-ip {
      type inet:ip-address;
      description
        "Multicast IP";
    }
    leaf stream-name {
      type string;
      description
        "Stream name";
    }
    leaf ap-mac {
      type yang:mac-address;
      description
        "AP MAC on which Multicast group is reported";
    }
    leaf is-direct {
      type boolean;
      description
        "Stream is Multicast-Direct or Multicast";
    }
  }

  grouping mcast-fabric-client-info {
    description
      "Multicast fabric client information";
    leaf client-mac {
      type yang:mac-address;
      description
        "Multicast fabric client MAC address";
    }
    leaf vlan-id {
      type uint16;
      description
        "Multicast client's VLAN";
    }
    list fabric-mcast-client-group {
      key "mcast-ip";
      description
        "Fabric multicast client group";
      uses wireless-mcast-oper:mcast-fabric-client-grp-info;
    }
  }

  grouping vlan-l2-mgid-op {
    description
      "vlan L2 MGID";
    leaf vlan-index {
      type uint32;
      description
        "Multicast VLAN index";
    }
    leaf is-nonip-multicast-enabled {
      type boolean;
      description
        "Is non IP multicast enabled";
    }
    leaf is-broadcast-enable {
      type boolean;
      description
        "Is broadcast enabled";
    }
  }

  grouping st-rrc-history-client-record-data-op {
    description
      "RRC history client record data";
    leaf user-time-stamp {
      type yang:date-and-time;
      description
        "RRC history client user timestamp";
    }
    leaf client-mac {
      type yang:mac-address;
      description
        "RRC history client MAC address";
    }
    leaf qos {
      type uint16;
      description
        "QOS for the streaming";
    }
    leaf decision {
      type wireless-enum-types:media-stream-decision-status;
      description
        "RRC history Video-streaming decision";
    }
    leaf reason-code {
      type uint32;
      description
        "RRC decision's reason code";
    }
    leaf ap-mac {
      type yang:mac-address;
      description
        "AP's MAC address to which client was connected";
    }
    leaf vap-id {
      type uint16;
      description
        "Client's VAP ID";
    }
    leaf slot-id {
      type uint32;
      description
        "AP's Slot ID to which client was connected";
    }
    leaf cac-enabled {
      type uint32;
      description
        "RRC CAC is enabled or not";
    }
    leaf stream-name {
      type string;
      description
        "Stream name associated with multicast group";
    }
    leaf dst-ip-address {
      type inet:ip-address;
      description
        "Multicast group destination IP address";
    }
    leaf cfg-stream-bw {
      type uint32;
      units "Kbps";
      description
        "Configured max video bandwidth for the new stream";
    }
    leaf current-rate {
      type uint32;
      units "Mbps";
      description
        "Current data rate of the client requesting stream";
    }
    leaf video-pkt-size {
      type uint32;
      units "byte";
      description
        "Packet size for the new video stream";
    }
    leaf curr-video-util {
      type uint32;
      description
        "Current video utilization of AP radio";
    }
    leaf curr-voice-util {
      type uint32;
      description
        "Current voice utilization of AP radio";
    }
    leaf curr-channel-util {
      type uint32;
      description
        "Current channel utilization of AP radio";
    }
    leaf curr-queue-util {
      type uint32;
      description
        "Current queue utilization of AP radio";
    }
    leaf curr-video-pps {
      type uint32;
      description
        "Current video rate in packets per second of AP radio";
    }
    leaf video-delay-hist-severe {
      type uint32;
      description
        "Number of video packets with severe delay";
    }
    leaf video-pkt-loss-discard {
      type uint32;
      description
        "Video packet loss discarded by AP";
    }
    leaf video-pkt-loss-fail {
      type uint32;
      description
        "Video packet loss fail";
    }
    leaf num-video-streams {
      type uint32;
      description
        "Number of video streams";
    }
  }

  grouping st-mstream-client-entry-key {
    description
      "Media-stream client entries";
    leaf stream-name-str {
      type string;
      description
        "Name of the Media-stream";
    }
    leaf group-ip {
      type inet:ip-address;
      description
        "Multicast group IP address for this stream";
    }
    leaf cl-mac {
      type yang:mac-address;
      description
        "Media-stream client MAC address";
    }
  }

  grouping st-rrc-sr-radio-record-key {
    description
      "RRC stream radio record";
    leaf ap-mac {
      type yang:mac-address;
      description
        "AP MAC on which Multicast group is reported";
    }
    leaf slot-id {
      type uint32;
      description
        "Radio Slot ID";
    }
  }

  grouping st-groups {
    description
      "Groups";
    leaf dest-ip {
      type inet:ip-address;
      description
        "Multicast Group IP address";
    }
    leaf no-of-streams {
      type uint16;
      description
        "Number of streams for group";
    }
  }

  grouping st-rrc-sr-radio-record {
    description
      "RRC stream radio record";
    leaf radio-type {
      type uint32;
      description
        "Radio type of the stream";
    }
    leaf duplicated-band-width {
      type uint32;
      description
        "Duplicated bandwidth on this radio";
    }
    leaf last-re-rrc {
      type yang:date-and-time;
      description
        "Last Re-RRC timestamp for stream";
    }
    leaf number-of-admitted {
      type uint16;
      description
        "Number of admitted streams";
    }
    list rrc-groups-in-radio {
      key "dest-ip";
      description
        "RRC stream groups in radio";
      uses wireless-mcast-oper:st-groups;
    }
  }

  grouping st-rrc-stream-record-key {
    description
      "RRC stream records";
    leaf client-mac {
      type yang:mac-address;
      description
        "Client MAC address";
    }
    leaf dest-ip {
      type inet:ip-address;
      description
        "Multicast group destination IP address";
    }
  }

  grouping st-rrc-stream-record-time {
    description
      "RRC stream record time";
    leaf last-updated {
      type yang:date-and-time;
      description
        "Stream last updated by RRC";
    }
    leaf client-mac {
      type yang:mac-address;
      description
        "Client MAC address";
    }
    leaf dest-ip {
      type inet:ip-address;
      description
        "Multicast group destination IP address";
    }
  }

  grouping st-rrc-stream-record {
    description
      "RRC stream record";
    leaf vap-id {
      type uint32;
      description
        "VAP ID associated with stream";
    }
    leaf vlan {
      type uint32;
      description
        "VLAN ID associated with stream";
    }
    leaf wlan-id {
      type uint32;
      description
        "Client's WLAN ID associated with this stream";
    }
    leaf mgid {
      type uint16;
      description
        "MGID assigned to stream";
    }
    leaf priority {
      type uint16 {
        range "1 .. 8";
      }
      description
        "Stream's priority";
    }
    leaf rerrc-enable {
      type boolean;
      description
        "Is Re-RRC enable on this stream";
    }
    leaf rerrc-drop {
      type boolean;
      description
        "Re-RRC drop decision in case of violation of constraints";
    }
    leaf decision {
      type wireless-enum-types:media-stream-decision-status;
      description
        "RRC decision for stream";
    }
    leaf qos {
      type wireless-enum-types:media-stream-qos;
      description
        "Stream's QOS";
    }
    leaf kbps-bandwidth {
      type uint32 {
        range "1 .. 35000";
      }
      units "Kbps";
      description
        "Kbps bandwidth of stream";
    }
    leaf radio {
      type wireless-enum-types:enm-radio-type;
      description
        "Radio on which Multicast group is reported";
    }
    leaf stream-name {
      type string;
      description
        "Name of the stream";
    }
    leaf ap-name {
      type string;
      description
        "AP name on which Multicast group is reported";
    }
    leaf start-time {
      type yang:date-and-time;
      description
        "Stream start time";
    }
    leaf last-updated {
      type yang:date-and-time;
      description
        "Latest timestamp when Stream is updated by RRC";
    }
    container rrc-radio-record {
      description
        "RRC stream radio record";
      uses wireless-mcast-oper:st-rrc-sr-radio-record-key;
    }
  }

  container mcast-oper-data {
    config false;
    description
      "Wireless multicast operational data";
    list rrc-history-client-record-data {
      key "user-time-stamp";
      description
        "RRC history client record data";
      uses wireless-mcast-oper:st-rrc-history-client-record-data-op;
    }
    list rrc-sr-radio-record {
      key "ap-mac slot-id";
      description
        "RRC stream radio record";
      uses wireless-mcast-oper:st-rrc-sr-radio-record-key;
      uses wireless-mcast-oper:st-rrc-sr-radio-record;
    }
    list rrc-stream-record {
      key "stream-name-str group-ip cl-mac";
      description
        "RRC stream record";
      uses wireless-mcast-oper:st-rrc-stream-record;
      uses wireless-mcast-oper:st-mstream-client-entry-key;
      uses wireless-mcast-oper:st-rrc-stream-record-key;
    }
    list rrc-stream-admit-record {
      key "last-updated client-mac dest-ip";
      description
        "RRC stream admit record";
      uses wireless-mcast-oper:st-rrc-stream-record-time;
    }
    list rrc-stream-deny-record {
      key "last-updated client-mac dest-ip";
      description
        "RRC stream deny record";
      uses wireless-mcast-oper:st-rrc-stream-record-time;
    }
    list flex-mediastream-client-summary {
      key "client-mac";
      description
        "FLEX media-stream client data";
      uses wireless-mcast-oper:mcast-flex-client-info;
    }
    list fabric-media-stream-client-summary {
      key "client-mac";
      description
        "Fabric media-stream client summary";
      uses wireless-mcast-oper:mcast-fabric-client-info;
    }
    list mcast-mgid-info {
      key "mgid";
      description
        "Multicast MGID information";
      uses wireless-mcast-oper:mcast-mgid-entry;
    }
    list vlan-l2-mgid-op {
      key "vlan-index";
      description
        "VLAN L2 MGID";
      uses wireless-mcast-oper:vlan-l2-mgid-op;
    }
    list multicast-oper-data {
      key "ms-mac-address";
      description
        "Multicast Operational data";
      uses wireless-mcast-oper:ewlc-multicast-oper-data;
    }
  }
}
