module Cisco-IOS-XE-wireless-fabric-cfg {
  yang-version 1;
  namespace "http://cisco.com/ns/yang/Cisco-IOS-XE-wireless-fabric-cfg";
  prefix wireless-fabric-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing fabric mode configuration.
     Copyright (c) 2016-2020 by Cisco Systems, Inc.
     All rights reserved.";

  revision 2021-03-01 {
    description
      "- Add ASCII 32-126 and leading/trailing spaces restriction for fabric profile name,
       - Support 32 character length for control plane and fabric profile name";
    reference
      "4.0.0";
    cisco-semver:module-version "4.0.0";
  }
  revision 2020-07-01 {
    description
      "Add constraints to allow only ASCII 32-126 in fabric profile name, fabric name and control plane name";
    reference
      "3.3.0";
    cisco-semver:module-version "3.3.0";
  }
  revision 2019-05-01 {
    description
      "Added semantic version";
    reference
      "3.2.0";
    cisco-semver:module-version "3.2.0";
  }
  revision 2018-12-15 {
    description
      "Modifying ordering of elements in fabric VNID config";
    reference
      "3.1.0";
    cisco-semver:module-version "3.1.0";
  }
  revision 2018-03-08 {
    description
      "Add constraints to fabric profile and control plane";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enm-fabric-profile-encap-type {
    type enumeration {
      enum dont-use {
        value 0;
        description
          "Not a Valid Type";
      }
      enum fabric-encap-type-vxlan {
        value 1;
        description
          "VXLAN Encapsulation Type for Fabric data path";
      }
    }
    description
      "Enumeration of Encapsulation Types for Fabric Data Path";
  }

  grouping fabric {
    description
      "Fabric Profile details";
    leaf fabric-profile-name {
      type string {
        length "0..32";
        pattern '[!-~]([ -~]*[!-~])?';
      }
      description
        "Fabric Profile name";
    }
    leaf description {
      type string;
      default "";
      description
        "Fabric profile description";
    }
    leaf encap-type {
      type wireless-fabric-cfg:enm-fabric-profile-encap-type;
      default "fabric-encap-type-vxlan";
      description
        "Encapsulation type used in this profile";
    }
    leaf sgt-tag {
      type uint16 {
        range "2 .. 65519";
      }
      description
        "Group tag associated with the fabric profile";
    }
    leaf client-l2-vnid {
      type uint32 {
        range "0 .. 16777215";
      }
      default "0";
      description
        "Client Virtual Network ID";
    }
  }

  grouping fabric-name-vnid {
    description
      "Fabric Name Identifier";
    leaf name {
      type string {
        length "0..32";
        pattern '[ -~]+';
      }
      description
        "Fabric name for AP Join and VNID override";
    }
    leaf l2-vnid {
      type uint32 {
        range "0 .. 16777215";
      }
      description
        "VNID for Client subnet";
    }
    leaf l3-vnid {
      type uint32 {
        range "0 .. 16777215";
      }
      default "0";
      description
        "VNID for AP Subnet";
    }
    leaf netmask {
      type inet:ip-address;
      default "0.0.0.0";
      description
        "Network mask of AP subnet";
    }
    leaf network-ip {
      type inet:ip-address;
      description
        "IP address of AP Subnet";
    }
    leaf control-plane-name {
      type string {
        pattern '[ -~]+';
      }
      description
        "Fabric Control Plane name";
    }
  }

  grouping fabric-control-plane {
    description
      "Fabric Control Plane information";
    leaf control-plane-ip {
      type inet:ip-address;
      description
        "IP address of the Control Plane";
    }
    leaf psk-key {
      type string;
      default "";
      description
        "PSK associated with the Control Plane entity";
    }
    leaf psk-key-type {
      type wireless-enum-types:crypt-type;
      default "clear";
      description
        "PSK type for the Control Plane";
    }
  }

  grouping fabric-control-plane-name {
    description
      "Fabric Control Plane Name Configuration";
    leaf control-plane-name {
      type string {
        length "0..32";
        pattern '[ -~]+';
      }
      description
        "Fabric Control plane name";
    }
    leaf description {
      type string;
      description
        "Fabric Control plane description";
    }
    container fabric-control-plane-ip-configs {
      description
        "Fabric Control Plane Configuration";
      list fabric-control-plane-ip-config {
        key "control-plane-ip";
        max-elements 2;
        description
          "List of Fabric Control Plane Configuration objects";
        uses wireless-fabric-cfg:fabric-control-plane;
      }
    }
  }

  grouping fabric-cfg {
    description
      "Global Fabric Configuration";
    leaf fabric-enabled {
      type boolean;
      default "false";
      description
        "Global Fabric Enable";
    }
    container fabric-name-vnid-entries {
      description
        "Global VNID Name Configuration";
      list fabric-name-vnid-entry {
        key "name";
        unique "l2-vnid";
        description
          "Global VNID Name Configuration";
        uses wireless-fabric-cfg:fabric-name-vnid {
          refine "l2-vnid" {
            mandatory true;
          }
        }
      }
    }
  }

  container fabric-cfg-data {
    description
      "SDA Wireless Configuration Data";
    container fabric-profiles {
      description
        "Fabric Profiles";
      list fabric-profile {
        key "fabric-profile-name";
        max-elements 1024;
        description
          "List of Fabric Profiles";
        uses wireless-fabric-cfg:fabric;
      }
    }
    container fabric {
      presence "fabric";
      description
        "Fabric Specific configuration";
      uses wireless-fabric-cfg:fabric-cfg;
    }
    container fabric-controlplane-names {
      description
        "Fabric Control Plane Name configuration";
      list fabric-controlplane-name {
        key "control-plane-name";
        max-elements 16;
        description
          "List of Fabric Control Plane Name configuration objects";
        uses wireless-fabric-cfg:fabric-control-plane-name;
      }
    }
  }
}
