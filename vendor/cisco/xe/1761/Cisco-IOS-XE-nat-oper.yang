module Cisco-IOS-XE-nat-oper {
  yang-version 1;
  namespace "http://cisco.com/ns/yang/Cisco-IOS-XE-nat-oper";
  prefix nat-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NAT operational data.
     Copyright (c) 2017-2019 by Cisco Systems, Inc.
     All rights reserved.";

  revision 2019-05-01 {
    description
      "Added semantic version";
    reference
      "2.2.0";
    cisco-semver:module-version "2.2.0";
  }
  revision 2018-10-29 {
    description
      "Cleaned up spelling errors in descriptions.";
    reference
      "2.1.0";
    cisco-semver:module-version "2.1.0";
  }
  revision 2018-03-17 {
    description
      "The second generally available version";
    reference
      "2.0.0";
    cisco-semver:module-version "2.0.0";
  }
  revision 2017-11-01 {
    description
      "Initial revision";
    reference
      "1.0.0";
    cisco-semver:module-version "1.0.0";
  }

  grouping ip-nat-statistics {
    description
      "ip nat global statistics";
    leaf initialized {
      type boolean;
      description
        "Indicates if the NAT feature has been initialized";
    }
    leaf entries {
      type uint64;
      description
        "Total translations";
    }
    leaf statics {
      type uint64;
      description
        "Total static translations";
    }
    leaf-list statics-sorted {
      type uint64;
      max-elements 4;
      ordered-by user;
      description
        "Sorted static translations by domain";
    }
    leaf flows {
      type uint64;
      description
        "Total flows";
    }
    leaf insides {
      type uint64;
      description
        "Number of inside interfaces";
    }
    leaf outsides {
      type uint64;
      description
        "Number of outside interfaces";
    }
    leaf entry-timeouts {
      type uint64;
      description
        "Number of entries which timed out ";
    }
    leaf hits {
      type uint64;
      description
        "Successful searches with matching NAT session";
    }
    leaf misses {
      type uint64;
      description
        "Unsuccessful searches without matching NAT session";
    }
    leaf interrupt-switched {
      type uint64;
      description
        "Translated in interrupt switching";
    }
    leaf packets-punted {
      type uint64;
      description
        "Packets punted to process";
    }
    leaf frag-pak-count {
      type uint64;
      description
        "Counter for saved fragment packets";
    }
    leaf pool-stats-drop {
      type uint64;
      description
        "Dropped pool stats from platform";
    }
    leaf mapping-stats-drop {
      type uint64;
      description
        "Dropped mapping stats from platform";
    }
    leaf portlist-req-fail {
      type uint64;
      description
        "Counter for port block allocation request failures";
    }
    leaf ipalias-add-fail {
      type uint64;
      description
        "Counter for add IP alias fails drops";
    }
    leaf limit-entry-add-fail {
      type uint64;
      description
        "Counter for add limit entry fails drops";
    }
    leaf in2out-drops {
      type uint64;
      description
        "Counter for NAT inside->outside drops";
    }
    leaf out2in-drops {
      type uint64;
      description
        "Counter for NAT outside->inside drops";
    }
    leaf mib-addr-binds {
      type uint32;
      description
        "MIB counter for address binds";
    }
    leaf mib-addport-binds {
      type uint32;
      description
        "MIB counter for address port binds";
    }
  }

  grouping nat-translation-key {
    description
      "NAT translation key";
    leaf inside-local-addr {
      type inet:ipv4-address;
      description
        "Inside local address";
    }
    leaf outside-local-addr {
      type inet:ipv4-address;
      description
        "Outside local address";
    }
    leaf inside-local-port {
      type uint16;
      description
        "Inside local port";
    }
    leaf outside-local-port {
      type uint16;
      description
        "Outside local port";
    }
    leaf vrfid {
      type uint16;
      description
        "VRF ID";
    }
    leaf protocol {
      type uint8;
      description
        "Protocol";
    }
  }

  grouping nat-translation-param {
    description
      "NAT translation parameters";
    leaf inside-global-addr {
      type inet:ipv4-address;
      description
        "Inside global address";
    }
    leaf outside-global-addr {
      type inet:ipv4-address;
      description
        "Outside global address";
    }
    leaf inside-global-port {
      type uint16;
      description
        "Inside global port";
    }
    leaf outside-global-port {
      type uint16;
      description
        "Outside global port";
    }
    leaf flags {
      type uint32;
      description
        "Translation flags";
    }
    leaf application-type {
      type uint8;
      description
        "Application type";
    }
    leaf vrf-name {
      type string;
      description
        "Virtual Routing and Forwarding name";
    }
  }

  container nat-data {
    config false;
    description
      "NAT statistics";
    container ip-nat-statistics {
      presence "ip-nat-statistics";
      description
        "Global NAT statistics";
      uses nat-ios-xe-oper:ip-nat-statistics;
    }
    list ip-nat-translation {
      key "inside-local-addr outside-local-addr inside-local-port outside-local-port vrfid protocol";
      description
        "IP NAT translations";
      uses nat-ios-xe-oper:nat-translation-param;
      uses nat-ios-xe-oper:nat-translation-key;
    }
  }
}
