module Cisco-IOS-XE-power {
  namespace "http://cisco.com/ns/yang/Cisco-IOS-XE-power";
  prefix ios-power;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Power over Ethernet Yang (PoE) model.
     Copyright (c) 2016-2019 by Cisco Systems, Inc.
     All rights reserved.";

  revision 2021-07-01 {
    description
      "Modify Maximum power allowed on interface";
    cisco-semver:module-version "1.2.0";
  }
  revision 2019-11-01 {
    description
      "Added redundancy mode config";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-02-07 {
    description
      "Initial revision";
  }

  grouping config-power-grouping {
    container power {
      description
        "Power configure";
      container inline {
        description
          "Inline power configuration";
        presence "true";
        container consumption {
          description
            "Inline device power consumption";
          leaf default {
            description
              "Inline device power consumption";
            type uint16 {
              range "4000..15400";
            }
          }
        }
        container logging {
          description
            "Inline power logging messages";
          leaf global {
            description
              "Enable global inline power logging messages";
            type empty;
          }
        }
      }
      container redundancy-mode-config {
        description
          "Configure redundancy-mode of power supply";
        leaf combined {
          description
            "Enable global inline power logging messages";
          type empty;
        }
        container redundant {
          description
            "Either power supply can operate system";
          leaf n-plus-one {
            description
              "Redundant N+1";
            type uint8 {
              range "1..8";
            }
          }
          leaf-list n-plus-n {
            description
              "Redundant N+N";
            max-elements 8;
            type uint8 {
              range "1..8";
            }
          }
        }
      }
      leaf redundancy-mode {
        status deprecated;
        description
          "This node is deprecated and replace by redundancy-mode-config";
        type enumeration {
          enum combined;
          enum redundant;
        }
      }
      container supply {
        description
          "Power supply configuration";
        container autoLC {
          description
            "Automatic linecard power configuration";
          leaf-list priority {
            description
              "Set priority (highest to lowest) of auto linecard shutdown";
            max-elements 8;
            ordered-by user;
            type uint8 {
              range "1..10";
            }
          }
          leaf shutdown {
            description
              "Linecard auto shutdown control";
            type empty;
          }
        }
      }
      leaf max-min {
        type enumeration {
          enum max;
        }
      }
      leaf inputs {
        type uint8;
      }
    }
  }

  grouping config-interface-power-grouping {
    container power {
      container efficient-ethernet {
        description
          "Energy efficient ethernet Configuration";
        leaf auto {
          description
            "Enable automatic efficient ethernet on this interface";
          type empty;
        }
      }
      container inline {
        leaf consumption {
          type uint16 {
            range "4000..15400";
          }
        }
        choice auto-static-never {
          leaf never-choice {
            type empty;
          }
          container auto-choice {
            description
              "Automatically detect and power inline devices";
            presence "true";
            leaf max {
              description
                "Maximum power allowed on this interface";
              type int32 {
                range "4000..90000";
              }
            }
          }
          container static-choice {
            description
              "High priority inline power interface";
            presence "true";
            leaf max {
              description
                "Maximum power allowed on this interface";
              type int32 {
                range "4000..90000";
              }
            }
          }
        }
        leaf never {
          status deprecated;
          description
            "DEPRECATED, use auto-static-never";
          type empty;
        }
        container auto {
          status deprecated;
          description
            "DEPRECATED, Automatically detect power inline devices";
          presence "true";
          leaf max {
            status deprecated;
            description
              "Maximum power allowed on this interface";
            type int32 {
              range "4000..90000";
            }
          }
        }
        container four-pair {
          description
            "Four-pair PoE power";
          leaf forced {
            description
              "Enable Four-pair PoE without L2 negotiation";
            type empty;
          }
        }
        container police {
          description
            "Police the power drawn on the port";
          presence "true";
          container action {
            description
              "Action to be taken when power is overdrawn on the port";
            leaf errdisable {
              description
                "Error-disable the port when power is overdrawn on the port";
              type empty;
            }
            leaf log {
              description
                "Log a message when power is overdrawn on the port";
              type empty;
            }
          }
        }
        container port {
          description
            "Configure Port Power Level";
          leaf poe-ha {
            description
              "Apply poe-ha to the port";
            type empty;
          }
          leaf perpetual-poe-ha {
            description
              "Apply perpetual-poe-ha to the port";
            type empty;
          }
          leaf two-event {
            description
              "Enable 2-event classification";
            type empty;
          }
          leaf twox-mode {
            description
              "Apply 2X power level to the port";
            type empty;
          }
          leaf no-xtalk-wa {
            description
              "Disable MagJack XTalk workaround";
            type empty;
          }
          leaf priority {
            description
              "set power priority of the port";
            type enumeration {
              enum high;
              enum low;
            }
            default "low";
          }
        }
        container static {
          status deprecated;
          description
            "DEPRECATED, High priority inline power interface";
          presence "true";
          leaf max {
            status deprecated;
            description
              "Maximum power allowed on this interface";
            type int32 {
              range "4000..90000";
            }
          }
        }
      }
    }
  }

  augment "/ios:native" {
    uses config-power-grouping;
  }

  augment "/ios:native/ios:interface/ios:FastEthernet" {
    uses config-interface-power-grouping;
  }

  augment "/ios:native/ios:interface/ios:GigabitEthernet" {
    uses config-interface-power-grouping;
  }

  augment "/ios:native/ios:interface/ios:TenGigabitEthernet" {
    uses config-interface-power-grouping;
  }

  augment "/ios:native/ios:interface/ios:FiveGigabitEthernet" {
    uses config-interface-power-grouping;
  }

  augment "/ios:native/ios:interface/ios:AppGigabitEthernet" {
    uses config-interface-power-grouping;
  }

  augment "/ios:native/ios:interface/ios:TwentyFiveGigE" {
    uses config-interface-power-grouping;
  }

  augment "/ios:native/ios:interface/ios:TwoGigabitEthernet" {
    uses config-interface-power-grouping;
  }

  augment "/ios:native/ios:interface/ios:FortyGigabitEthernet" {
    uses config-interface-power-grouping;
  }

  augment "/ios:native/ios:interface/ios:HundredGigE" {
    uses config-interface-power-grouping;
  }
}
