module Cisco-IOS-XE-ospf-common {
  yang-version 1;
  namespace "http://cisco.com/ns/yang/Cisco-IOS-XE-ospf-common";
  prefix ospf-ios-xe-common;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring OSPF operational information.
     Copyright (c) 2020 by Cisco Systems, Inc.
     All rights reserved.";

  revision 2020-07-01 {
    description
      "Initial revision";
    reference
      "1.0.0";
    cisco-semver:module-version "1.0.0";
  }

  typedef ospfv3-address-family-types {
    type enumeration {
      enum ospfv3-address-family-unknown {
        value 0;
        description
          "OSPFv3 address family unknown";
      }
      enum ospfv3-address-family-ipv4 {
        value 1;
        description
          "OSPFv3 address family IPV4";
      }
      enum ospfv3-address-family-ipv6 {
        value 2;
        description
          "OSPFv3 address family IPV6";
      }
    }
    description
      "Address Family type";
  }

  typedef ospfv3-network-type {
    type enumeration {
      enum unknown {
        value 0;
        description
          "OSPFv3 network unknown";
      }
      enum broadcast {
        value 1;
        description
          "OSPFv3 broadcast multi-access network";
      }
      enum non-broadcast {
        value 2;
        description
          "OSPFv3 non broadcast multi-access (NBMA) network";
      }
      enum point-to-multipoint {
        value 3;
        description
          "OSPFv3 point-to-multipoint network";
      }
      enum point-to-point {
        value 4;
        description
          "OSPFv3 point-to-point network";
      }
      enum virtual-link {
        value 5;
        description
          "OSPFv3 virtual link network";
      }
      enum loopback-network {
        value 6;
        description
          "OSPFv3 loopback network";
      }
      enum sham-link {
        value 7;
        description
          "OSPFv3 sham link network";
      }
      enum manet {
        value 8;
        description
          "OSPFv3 manet network";
      }
    }
    description
      "OSPFv3 network type";
  }

  typedef ospfv3-if-state {
    type enumeration {
      enum down {
        value 0;
        description
          "The interface is in down state";
      }
      enum loopback {
        value 1;
        description
          "The interface is in loopback state";
      }
      enum waiting {
        value 2;
        description
          "The interface is in waiting state";
      }
      enum point-to-mpoint {
        value 3;
        description
          "The interface is in point-to-multipoint state";
      }
      enum point-to-point-state {
        value 4;
        description
          "The interface is in point-to-point state";
      }
      enum dr {
        value 5;
        description
          "The interface is in designated router state";
      }
      enum backup {
        value 6;
        description
          "The interface is in backup state";
      }
      enum other {
        value 7;
        description
          "The interface is in invalid state";
      }
    }
    description
      "OSPFv3 interface state type";
  }

  typedef ospfv3-nbr-state {
    type enumeration {
      enum nbr-down {
        value 0;
        description
          "Neighbor state down";
      }
      enum attempt {
        value 1;
        description
          "Neighbor attempt state";
      }
      enum init {
        value 2;
        description
          "Neighbor initial state";
      }
      enum two-way {
        value 3;
        description
          "Neighbor 2-way state";
      }
      enum exchange-start {
        value 4;
        description
          "Neighbor exchange start state";
      }
      enum exchange {
        value 5;
        description
          "Neighbor exchange state";
      }
      enum loading {
        value 6;
        description
          "Neighbor loading state";
      }
      enum full {
        value 7;
        description
          "Neighbor full state";
      }
      enum other-state {
        value 8;
        description
          "Neighbor is in invalid state";
      }
    }
    description
      "OSPFv3 neighbor state type";
  }
}
