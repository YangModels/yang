module Cisco-IOS-XE-ethernet-deviation {
  namespace "http://cisco.com/ns/yang/Cisco-IOS-XE-ethernet-deviation";
  prefix ios-ethernet-d;

  import Cisco-IOS-XE-native {
    prefix ios;
  }
  import Cisco-IOS-XE-ethernet {
    prefix ios-ethernet;
  }
  import cisco-semver {
    prefix cisco-semver;
  }

  organization
    "Cisco Systems";
  description
    "Cisco XE Native Deviation YANG module for IOS
     Copyright (c) 2020 by Cisco Systems, Inc.
     All rights reserved.";

  revision 2020-11-01 {
    description
      "Added ethernet mtu deviation";
    cisco-semver:module-version "1.0.0";
  }

  deviation "/ios:native/ios:interface/ios:Ethernet/ios:mtu" {
    deviate replace {
      type uint16 {
        range "100..1800";
      }
    }
  }
}
