module cisco-xe-openconfig-network-instance-deviation {
  namespace "http://cisco.com/ns/yang/cisco-xe-openconfig-network-instance-deviation";
  prefix oc-netinst-devs;

  import openconfig-network-instance {
    prefix oc-netinst;
  }
  import Cisco-IOS-XE-types {
    prefix ios-types;
  }

  organization
    "Cisco Systems, Inc.";
  contact
    " Cisco Systems, Inc.
     Customer Service
     
     Postal: 170 W Tasman Drive
     San Jose, CA 95134
     
     Tel: +1 1800 553-NETS
     
     E-mail: cs-yang@cisco.com";
  description
    "This module defines deviation statements for openconfig-network-instance
     module.";

  revision 2017-02-14 {
    description
      "Initial Revision";
    reference
      "RFC 6020: YANG - A Data Modeling Language for the
       Network Configuration Protocol (NETCONF)";
  }

  deviation "/oc-netinst:network-instances/oc-netinst:network-instance/oc-netinst:fdb" {
    deviate not-supported;
    description
      "Not supported 16.6 release.";
  }
  deviation "/oc-netinst:network-instances/oc-netinst:network-instance/oc-netinst:encapsulation" {
    deviate not-supported;
    description
      "Not supported 16.6 release.";
  }
  deviation "/oc-netinst:network-instances/oc-netinst:network-instance/oc-netinst:connection-points" {
    deviate not-supported;
    description
      "Not supported 16.6 release.";
  }
  deviation "/oc-netinst:network-instances/oc-netinst:network-instance/oc-netinst:vlans" {
    deviate not-supported;
    description
      "Not supported 16.6 release.";
  }
  deviation "/oc-netinst:network-instances/oc-netinst:network-instance/oc-netinst:config/oc-netinst:enabled" {
    deviate not-supported;
    description
      "Not supported 16.6 release.";
  }
  deviation "/oc-netinst:network-instances/oc-netinst:network-instance/oc-netinst:config/oc-netinst:router-id" {
    deviate not-supported;
    description
      "Not supported 16.6 release.";
  }
  deviation "/oc-netinst:network-instances/oc-netinst:network-instance/oc-netinst:inter-instance-policies" {
    deviate not-supported;
    description
      "Not supported 16.6 release.";
  }
  deviation "/oc-netinst:network-instances/oc-netinst:network-instance/oc-netinst:interfaces/oc-netinst:interface/oc-netinst:config/oc-netinst:associated-address-families" {
    deviate not-supported;
    description
      "Address families are not configurable at interface level in XE";
  }
  deviation "/oc-netinst:network-instances/oc-netinst:network-instance/oc-netinst:protocols/oc-netinst:protocol/oc-netinst:config/oc-netinst:enabled" {
    deviate not-supported;
    description
      "Not supported 16.6 release.";
  }
  deviation "/oc-netinst:network-instances/oc-netinst:network-instance/oc-netinst:protocols/oc-netinst:protocol/oc-netinst:static-routes/oc-netinst:static/oc-netinst:next-hops/oc-netinst:next-hop/oc-netinst:config/oc-netinst:recurse" {
    deviate not-supported;
    description
      "Not supported 16.6 release.";
  }
  deviation "/oc-netinst:network-instances/oc-netinst:network-instance/oc-netinst:config/oc-netinst:route-distinguisher" {
    deviate replace {
      type ios-types:cisco-route-distinguisher;
    }
    description
      "Replace OC type with Cisco type that supports expanded range of values";
  }
  deviation "/oc-netinst:network-instances/oc-netinst:network-instance/oc-netinst:protocols/oc-netinst:protocol/oc-netinst:local-aggregates" {
    deviate not-supported;
    description
      "Not supported in IOS-XE";
  }
}
