module Cisco-IOS-XE-digitalio {
  namespace "http://cisco.com/ns/yang/Cisco-IOS-XE-digitalio";
  prefix ios-digitalio;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Digital IO Yang model.
     Copyright (c) 2019-2020 by Cisco Systems, Inc.
     All rights reserved.";

  revision 2020-03-01 {
    description
      "- Initial revision";
    cisco-semver:module-version "1.0.0";
  }

  grouping config-alarm-grouping {
    container alarm {
      description
        "Configure the system alarm port settings";
      container contact {
        description
          "Configure the system alarm contact (digital I/O)";
        leaf attach-to-iox {
          description
            "Enable Digital IO Ports access from IOX";
          type empty;
        }
        list port {
          key "id";
          leaf id {
            description
              "Alarm contact number (0: Alarm port, 1-4: Digital I/O)";
            type uint8 {
              range "0..4";
            }
          }
          leaf application {
            description
              "Set the alarm application";
            when "../enable and ((../id > 0) and not (../output))";
            type enumeration {
              enum "dry";
              enum "wet";
            }
          }
          leaf description {
            description
              "Alarm description string";
            when "../enable";
            type string {
              length "1..200";
            }
          }
          leaf enable {
            description
              "Enable the alarm/digital IO port";
            when "../id = 0 or (../id > 0 and not (../../attach-to-iox))";
            type empty;
          }
          leaf severity {
            description
              "Set the severity level reported";
            when
              "../enable and (../id = 0 or
               (../id > 0 and not (../output)))";
            type enumeration {
              enum "critical";
              enum "major";
              enum "minor";
              enum "none";
            }
          }
          leaf threshold {
            description
              "Threshold in mv (1600 as default)";
            when "../enable and (../id > 0) and not (../output)";
            type uint16 {
              range "1600..2700";
            }
          }
          leaf trigger {
            description
              "Set the alarm trigger";
            when
              "../enable and ((../id = 0) or 
               ((../id > 0) and not (../output)))";
            type enumeration {
              enum "open";
              enum "closed";
            }
          }
          container output {
            description
              "Set mode as output";
            presence "alarm output";
            when "../enable and (../id > 0)";
            choice output-type {
              case value {
                leaf value {
                  description
                    "output value (1 for High, 0 for Low)";
                  type uint8 {
                    range "0..1";
                  }
                }
              }
              case relay {
                container relay {
                  description
                    "Configure the system alarm relay (output)";
                  choice relay-type {
                    case input-alarm {
                      leaf input-alarm {
                        description
                          "External input alarm number";
                        type uint8 {
                          range "0..4";
                        }
                      }
                    }
                    case temperature {
                      leaf temperature {
                        description
                          "Temperature alarm";
                        type enumeration {
                          enum "critical";
                          enum "major";
                          enum "minor";
                        }
                      }
                    }
                  }
                }
              }
            }
          }
        }
      }
    }
  }

  augment "/ios:native" {
    uses config-alarm-grouping;
  }
}
