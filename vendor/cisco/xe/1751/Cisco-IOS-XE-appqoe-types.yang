module Cisco-IOS-XE-appqoe-types {
  yang-version 1;
  namespace "http://cisco.com/ns/yang/Cisco-IOS-XE-appqoe-types";
  prefix appqoe-types-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service-insertion operational data.
     Copyright (c) 2020 by Cisco Systems, Inc.
     All rights reserved.";

  revision 2020-11-01 {
    description
      "Initial revision";
    reference
      "1.0.0";
    cisco-semver:module-version "1.0.0";
  }

  typedef appqoe-sn-status {
    type enumeration {
      enum sn-status-down {
        value 0;
        description
          "Service node status is down";
      }
      enum sn-status-green {
        value 1;
        description
          "Service node status is green";
      }
      enum sn-status-yellow {
        value 2;
        description
          "Service node status is yellow";
      }
      enum sn-status-red {
        value 3;
        description
          "Service node status is red";
      }
    }
    description
      "Service node status";
  }

  typedef appqoe-device-mode {
    type enumeration {
      enum device-mode-cedge-sdwan {
        value 0;
        description
          "Device mode is not configured";
      }
      enum device-mode-service-node {
        value 1;
        description
          "Device mode is service node";
      }
      enum device-mode-integrated-service-node {
        value 2;
        description
          "Device mode is integrated service node";
      }
      enum device-mode-service-controller {
        value 3;
        description
          "Device mode is service controller";
      }
    }
    description
      "Device mode state";
  }
}
