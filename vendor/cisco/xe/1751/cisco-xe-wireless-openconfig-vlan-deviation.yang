module cisco-xe-wireless-openconfig-vlan-deviation {
  namespace "http://cisco.com/ns/yang/cisco-xe-wireless-openconfig-vlan-deviation";
  prefix cisco-xe-wireless-oc-vlan-devs;

  import openconfig-interfaces {
    prefix oc-if;
  }
  import openconfig-vlan {
    prefix oc-vlan;
  }
  import cisco-xe-openconfig-vlan-ext {
    prefix oc-vlan-ext;
  }

  organization
    "Cisco Systems";
  description
    "Deviation YANG module for Openconfig-vlan for IOS XE Wireless devices
     Copyright (c) 2018-2019 by Cisco Systems, Inc.
     All rights reserved.";

  revision 2019-04-24 {
    description
      "Enable openconfig-vlan";
  }
  revision 2018-12-12 {
    description
      "Initial revision";
  }

  deviation "/oc-vlan:vlans/oc-vlan-ext:default-vlan/oc-vlan-ext:ports/oc-vlan-ext:subinterface" {
    deviate not-supported;
  }
  deviation "/oc-if:interfaces/oc-if:interface/oc-if:subinterfaces/oc-if:subinterface/oc-vlan:vlan" {
    deviate not-supported;
  }
}
