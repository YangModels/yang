module Cisco-IOS-XE-icmp {
  namespace "http://cisco.com/ns/yang/Cisco-IOS-XE-icmp";
  prefix ios-icmp;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Internet Control Message Protocol (ICMP) Yang model.
     Copyright (c) 2016-2020 by Cisco Systems, Inc.
     All rights reserved.";

  revision 2021-03-01 {
    description
      "- Added default true for 'ip unreachables' and 'ipv6 unreachables' CLI";
  }
  revision 2020-11-01 {
    description
      "- Added support for 'ip icmp od-length enable' CLI";
  }
  revision 2020-03-01 {
    description
      "Take out redirect leaf from parent leaf";
  }
  revision 2019-11-01 {
    description
      "Added ICMP config under IPv6";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2018-08-29 {
    description
      "add config-interface-ip-icmp-grouping use for interface Multilink and Cellular";
  }
  revision 2017-11-27 {
    description
      "Added Change 25GE name";
  }
  revision 2017-11-14 {
    description
      "This revision has changes for new 40 and 100 GE interface addition";
  }
  revision 2017-09-14 {
    description
      "This revision has changes for new 2gig interface addition";
  }
  revision 2017-08-16 {
    description
      "This revision has changes for new 5gig and 25gig interfaces addition";
  }
  revision 2017-06-12 {
    description
      "add config-interface-ip-icmp-grouping use for interface Vlan";
  }
  revision 2017-02-07 {
    description
      "Initial revision";
  }

  grouping config-icmp-grouping {
    container icmp {
      description
        "ICMP options";
      container od-length {
        description
          "Original Datagram Length";
        leaf enable {
          description
            "Enable Feature";
          default "true";
          type boolean;
        }
      }
      container rate-limit {
        description
          "rate limit ICMP messages generated";
        container unreachable {
          description
            "ICMP type 3, Destination Unreachable";
          leaf time {
            description
              "Once per milliseconds";
            type uint32 {
              range "1..4294967295";
            }
            default "500";
          }
          container DF {
            description
              "code 4, fragmentation needed and DF set";
            leaf time {
              description
                "Once per milliseconds";
              type uint32 {
                range "1..4294967295";
              }
            }
          }
          container log {
            description
              "log message if rate limiting is excessive";
            presence "true";
            leaf number-unreachables {
              description
                "number of unreachables within interval to trigger a message";
              type uint32;
            }
            leaf log-message {
              description
                "log message once per milliseconds";
              type uint32 {
                range "10000..4294967295";
              }
            }
          }
        }
        leaf redirect {
          description
            "description";
          status obsolete;
          type enumeration {
            enum "host";
            enum "subnet";
          }
        }
      }
      leaf redirect {
        description
          "description";
        type enumeration {
          enum "host";
          enum "subnet";
        }
      }
    }
  }

  grouping config-interface-ip-icmp-grouping {
    leaf unreachables {
      description
        "Enable sending ICMP Unreachable messages";
      type boolean;
      default "true";
    }
  }

  augment "/ios:native/ios:ip" {
    uses config-icmp-grouping;
  }
  augment "/ios:native/ios:interface/ios:FastEthernet/ios:ip" {
    uses config-interface-ip-icmp-grouping;
  }
  augment "/ios:native/ios:interface/ios:GigabitEthernet/ios:ip" {
    uses config-interface-ip-icmp-grouping;
  }
  augment "/ios:native/ios:interface/ios:TenGigabitEthernet/ios:ip" {
    uses config-interface-ip-icmp-grouping;
  }
  augment "/ios:native/ios:interface/ios:FiveGigabitEthernet/ios:ip" {
    uses config-interface-ip-icmp-grouping;
  }
  augment "/ios:native/ios:interface/ios:AppGigabitEthernet/ios:ip" {
    uses config-interface-ip-icmp-grouping;
  }
  augment "/ios:native/ios:interface/ios:TwentyFiveGigE/ios:ip" {
    uses config-interface-ip-icmp-grouping;
  }
  augment "/ios:native/ios:interface/ios:TwoGigabitEthernet/ios:ip" {
    uses config-interface-ip-icmp-grouping;
  }
  augment "/ios:native/ios:interface/ios:FortyGigabitEthernet/ios:ip" {
    uses config-interface-ip-icmp-grouping;
  }
  augment "/ios:native/ios:interface/ios:HundredGigE/ios:ip" {
    uses config-interface-ip-icmp-grouping;
  }
  augment "/ios:native/ios:interface/ios:Multilink/ios:ip" {
    uses config-interface-ip-icmp-grouping;
  }
  augment "/ios:native/ios:interface/ios:Cellular/ios:ip" {
    uses config-interface-ip-icmp-grouping;
  }
  augment "/ios:native/ios:interface/ios:Tunnel/ios:ip" {
    uses config-interface-ip-icmp-grouping;
  }
  augment "/ios:native/ios:interface/ios:Vlan/ios:ip" {
    uses config-interface-ip-icmp-grouping;
  }
  augment "/ios:native/ios:interface/ios:Port-channel/ios:ip" {
    uses config-interface-ip-icmp-grouping;
  }
  augment "/ios:native/ios:interface/ios:BDI/ios:ip" {
    uses config-interface-ip-icmp-grouping;
  }
  augment "/ios:native/ios:interface/ios:Dialer/ios:ip" {
    uses config-interface-ip-icmp-grouping;
  }
  augment "/ios:native/ios:interface/ios:AppNav-Compress/ios:ip" {
    uses config-interface-ip-icmp-grouping;
  }
  augment "/ios:native/ios:interface/ios:AppNav-UnCompress/ios:ip" {
    uses config-interface-ip-icmp-grouping;
  }
  augment "/ios:native/ios:interface/ios:ATM/ios:ip" {
    uses config-interface-ip-icmp-grouping;
  }
  augment "/ios:native/ios:interface/ios:Embedded-Service-Engine/ios:ip" {
    uses config-interface-ip-icmp-grouping;
  }
  augment "/ios:native/ios:interface/ios:Ethernet/ios:ip" {
    uses config-interface-ip-icmp-grouping;
  }
  augment "/ios:native/ios:interface/ios:ucse/ios:ip" {
    uses config-interface-ip-icmp-grouping;
  }
  augment "/ios:native/ios:interface/ios:Ethernet-Internal/ios:ip" {
    uses config-interface-ip-icmp-grouping;
  }
  augment "/ios:native/ios:interface/ios:Service-Engine/ios:ip" {
    uses config-interface-ip-icmp-grouping;
  }
  augment "/ios:native/ios:interface/ios:TwentyFiveGigabitEthernet/ios:ip" {
    status obsolete;
    uses config-interface-ip-icmp-grouping;
  }
  augment "/ios:native/ios:interface/ios:Loopback/ios:ip" {
    uses config-interface-ip-icmp-grouping;
  }
  augment "/ios:native/ios:interface/ios:LISP/ios:ip" {
    uses config-interface-ip-icmp-grouping;
  }
  augment "/ios:native/ios:interface/ios:nve/ios:ip" {
    uses config-interface-ip-icmp-grouping;
  }
  augment "/ios:native/ios:interface/ios:SM/ios:ip" {
    uses config-interface-ip-icmp-grouping;
  }
  augment "/ios:native/ios:interface/ios:GMPLS/ios:ip" {
    uses config-interface-ip-icmp-grouping;
  }
  augment "/ios:native/ios:interface/ios:Group-Async/ios:ip" {
    uses config-interface-ip-icmp-grouping;
  }
  augment "/ios:native/ios:interface/ios:Serial/ios:ip" {
    uses config-interface-ip-icmp-grouping;
  }
  augment "/ios:native/ios:interface/ios:Async/ios:ip" {
    uses config-interface-ip-icmp-grouping;
  }
  augment "/ios:native/ios:interface/ios:Virtual-Template/ios:ip" {
    uses config-interface-ip-icmp-grouping;
  }
  augment "/ios:native/ios:interface/ios:Virtual-PPP/ios:ip" {
    uses config-interface-ip-icmp-grouping;
  }
  augment "/ios:native/ios:interface/ios:VirtualPortGroup/ios:ip" {
    uses config-interface-ip-icmp-grouping;
  }
  augment "/ios:native/ios:interface/ios:vasileft/ios:ip" {
    uses config-interface-ip-icmp-grouping;
  }
  augment "/ios:native/ios:interface/ios:vasiright/ios:ip" {
    uses config-interface-ip-icmp-grouping;
  }
  augment "/ios:native/ios:interface/ios:Vif/ios:ip" {
    uses config-interface-ip-icmp-grouping;
  }
  augment "/ios:native/ios:interface/ios:Wlan-GigabitEthernet/ios:ip" {
    uses config-interface-ip-icmp-grouping;
  }
  augment "/ios:native/ios:interface/ios:BD-VIF/ios:ip" {
    uses config-interface-ip-icmp-grouping;
  }
  augment "/ios:native/ios:interface/ios:MFR/ios:ip" {
    uses config-interface-ip-icmp-grouping;
  }
  augment "/ios:native/ios:interface/ios:ATM-subinterface/ios:ATM/ios:ip" {
    uses config-interface-ip-icmp-grouping;
  }
  augment "/ios:native/ios:interface/ios:LISP-subinterface/ios:LISP/ios:ip" {
    uses config-interface-ip-icmp-grouping;
  }
  augment "/ios:native/ios:interface/ios:Port-channel-subinterface/ios:Port-channel/ios:ip" {
    uses config-interface-ip-icmp-grouping;
  }
  augment "/ios:native/ios:interface/ios:Serial-subinterface/ios:Serial/ios:ip" {
    uses config-interface-ip-icmp-grouping;
  }
  augment "/ios:native/ios:interface/ios:MFR-subinterface/ios:MFR/ios:ip" {
    uses config-interface-ip-icmp-grouping;
  }
  augment "/ios:native/ios:interface/ios:FastEthernet/ios:ipv6" {
    uses config-interface-ip-icmp-grouping;
  }
  augment "/ios:native/ios:interface/ios:GigabitEthernet/ios:ipv6" {
    uses config-interface-ip-icmp-grouping;
  }
  augment "/ios:native/ios:interface/ios:TenGigabitEthernet/ios:ipv6" {
    uses config-interface-ip-icmp-grouping;
  }
  augment "/ios:native/ios:interface/ios:FiveGigabitEthernet/ios:ipv6" {
    uses config-interface-ip-icmp-grouping;
  }
  augment "/ios:native/ios:interface/ios:AppGigabitEthernet/ios:ipv6" {
    uses config-interface-ip-icmp-grouping;
  }
  augment "/ios:native/ios:interface/ios:TwentyFiveGigE/ios:ipv6" {
    uses config-interface-ip-icmp-grouping;
  }
  augment "/ios:native/ios:interface/ios:TwoGigabitEthernet/ios:ipv6" {
    uses config-interface-ip-icmp-grouping;
  }
  augment "/ios:native/ios:interface/ios:FortyGigabitEthernet/ios:ipv6" {
    uses config-interface-ip-icmp-grouping;
  }
  augment "/ios:native/ios:interface/ios:HundredGigE/ios:ipv6" {
    uses config-interface-ip-icmp-grouping;
  }
  augment "/ios:native/ios:interface/ios:Tunnel/ios:ipv6" {
    uses config-interface-ip-icmp-grouping;
  }
  augment "/ios:native/ios:interface/ios:Port-channel/ios:ipv6" {
    uses config-interface-ip-icmp-grouping;
  }
  augment "/ios:native/ios:interface/ios:BDI/ios:ipv6" {
    uses config-interface-ip-icmp-grouping;
  }
  augment "/ios:native/ios:interface/ios:Dialer/ios:ipv6" {
    uses config-interface-ip-icmp-grouping;
  }
  augment "/ios:native/ios:interface/ios:AppNav-Compress/ios:ipv6" {
    uses config-interface-ip-icmp-grouping;
  }
  augment "/ios:native/ios:interface/ios:AppNav-UnCompress/ios:ipv6" {
    uses config-interface-ip-icmp-grouping;
  }
  augment "/ios:native/ios:interface/ios:ATM/ios:ipv6" {
    uses config-interface-ip-icmp-grouping;
  }
  augment "/ios:native/ios:interface/ios:Embedded-Service-Engine/ios:ipv6" {
    uses config-interface-ip-icmp-grouping;
  }
  augment "/ios:native/ios:interface/ios:Ethernet/ios:ipv6" {
    uses config-interface-ip-icmp-grouping;
  }
  augment "/ios:native/ios:interface/ios:ucse/ios:ipv6" {
    uses config-interface-ip-icmp-grouping;
  }
  augment "/ios:native/ios:interface/ios:Ethernet-Internal/ios:ipv6" {
    uses config-interface-ip-icmp-grouping;
  }
  augment "/ios:native/ios:interface/ios:Service-Engine/ios:ipv6" {
    uses config-interface-ip-icmp-grouping;
  }
  augment "/ios:native/ios:interface/ios:TwentyFiveGigabitEthernet/ios:ipv6" {
    status obsolete;
    uses config-interface-ip-icmp-grouping;
  }
  augment "/ios:native/ios:interface/ios:Loopback/ios:ipv6" {
    uses config-interface-ip-icmp-grouping;
  }
  augment "/ios:native/ios:interface/ios:LISP/ios:ipv6" {
    uses config-interface-ip-icmp-grouping;
  }
  augment "/ios:native/ios:interface/ios:nve/ios:ipv6" {
    uses config-interface-ip-icmp-grouping;
  }
  augment "/ios:native/ios:interface/ios:SM/ios:ipv6" {
    uses config-interface-ip-icmp-grouping;
  }
  augment "/ios:native/ios:interface/ios:Cellular/ios:ipv6" {
    uses config-interface-ip-icmp-grouping;
  }
  augment "/ios:native/ios:interface/ios:Vlan/ios:ipv6" {
    uses config-interface-ip-icmp-grouping;
  }
  augment "/ios:native/ios:interface/ios:GMPLS/ios:ipv6" {
    uses config-interface-ip-icmp-grouping;
  }
  augment "/ios:native/ios:interface/ios:Group-Async/ios:ipv6" {
    uses config-interface-ip-icmp-grouping;
  }
  augment "/ios:native/ios:interface/ios:Serial/ios:ipv6" {
    uses config-interface-ip-icmp-grouping;
  }
  augment "/ios:native/ios:interface/ios:Async/ios:ipv6" {
    uses config-interface-ip-icmp-grouping;
  }
  augment "/ios:native/ios:interface/ios:Virtual-Template/ios:ipv6" {
    uses config-interface-ip-icmp-grouping;
  }
  augment "/ios:native/ios:interface/ios:Virtual-PPP/ios:ipv6" {
    uses config-interface-ip-icmp-grouping;
  }
  augment "/ios:native/ios:interface/ios:VirtualPortGroup/ios:ipv6" {
    uses config-interface-ip-icmp-grouping;
  }
  augment "/ios:native/ios:interface/ios:vasileft/ios:ipv6" {
    uses config-interface-ip-icmp-grouping;
  }
  augment "/ios:native/ios:interface/ios:vasiright/ios:ipv6" {
    uses config-interface-ip-icmp-grouping;
  }
  augment "/ios:native/ios:interface/ios:Vif/ios:ipv6" {
    uses config-interface-ip-icmp-grouping;
  }
  augment "/ios:native/ios:interface/ios:Wlan-GigabitEthernet/ios:ipv6" {
    uses config-interface-ip-icmp-grouping;
  }
  augment "/ios:native/ios:interface/ios:BD-VIF/ios:ipv6" {
    uses config-interface-ip-icmp-grouping;
  }
  augment "/ios:native/ios:interface/ios:MFR/ios:ipv6" {
    uses config-interface-ip-icmp-grouping;
  }
  augment "/ios:native/ios:interface/ios:ATM-subinterface/ios:ATM/ios:ipv6" {
    uses config-interface-ip-icmp-grouping;
  }
  augment "/ios:native/ios:interface/ios:LISP-subinterface/ios:LISP/ios:ipv6" {
    uses config-interface-ip-icmp-grouping;
  }
  augment "/ios:native/ios:interface/ios:Port-channel-subinterface/ios:Port-channel/ios:ipv6" {
    uses config-interface-ip-icmp-grouping;
  }
  augment "/ios:native/ios:interface/ios:Serial-subinterface/ios:Serial/ios:ipv6" {
    uses config-interface-ip-icmp-grouping;
  }
  augment "/ios:native/ios:interface/ios:MFR-subinterface/ios:MFR/ios:ipv6" {
    uses config-interface-ip-icmp-grouping;
  }
  augment "/ios:native/ios:interface/ios:Multilink/ios:ipv6" {
    uses config-interface-ip-icmp-grouping;
  }
}
