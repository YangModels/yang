module cisco-xe-cbr-openconfig-vlan-deviation {
  namespace "http://cisco.com/ns/yang/cisco-xe-cbr-openconfig-vlan-deviation";
  prefix cisco-xe-cbr-oc-vlan-devs;

  import openconfig-interfaces {
    prefix oc-if;
  }
  import openconfig-vlan {
    prefix oc-vlan;
  }

  organization
    "Cisco Systems";
  description
    "Deviation YANG module for Openconfig-vlan model for IOS XE Cable platforms
     Copyright (c) 2018 by Cisco Systems, Inc.
     All rights reserved.";

  revision 2018-12-12 {
    description
      "Initial revision";
  }

  deviation "/oc-vlan:vlans" {
    deviate not-supported;
  }
  deviation "/oc-if:interfaces/oc-if:interface/oc-if:subinterfaces/oc-if:subinterface/oc-vlan:vlan" {
    deviate not-supported;
  }
}
