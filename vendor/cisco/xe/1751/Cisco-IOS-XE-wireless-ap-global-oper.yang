module Cisco-IOS-XE-wireless-ap-global-oper {
  yang-version 1;
  namespace "http://cisco.com/ns/yang/Cisco-IOS-XE-wireless-ap-global-oper";
  prefix wireless-ap-global-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains access point operational data aggregated across wireless processes.
     Copyright (c) 2020 by Cisco Systems, Inc.
     All rights reserved.";

  revision 2021-03-01 {
    description
      "Initial revision";
    reference
      "1.0.0";
    cisco-semver:module-version "1.0.0";
  }

  grouping predownload-stats {
    description
      "AP image predownload statistics";
    leaf num-initiated {
      type uint32;
      description
        "Total number of AP predownload initiated";
    }
    leaf num-in-progress {
      type uint32;
      description
        "Total number of AP predownload in-progress";
    }
    leaf num-complete {
      type uint32;
      description
        "Total number of AP predownload completed";
    }
    leaf num-unsupported {
      type uint32;
      description
        "Total number of AP predownload not supported";
    }
    leaf num-failed {
      type uint32;
      description
        "Total number of AP predownload failed";
    }
    leaf is-predownload-in-progress {
      type boolean;
      description
        "Status of AP image predownload";
    }
    leaf num-total {
      type uint32;
      description
        "Total number of AP connected";
    }
  }

  grouping global-ap-stats {
    description
      "AP aggregated statistics";
    container predownload-stats {
      description
        "AP predownload statistics";
      uses wireless-ap-global-oper:predownload-stats;
    }
    leaf downloads-in-progress {
      type uint32;
      description
        "Total number of APs download in-progress";
    }
    leaf downloads-complete {
      type uint32;
      description
        "Total number of APs download completed";
    }
    container wlc-predownload-stats {
      description
        "Wireless controller predownload statistics";
      uses wireless-ap-global-oper:predownload-stats;
    }
  }

  container ap-global-oper-data {
    config false;
    description
      "Root container for AP operational data aggregated across wireless processes";
    container ap-img-predownload-stats {
      presence "ap-img-predownload-stats";
      description
        "AP image predownload stats";
      uses wireless-ap-global-oper:global-ap-stats;
    }
  }
}
