module cisco-xe-routing-openconfig-system-management-deviation {
  namespace "http://cisco.com/ns/cisco-xe-routing-openconfig-system-management-deviation";
  prefix oc-routing-system-management-devs;

  import openconfig-system {
    prefix oc-sys;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module defines deviation statements for openconfig-system module for IOS XE Routing devices.";

  revision 2019-07-01 {
    description
      "Initial Revision";
  }

  deviation "/oc-sys:system/oc-sys:grpc-server" {
    deviate not-supported;
    description
      "Currently not supported";
  }
}
