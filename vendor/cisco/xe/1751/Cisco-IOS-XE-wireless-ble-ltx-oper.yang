module Cisco-IOS-XE-wireless-ble-ltx-oper {
  yang-version 1;
  namespace "http://cisco.com/ns/yang/Cisco-IOS-XE-wireless-ble-ltx-oper";
  prefix wireless-ble-ltx-oper;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless Bluetooth Low Energy (BLE) LTX operational data.
     Copyright (c) 2019-2020 by Cisco Systems, Inc.
     All rights reserved.";

  revision 2020-07-01 {
    description
      "Initial revision";
    reference
      "1.0.0";
    cisco-semver:module-version "1.0.0";
  }

  grouping ble-ltx-report {
    description
      "Status of the AP BLE report";
    leaf last-report-time {
      when "../valid = 'true'";
      type yang:date-and-time;
      description
        "Timestamp of the last AP report received";
    }
    leaf valid {
      type boolean;
      description
        "Indicates whether data is valid";
    }
  }

  grouping ble-ltx-scan-counters {
    description
      "AP BLE scan counters";
    leaf total {
      when "../report/valid = 'true'";
      type uint32;
      description
        "Total scan records";
    }
    leaf dna-ltx {
      when "../report/valid = 'true'";
      type uint32;
      description
        "Total DNA LTX records";
    }
    leaf system-tlm {
      when "../report/valid = 'true'";
      type uint32;
      description
        "Total system telemetry records";
    }
    leaf event-tlm {
      when "../report/valid = 'true'";
      type uint32;
      description
        "Total event telemetry records";
    }
    leaf regular-tlm {
      when "../report/valid = 'true'";
      type uint32;
      description
        "Total regular telemetry records";
    }
    leaf emergency {
      when "../report/valid = 'true'";
      type uint32;
      description
        "Total emergency records";
    }
    leaf event-emergency {
      when "../report/valid = 'true'";
      type uint32;
      description
        "Total event emergency records";
    }
    leaf other {
      when "../report/valid = 'true'";
      type uint32;
      description
        "Other records received by AP";
    }
    container report {
      description
        "Status of the last report from AP BLE";
      uses wireless-ble-ltx-oper:ble-ltx-report;
    }
  }

  grouping ble-ltx-scan-config-feedback {
    description
      "AP BLE scan configuration command feedback";
    leaf interval-sec-status {
      type uint8;
      description
        "Reported status of AP BLE scan cycle time";
    }
    leaf state-status {
      type uint8;
      description
        "Reported status of AP BLE scan enable flag";
    }
    leaf max-value-status {
      type uint8;
      description
        "Reported status of AP BLE max number of scans";
    }
    leaf window-msec-status {
      type uint8;
      description
        "Reported status of AP BLE scan time during each cycle";
    }
    leaf filter-status {
      type uint8;
      description
        "Reported status of AP BLE flag to enable or disable MAC based scan filtering";
    }
  }

  grouping ble-ltx-scan-config {
    description
      "AP BLE scan configuration";
    leaf interval-sec {
      when "../report/valid = 'true'";
      type uint32;
      units "seconds";
      description
        "AP BLE scan cycle time in seconds";
    }
    leaf state {
      when "../report/valid = 'true'";
      type wireless-enum-types:ble-ltx-scan-state;
      description
        "AP BLE scan enable flag";
    }
    leaf max-value {
      when "../report/valid = 'true'";
      type uint8;
      description
        "AP BLE max number of scan performed in the scan cycle";
    }
    leaf window-msec {
      when "../report/valid = 'true'";
      type uint16;
      units "milliseconds";
      description
        "AP BLE scan time during each cycle in milliseconds";
    }
    leaf filter {
      when "../report/valid = 'true'";
      type wireless-enum-types:ble-ltx-scan-filter;
      description
        "AP BLE flag to enable or disable MAC based scan filtering";
    }
    container feedback {
      when "../report/valid = 'true'";
      description
        "Feedback of the last config command";
      uses wireless-ble-ltx-oper:ble-ltx-scan-config-feedback;
    }
    container report {
      description
        "Status of the last report from AP BLE";
      uses wireless-ble-ltx-oper:ble-ltx-report;
    }
  }

  grouping ble-ltx-host-data {
    description
      "AP BLE host data";
    leaf device-name {
      when "../report/valid = 'true'";
      type string;
      description
        "AP BLE device name";
    }
    leaf ble-mac {
      when "../report/valid = 'true'";
      type yang:mac-address;
      description
        "BLE over the Air MAC address";
    }
    leaf api-version {
      when "../report/valid = 'true'";
      type uint16;
      description
        "AP BLE API version";
    }
    leaf fw-version {
      when "../report/valid = 'true'";
      type binary;
      description
        "AP BLE Device/major/minor/revision";
    }
    leaf advertise-count {
      when "../report/valid = 'true'";
      type uint32;
      description
        "Total number of broadcasts since powered on";
    }
    leaf uptime-dsec {
      when "../report/valid = 'true'";
      type uint32;
      units "deciseconds";
      description
        "Time since chip was last powered on in deciseconds";
    }
    leaf active-profile {
      when "../report/valid = 'true'";
      type wireless-enum-types:ble-ltx-profile;
      description
        "AP BLE active chirping profile";
    }
    container report {
      description
        "Status of the last report from AP BLE";
      uses wireless-ble-ltx-oper:ble-ltx-report;
    }
  }

  grouping ble-ltx-feature-mode {
    description
      "AP BLE feature mode";
    leaf feature {
      when "../report/valid = 'true'";
      type wireless-enum-types:ble-ltx-iot-feature;
      description
        "Type of BLE feature";
    }
    leaf mode {
      when "../report/valid = 'true'";
      type wireless-enum-types:ble-ltx-mode;
      description
        "Mode of the BLE device";
    }
    container report {
      description
        "Status of the last report from AP BLE";
      uses wireless-ble-ltx-oper:ble-ltx-report;
    }
  }

  grouping ble-ltx-ibeacon-feedback {
    description
      "AP BLE iBeacon profile config command feedback";
    leaf uuid-status {
      type uint8;
      description
        "Reported status of iBeacon UUID";
    }
    leaf major-status {
      type uint8;
      description
        "Reported status of iBeacon type (major)";
    }
    leaf minor-status {
      type uint8;
      description
        "Reported status of iBeacon subtype (minor)";
    }
    leaf tx-power-status {
      type uint8;
      description
        "Reported status of transmit power";
    }
    leaf frequency-msec-status {
      type uint8;
      description
        "Reported status of iBeacon frequency";
    }
    leaf adv-tx-power-status {
      type uint8;
      description
        "Reported status of advertised transmit power";
    }
  }

  grouping ble-ltx-ibeacon {
    description
      "AP BLE iBeacon chirping profile";
    leaf uuid {
      when "../report/valid = 'true'";
      type string;
      description
        "iBeacon UUID";
    }
    leaf major {
      when "../report/valid = 'true'";
      type uint16;
      description
        "Type of the iBeacon (major)";
    }
    leaf minor {
      when "../report/valid = 'true'";
      type uint16;
      description
        "Subtype of the iBeacon (minor)";
    }
    leaf tx-power {
      when "../report/valid = 'true'";
      type uint8;
      units "dBm";
      description
        "iBeacon transmit power in dBm";
    }
    leaf frequency-msec {
      when "../report/valid = 'true'";
      type uint16;
      units "milliseconds";
      description
        "iBeacon chirping frequency in milliseconds";
    }
    leaf adv-tx-power {
      when "../report/valid = 'true'";
      type uint8;
      units "dBm";
      description
        "iBeacon advertised transmit power in dBm";
    }
    container feedback {
      when "../report/valid = 'true'";
      description
        "Feedback of the last config command";
      uses wireless-ble-ltx-oper:ble-ltx-ibeacon-feedback;
    }
    container report {
      description
        "Status of the last report from AP BLE";
      uses wireless-ble-ltx-oper:ble-ltx-report;
    }
  }

  grouping ble-ltx-eddystone-url-feedback {
    description
      "AP BLE chirping Eddystone URL profile command feedback";
    leaf url-status {
      type uint8;
      description
        "Reported status of Eddystone URL";
    }
  }

  grouping ble-ltx-eddystone-url {
    description
      "AP BLE chirping Eddystone URL profile";
    leaf url {
      when "../report/valid = 'true'";
      type string;
      description
        "Eddystone URL";
    }
    container feedback {
      when "../report/valid = 'true'";
      description
        "Feedback of the last config command";
      uses wireless-ble-ltx-oper:ble-ltx-eddystone-url-feedback;
    }
    container report {
      description
        "Status of the last report from AP BLE";
      uses wireless-ble-ltx-oper:ble-ltx-report;
    }
  }

  grouping ble-ltx-eddystone-uid-feedback {
    description
      "AP BLE chirping Eddystone UID profile command feedback";
    leaf namespace-status {
      type uint8;
      description
        "Reported status of Eddystone namespace";
    }
    leaf instance-id-status {
      type uint8;
      description
        "Reported status of Eddystone instance id";
    }
  }

  grouping ble-ltx-eddystone-uid {
    description
      "AP BLE chirping Eddystone UID profile";
    leaf namespace {
      when "../report/valid = 'true'";
      type string;
      description
        "Eddystone namespace";
    }
    leaf instance-id {
      when "../report/valid = 'true'";
      type string;
      description
        "Eddystone instance id";
    }
    container feedback {
      when "../report/valid = 'true'";
      description
        "Feedback of the last config command";
      uses wireless-ble-ltx-oper:ble-ltx-eddystone-uid-feedback;
    }
    container report {
      description
        "Status of the last report from AP BLE";
      uses wireless-ble-ltx-oper:ble-ltx-report;
    }
  }

  grouping ble-ltx-device-status {
    description
      "AP BLE device status";
    leaf device {
      when "../report/valid = 'true'";
      type wireless-enum-types:ble-ltx-device;
      description
        "Type of BLE device";
    }
    leaf state {
      when "../report/valid = 'true'";
      type wireless-enum-types:ble-ltx-device-state;
      description
        "State of BLE device";
    }
    container report {
      description
        "Status of the last report from AP BLE";
      uses wireless-ble-ltx-oper:ble-ltx-report;
    }
  }

  grouping ble-ltx-admin-feedback {
    description
      "AP BLE administrative command feedback";
    leaf state-status {
      type uint8;
      description
        "Reported status of overall BLE hardware module";
    }
  }

  grouping ble-ltx-admin {
    description
      "AP BLE administrative setting";
    leaf state {
      when "../report/valid = 'true'";
      type wireless-enum-types:ble-ltx-admin-state;
      description
        "State of the overall BLE hardware module";
    }
    container feedback {
      when "../report/valid = 'true'";
      description
        "Feedback of the last config command";
      uses wireless-ble-ltx-oper:ble-ltx-admin-feedback;
    }
    container report {
      description
        "Status of the last report from AP BLE";
      uses wireless-ble-ltx-oper:ble-ltx-report;
    }
  }

  grouping ble-ltx-vibeacon-common-feedback {
    description
      "AP BLE viBeacon config command feedback";
    leaf interval-msec-status {
      type uint8;
      description
        "Reported status of viBeacon chirping interval";
    }
  }

  grouping ble-ltx-vibeacon-common {
    description
      "Common configuration of all AP BLE viBeacon chirping profiles";
    leaf interval-msec {
      when "../report/valid = 'true'";
      type uint16;
      units "milliseconds";
      description
        "viBeacon chirping interval";
    }
    container feedback {
      when "../report/valid = 'true'";
      description
        "Feedback of the last config command";
      uses wireless-ble-ltx-oper:ble-ltx-vibeacon-common-feedback;
    }
    container report {
      description
        "Status of the last report from AP BLE";
      uses wireless-ble-ltx-oper:ble-ltx-report;
    }
  }

  grouping ble-ltx-vibeacon-feedback {
    description
      "AP BLE viBeacon profile config command feedback";
    leaf beacon-id-status {
      type uint8;
      description
        "Reported status of viBeacon ID";
    }
    leaf uuid-status {
      type uint8;
      description
        "Reported status of viBeacon UUID";
    }
    leaf tx-power-status {
      type uint8;
      description
        "Reported status of transmit power";
    }
    leaf major-status {
      type uint8;
      description
        "Reported status of viBeacon type (major)";
    }
    leaf minor-status {
      type uint8;
      description
        "Reported status of viBeacon subtype (minor)";
    }
    leaf status-status {
      type uint8;
      description
        "Reported status of viBeacon status";
    }
    leaf adv-tx-power-status {
      type uint8;
      description
        "Reported status of viBeacon advertised transmit power";
    }
  }

  grouping ble-ltx-vibeacon {
    description
      "AP BLE viBeacon chirping profile";
    leaf beacon-id {
      when "../report/valid = 'true'";
      type uint16;
      description
        "viBeacon ID";
    }
    leaf uuid {
      when "../report/valid = 'true'";
      type string;
      description
        "viBeacon UUID";
    }
    leaf tx-power {
      when "../report/valid = 'true'";
      type uint8;
      units "dBm";
      description
        "Transmit power in dBm";
    }
    leaf major {
      when "../report/valid = 'true'";
      type uint16;
      description
        "Type of the viBeacon (major)";
    }
    leaf minor {
      when "../report/valid = 'true'";
      type uint16;
      description
        "Subtype of the viBeacon (minor)";
    }
    leaf adv-tx-power {
      when "../report/valid = 'true'";
      type uint8;
      units "dBm";
      description
        "viBeacon advertised transmit power in dBm";
    }
    leaf status {
      when "../report/valid = 'true'";
      type wireless-enum-types:ble-ltx-vibeacon-status;
      description
        "viBeacon status";
    }
    container feedback {
      when "../report/valid = 'true'";
      description
        "Feedback of the last config command";
      uses wireless-ble-ltx-oper:ble-ltx-vibeacon-feedback;
    }
    container report {
      description
        "Status of the last report from AP BLE";
      uses wireless-ble-ltx-oper:ble-ltx-report;
    }
  }

  grouping ble-ltx-vibeacons {
    description
      "AP BLE viBeacon configuration, that represents multiple viBeacons";
    container common {
      when "../report/valid = 'true'";
      description
        "Common configuration for all viBeacons chirping profiles";
      uses wireless-ble-ltx-oper:ble-ltx-vibeacon-common;
    }
    list vibeacons {
      when "../report/valid = 'true'";
      description
        "BLE viBeacons chirping profiles";
      uses wireless-ble-ltx-oper:ble-ltx-vibeacon;
    }
    container report {
      description
        "Status of the last report from AP BLE";
      uses wireless-ble-ltx-oper:ble-ltx-report;
    }
  }

  grouping ble-ltx-capability {
    description
      "AP BLE capabilities";
    leaf ble {
      when "../report/valid = 'true'";
      type boolean;
      description
        "BLE capability";
    }
    leaf zigbee {
      when "../report/valid = 'true'";
      type boolean;
      description
        "Zigbee capability";
    }
    leaf thread {
      when "../report/valid = 'true'";
      type boolean;
      description
        "Thread capability";
    }
    leaf usb {
      when "../report/valid = 'true'";
      type boolean;
      description
        "USB capability";
    }
    container report {
      description
        "Status of the last report from AP BLE";
      uses wireless-ble-ltx-oper:ble-ltx-report;
    }
  }

  grouping ble-ltx-ap {
    description
      "BLE LTX data for each AP";
    leaf ap-mac {
      type yang:mac-address;
      description
        "AP MAC address";
    }
    container admin {
      description
        "AP administrative state";
      uses wireless-ble-ltx-oper:ble-ltx-admin;
    }
    container scan-config {
      description
        "AP BLE scan configuration";
      uses wireless-ble-ltx-oper:ble-ltx-scan-config;
    }
    container profile-ibeacon {
      description
        "AP BLE iBeacon chirping profile";
      uses wireless-ble-ltx-oper:ble-ltx-ibeacon;
    }
    container profile-eddy-url {
      description
        "AP BLE Eddystone URL chirping profile";
      uses wireless-ble-ltx-oper:ble-ltx-eddystone-url;
    }
    container profile-eddy-uid {
      description
        "AP BLE Eddystone UID chirping profile";
      uses wireless-ble-ltx-oper:ble-ltx-eddystone-uid;
    }
    container profile-vibeacons {
      description
        "AP BLE viBeacons chirping profiles";
      uses wireless-ble-ltx-oper:ble-ltx-vibeacons;
    }
    container scan-counters {
      description
        "AP BLE scan counters";
      uses wireless-ble-ltx-oper:ble-ltx-scan-counters;
    }
    container host-data {
      description
        "AP BLE host data";
      uses wireless-ble-ltx-oper:ble-ltx-host-data;
    }
    container feature-mode {
      description
        "AP BLE LTX feature mode";
      uses wireless-ble-ltx-oper:ble-ltx-feature-mode;
    }
    container device-status {
      description
        "AP BLE interface status";
      uses wireless-ble-ltx-oper:ble-ltx-device-status;
    }
    container capability {
      description
        "AP BLE capability";
      uses wireless-ble-ltx-oper:ble-ltx-capability;
    }
  }

  grouping ble-ltx-ap-antenna-key {
    description
      "BLE LTX AP antenna key for each AP";
    leaf ap-mac {
      type yang:mac-address;
      description
        "BLE LTX AP MAC address";
    }
    leaf ble-slot-id {
      type uint8;
      description
        "BLE LTX AP BLE antenna slot id";
    }
    leaf ble-antenna-id {
      type uint8;
      description
        "BLE LTX AP BLE antenna id";
    }
  }

  grouping ble-ltx-ap-antenna-data {
    description
      "BLE LTX AP antenna data for BLE antenna";
    leaf is-ble-antenna-present {
      type boolean;
      description
        "AP has BLE antenna present";
    }
    leaf ble-antenna-pid {
      type string;
      description
        "AP BLE antenna PID";
    }
    leaf ble-antenna-gain {
      type uint8;
      description
        "AP BLE antenna gain";
    }
    leaf ble-antenna-type {
      type wireless-enum-types:ble-ltx-module-type;
      description
        "AP BLE antenna type";
    }
    leaf ble-antenna-mode {
      type wireless-enum-types:ble-ltx-antenna-mode;
      description
        "AP BLE antenna mode";
    }
    leaf ble-antenna-diversity {
      type wireless-enum-types:ble-ltx-antenna-diversity-status;
      description
        "AP BLE antenna diversity status";
    }
    leaf ble-antenna-options {
      type wireless-enum-types:ble-ltx-module-type;
      description
        "AP BLE antenna options";
    }
  }

  container ble-ltx-oper-data {
    config false;
    description
      "BLE LTX operational data";
    list ble-ltx-ap-antenna {
      key "ap-mac ble-slot-id ble-antenna-id";
      description
        "BLE LTX AP Antenna Information";
      uses wireless-ble-ltx-oper:ble-ltx-ap-antenna-data;
      uses wireless-ble-ltx-oper:ble-ltx-ap-antenna-key;
    }
    list ble-ltx-ap {
      key "ap-mac";
      description
        "BLE LTX AP data";
      uses wireless-ble-ltx-oper:ble-ltx-ap;
    }
  }
}
