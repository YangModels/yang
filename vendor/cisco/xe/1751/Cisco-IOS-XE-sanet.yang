module Cisco-IOS-XE-sanet {
  namespace "http://cisco.com/ns/yang/Cisco-IOS-XE-sanet";
  prefix ios-sanet;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Session Aware Networking (SaNet) Yang model.
     Copyright (c) 2016-2017, 2019-2020 by Cisco Systems, Inc.
     All rights reserved.";

  revision 2020-11-01 {
    description
      "- Added support for uint32 values for reauthentication timer";
  }
  revision 2020-07-01 {
    description
      "- Added when statement for authentication container so that authentication
         cli is not supported on subinterfaces;
       - Hardened the authorize-action with must condition";
  }
  revision 2020-03-01 {
    description
      "- Added interface authentication order-config and priority-config
         to replace order and priority, respectively
       - Added session limit configuration";
  }
  revision 2019-11-01 {
    description
      "- Added support for access-session tls-version CLI
       - Added timer config
       - Added support for access-session mac-move deny-uncontrolled CLI";
    cisco-semver:module-version "2.0.0";
  }
  revision 2019-07-01 {
    description
      "- Establish semantic version baseline
       - Added support for authentication timer unauthorized
       - Added support for authentication event fail retry commands
       - Added description and range for authentication event fail action authorize
         vlan cli and default for authentication control-direction
       - Added support for authentication convert-to new-style forced
       - Add support for authentication link security policy
       - Add support for autoconf enable
       - Added description for authentication command disable-port ignore
       - Added authentication event fail action next-method cli support
       - Added missing range for authentication fallback and defaults for authentication commands
       - Added support for dhcpv6, vlan-id in access-session attributes filter-list
         and access-session authentication attributes filter-spec include list cli";
    cisco-semver:module-version "1.0.0";
  }
  revision 2019-01-30 {
    description
      "Added support for access-session accounting and acl along with http filter";
  }
  revision 2019-01-22 {
    description
      "Added leaf for App-hosting Gigabit Ethernet interface";
  }
  revision 2018-11-07 {
    description
      "Cleanup spelling errors in description statements";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-11 {
    description
      "This revision has changes for new 5gig and 25gig interfaces addition";
  }
  revision 2017-02-07 {
    description
      "Initial revision";
  }

  grouping config-access-session-grouping {
    container access-session {
      description
        "Access Session Global Configuration Commands";
      container accounting {
        description
          "Accounting Filter List Configuration";
        container attributes {
          description
            "Attributes Filter List Configuration";
          container filter-spec {
            description
              "Filter Spec Configuration";
            container include {
              description
                "Include Filter Spec Configuration";
              leaf list {
                description
                  "Filter list";
                type leafref {
                  path "/ios:native/ios-sanet:access-session/ios-sanet:attributes/ios-sanet:filter-list/ios-sanet:list/ios-sanet:name";
                }
              }
            }
          }
        }
      }
      container acl {
        description
          "Application of ACLs on access-session";
        container default {
          description
            "Defines the behaviour in the absence of an explicit ACL";
          leaf passthrough {
            description
              "Allows session to send traffic through acl";
            type empty;
          }
        }
        leaf ack-timer {
          description
            "Defines the timeout in seconds for receiving ACK on applying the policy";
          type uint16 {
            range "20..300";
          }
        }
      }
      container attributes {
        description
          "Attributes Filter List Configuration";
        container filter-list {
          description
            "Filter List Configuration";
          list list {
            description
              "Filter List";
            key "name";
            leaf name {
              type string;
            }
            leaf cdp {
              description
                "Include CDP Protocol attributes";
              type empty;
            }
            leaf dhcp {
              description
                "Include DHCP Protocol attributes";
              type empty;
            }
            leaf dhcpv6 {
              description
                "Include DHCPv6 Protocol attributes";
              type empty;
            }
            leaf http {
              description
                "Include HTTP Protocol attributes";
              type empty;
            }
            leaf lldp {
              description
                "Include LLDP Protocol attributes";
              type empty;
            }
            leaf vlan-id {
              description
                "Include vlan attribute";
              type empty;
            }
          }
        }
      }
      container authentication {
        description
          "Authentication Filter List Configuration";
        container attributes {
          description
            "Attributes Filter List Configuration";
          container filter-spec {
            description
              "Filter Spec Configuration";
            container include {
              description
                "Include Filter Spec Configuration";
              leaf list {
                description
                  "Filter list";
                type leafref {
                  path "/ios:native/ios-sanet:access-session/ios-sanet:attributes/ios-sanet:filter-list/ios-sanet:list/ios-sanet:name";
                }
              }
            }
          }
        }
      }
      container cache {
        description
          "Set cache configuration";
        leaf limit {
          description
            "Limit";
          type uint16 {
            range "0..24000";
          }
          default "24000";
        }
      }
      container event-logging {
        description
          "Event log Configuration";
        container enable {
          description
            "Enable Event logging";
          container session-limit {
            description
              "maximum number of sessions to be tracked";
            leaf value {
              description
                "Session Limit or max sessions to be logged";
              type uint16 {
                range "1..4000";
              }
            }
            leaf event-limit {
              description
                "max events per session to be logged";
              type uint8 {
                range "1..200";
              }
            }
          }
        }
      }
      container interface-template {
        description
          "Set the interface-template sticky globally";
        container sticky {
          description
            "Interface templates set to sticky";
          presence "true";
          leaf timer {
            description
              "Sticky timer value";
            type uint16 {
              range "1..65535";
            }
          }
        }
      }
      container mac-move {
        description
          "Set required action when a MAC move is detected";
        leaf deny {
          description
            "DENY MAC moves (clears existing session)";
          type empty;
        }
        leaf deny-uncontrolled {
          description
            "Deny MAC move to uncontrolled port";
          type empty;
        }
      }
      leaf monitor {
        description
          "Apply template to monitor access sessions on the port";
        type empty;
      }
      leaf tls-version {
        description
          "Set required TLS version";
        type enumeration {
          enum "1.0";
          enum "1.2";
          enum "all";
        }
        default "all";
      }
      container tunnel {
        status obsolete;
        leaf vlan {
          status obsolete;
          description
            "Set Tunnel Vlan Id";
          type uint16 {
            range "1..4096";
          }
        }
      }
      container voice {
        description
          "voice client auth options";
        leaf skip-data-vlan {
          description
            "Skip Default Data Vlan Auth for voice client";
          type empty;
        }
      }
      container limit {
        description
          "Set session limit parameter";
        container profiles {
          description
            "Session limit profile";
          list profile {
            description
              "Session limit profile name list";
            key "name";
            leaf name {
              description
                "Session limit profile name";
              type string {
                length "1..32";
              }
            }
            container max-limit {
              description
                "Set maximum session limit";
              leaf value {
                description
                  "Enter a value between 1 and 65535";
                type uint16 {
                  range "1..65535";
                }
                default "65535";
              }
            }
            container data-limit {
              description
                "Set data session limit";
              leaf value {
                description
                  "Enter a value between 0 and 65535";
                type uint16 {
                  range "0..65535";
                }
                default "65535";
              }
            }
            container voice-limit {
              description
                "Set voice session limit";
              leaf value {
                description
                  "Enter a value between 0 and 65535";
                type uint16 {
                  range "0..65535";
                }
                default "65535";
              }
            }
            leaf multi-host {
              description
                "Enable multi host mode";
              type empty;
            }
            leaf cdp-bypass {
              description
                "Enable cdp bypass";
              type empty;
            }
          }
        }
      }
    }
    container autoconf {
      description
        "Configure autoconf";
      leaf enable {
        description
          "Enable autoconf";
        type empty;
      }
    }
  }

  grouping config-authentication-grouping {
    container authentication {
      description
        "Auth Manager Global Configuration Commands";
      container command {
        description
          "Allow the following CoA commands to be ignored by the switch";
        container bounce-port {
          description
            "CoA bounce-port command";
          leaf ignore {
            description
              "ignore bounce-port CoA command";
            type empty;
          }
        }
        container disable-port {
          description
            "CoA disable-port command";
          leaf ignore {
            description
              "ignore disable-port CoA command";
            type empty;
          }
        }
      }
      container critical {
        description
          "Set Critical Authentication parameters";
        container recovery {
          description
            "Set Critical Authentication Recovery parameters";
          leaf delay {
            description
              "Set Critical Authentication Recovery Delay period";
            type uint32 {
              range "1..10000";
            }
            default "100";
          }
        }
      }
      leaf dis-scale-opt {
        description
          "Scale Optimise disable";
        type empty;
      }
      container logging {
        description
          "Set logging parameters";
        leaf verbose {
          description
            "Show verbose messages in system logs";
          type empty;
        }
      }
      container mac-move {
        description
          "Set required action when a MAC move is detected";
        leaf permit {
          description
            "PERMIT MAC moves (clears existing session)";
          type empty;
        }
        leaf deny-uncontrolled {
          description
            "Deny MAC move to uncontrolled port";
          type empty;
        }
      }
      container convert-to {
        description
          "Convert the configuration mode to eEdge";
        container new-style {
          description
            "New style (c3pl) configuration";
          leaf forced {
            description
              "Force new style (c3pl) configuration";
            type empty;
          }
        }
      }
    }
  }

  grouping config-interface-authentication-grouping {
    container authentication {
      description
        "Auth Manager Interface Configuration Commands";
      when "not(contains(../ios:name,'.'))";
      leaf control-direction {
        description
          "Set the control-direction on the interface";
        type enumeration {
          enum "both";
          enum "in";
        }
        default "both";
      }
      container event {
        description
          "Set action for authentication events";
        container server {
          description
            "Configure actions for AAA server events";
          container alive {
            description
              "Configure AAA server alive action";
            container action {
              description
                "Required action for authentication event";
              leaf reinitialize {
                description
                  "Reinitialize all authorized clients";
                type empty;
              }
            }
          }
          container dead {
            description
              "Configure AAA server dead action";
            container action {
              description
                "Required action for authentication event";
              container authorize {
                description
                  "Authorize the port";
                presence "true";
                leaf vlan {
                  description
                    "Configure Critical Authorization VLAN";
                  must "not (../../reinitialize/vlan)" {
                    error-message "Action can either be authorize vlan or reinitialize vlan, reinitialize vlan is already configured, please remove it and configure authorize vlan";
                  }
                  type uint16 {
                    range "1..4094";
                  }
                }
                leaf voice {
                  description
                    "Authorize the port for VOICE traffic";
                  type empty;
                }
              }
              container reinitialize {
                description
                  "Reinitialize all client on the port";
                leaf vlan {
                  description
                    "Configure Critical Authorization VLAN";
                  must "not (../../authorize/vlan)" {
                    error-message "Action can either be authorize vlan or reinitialize vlan, authorize vlan is already configured, please remove it and configure reinitialize vlan";
                  }
                  type uint16 {
                    range "1..4094";
                  }
                }
              }
            }
          }
        }
        container fail-config {
          description
            "Configure failed authentication actions/parameters";
          choice fail-type {
            container action {
              description
                "Required action for authentication event";
              choice action-type {
                container authorize {
                  description
                    "Authorize the port";
                  leaf vlan {
                    description
                      "Configure Authentication Fail vlan";
                    type uint16 {
                      range "1..4094";
                    }
                  }
                }
                leaf next-method {
                  description
                    "Move to next authentication method";
                  type empty;
                }
              }
            }
            container retry {
              description
                "Number of times to retry failed authentications";
              leaf value {
                description
                  "Enter the retry count";
                type uint8 {
                  range "0..5";
                }
              }
              container action {
                description
                  "Required action for authentication event";
                choice retry-action {
                  container authorize {
                    description
                      "Authorize the port";
                    leaf vlan {
                      description
                        "Configure Authentication Fail vlan";
                      type uint16 {
                        range "1..4094";
                      }
                    }
                  }
                  leaf next-method {
                    description
                      "Move to next authentication method";
                    type empty;
                  }
                }
              }
            }
          }
        }
        container fail {
          status deprecated;
          description
            "Configure failed authentication actions/parameters. DEPRECATED, Use
             fail-config container";
          container action {
            status deprecated;
            description
              "Required action for authentication event";
            container authorize {
              status deprecated;
              description
                "Authorize the port";
              leaf vlan {
                status deprecated;
                description
                  "Configure Authentication Fail vlan";
                type uint16 {
                  range "1..4094";
                }
              }
            }
            leaf next-method {
              status deprecated;
              description
                "Move to next authentication method";
              type empty;
            }
          }
          container retry {
            status deprecated;
            description
              "Number of times to retry failed authentications";
            leaf value {
              status deprecated;
              description
                "Enter the retry count";
              type uint8 {
                range "0..5";
              }
            }
            container action {
              status deprecated;
              description
                "Required action for authentication event";
              choice retry-action {
                container authorize {
                  status deprecated;
                  description
                    "Authorize the port";
                  leaf vlan {
                    status deprecated;
                    description
                      "Configure Authentication Fail vlan";
                    type uint16 {
                      range "1..4094";
                    }
                  }
                }
                leaf next-method {
                  status deprecated;
                  description
                    "Move to next authentication method";
                  type empty;
                }
              }
            }
          }
        }
        container no-response {
          description
            "Configure non-responsive host actions";
          container action {
            description
              "Required action for authentication event";
            container authorize {
              description
                "Authorize the port";
              leaf vlan {
                description
                  "Configure Guest vlan";
                type uint16 {
                  range "1..4094";
                }
              }
            }
          }
        }
        container linksec {
          description
            "Configure actions for link security events";
          container fail {
            description
              "Configure linksec failure actions";
            container action {
              description
                "Required action for authentication event";
              leaf next-method {
                description
                  "Move to next authentication method";
                type empty;
              }
            }
          }
        }
      }
      leaf fallback {
        description
          "Enable the Webauth fallback mechanism";
        type string {
          length "1..200";
        }
      }
      leaf host-mode {
        description
          "Set the Host mode for authentication on this interface";
        type enumeration {
          enum "multi-auth";
          enum "multi-domain";
          enum "multi-host";
          enum "single-host";
        }
        default "single-host";
      }
      leaf open {
        description
          "Enable or Disable open access on this port";
        type empty;
      }
      container order-config {
        description
          "Add an authentication method to the order list";
        choice method {
          container dot1x-config {
            description
              "Authentication method dot1x allowed";
            presence "true";
            leaf mab {
              description
                "Authentication method mab allowed";
              type empty;
            }
            leaf webauth {
              description
                "Authentication method webauth allowed";
              type empty;
            }
          }
          container mab-config {
            description
              "Authentication method mab allowed";
            presence "true";
            leaf dot1x {
              description
                "Authentication method dot1x allowed";
              type empty;
            }
            leaf webauth {
              description
                "Authentication method webauth allowed";
              type empty;
            }
          }
          leaf webauth-config {
            description
              "Authentication method webauth allowed";
            type empty;
          }
        }
      }
      container order {
        description
          "Add an authentication method to the order list. DEPRECATED.
           Use order-config instead";
        status deprecated;
        leaf dot1x {
          description
            "Authentication method dot1x allowed";
          status deprecated;
          type empty;
        }
        leaf mab {
          description
            "Authentication method mab allowed";
          status deprecated;
          type empty;
        }
        leaf webauth {
          description
            "Authentication method webauth allowed";
          status deprecated;
          type empty;
        }
      }
      container priority-config {
        description
          "Add an authentication method to the priority list";
        choice method {
          container dot1x-config {
            description
              "Authentication method dot1x allowed";
            presence "true";
            leaf mab {
              description
                "Authentication method mab allowed";
              type empty;
            }
            leaf webauth {
              description
                "Authentication method webauth allowed";
              type empty;
            }
          }
          container mab-config {
            description
              "Authentication method mab allowed";
            presence "true";
            leaf dot1x {
              description
                "Authentication method dot1x allowed";
              type empty;
            }
            leaf webauth {
              description
                "Authentication method webauth allowed";
              type empty;
            }
          }
          leaf webauth-config {
            description
              "Authentication method webauth allowed";
            type empty;
          }
        }
      }
      container priority {
        description
          "Add an authentication method to the priority list. Deprecated.
           Use priority-config instead";
        status deprecated;
        leaf dot1x {
          description
            "Authentication method dot1x allowed";
          status deprecated;
          type empty;
        }
        leaf mab {
          description
            "Authentication method mab allowed";
          status deprecated;
          type empty;
        }
        leaf webauth {
          description
            "Authentication method webauth allowed";
          status deprecated;
          type empty;
        }
      }
      leaf port-control {
        description
          "set the port-control value";
        type enumeration {
          enum "auto";
          enum "force-authorized";
          enum "force-unauthorized";
        }
        default "force-authorized";
      }
      leaf periodic {
        description
          "Enable or Disable Reauthentication for this port";
        type empty;
      }
      container timer {
        description
          "Set authentication timer values";
        container reauthenticate {
          description
            "Time in seconds after which an automatic re-authentication should be initiated (default 1 hour)";
          choice timer-val {
            leaf value-config {
              description
                "Enter a value between 1 and 1073741823";
              type uint32 {
                range "1..1073741823";
              }
              default "3600";
            }
            leaf server-config {
              description
                "Obtain re-authentication timeout value from the server";
              type empty;
            }
          }
          leaf value {
            description
              "Enter a value between 1 and 65535";
            status deprecated;
            type uint16 {
              range "1..65535";
            }
          }
          leaf server {
            status deprecated;
            description
              "Obtain re-authentication timeout value from the server";
            type empty;
          }
        }
        container inactivity {
          description
            "Interval in seconds after which if there is no activity from the client then it will be unauthorized (default OFF)";
          choice timer-val {
            container value-config {
              leaf value {
                description
                  "Enter a value between 1 and 65535";
                type uint16 {
                  range "1..65535";
                }
              }
              leaf dynamic {
                description
                  "Initiate a dynamic probe on inactivity timeout";
                type empty;
              }
            }
            container server-config {
              description
                "Obtain inactivity timeout value from the server";
              presence "true";
              leaf dynamic {
                description
                  "Initiate a dynamic probe on inactivity timeout";
                type empty;
              }
            }
          }
          container value {
            description
              "Enter a value between 1 and 65535";
            status deprecated;
            leaf value {
              status deprecated;
              type uint16 {
                range "1..65535";
              }
            }
            leaf dynamic {
              status deprecated;
              description
                "Initiate a dynamic probe on inactivity timeout";
              type empty;
            }
          }
          container server {
            status deprecated;
            description
              "Obtain inactivity timeout value from the server";
            presence "true";
            leaf dynamic {
              status deprecated;
              description
                "Initiate a dynamic probe on inactivity timeout";
              type empty;
            }
          }
        }
        leaf restart {
          description
            "Interval in seconds after which an attempt should be made to authenticate an unauthorized port (default 60 sec)";
          type uint16;
          default "60";
        }
        leaf unauthorized {
          description
            "Time in seconds after which an unauthorized session will get deleted";
          type uint16;
          default "0";
        }
      }
      leaf violation {
        description
          "Configure action to take on security violations";
        type enumeration {
          enum "protect";
          enum "replace";
          enum "restrict";
          enum "shutdown";
        }
        default "shutdown";
      }
      container linksec {
        description
          "Configure link security parameters";
        leaf policy {
          description
            "Set the link security policy";
          type enumeration {
            enum "must-not-secure";
            enum "must-secure";
            enum "should-secure";
          }
          default "should-secure";
        }
      }
    }
  }

  grouping config-interface-mab-grouping {
    container mab {
      description
        "MAC Authentication Bypass Interface Config Commands";
      presence "true";
      leaf eap {
        description
          "Use EAP authentication for MAC Auth Bypass";
        type empty;
      }
    }
  }

  grouping config-interface-access-session-grouping {
    container limit {
      description
        "Attach session limit profile";
      choice sess-limit {
        leaf max-limit {
          description
            "Set maximum session limit";
          type uint16 {
            range "1..65535";
          }
        }
        leaf profile-name {
          description
            "Session limit profile name";
          type leafref {
            path "/ios:native/ios-sanet:access-session/ios-sanet:limit/ios-sanet:profiles/ios-sanet:profile/ios-sanet:name";
          }
        }
      }
    }
  }

  augment "/ios:native" {
    uses config-access-session-grouping;
    uses config-authentication-grouping;
  }
  augment "/ios:native/ios:interface/ios:FastEthernet" {
    uses config-interface-authentication-grouping;
    uses config-interface-mab-grouping;
  }
  augment "/ios:native/ios:interface/ios:GigabitEthernet" {
    uses config-interface-authentication-grouping;
    uses config-interface-mab-grouping;
  }
  augment "/ios:native/ios:interface/ios:TenGigabitEthernet" {
    uses config-interface-authentication-grouping;
    uses config-interface-mab-grouping;
  }
  augment "/ios:native/ios:interface/ios:FiveGigabitEthernet" {
    uses config-interface-authentication-grouping;
    uses config-interface-mab-grouping;
  }
  augment "/ios:native/ios:interface/ios:AppGigabitEthernet" {
    uses config-interface-authentication-grouping;
    uses config-interface-mab-grouping;
  }
  augment "/ios:native/ios:interface/ios:TwentyFiveGigE" {
    uses config-interface-authentication-grouping;
    uses config-interface-mab-grouping;
  }
  augment "/ios:native/ios:interface/ios:TwoGigabitEthernet" {
    uses config-interface-authentication-grouping;
    uses config-interface-mab-grouping;
  }
  augment "/ios:native/ios:interface/ios:FortyGigabitEthernet" {
    uses config-interface-authentication-grouping;
    uses config-interface-mab-grouping;
  }
  augment "/ios:native/ios:interface/ios:HundredGigE" {
    uses config-interface-authentication-grouping;
    uses config-interface-mab-grouping;
  }
  augment "/ios:native/ios:interface/ios:Port-channel" {
    uses config-interface-authentication-grouping;
    uses config-interface-mab-grouping;
  }
  augment "/ios:native/ios:interface/ios:FastEthernet/ios:access-session" {
    uses config-interface-access-session-grouping;
  }
  augment "/ios:native/ios:interface/ios:GigabitEthernet/ios:access-session" {
    uses config-interface-access-session-grouping;
  }
  augment "/ios:native/ios:interface/ios:TenGigabitEthernet/ios:access-session" {
    uses config-interface-access-session-grouping;
  }
  augment "/ios:native/ios:interface/ios:FiveGigabitEthernet/ios:access-session" {
    uses config-interface-access-session-grouping;
  }
  augment "/ios:native/ios:interface/ios:AppGigabitEthernet/ios:access-session" {
    uses config-interface-access-session-grouping;
  }
  augment "/ios:native/ios:interface/ios:TwentyFiveGigE/ios:access-session" {
    uses config-interface-access-session-grouping;
  }
  augment "/ios:native/ios:interface/ios:TwoGigabitEthernet/ios:access-session" {
    uses config-interface-access-session-grouping;
  }
  augment "/ios:native/ios:interface/ios:FortyGigabitEthernet/ios:access-session" {
    uses config-interface-access-session-grouping;
  }
  augment "/ios:native/ios:interface/ios:HundredGigE/ios:access-session" {
    uses config-interface-access-session-grouping;
  }
  augment "/ios:native/ios:interface/ios:Virtual-Template" {
    uses config-interface-mab-grouping;
  }
  augment "/ios:native/ios:interface/ios:VirtualPortGroup" {
    uses config-interface-mab-grouping;
  }
}
