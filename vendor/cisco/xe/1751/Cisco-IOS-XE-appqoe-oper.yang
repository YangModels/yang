module Cisco-IOS-XE-appqoe-oper {
  yang-version 1;
  namespace "http://cisco.com/ns/yang/Cisco-IOS-XE-appqoe-oper";
  prefix appqoe-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Application Quality of Experience (AppQoE) operational data.
     Copyright (c) 2020 by Cisco Systems, Inc.
     All rights reserved.";

  revision 2020-11-01 {
    description
      "Initial revision";
    reference
      "1.0.0";
    cisco-semver:module-version "1.0.0";
  }

  grouping appqoe-sc {
    description
      "Service controller detail";
    leaf sc-lan-ip {
      type inet:ip-address;
      description
        "Local Area Network Internet Protocol
         (LAN IP) address of service controller";
    }
    leaf system-ip {
      type inet:ip-address;
      description
        "System Internet Protocol (IP) address of
         service controller";
    }
    leaf site-id {
      type uint32;
      description
        "Site Identifier (ID) of service controller";
    }
    leaf sn-lan-ip {
      type inet:ip-address;
      description
        "Local Area Network Internet Protocol
         (LAN IP) address of service node";
    }
  }

  container appqoe-oper-data {
    config false;
    description
      "Application Quality of Experience (AppQoE)
       operational data";
    list appqoe-sc {
      key "sc-lan-ip";
      description
        "Application Quality of Experience (AppQoE)
         service controllers";
      uses appqoe-xe-oper:appqoe-sc;
    }
  }
}
