module Cisco-IOS-XE-psecure-oper {
  yang-version 1;
  namespace "http://cisco.com/ns/yang/Cisco-IOS-XE-psecure-oper";
  prefix psecure-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of port security state information.
     Copyright (c) 2020 by Cisco Systems, Inc.
     All rights reserved.";

  revision 2021-03-01 {
    description
      "Initial revision";
    reference
      "1.0.0";
    cisco-semver:module-version "1.0.0";
  }

  typedef psecure-type {
    type enumeration {
      enum psecure-configured {
        value 0;
        description
          "Port security type configured";
      }
      enum psecure-dynamic {
        value 1;
        description
          "Port security type dynamic";
      }
      enum psecure-sticky {
        value 2;
        description
          "Port security type sticky";
      }
      enum psecure-none {
        value 3;
        description
          "Port security type none";
      }
    }
    description
      "Port security type";
  }

  grouping psecure-param {
    description
      "Port security parameters for a local interface";
    leaf vlan {
      type uint16;
      description
        "VLAN identifier for port security";
    }
    leaf mac {
      type yang:mac-address;
      description
        "Secure MAC address for port security";
    }
    leaf type {
      type psecure-ios-xe-oper:psecure-type;
      description
        "Type of secure MAC address for port security";
    }
    leaf age-remain {
      type uint32;
      units "minutes";
      description
        "Remaining aging time in minutes for port security";
    }
  }

  grouping psecure-state {
    description
      "Port security entries";
    leaf if-name {
      type string;
      description
        "Local interface name";
    }
    list psecure-param {
      key "mac";
      description
        "Port security parameters for a local interface";
      uses psecure-ios-xe-oper:psecure-param;
    }
  }

  container psecure-oper-data {
    config false;
    description
      "Port security information";
    list psecure-state {
      key "if-name";
      description
        "Port security operational state";
      uses psecure-ios-xe-oper:psecure-state;
    }
  }
}
