module cisco-xe-openconfig-platform-ext {
    namespace "http://cisco.com/ns/yang/cisco-xe-openconfig-platform-ext";
    
    prefix oc-platform-ext;

    import openconfig-platform {
       prefix oc-platform;
    }

    import openconfig-platform-types {
       prefix oc-platform-types;
    }

    import openconfig-transport-types {
       prefix oc-opt-types;
    }

    organization "Cisco Systems";

    description
       "Augmentation for oc-platform";

////////////////////////////////////////////////////////////////////////////
// REVISION
///////////////////////////////////////////////////////////////////////////

 revision 2018-10-16 {
   description "Added the definitions for ASICs anf the Forwarding Processes modeling";
 }

 revision 2018-02-05 {
   description "Add UNKNOWN for connector type";
 }

 revision 2017-05-11 {
   description "Initial Draft to add type CONTAINER";
 }

////////////////////////////////////////////////////////////////////////////
// IDENTITY
///////////////////////////////////////////////////////////////////////////

  identity CONTAINER {
    base oc-platform-types:OPENCONFIG_HARDWARE_COMPONENT;
    description
      "Cisco added type CONTAINER";
  }

  identity ASICS {
    base oc-platform-types:OPENCONFIG_HARDWARE_COMPONENT;
    description
      "Cisco added type ASICS";
  }

  identity FORWARDING_PROCESS {
    base oc-platform-types:OPENCONFIG_SOFTWARE_COMPONENT;
    description
      "Cisco added type for the forwarding processes, i.e. QFP process";
  }


  identity UNKNOWN_CONNECTOR {
    base oc-opt-types:FIBER_CONNECTOR_TYPE;
    description
      "unknown type connector";
  }

  augment "/oc-platform:components/oc-platform:component"
      {
        when "/oc-platform:components/oc-platform:component[oc-platform:name = current()]/oc-platform:state/oc-platform:type = 'ASICS'";
       container integrated-circuit {
        container realized-processes {
          list realized-process {
            config false;
            key "name";
            description
              "List of the processes realized or hosted by the ASICs";
            leaf name {
               type leafref {
                path "../state/name";
                }
             description
             "The key for the list of forwarding processes, i.e. Doppler or QFP, realized by this ASICS";
              }
             container state {
              leaf name {
               type leafref {
                path "/oc-platform:components/oc-platform:component/oc-platform:state/oc-platform:name";
                }
             description
             "Reference to the process realized or hosted by the ASICs";
              }
            }
      
         }
      }
     }
    }
}
