module Cisco-IOS-XE-cts {
  namespace "http://cisco.com/ns/yang/Cisco-IOS-XE-cts";
  prefix ios-cts;

  import cisco-semver {
    prefix cisco-semver;
  }
  import ietf-inet-types {
    prefix inet;
  }
  import Cisco-IOS-XE-native {
    prefix ios;
  }
  import Cisco-IOS-XE-types {
    prefix ios-types;
  }
  import Cisco-IOS-XE-features {
    prefix ios-features;
  }
  import Cisco-IOS-XE-acl {
    prefix ios-acl;
  }
  import Cisco-IOS-XE-crypto {
    prefix ios-crypto;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Cisco TrustSec (CTS) Yang model.
     Copyright (c) 2017, 2020 by Cisco Systems, Inc.
     All rights reserved.";

  revision 2021-03-01 {
    description
      "- Deprecate enforcement leaf.
       - Deprecate sxp enable leaf, add new leaf sxp-def-enable boolean type.
       - Add new leaf enforcement-switching for interface level enforcement deprecated model";
  }
  revision 2020-11-01 {
    description
      "- Deprecated current CTS-SXP-CONNECTION model and modelled as required.;
       - All nodes of old CTS-SXP-CONNECTION model moved to 'obsolete' state.";
  }
  revision 2020-07-01 {
    description
      "-Added default value for 'propagate sgt' under 'cts manual';
       - Added constraints in role-based permissions to handle dependency";
  }
  revision 2020-03-01 {
    description
      "- Deprecated ipv4 leaf under policy-server-address. Added new 
       ipv4 and ipv6 leaf-list
       - Deprecated sg-epg leaf under cts. Added new optional keyword 
       ignore-vrf as leaf";
  }
  revision 2019-11-01 {
    description
      "- Added policy-server configuration support";
    cisco-semver:module-version "1.1.0";
  }
  revision 2019-07-01 {
    description
      "- Establish semantic version baseline
        - Added support for sgt group for virtual-template
        - Added range for cts role-based sgt-map sgt
        - Corrected cts role-based sgt-map behavior";
    cisco-semver:module-version "1.0.0";
  }
  revision 2019-01-22 {
    description
      "Added leaf for App-hosting Gigabit Ethernet interface";
  }
  revision 2018-12-03 {
    description
      "Added Description for cts role-based enforcement";
  }
  revision 2017-11-27 {
    description
      "Added Change 25GE name";
  }
  revision 2017-11-14 {
    description
      "Add 100GE interface";
  }
  revision 2017-09-14 {
    description
      "This revision has changes for new 2gig interface addition";
  }
  revision 2017-08-16 {
    description
      "This revision has changes for new 5gig and 25gig interfaces addition";
  }
  revision 2017-06-29 {
    description
      "This revison fix the problem in cts roll-based enforcement";
  }
  revision 2017-06-16 {
    description
      "Extension for model CTS role-based commands under interface";
  }
  revision 2017-04-28 {
    description
      "inet:ipv6-prefix changed to ios-types:ipv6-prefix";
  }
  revision 2017-03-23 {
    description
      "NED extension- Trustsec Routing - interface cts options";
  }
  revision 2017-03-07 {
    description
      "NED extension- Trustsec Routing - cts options";
  }
  revision 2017-02-07 {
    description
      "Initial revision";
  }

  typedef hex-string {
    type string {
      length "8" {
        error-message "node-id length should be 8";
      }
      pattern "([0-9A-F]*)";
    }
    description
      "A hexadecimal digits of length 4 bytes";
  }

  grouping cts-server-grouping {
    leaf deadtime {
      description
        "Configure how long a server marked as dead should not be used";
      type uint32 {
        range "0..864000";
      }
    }
    leaf enable {
      description
        "Enable server liveness automated test";
      type boolean;
    }
    leaf idle-time {
      description
        "Configure how often to send an automated test message";
      type uint32 {
        range "0..14400";
      }
    }
  }

  grouping connection-vrf-grouping {
    leaf vrf {
      description
        "Name of the vrf this connection is in";
      status obsolete;
      type string;
    }
  }

  grouping cts-sxp-connection-mode-both-grouping {
    container both {
      status obsolete;
      description
        "Configure the mode as both";
      presence "true";
      uses connection-vrf-grouping;
    }
  }

  grouping cts-sxp-connection-holdtime-min-grouping {
    container hold-time {
      status obsolete;
      description
        "Connection hold time period";
      leaf min-time {
        status obsolete;
        description
          "Enter minimum allowed Hold Time in seconds (0: apply global, 65535: no keepalive)";
        type uint16 {
          range "0..65535";
        }
      }
      uses connection-vrf-grouping;
    }
    uses connection-vrf-grouping;
  }

  grouping cts-sxp-connection-holdtime-min-max-grouping {
    container hold-time {
      status obsolete;
      description
        "Connection hold time period";
      leaf min-time {
        status obsolete;
        description
          "Enter minimum allowed Hold Time in seconds (0: apply global, 65535: no keepalive)";
        type uint16 {
          range "0..65535";
        }
      }
      leaf max-time {
        status obsolete;
        description
          "Enter maximum allowed Hold Time in seconds (0: apply global, 65535: no keepalive)";
        type uint16 {
          range "0..65535";
        }
      }
      uses connection-vrf-grouping;
    }
    uses connection-vrf-grouping;
  }

  grouping cts-sxp-connection-mode-local-grouping {
    container local {
      status obsolete;
      description
        "Configure the mode on the local device";
      presence "true";
      uses cts-sxp-connection-mode-both-grouping;
      container listener {
        status obsolete;
        description
          "Receive SXP messages on the conn";
        presence "true";
        uses cts-sxp-connection-holdtime-min-max-grouping;
      }
      container speaker {
        status obsolete;
        description
          "Send SXP messages on the conn";
        presence "true";
        uses cts-sxp-connection-holdtime-min-grouping;
      }
    }
  }

  grouping cts-sxp-connection-mode-peer-grouping {
    container peer {
      status obsolete;
      description
        "Configure the mode on the peer device";
      presence "true";
      uses cts-sxp-connection-mode-both-grouping;
      container listener {
        status obsolete;
        description
          "Receive SXP messages on the conn";
        presence "true";
        uses cts-sxp-connection-holdtime-min-grouping;
      }
      container speaker {
        status obsolete;
        description
          "Send SXP messages on the conn";
        presence "true";
        uses cts-sxp-connection-holdtime-min-max-grouping;
      }
    }
  }

  grouping cts-sxp-connection-peer-password-grouping {
    list password {
      status obsolete;
      max-elements "1";
      key "password-type";
      description
        "password details";
      leaf password-type {
        status obsolete;
        type enumeration {
          enum "default";
          enum "none";
          enum "key-chain";
        }
      }
      container mode {
        status obsolete;
        description
          "Specify SXP connection mode";
        uses cts-sxp-connection-mode-local-grouping;
        uses cts-sxp-connection-mode-peer-grouping;
      }
    }
  }

  grouping config-cts-grouping {
    container cache {
      description
        "CTS cache configuration";
      leaf enable {
        description
          "Enable CTS cache support";
        type empty;
      }
      container nv-storage {
        description
          "CTS nv-storage options";
        leaf nv-storage {
          type enumeration {
            enum "bootflash:";
            enum "crashinfo:";
            enum "kinfo:";
            enum "slot0:";
            enum "usb0:";
          }
        }
      }
    }
    leaf critical-authentication-conf {
      type empty;
    }
    container critical-authentication {
      description
        "Critical-Auth configuration commands";
      presence "true";
      container default {
        description
          "Enter default value";
        container peer-sgt {
          description
            "Default Peer SGT value";
          list range {
            key "range";
            leaf range {
              description
                "Enter default peer-sgt value";
              type uint16 {
                range "2..65519";
              }
            }
            leaf trusted {
              description
                "Trust the Source Group Tags that peer uses for sending";
              type empty;
            }
          }
        }
        container pmk {
          description
            "Default PMK value to be used for all SAP";
          leaf type {
            type enumeration {
              enum "0";
              enum "6";
            }
          }
          leaf secret {
            type string;
          }
        }
      }
      container fallback {
        description
          "Access policy to be applied in Critical-Auth";
        leaf Cached {
          description
            "Cached values to be used for existing sessions";
          type empty;
        }
        leaf default {
          description
            "Configured values to be applied for existing sessions";
          type empty;
        }
      }
    }
    container authorization {
      description
        "CTS global authorization configuration";
      leaf list {
        description
          "Local authorization list to use for CTS";
        type string {
          length "1..64" {
            error-message "list name length exceeds maximum allowed 64";
          }
        }
      }
    }
    leaf dot1x-server-timeout {
      description
        "Timeout for Radius Retries";
      type uint16 {
        range "30..65535";
      }
    }
    leaf dot1x-supp-timeout {
      description
        "Timeout for supplicant reply";
      type uint16 {
        range "30..65535";
      }
    }
    leaf logging {
      description
        "Set logging parameters";
      type enumeration {
        enum "verbose";
      }
    }
    container environment-data {
      description
        "Download environment-data over HTTPS";
      leaf enable {
        description
          "Enable environment-data download";
        type empty;
      }
    }
    container role-based {
      description
        "Role-based Access Control configuration commands";
      leaf sgt-caching {
        description
          "Enable SGT caching";
        type empty;
      }
      container permissions {
        description
          "Permissions from a source group to a destination group";
        container default {
          description
            "Default Permission list";
          leaf-list ACL-name {
            description
              "Role-based Access-list name";
            must "/ios:native/ios:ip/ios:access-list/ios-acl:role-based[ios-acl:name=current()] and /ios:native/ios:ip/ios:access-list/ios-acl:role-based[ios-acl:name=current()]/ios-acl:access-list-seq-rule" {
              error-message "Please define Role-based ACL first and make sure it is not empty";
            }
            max-elements "8";
            type string;
          }
          leaf name {
            status deprecated;
            description
              "Role-based Access-list name";
            must "/ios:native/ios:ip/ios:access-list/ios-acl:role-based[ios-acl:name=current()] and /ios:native/ios:ip/ios:access-list/ios-acl:role-based[ios-acl:name=current()]/ios-acl:access-list-seq-rule" {
              error-message "Please define Role-based ACL first and make sure it is not empty";
            }
            type string;
          }
          container ipv6 {
            description
              "Protocol Version - IPv6";
            leaf-list ACL-name {
              description
                "Role-based Access-list name";
              must "/ios:native/ios:ipv6/ios:access-list/ios-acl:named-rb-acl[ios-acl:name=current()] and /ios:native/ios:ipv6/ios:access-list/ios-acl:named-rb-acl[ios-acl:name=current()]/ios-acl:access-list-seq-rule" {
                error-message "Please define Role-based ACL first and make sure it is not empty";
              }
              max-elements "8";
              type string;
            }
          }
        }
        container from {
          description
            "Source Group Tag (SGT) of filtered traffic";
          list range {
            key "range";
            leaf range {
              description
                "Security Group Tag";
              type uint16 {
                range "0..65519";
              }
            }
            container to {
              description
                "Destination Group Tag (DGT) of filtered traffic";
              list range {
                key "range";
                leaf range {
                  description
                    "Security Group Tag";
                  type uint16 {
                    range "0..65519";
                  }
                }
                leaf-list ACL-name {
                  description
                    "Role-based Access-list name";
                  must "/ios:native/ios:ip/ios:access-list/ios-acl:role-based[ios-acl:name=current()] and /ios:native/ios:ip/ios:access-list/ios-acl:role-based[ios-acl:name=current()]/ios-acl:access-list-seq-rule" {
                    error-message "Please define Role-based ACL first and make sure it is not empty";
                  }
                  max-elements "8";
                  type string;
                }
                leaf name {
                  status deprecated;
                  must "/ios:native/ios:ip/ios:access-list/ios-acl:role-based[ios-acl:name=current()] and /ios:native/ios:ip/ios:access-list/ios-acl:role-based[ios-acl:name=current()]/ios-acl:access-list-seq-rule" {
                    error-message "Please define Role-based ACL first and make sure it is not empty";
                  }
                  type string;
                }
                container ipv6 {
                  description
                    "Protocol Version - IPv6";
                  leaf-list ACL-name {
                    description
                      "Role-based Access-list name";
                    must "/ios:native/ios:ipv6/ios:access-list/ios-acl:named-rb-acl[ios-acl:name=current()] and /ios:native/ios:ipv6/ios:access-list/ios-acl:named-rb-acl[ios-acl:name=current()]/ios-acl:access-list-seq-rule" {
                      error-message "Please define Role-based ACL first and make sure it is not empty";
                    }
                    max-elements "8";
                    type string;
                  }
                }
              }
            }
          }
        }
      }
      container enforcement-only {
        leaf enforcement {
          description
            "Enable Role-based Access Control enforcement";
          type empty;
        }
      }
      container enforcement {
        description
          "Enable Role-based Access Control enforcement";
        leaf logging-interval {
          description
            "Configure sgacl logging interval";
          type uint32 {
            range "5..86400";
          }
        }
        list vlan-list {
          description
            "VLANs on which Role-based ACLs are enforced";
          key "id";
          leaf id {
            description
              "VLAN id";
            type union {
              type string;
              type enumeration {
                enum "all";
              }
            }
          }
        }
      }
      container monitor {
        description
          "Role-based Access List Monitor Commands";
        leaf all {
          description
            "Monitoring permissions for all source group to all destination group";
          type empty;
        }
      }
      list sgt-map-list {
        description
          "Assign Security Group Tag (SGT) to IP host or network address";
        key "ip";
        leaf ip {
          description
            "IPv4/IPv6 Host Address";
          type union {
            type inet:ipv4-address;
            type inet:ipv4-prefix;
            type inet:ipv6-address;
            type ios-types:ipv6-prefix;
          }
        }
        leaf sgt {
          description
            "Security Group Tag (SGT)";
          type uint16 {
            range "2..65519";
          }
        }
        leaf host {
          description
            "Host IP Address";
          type empty;
        }
      }
      container sgt-map-vrf-list {
        description
          "Select VPN Routing/Forwarding instance for the binding";
        list sgt-map {
          must
            "(/ios:native/ios:vrf/ios:definition[ios:name=current()/vrf] and ((/ios:native/ios:vrf/ios:definition[ios:name=current()/vrf]/ios:address-family/ios:ipv4) and (contains(current()/ip, '.'))) or
             ((/ios:native/ios:vrf/ios:definition[ios:name=current()/vrf]/ios:address-family/ios:ipv6) and (contains(current()/ip, ':')))) or (/ios:native/ios:ip/ios:vrf[ios:name=current()/vrf] and (contains(current()/ip, '.')))" {
            error-message "VRF must be created/deleted first with address-family IPv4/IPv6 corresponding to binding";
          }
          key "vrf ip";
          leaf vrf {
            description
              "Select VPN Routing/Forwarding instance for the binding";
            type string;
          }
          leaf ip {
            description
              "IPv4/IPv6 Host Address";
            type union {
              type inet:ipv4-address;
              type inet:ipv4-prefix;
              type inet:ipv6-address;
              type ios-types:ipv6-prefix;
            }
          }
          leaf sgt {
            description
              "Security Group Tag (SGT)";
            type uint16 {
              range "2..65519";
            }
          }
          leaf host {
            description
              "Host IP Address";
            type empty;
          }
        }
      }
      list sgt-map {
        status deprecated;
        description
          "Assign Security Group Tag (SGT) to IP host or network address";
        key "ip sgt";
        leaf ip {
          status deprecated;
          type union {
            type inet:ipv4-address;
            type inet:ipv4-prefix;
            type inet:ipv6-address;
            type ios-types:ipv6-prefix;
          }
        }
        leaf sgt {
          status deprecated;
          description
            "Security Group Tag (SGT)";
          type uint16;
        }
        leaf vrf {
          status deprecated;
          description
            "Select VPN Routing/Forwarding instance for the binding";
          type string;
        }
        leaf host {
          status deprecated;
          type empty;
        }
      }
      container sgt-map-vlan-list {
        description
          "VLANs on which Role-based ACLs are enforced";
        list sgt-map {
          key "vlan-list";
          leaf vlan-list {
            description
              "VLANs id";
            type union {
              type string;
              type enumeration {
                enum "all";
              }
            }
          }
          leaf sgt {
            description
              "Security Group Tag value";
            type int16;
          }
        }
      }
    }
    container server {
      description
        "CTS server list configuration";
      leaf deadtime {
        description
          "Configure server group deadtime to specify how long a servermarked as dead should not be used";
        type uint32 {
          range "0..864000";
        }
      }
      container key-wrap {
        description
          "CTS key-wrap configuration";
        leaf enable {
          description
            "Enable CTS key-wrap for Private server-list";
          type empty;
        }
      }
      container load-balance {
        description
          "CTS Server group load-balancing options";
        container method {
          description
            "Method by which the next server will be picked";
          container least-outstanding {
            description
              "Pick the server with the least transactions outstanding";
            presence "true";
            leaf batch-size {
              description
                "Size of the transaction batch that should be load-balanced";
              type uint32 {
                range "1..2147483647";
              }
            }
            leaf ignore-preferred-server {
              description
                "Do not attempt to stick with the same server throughout a session";
              type empty;
            }
          }
        }
      }
      container test {
        description
          "Configure server automated test for liveness check";
        list server {
          key "ip";
          leaf ip {
            type inet:ipv4-address;
          }
          uses cts-server-grouping;
        }
        container all {
          description
            "Configure for all servers";
          uses cts-server-grouping;
        }
      }
    }
    leaf sgt {
      description
        "Local device security group";
      type uint16 {
        range "2..65519";
      }
    }
    container sg-epg-translation {
      description
        "Security-Group and Endpoint-Group Configuration commands";
      container translation {
        description
          "Sets Security-Group to Endpoint-Group translation status";
        presence "true";
        leaf ignore-vrf {
          if-feature "ios-features:sg-epg-ignore-vrf";
          description
            "Disable vrf awareness";
          type empty;
        }
      }
    }
    leaf sg-epg {
      status deprecated;
      description
        "This node is deprecated and replaced by container sg-epg-translation";
      type enumeration {
        enum "translation";
      }
    }
    container sxp {
      description
        "CTS sxp configuration";
      container reconciliation {
        description
          "Configure reconciliation period timer";
        leaf period {
          description
            "Enter reconciliation period value in seconds";
          type uint32 {
            range "0..64000";
          }
          default "120";
        }
      }
      container retry {
        description
          "configure retry period for sxp connection";
        leaf period {
          description
            "Enter retry period value for sxp connection in seconds";
          type uint32 {
            range "0..64000";
          }
          default "120";
        }
      }
      container speaker {
        description
          "Configure speaker hold-time";
        leaf hold-time {
          description
            "Enter speaker hold-time value in seconds";
          type uint32 {
            range "1..65534";
          }
          default "120";
        }
      }
      container node-id {
        description
          "Enter values for sxp node";
        choice nodeid {
          description
            "Enter any one of the three options for node-id";
          leaf hex-value {
            type hex-string;
            default "00000000";
          }
          leaf ipv4 {
            type inet:ipv4-address;
          }
          leaf interface {
            description
              "Interface Name";
            type string;
            must
              "(/ios:native/ios:interface/*[concat(local-name(.), ios:name) = current()]) and
               (/ios:native/ios:interface/*[concat(local-name(.), ios:name) = current()]/ios:ip/ios:address/ios:primary/ios:address)" {
              error-message "Please configure an IPv4 address on the interface first.";
            }
          }
        }
      }
      container listener {
        description
          "Configure min and max hold time for listener in seconds";
        container hold-time {
          description
            "Configure min and max hold time in seconds";
          leaf min-time {
            description
              "Enter minimum allowed Hold Time in seconds";
            type uint16 {
              range "1..65534";
            }
            default "90";
          }
          leaf max-time {
            description
              "Enter maximum allowed Hold Time in seconds";
            must ". > ../min-time" {
              error-message "Invalid minimum,maximum hold time parameters";
            }
            type uint16 {
              range "1..65534";
            }
            default "180";
          }
        }
      }
      container default {
        description
          "Enter default value";
        container password {
          leaf type {
            type enumeration {
              enum "0";
              enum "6";
              enum "7";
            }
          }
          leaf secret {
            type string {
              length "1..162";
            }
          }
        }
        leaf source-ip {
          description
            "Enter Source IPv4 Address";
          type inet:ipv4-address;
        }
        leaf key-chain {
          description
            "Enter Keychain";
          must "/ios:native/ios:key/ios-crypto:chain[ios-crypto:name=current()]" {
            error-message "Invalid TCP key-chain name or key-chain doesn't exist";
          }
          type string;
        }
      }
      container connection {
        description
          "CTS SXP Connection Configuration";
        container peer {
          description
            "SXP Peer IP address";
          list ipv4-no-vrf {
            key "ipv4";
            leaf ipv4 {
              description
                "Enter SXP Peer IP address (IPv4)";
              type inet:ipv4-address;
            }
            leaf source {
              description
                "Enter SXP Source IP address (IPv4)";
              type inet:ipv4-address;
            }
            leaf password {
              description
                "Password type";
              type enumeration {
                enum "default";
                enum "none";
                enum "key-chain";
              }
            }
            leaf mode {
              description
                "Mode of connection";
              type enumeration {
                enum "local";
                enum "peer";
              }
            }
            leaf option {
              description
                "Role of a device speaker/listener/both";
              type enumeration {
                enum "both";
                enum "listener";
                enum "speaker";
              }
              default "speaker";
            }
            leaf hold-time {
              description
                "Minimum hold time period";
              when "../option = 'listener' or ../option = 'speaker'";
              type uint32 {
                range "0..65535";
              }
              default "0";
            }
            leaf max-time {
              description
                "Maximum hold time period";
              when "(../mode = 'local' and ../option = 'listener') or (../mode = 'peer' and ../option = 'speaker')";
              must "(. > ../hold-time) or (. = 0 and ../hold-time = 0)" {
                error-message "Max value must be greater than min value";
              }
              type uint32 {
                range "0..65535";
              }
              default "0";
            }
          }
          list ipv4-with-vrf {
            key "ipv4 vrf";
            leaf ipv4 {
              description
                "Enter SXP Peer IP address (IPv4)";
              type inet:ipv4-address;
            }
            leaf vrf {
              description
                "VRF details";
              must "/ios:native/ios:vrf/ios:definition[ios:name=current()]" {
                error-message "VRF must be created first and deleted last";
              }
              type string;
            }
            leaf source {
              description
                "Enter SXP Source IP address (IPv4)";
              type inet:ipv4-address;
            }
            leaf password {
              description
                "Password type";
              type enumeration {
                enum "default";
                enum "none";
                enum "key-chain";
              }
            }
            leaf mode {
              description
                "Mode of connection";
              type enumeration {
                enum "local";
                enum "peer";
              }
            }
            leaf option {
              description
                "Role of a device speaker/listener/both";
              type enumeration {
                enum "both";
                enum "listener";
                enum "speaker";
              }
              default "speaker";
            }
            leaf hold-time {
              description
                "Minimum hold time period";
              when "../option = 'listener' or ../option = 'speaker'";
              type uint32 {
                range "0..65535";
              }
              default "0";
            }
            leaf max-time {
              description
                "Maximum hold time period";
              when "(../mode = 'local' and ../option = 'listener') or (../mode = 'peer' and ../option = 'speaker')";
              must "(. > ../hold-time) or (. = 0 and ../hold-time = 0)" {
                error-message "Max value must be greater than min value";
              }
              type uint32 {
                range "0..65535";
              }
              default "0";
            }
          }
          list ipv4 {
            status obsolete;
            key "ipv4";
            leaf ipv4 {
              status obsolete;
              description
                "Enter SXP Peer IP address (IPv4)";
              type inet:ipv4-address;
            }
            container source {
              status obsolete;
              description
                "Source IP address";
              list ipv4 {
                status obsolete;
                key "ipv4";
                leaf ipv4 {
                  status obsolete;
                  description
                    "Enter SXP Source IP address (IPv4)";
                  type inet:ipv4-address;
                }
                uses cts-sxp-connection-peer-password-grouping;
              }
            }
            uses cts-sxp-connection-peer-password-grouping;
          }
        }
      }
      leaf sxp-def-enable {
        description
          "Enable CTS SXP support";
        type boolean;
        default "false";
      }
      leaf enable {
        status deprecated;
        description
          "Enable CTS SXP support";
        type empty;
      }
      container log {
        description
          "SXP logging";
        leaf binding-changes {
          description
            "Log SXP binding changes";
          type boolean;
          default "false";
        }
      }
    }
    container credentials {
      description
        "Insert CTS device ID and password into the keystore";
      leaf id {
        description
          "Specify the TrustSec Network Access Device (NAD) identification name which should be same as mentioned in the Identity Services Engine (ISE)(upto 32 char)";
        type string {
          length "1..32";
        }
      }
      leaf password {
        description
          "Set the password for the device.";
        type empty;
      }
      leaf type {
        description
          "Specify the password encryption type";
        type enumeration {
          enum "0";
          enum "6";
          enum "7";
        }
      }
      leaf secret {
        description
          "Specify the password for the device";
        type string {
          length "1..162";
          pattern ".*";
        }
      }
    }
    container policy-server {
      description
        "CTS Http Server Configuration";
      list name {
        description
          "Configure name of the server, max string length 225 char";
        key "server-profile-name";
        leaf server-profile-name {
          description
            "Specify a profile name";
          type string {
            length "1..225";
          }
        }
        container address {
          description
            "Policy server address";
          leaf-list ipv4-address {
            description
              "IPv4 Address of policy server";
            max-elements "8";
            type inet:host;
          }
          leaf ipv4 {
            status deprecated;
            description
              "IPv4 Address (DEPRECATED, use ipv4-entry)";
            type union {
              type string;
              type inet:ipv4-address;
            }
          }
          leaf-list ipv6 {
            description
              "IPv6 Address of policy server";
            max-elements "8";
            type inet:host;
          }
          leaf domain-name {
            description
              "A fully qualified URL, max string length 128 char";
            type string {
              length "1..128";
            }
          }
        }
        container content-type {
          description
            "Application content type";
          leaf json {
            description
              "data format in REST API";
            type empty;
          }
        }
        leaf port {
          description
            "Policy server port number";
          type uint16 {
            range "1025..65535";
          }
        }
        leaf retransmit {
          description
            "Maximum number of retries to server";
          type uint8 {
            range "0..5";
          }
        }
        leaf timeout {
          description
            "Time to wait for response";
          type uint8 {
            range "1..60";
          }
        }
        container tls {
          description
            "TLS parameters";
          leaf server-trustpoint {
            description
              "Server trustpoint, max string length 128 char";
            type string {
              length "1..128";
            }
          }
        }
      }
      container device-id {
        description
          "Device id parameter";
        leaf device-name {
          description
            "Name of the device used on ISE";
          type string;
        }
      }
      container order {
        description
          "Order of server selection";
        leaf random {
          description
            "Pick a server in random order";
          type empty;
        }
      }
      container server-credential {
        description
          "Credentials to access the REST API";
        leaf username {
          description
            "Specify the username for the user";
          type string;
        }
        leaf password {
          description
            "Set the password for the user";
          type empty;
        }
        leaf encryption {
          description
            "Specify the password encryption type";
          type enumeration {
            enum "0";
            enum "6";
            enum "7";
          }
        }
        leaf password-string {
          type string {
            pattern ".*";
          }
        }
      }
    }
  }

  grouping interface-cts-manual-grouping {
    container manual {
      description
        "Supply local configuration for CTS parameters";
      presence "true";
      container policy {
        description
          "CTS policy for manual mode";
        container static {
          description
            "Configure policy to be applied on the link";
          leaf sgt {
            description
              "Source Security Group Tag to apply to untagged or non-trusted 
               incoming traffic";
            type uint16 {
              range "2..65519";
            }
          }
          leaf trusted {
            description
              "Trust the Source Group Tags (SGT) that the peer uses for 
               sending";
            must "(../../../propagate/sgt = 'true')" {
              error-message
                "CTS Link in Manual mode with 'no propagate sgt'
                 configured cannot be made trusted";
            }
            type empty;
          }
        }
      }
      container sap {
        description
          "CTS SAP configuration for manual mode";
        list pmk {
          description
            "Pre-Master Key (PMK) to use for CTS SAP";
          key "word";
          leaf word {
            type string;
          }
          container mode-list {
            description
              "List of advertised modes (prioritized from highest to lowest)";
            container gcm-encrypt {
              description
                "GCM authentication, GCM encryption";
              presence "true";
              container gmac {
                description
                  "GCM authentication, no encryption";
                presence "true";
                leaf null {
                  description
                    "Encapsulation present, no authentication, 
                     no encryption";
                  type empty;
                }
              }
            }
            container no-encap {
              description
                "No encapsulation";
              presence "true";
              container gmac {
                description
                  "GCM authentication, no encryption";
                presence "true";
                leaf gcm-encrypt {
                  description
                    "GCM authentication, GCM encryption";
                  type empty;
                }
              }
            }
          }
        }
      }
      container propagate {
        description
          "CTS SGT Propagation configuration for manual mode";
        leaf sgt {
          description
            "CTS SGT Propagation configuration";
          type boolean;
          default "true";
        }
      }
    }
  }

  grouping interface-cts-role-based-grouping {
    container role-based {
      description
        "Role-based Access Control per-port config commands";
      leaf-list sgt-cache {
        description
          "Enable SGT caching on the interface";
        type enumeration {
          enum "egress";
          enum "ingress";
        }
      }
      leaf enforcement-routing {
        description
          "Enable Role-based Access Control enforcement";
        must "not(/ios:native/ios:cts/ios-cts:role-based/ios-cts:enforcement-only/ios-cts:enforcement and current() = 'true')" {
          error-message "Note that role-based enforcement is already active on this interfacedue to global enforcement enable.";
        }
        must "not(../../../ios:vrf/ios:forwarding and (../../../ios:vrf/ios:forwarding='Mgmt-intf'or ../../../ios:vrf/ios:forwarding='Mgmt-vrf'))";
        if-feature "ios-features:enforcement-routing-platform";
        type boolean;
      }
      leaf enforcement-switching {
        if-feature "ios-features:cts-switching";
        description
          "Enable Role-based Access Control enforcement";
        type boolean;
        default "true";
      }
      leaf enforcement {
        status deprecated;
        description
          "Enable Role-based Access Control enforcement";
        type empty;
      }
      container sgt-map {
        description
          "Assign Security Group Tag (SGT) to IP host or network address";
        leaf security-group {
          description
            "Security Group Name";
          type string;
        }
        leaf sgt {
          description
            "Security Group Tag (SGT)";
          type uint16 {
            range "2..65519";
          }
        }
      }
    }
  }

  grouping interface-cts-role-based-enforcement-grouping {
    container role-based {
      description
        "Role-based Access Control per-port config commands";
      leaf enforcement {
        description
          "Enable Role-based Access Control enforcement";
        type empty;
      }
    }
  }

  grouping interface-cts-sgt-grouping {
    leaf sgt {
      description
        "SGT command options";
      type enumeration {
        enum "inline";
      }
    }
  }

  grouping config-interface-cts-manual-grouping {
    container cts {
      description
        "Configure Cisco Trusted Security";
      uses interface-cts-manual-grouping;
    }
  }

  grouping config-interface-cts-manual-role-based-enforcement-grouping {
    container cts {
      description
        "Configure Cisco Trusted Security";
      uses interface-cts-manual-grouping;
      uses interface-cts-role-based-enforcement-grouping;
    }
  }

  grouping config-interface-cts-manual-role-based-grouping {
    container cts {
      description
        "Configure Cisco Trusted Security";
      uses interface-cts-manual-grouping;
      uses interface-cts-role-based-grouping;
    }
  }

  grouping config-interface-cts-manual-sgt-grouping {
    container cts {
      description
        "Configure Cisco Trusted Security";
      uses interface-cts-manual-grouping;
      uses interface-cts-sgt-grouping;
    }
  }

  grouping config-interface-cts-manual-role-based-sgt-grouping {
    container cts {
      description
        "Configure Cisco Trusted Security";
      uses interface-cts-manual-grouping;
      uses interface-cts-role-based-grouping;
      uses interface-cts-sgt-grouping;
    }
  }

  grouping config-interface-cts-role-based-grouping {
    container cts {
      description
        "Configure Cisco Trusted Security";
      uses interface-cts-role-based-grouping;
    }
  }

  augment "/ios:native/ios:cts" {
    uses config-cts-grouping;
  }
  augment "/ios:native/ios:interface/ios:FastEthernet" {
    uses config-interface-cts-manual-role-based-grouping;
  }
  augment "/ios:native/ios:interface/ios:GigabitEthernet" {
    uses config-interface-cts-manual-role-based-grouping;
  }
  augment "/ios:native/ios:interface/ios:TwoGigabitEthernet" {
    uses config-interface-cts-manual-role-based-grouping;
  }
  augment "/ios:native/ios:interface/ios:FiveGigabitEthernet" {
    uses config-interface-cts-manual-role-based-grouping;
  }
  augment "/ios:native/ios:interface/ios:AppGigabitEthernet" {
    uses config-interface-cts-manual-role-based-grouping;
  }
  augment "/ios:native/ios:interface/ios:TenGigabitEthernet" {
    uses config-interface-cts-manual-role-based-grouping;
  }
  augment "/ios:native/ios:interface/ios:TwentyFiveGigE" {
    uses config-interface-cts-manual-role-based-grouping;
  }
  augment "/ios:native/ios:interface/ios:FortyGigabitEthernet" {
    uses config-interface-cts-manual-role-based-enforcement-grouping;
  }
  augment "/ios:native/ios:interface/ios:HundredGigE" {
    uses config-interface-cts-manual-role-based-enforcement-grouping;
  }
  augment "/ios:native/ios:interface/ios:Loopback" {
    uses config-interface-cts-manual-role-based-grouping;
  }
  augment "/ios:native/ios:interface/ios:Tunnel" {
    uses config-interface-cts-manual-role-based-sgt-grouping;
  }
  augment "/ios:native/ios:interface/ios:Port-channel" {
    uses config-interface-cts-manual-grouping;
  }
  augment "/ios:native/ios:interface/ios:Virtual-Template" {
    uses config-interface-cts-manual-sgt-grouping;
  }
  augment "/ios:native/ios:interface/ios:VirtualPortGroup" {
    uses config-interface-cts-manual-grouping;
  }
  augment "/ios:native/ios:interface/ios:Vlan" {
    uses config-interface-cts-manual-grouping;
  }
  augment "/ios:native/ios:interface/ios:LISP" {
    uses config-interface-cts-role-based-grouping;
  }
}
