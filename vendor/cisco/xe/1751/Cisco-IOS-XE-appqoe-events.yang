module Cisco-IOS-XE-appqoe-events {
  yang-version 1;
  namespace "http://cisco.com/ns/yang/Cisco-IOS-XE-appqoe-events";
  prefix appqoe-ios-xe-events;

  import Cisco-IOS-XE-appqoe-types {
    prefix appqoe-types-ios-xe;
  }
  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AppQoE events operational data.
     Copyright (c) 2017-2018, 2020 by Cisco Systems, Inc.
     All rights reserved.";

  revision 2021-03-01 {
    description
      "- Added clear leaf to alarm notification.";
    reference
      "1.1.0";
    cisco-semver:module-version "1.1.0";
  }
  revision 2020-11-01 {
    description
      "Initial revision";
    reference
      "1.0.0";
    cisco-semver:module-version "1.0.0";
  }

  typedef appqoe-alarm-id {
    type enumeration {
      enum alarm-id-undefined {
        value 0;
        description
          "An unexpected condition has been detected";
      }
      enum alarm-id-sn-state-held-down {
        value 1;
        description
          "Service Node in Held-Down state";
      }
      enum alarm-id-sn-state-down {
        value 2;
        description
          "Service Node in Down state";
      }
      enum alarm-id-sn-state-green {
        value 3;
        description
          "Service Node in Green state";
      }
      enum alarm-id-sn-state-yellow {
        value 4;
        description
          "Service Node in Yellow state";
      }
      enum alarm-id-sn-state-red {
        value 5;
        description
          "Service Node in Red state";
      }
      enum alarm-id-site-id-mismatch {
        value 6;
        description
          "Service Node Site-ID does not match Service Controller Site-ID";
      }
      enum alarm-id-system-ip {
        value 7;
        description
          "There is an issue with the device System-IP";
      }
      enum alarm-id-unknown-site-id {
        value 8;
        description
          "Service Node Site-ID is unknown or not defined";
      }
    }
    description
      "Alarm ID";
  }

  typedef appqoe-event-id {
    type enumeration {
      enum event-id-undefined {
        value 0;
        description
          "An unexpected condition has been detected";
      }
      enum event-id-sn-state-green {
        value 1;
        description
          "Service Node in Green state";
      }
    }
    description
      "Event ID";
  }

  typedef appqoe-cause {
    type enumeration {
      enum cause-undefined {
        value 0;
        description
          "The cause is undefined";
      }
      enum cause-bringup {
        value 1;
        description
          "Service has been started";
      }
      enum cause-shutdown {
        value 2;
        description
          "Service has been stopped";
      }
      enum cause-configuration-error {
        value 3;
        description
          "Configuration error encountered";
      }
      enum cause-internal-error {
        value 4;
        description
          "Internal error encountered";
      }
      enum cause-resource-error {
        value 5;
        description
          "Resource error encountered";
      }
      enum cause-resource-overload {
        value 6;
        description
          "A resource has been exhausted";
      }
      enum cause-connection-established {
        value 7;
        description
          "Connection to peer has been established";
      }
      enum cause-connection-lost {
        value 8;
        description
          "Connection to peer has been lost";
      }
      enum cause-too-many-restarts {
        value 9;
        description
          "An AppQoE service has been restarted multiple times";
      }
      enum cause-unknown-system-ip {
        value 10;
        description
          "System-IP is unknown or not defined";
      }
      enum cause-unknown-site-id {
        value 11;
        description
          "Service Node Site-ID is unknown or not defined";
      }
      enum cause-site-id-mismatch {
        value 12;
        description
          "Service Node Site-ID does not match Service Controller Site-ID";
      }
    }
    description
      "AppQoE Notification cause/reason";
  }

  typedef appqoe-action {
    type enumeration {
      enum action-undefined {
        value 0;
        description
          "The action is undefined";
      }
      enum action-na {
        value 1;
        description
          "No action needs to be taken";
      }
      enum action-check-network-conn {
        value 2;
        description
          "Verify network connection to Service Node is UP";
      }
      enum action-check-appqoe-state {
        value 3;
        description
          "Verify AppQoE feature is in Operational";
      }
      enum action-restart-appqoe {
        value 4;
        description
          "Restart the AppQoE service";
      }
      enum action-resolve-config-error {
        value 5;
        description
          "Resolve the Configuration error";
      }
      enum action-contact-tac {
        value 6;
        description
          "Please contact TAC for further assistance";
      }
    }
    description
      "Recommended action to be taken to resolve the issue";
  }

  grouping appqoe-alarm-notification {
    description
      "AppQoE Alarm Notification";
    leaf severity-level {
      type ios-common-ios-xe-oper:notification-severity;
      description
        "Alarm notification severity";
    }
    leaf host-name {
      type string;
      description
        "Service Controller Hostname";
    }
    leaf system-ip {
      type inet:ip-address;
      description
        "Service Controller System-IP";
    }
    leaf alarm-id {
      type appqoe-ios-xe-events:appqoe-alarm-id;
      description
        "Uniquely identifies the alarm type";
    }
    leaf device-mode {
      type appqoe-types-ios-xe:appqoe-device-mode;
      description
        "Device Mode";
    }
    leaf module {
      type string;
      description
        "AppQoE Module";
    }
    leaf headline {
      type string;
      description
        "Brief description of the alarm";
    }
    leaf cause {
      type appqoe-ios-xe-events:appqoe-cause;
      description
        "If known, provides an explanation of why the alarm was generated";
    }
    leaf action {
      type appqoe-ios-xe-events:appqoe-action;
      description
        "Any action, including steps that can be taken";
    }
    leaf detail {
      type string;
      description
        "Detailed description of the alarm";
    }
    leaf sn-system-ip {
      type inet:ip-address;
      description
        "Service Node System-IP";
    }
    leaf clear {
      type boolean;
      description
        "Indicates if alarm is being raised or cleared";
    }
  }

  grouping appqoe-event-notification {
    description
      "AppQoE Event Notification";
    leaf severity-level {
      type ios-common-ios-xe-oper:notification-severity;
      description
        "Alarm notification severity";
    }
    leaf host-name {
      type string;
      description
        "Service Controller Hostname";
    }
    leaf system-ip {
      type inet:ip-address;
      description
        "Service Controller System-IP";
    }
    leaf event-id {
      type appqoe-ios-xe-events:appqoe-event-id;
      description
        "Uniquely identifies the event type";
    }
    leaf device-mode {
      type appqoe-types-ios-xe:appqoe-device-mode;
      description
        "Device Mode";
    }
    leaf module {
      type string;
      description
        "AppQoE Module";
    }
    leaf headline {
      type string;
      description
        "Brief description of the alarm";
    }
    leaf cause {
      type appqoe-ios-xe-events:appqoe-cause;
      description
        "If known, provides an explanation of why the alarm was generated";
    }
    leaf action {
      type appqoe-ios-xe-events:appqoe-action;
      description
        "Any action, including steps that can be taken";
    }
    leaf detail {
      type string;
      description
        "Detailed description of the alarm";
    }
    leaf sn-system-ip {
      type inet:ip-address;
      description
        "Service Node System-IP";
    }
  }

  notification appqoe-alarm {
    description
      "AppQoE Alarm Notification";
    uses appqoe-ios-xe-events:appqoe-alarm-notification;
  }

  notification appqoe-event {
    description
      "AppQoE Event Notification";
    uses appqoe-ios-xe-events:appqoe-event-notification;
  }
}
