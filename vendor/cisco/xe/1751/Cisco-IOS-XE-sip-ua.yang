submodule Cisco-IOS-XE-sip-ua {
  belongs-to Cisco-IOS-XE-voice {
    prefix ios-voice;
  }

  import cisco-semver {
    prefix cisco-semver;
  }
  import Cisco-IOS-XE-native {
    prefix ios;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native sip-ua Yang model.
     Copyright (c) 2020 by Cisco Systems, Inc.
     All rights reserved.";

  revision 2021-03-01 {
    description
      "- Added sip-ua";
    cisco-semver:module-version "1.0.0";
  }

  grouping config-sip-ua-grouping {
    container sip-ua {
      description
        "SIP User Agent (UA)";
      presence "true";
      container crypto {
        description
          "sip-ua crypto commands";
        container signaling {
          description
            "Configure crypto signaling for sip-ua configuration mode";
          container default {
            description
              "Configure the default trust point";
            leaf tls-profile {
              description
                "Associate a tls-profile";
              type leafref {
                path "/ios:native/voice/class/tls-profile/id";
              }
            }
          }
          list remote-addr {
            description
              "Associate an IP network to a trustpoint";
            max-elements "10";
            key "ipv4address subnetmask";
            leaf ipv4address {
              description
                "Enter the IP address";
              type inet:ipv4-address;
            }
            leaf subnetmask {
              description
                "Enter the mask";
              type union {
                type inet:ipv4-address;
                type string {
                  pattern "/([0-9]|[1-2][0-9]|3[0-2])";
                }
              }
            }
            leaf tls-profile {
              description
                "Associate a tls-profile";
              mandatory true;
              type leafref {
                path "/ios:native/voice/class/tls-profile/id";
              }
            }
          }
        }
      }
      container transport {
        description
          "Enable SIP UA transport for TCP/UDP";
        leaf udp {
          description
            "Enable SIP User Agent in UDP Mode";
          type boolean;
          default "true";
        }
        leaf tcp {
          description
            "Enable SIP User Agent in TCP Mode";
          type boolean;
          default "true";
        }
        container tcp-tls {
          container tcp {
            description
              "Enable SIP User Agent in TCP Mode";
            choice tls-choice {
              default "tls";
              case tls {
                leaf tls {
                  description
                    "Enable SIP User Agent in TLS over TCP mode (Default: All TLS versions with fallback)";
                  type boolean;
                  default "true";
                }
              }
              case tls-version {
                container tls-version {
                  container tls {
                    description
                      "Enable SIP User Agent in TLS over TCP mode (Default: All TLS versions with fallback)";
                    leaf version {
                      type enumeration {
                        enum "v1.0" {
                          description
                            "Enable TLS Version 1.0";
                        }
                        enum "v1.1" {
                          description
                            "Enable TLS Version 1.1";
                        }
                        enum "v1.2" {
                          description
                            "Enable TLS Version 1.2";
                        }
                      }
                    }
                  }
                }
              }
            }
          }
        }
      }
      leaf sip-server {
        description
          "Configure a SIP Server Interface";
        type string {
          pattern "(dns:.*)|(ipv4:[0-9]+\\.[0-9]+\\.[0-9]+\\.[0-9]+(:[0-9]+)?)|(ipv6:\\[([0-9A-Fa-f.:])+\\](:[0-9]+)?)" {
            error-message "Must be of the form (dns:.*)|(ipv4:[0-9]+.[0-9]+.[0-9]+.[0-9]+(:[0-9]+)?) | ((ipv6:[([0-9A-Fa-f.:])+](:[0-9]+)?))";
          }
        }
      }
      container reason-header {
        description
          "Configure settings for supporting SIP Reason Header";
        leaf override {
          description
            "Enable Reason header to override SIP<->Q850 Mappings";
          type empty;
        }
      }
      container retry {
        description
          "Change default retries for each SIP Method";
        leaf bye {
          description
            "BYE retry value";
          type uint8 {
            range "1..10";
          }
          default "10";
        }
        leaf cancel {
          description
            "CANCEL retry value";
          type uint8 {
            range "1..10";
          }
          default "10";
        }
        leaf info {
          description
            "INFO retry value";
          type uint8 {
            range "1..10";
          }
          default "6";
        }
        leaf invite {
          description
            "INVITE retry value";
          type uint8 {
            range "1..10";
          }
          default "6";
        }
        leaf keepalive {
          description
            "KEEPALIVE retry value";
          type uint8 {
            range "1..10";
          }
          default "6";
        }
        leaf notify {
          description
            "NOTIFY retry value";
          type uint8 {
            range "1..10";
          }
          default "10";
        }
        leaf options {
          description
            "OPTIONS retry value";
          type uint8 {
            range "1..10";
          }
          default "6";
        }
        leaf prack {
          description
            "PRACK retry value";
          type uint8 {
            range "1..10";
          }
          default "10";
        }
        leaf refer {
          description
            "REFER retry value";
          type uint8 {
            range "1..10";
          }
          default "10";
        }
        leaf register {
          description
            "REGISTER retry value";
          type uint8 {
            range "1..10";
          }
          default "6";
        }
        leaf rel1xx {
          description
            "Reliable 1xx retry value";
          type uint8 {
            range "1..10";
          }
          default "6";
        }
        leaf response {
          description
            "Response retry value";
          type uint8 {
            range "1..10";
          }
          default "6";
        }
        leaf subscribe {
          description
            "SUBSCRIBE retry value";
          type uint8 {
            range "1..10";
          }
          default "6";
        }
        leaf update {
          description
            "UPDATE retry value";
          type uint8 {
            range "1..10";
          }
          default "6";
        }
      }
      container timers {
        description
          "SIP Signaling Timers Configuration";
        leaf buffer-invite {
          description
            "Time to buffer the INVITE while waiting for display info";
          type uint16 {
            range "50..5000";
          }
        }
        leaf connect {
          description
            "Time to wait for confirmation a session connected";
          type uint16 {
            range "100..1000";
          }
          default "500";
        }
        container connection {
          description
            "Connection related timers";
          container aging {
            description
              "Time to wait before aging out a TCP/UDP connection";
            leaf value {
              description
                "TCP/UDP aging timer value in minutes";
              type uint16 {
                range "5..1440";
              }
              default "5";
            }
            leaf tls {
              description
                "TCP/UDP aging timer value in minutes";
              type uint16 {
                range "60..4320";
              }
              default "60";
            }
          }
        }
        leaf disconnect {
          description
            "Time to wait for confirmation a session disconnected";
          type uint16 {
            range "100..1000";
          }
          default "500";
        }
        container dns {
          description
            "Expiry timer value for the DNS resolved address cache";
          container registrar-cache {
            description
              "DNS cache refresh time for registrar";
            choice cache-choice {
              case timer-val {
                leaf timer {
                  description
                    "timer value in seconds";
                  type uint16 {
                    range "60..65535";
                  }
                }
              }
              case ttl-val {
                leaf ttl {
                  description
                    "timer value to be set as ttl seconds";
                  type empty;
                }
              }
            }
          }
        }
        leaf expires {
          description
            "Time to wait for the expiration of an INVITE request";
          type uint32 {
            range "60000..1800000";
          }
          default "180000";
        }
        leaf hold {
          description
            "Time to wait during hold before disconnecting";
          type uint16 {
            range "15..2880";
          }
          default "2880";
        }
        leaf info {
          description
            "Time to wait before INFO retransmission";
          type uint16 {
            range "100..1000";
          }
          default "500";
        }
        container keepalive {
          description
            "Options keepalive related timers";
          leaf active {
            description
              "Time to wait between keepalive messages in active state";
            type uint16 {
              range "10..600";
            }
            default "120";
          }
          leaf down {
            description
              "Time to wait between keepalive messages in down state";
            type uint8 {
              range "1..120";
            }
            default "30";
          }
        }
        leaf notify {
          description
            "Time to wait before NOTIFY retransmission";
          type uint16 {
            range "100..1000";
          }
          default "500";
        }
        leaf options {
          description
            "Time to wait before OPTIONS retransmission";
          type uint16 {
            range "100..1000";
          }
          default "500";
        }
        leaf prack {
          description
            "Time to wait before PRACK retransmission";
          type uint16 {
            range "100..1000";
          }
          default "500";
        }
        leaf refer {
          description
            "Time to wait before REFER retransmission";
          type uint16 {
            range "100..1000";
          }
          default "500";
        }
        leaf register {
          description
            "Time to wait before REGISTER retransmission";
          type uint16 {
            range "100..1000";
          }
          default "500";
        }
        leaf rel1xx {
          description
            "Time to wait before starting reliable 1xx retransmission";
          type uint16 {
            range "100..1000";
          }
          default "500";
        }
        leaf trying {
          description
            "Time to wait for provisional response to INVITE";
          type uint16 {
            range "100..1000";
          }
          default "500";
        }
        leaf update {
          description
            "Time to wait before starting UPDATE retransmission";
          type uint16 {
            range "100..1000";
          }
          default "500";
        }
      }
    }
  }
}
