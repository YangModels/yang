/*
 * Generated by confdc --mib2yang-std
 * Source: mgmt/dmi/model/mib/src/patched/DOCS-IF31-MIB.mib
 */
/*
 * This YANG module has been generated by smidump 0.5.0:
 *
 *      smidump -f yang DOCS-IF31-MIB
 *
 * Do not edit. Edit the source file instead!
 */

module DOCS-IF31-MIB {

  namespace "urn:ietf:params:xml:ns:yang:smiv2:DOCS-IF31-MIB";
  prefix DOCS-IF31-MIB;

  import DOCS-IF-MIB {
    prefix "docs-if";
  }

  import DOCS-IF3-MIB {
    prefix "docs-if3";
  }

  import IF-MIB {
    prefix "if-mib";
  }

  import SNMPv2-TC {
    prefix "snmpv2-tc";
  }

  import ietf-yang-smiv2 {
    prefix "smiv2";
  }

  import ietf-yang-types {
    prefix "yang";
  }

  organization
   "Cable Television Laboratories, Inc.";

  contact
   "
    Postal: Cable Television Laboratories, Inc.
    858 Coal Creek Circle
    Louisville, Colorado 80027-9750
    U.S.A.
    Phone: +1 303-661-9100
    Fax:   +1 303-661-9199
    E-mail: mibs@cablelabs.com";

  description
   "This MIB module contains the management objects for the
    management of DOCSIS 3.1 features, primarily OFDM and OFDMA
    channels.
    Copyright 2017 Cable Television Laboratories, Inc.
    All rights reserved.";

  revision 2017-07-27 {
    description
     "Revised per ECN DOCS-IF31-MIB-N-17.1765-1
      for changing docsIf31RxChStatusTable to apply to CM only.
      Only descriptive text is changed.";
  }

  revision 2017-05-25 {
    description
     "Revised Version includes ECN change for diplexer objects
      DOCS-IF31-MIB-N-17.1733-1";
  }

  revision 2016-12-15 {
    description
     "Revised Version includes ECN
      DOCS-IF31-MIB-N-16.1621-3.";
  }

  revision 2016-08-18 {
    description
     "Revised Version includes ECN
      DOCS-IF31-MIB-N-16.1549-3.";
  }

  revision 2016-05-05 {
    description
     "Revised Version includes ECN
      CCAP-OSSIv3.1-N-16.1472-4;
      supersedes CCAP-OSSIv3.1-N-16.1432-3.";
  }

  revision 2015-11-04 {
    description
     "Revised per CM-OSSIv3.1-N-15.1385-3,
      which rolls up changes from the following ECNs:
      CM-OSSIv3.1-N-15.1375-1 and CCAP-OSSIv3.1-N-15.1376-1,
      adding additional indices for the
      docsIf31CmUsOfdmaMinislotCfgStateTable per the OSSI-CM spec.";
  }

  revision 2015-07-15 {
    description
     "Revised Version includes ECN
      CCAP-OSSIv3.1-N-15.1324-1";
  }

  revision 2015-05-20 {
    description
     "Revised Version includes ECN
      CCAP-OSSIv3.1-N-15.1308-2
      Synchronized with
      CM-SP-CM-OSSIv3.1-I04 and
      CM-SP-CCAP-OSSIv3.1-I04";
  }

  revision 2015-04-08 {
    description
     "Initial version, per CCAP-OSSIv3.1-N-15.1278-4";
  }

  typedef ClabsDocsisVersion {
    type enumeration {
      enum "other" {
        value "0";
      }
      enum "docsis10" {
        value "1";
      }
      enum "docsis11" {
        value "2";
      }
      enum "docsis20" {
        value "3";
      }
      enum "docsis30" {
        value "4";
      }
      enum "docsis31" {
        value "5";
      }
    }
    description
     "Indicates the DOCSIS Radio Frequency specification being
      referenced.
      'docsis10' indicates DOCSIS 1.0.
      'docsis11' indicates DOCSIS 1.1.
      'docsis20' indicates DOCSIS 2.0.
      'docsis30' indicates DOCSIS 3.0.
      'docsis31' indicates DOCSIS 3.1.";
  }

  typedef EmIdList {
    type string;
    description
     "A list of Energy Management Ids displayed as a comma-separated
      list of 15-bit hexadecimal values. These values are encoded into
      16-bits but the high-order bit is always 0.";
    smiv2:display-hint "2x,";
  }

  typedef SubcarrierSpacingType {
    type int32 {
      range "25|50";
    }
    description
     "This data type defines the subcarrier spacing for the FFT
      mode in use. For downstream OFDM channels, if the FFT mode
      is 4K mode, then spacing is 50 kHz; if it is 8K mode, then
      the spacing is 25 kHz. For upstream OFDMA channels, if the
      FFT mode is 2K mode, then the spacing is 50kHz; if the mode
      is 4K mode, then the spacing is 25kHz. In units of kHz.";
    reference
     "DOCSIS 3.1 Physical Layer Specification CM-SP-PHYv3.1-I03-140610,
      Downstream OFDM Parameters and Upstream OFDMA Parameters tables.";
    smiv2:display-hint "d";
  }

  typedef PrimaryDsIndicatorType {
    type enumeration {
      enum "other" {
        value "1";
      }
      enum "primary" {
        value "2";
      }
      enum "backupPrimary" {
        value "3";
      }
      enum "nonPrimary" {
        value "4";
      }
    }
    description
     "This data type is defined to represent the channel indicator
      type for the downstream channel.";
  }

  typedef OfdmProfiles {
    type bits {
      bit profile0 {
        position "0";
      }
      bit profile1 {
        position "1";
      }
      bit profile2 {
        position "2";
      }
      bit profile3 {
        position "3";
      }
      bit profile4 {
        position "4";
      }
      bit profile5 {
        position "5";
      }
      bit profile6 {
        position "6";
      }
      bit profile7 {
        position "7";
      }
      bit profile8 {
        position "8";
      }
      bit profile9 {
        position "9";
      }
      bit profile10 {
        position "10";
      }
      bit profile11 {
        position "11";
      }
      bit profile12 {
        position "12";
      }
      bit profile13 {
        position "13";
      }
      bit profile14 {
        position "14";
      }
      bit profile15 {
        position "15";
      }
    }
    description
     "This data type enumerates the configured channel profiles on
      the CM.";
  }

  typedef DsOfdmCyclicPrefix {
    type uint32 {
      range "192|256|512|768|1024";
    }
    description
     "This data type is defined to indicate the five possible values
      for the length of cyclic prefix.  This represents the number
      of samples of the 204.8 MHz clock";
    smiv2:display-hint "d";
  }

  typedef UsOfdmaCyclicPrefix {
    type uint32 {
      range "96|128|160|192|224|256|288|320|384|512|640";
    }
    description
     "This data type is defined to indicate the eleven possible values
      for the length of cyclic prefix. The cyclic prefix represents the
      number of samples of the 204.8 MHz clock.";
    smiv2:display-hint "d";
  }

  typedef DsOfdmRollOffPeriod {
    type uint32 {
      range "0|64|128|192|256";
    }
    description
     "This data type is defined to indicate the five possible values
      for the windowing roll-off period. This represents the number
      of samples of the 204.8 MHz clock.";
    smiv2:display-hint "d";
  }

  typedef UsOfdmaRollOffPeriod {
    type uint32 {
      range "0|32|64|96|128|160|192|224";
    }
    description
     "This data type is defined to indicate the eight possible values
      for the windowing roll-off period. This represents the number
      of samples of the 204.8 MHz clock";
    smiv2:display-hint "d";
  }

  typedef TimeInterleaverDepth {
    type uint32 {
      range "1..32";
    }
    description
     "This data type is defined to indicate the depth of time
      interleaving used for this downstream channel in symbols.";
    smiv2:display-hint "d";
  }

  typedef DsOfdmModulationType {
    type enumeration {
      enum "unknownQam" {
        value "0";
      }
      enum "other" {
        value "1";
      }
      enum "zeroValued" {
        value "2";
      }
      enum "qpsk" {
        value "3";
      }
      enum "qam16" {
        value "4";
      }
      enum "qam64" {
        value "5";
      }
      enum "qam128" {
        value "6";
      }
      enum "qam256" {
        value "7";
      }
      enum "qam512" {
        value "8";
      }
      enum "qam1024" {
        value "9";
      }
      enum "qam2048" {
        value "10";
      }
      enum "qam4096" {
        value "11";
      }
      enum "qam8192" {
        value "12";
      }
      enum "qam16384" {
        value "13";
      }
    }
    description
     "This data type is defined to indicate the bit loading of
      subcarriers in an OFDM downstream channel.";
    reference
     "DOCSIS 3.1 Physical layer Specification CM-SP-PHYv3.1-I03-140610,
      Modulation Formats section.";
  }

  typedef UsOfdmaModulationType {
    type enumeration {
      enum "other" {
        value "1";
      }
      enum "zeroValued" {
        value "2";
      }
      enum "bpsk" {
        value "3";
      }
      enum "qpsk" {
        value "4";
      }
      enum "qam8" {
        value "5";
      }
      enum "qam16" {
        value "6";
      }
      enum "qam32" {
        value "7";
      }
      enum "qam64" {
        value "8";
      }
      enum "qam128" {
        value "9";
      }
      enum "qam256" {
        value "10";
      }
      enum "qam512" {
        value "11";
      }
      enum "qam1024" {
        value "12";
      }
      enum "qam2048" {
        value "13";
      }
      enum "qam4096" {
        value "14";
      }
    }
    description
     "This data type is defined to indicate the bit loading of
      subcarriers in an OFDMA upstream channel.";
    reference
     "DOCSIS 3.1 Physical layer Specification CM-SP-PHYv3.1-I03-140610,
      Modulation Formats section.";
  }

  typedef PartialChannelType {
    type bits {
      bit fecErrorsDsProfile {
        position "0";
      }
      bit fecErrorsNcpProfile {
        position "1";
      }
      bit fecErrorsPlc {
        position "2";
      }
    }
    description
     "This data type enumerates each of the possible profiles or channel
      attributes which can contribute to an OFDM channel being considered
      a Partial Channel by the MAC layer. As more than one of these error
      conditions can exist at the same time this data type is based on a
      BITS data type. The bits from low to high are:
              Bit 0: fecErrorsDsProfile
              Bit 1: fecErrorsNcpProfile
              Bit 2: fecErrorsPlc";
    reference
     "DOCSIS 3.1 MAC and Upper Layer Protocols Interface
      Specification CM-SP-MULPIv3.1-I03-140610,
      CM Status Report section.";
  }

  typedef PartialServiceType {
    type enumeration {
      enum "unknown" {
        value "0";
      }
      enum "other" {
        value "1";
      }
      enum "none" {
        value "2";
      }
      enum "partialSvcDsOnlyImpaired" {
        value "3";
      }
      enum "partialSvcUsOnlyImpaired" {
        value "4";
      }
      enum "partialSvcDsAndUsImpaired" {
        value "5";
      }
    }
    description
     "This data type enumerates the type of channel issue which the
      MAC Layer indicates is causing the CM to be in DOCSIS 3.0 Partial
      Service mode. The possible values are as follows:
             other(1)
             none(2)
             partialSvcDsOnlyImpaired(3)
             partialSvcUsOnlyImpaired(4)
             partialSvcDsAndUsImpaired(5)";
    reference
     "DOCSIS 3.1 MAC and Upper Layer Protocols Interface
      Specification CM-SP-MULPIv3.1-I03-140610,
      CM Status Report section.";
  }

  typedef PartialChanReasonType {
    type enumeration {
      enum "none" {
        value "0";
      }
      enum "dsOfdmProfileFailure" {
        value "16";
      }
      enum "dpdMismatch" {
        value "18";
      }
      enum "ncpProfileFailure" {
        value "20";
      }
      enum "plcFailure" {
        value "21";
      }
    }
    description
     "This data type enumerates the CM-STATUS events which
      a CM can utilize to report a Partial Channel situation.";
    reference
     "DOCSIS 3.1 MAC and Upper Layer Protocols Interface
      Specification CM-SP-MULPIv3.1-I03-140610,
      CM Status Report section.";
  }

  typedef PartialSvcReasonType {
    type enumeration {
      enum "none" {
        value "0";
      }
      enum "secondaryChanMddTimeout" {
        value "1";
      }
      enum "lostFecLock" {
        value "2";
      }
    }
    description
     "This data type enumerates the CM-STATUS events which
      a CM can utilize to report a Partial Service situation.";
    reference
     "DOCSIS 3.1 MAC and Upper Layer Protocols Interface
      Specification CM-SP-MULPIv3.1-I03-140610,
      CM Status Report section.";
  }

  typedef HundredthdBmV {
    type int32;
    description
     "This data type represents power levels that are normally
      expressed in dBmV.  Units are in hundredths of a dBmV;
      for example, 5.17 dBmV will be represented as 517.";
    smiv2:display-hint "d-2";
  }

  typedef HundredthdB {
    type int32;
    description
     "This data type represents power levels that are normally
      expressed in dB.  Units are in hundredths of a dB;
      for example, 5.17 dB will be represented as 517.";
    smiv2:display-hint "d-2";
  }


  container DOCS-IF31-MIB {
    config false;

    container docsIf31MibObjects {
      smiv2:oid "1.3.6.1.4.1.4491.2.1.28.1";

      leaf docsIf31DocsisBaseCapability {
        type DOCS-IF31-MIB:ClabsDocsisVersion;
        description
         "This attribute reports the DOCSIS capability of the device.
          A CMTS reports its highest supported DOCSIS version while
          a CM reports its supported DOCSIS version.
          
          This attribute replaces docsIfDocsisBaseCapability defined
          in RFC 4546.";
        smiv2:max-access "read-only";
        smiv2:oid "1.3.6.1.4.1.4491.2.1.28.1.1";
      }
    }

    container docsIf31CmSystemCfgState {
      smiv2:oid "1.3.6.1.4.1.4491.2.1.28.1.18";

      leaf docsIf31CmSystemCfgStateDiplexerCapability {
        type uint32;
        description
         "This attribute specifies the maximum diplexer upstream upper band edge
          supported by the CM device. This corresponds to the maximum
          capability reported by the CM in the Diplexer Upstream Upper Band Edge
          modem capability.";
        reference
         "DOCSIS 3.1 MAC and Upper Layer Protocols Interface
          Specification CM-SP-MULPIv3.1-I11-xxxxxx,
          Diplexer Upstream Upper Band Edge section.";
        smiv2:max-access "read-only";
        smiv2:oid "1.3.6.1.4.1.4491.2.1.28.1.18.1";
      }

      leaf docsIf31CmSystemCfgStateDiplexerCfgBandEdge {
        type uint32;
        description
         "This attribute specifies the current configured value for the upstream
          upper band edge of the diplexer in the CM device. This corresponds
          to the Diplexer Upstream Upper Band Edge Configuration reported by the
          CM in its REG-REQ.";
        reference
         "DOCSIS 3.1 MAC and Upper Layer Protocols Interface
          Specification CM-SP-MULPIv3.1-I11-xxxxxx,
          Diplexer Upstream Upper Band Edge Configuration section.";
        smiv2:max-access "read-only";
        smiv2:oid "1.3.6.1.4.1.4491.2.1.28.1.18.2";
      }

      leaf docsIf31CmSystemCfgStateDiplexerDsLowerCapability {
        type uint32;
        description
         "This attribute specifies the minimum diplexer downstream
          lower band edge supported by the CM device. This corresponds
          to the minimum capability reported by the CM in the Diplexer
          Downstream Lower Band Edge modem capability.";
        reference
         "DOCSIS 3.1 MAC and Upper Layer Protocols Interface
          Specification CM-SP-MULPIv3.1-I11-xxxxxx,
          Diplexer Downstream Lower Band Edge section.";
        smiv2:max-access "read-only";
        smiv2:oid "1.3.6.1.4.1.4491.2.1.28.1.18.3";
      }

      leaf docsIf31CmSystemCfgStateDiplexerCfgDsLowerBandEdge {
        type uint32;
        description
         "This attribute specifies the current configured value for the
          downstream lower band edge of the diplexer in the CM device. This
          corresponds to the Diplexer Downstream Lower Band Edge Configuration
          reported by the CM in its REG-REQ.";
        reference
         "DOCSIS 3.1 MAC and Upper Layer Protocols Interface
          Specification CM-SP-MULPIv3.1-I11-xxxxxx,
          Diplexer Downstream Lower Band Edge Configuration section.";
        smiv2:max-access "read-only";
        smiv2:oid "1.3.6.1.4.1.4491.2.1.28.1.18.4";
      }

      leaf docsIf31CmSystemCfgStateDiplexerDsUpperCapability {
        type uint32;
        description
         "This attribute specifies the maximum diplexer downstream
          upper band edge supported by the CM device. This corresponds
          to the maximum capability reported by the CM in the Diplexer
          Downstream Upper Band Edge modem capability.";
        reference
         "DOCSIS 3.1 MAC and Upper Layer Protocols Interface
          Specification CM-SP-MULPIv3.1-I11-xxxxxx,
          Diplexer Downstream Upper Band Edge section.";
        smiv2:max-access "read-only";
        smiv2:oid "1.3.6.1.4.1.4491.2.1.28.1.18.5";
      }

      leaf docsIf31CmSystemCfgStateDiplexerCfgDsUpperBandEdge {
        type uint32;
        description
         "This attribute specifies the current configured value for the
          Downstream upper band edge of the diplexer in the CM device.
          This corresponds to the Diplexer Downstream Upper Band Edge
          Configuration reported by the CM in its REG-REQ.";
        reference
         "DOCSIS 3.1 MAC and Upper Layer Protocols Interface
          Specification CM-SP-MULPIv3.1-I11-xxxxxx,
          Diplexer Downstream Upper Band Edge Configuration section.";
        smiv2:max-access "read-only";
        smiv2:oid "1.3.6.1.4.1.4491.2.1.28.1.18.6";
      }
    }

    container docsIf31RxChStatusTable {
      description
       "The Receive Channel Status object reports the status
        of the statically-configured and dynamically-created
        Receive Channels within an RCC.
        This table is supported by the CM only.";
      smiv2:oid "1.3.6.1.4.1.4491.2.1.28.1.2";

      list docsIf31RxChStatusEntry {
        key "ifIndex";
        description
         "The conceptual row of docsIf31RxChStatusTable.";
        smiv2:oid "1.3.6.1.4.1.4491.2.1.28.1.2.1";

        leaf ifIndex {
          type leafref {
            path "/if-mib:IF-MIB/if-mib:ifTable/if-mib:ifEntry/if-mib:ifIndex";
          }
        }

        leaf docsIf31RxChStatusPrimaryDsIndicator {
          type DOCS-IF31-MIB:PrimaryDsIndicatorType;
          description
           "This attribute is used to identify the downstream channel
            as primary, backup primary or non-primary. A value of
            'primary(2)' indicates that OFDM channel is assigned to be the
            CM's primary downstream channel. A value of 'backupPrimary(3)'
            indicates that the OFDM channel is assigned to be the CM's
            backup primary downstream channel. A value of 'nonPrimary(4)'
            indicates the OFDM channel is not assigned to be CM's primary
            or backup primary downstream channel.";
          smiv2:max-access "read-only";
          smiv2:oid "1.3.6.1.4.1.4491.2.1.28.1.2.1.1";
        }

        leaf docsIf31RxChStatusOfdmProfiles {
          type DOCS-IF31-MIB:OfdmProfiles;
          description
           "This attribute is used to identify the downstream channel
            profiles provisioned on the CM.
            
            Example: A Cable Modem configured with OFDM Profiles 3 and 8
            returns a query response as follows.
            EnumBits: 0001000010000000 or 0x1080.
            
            Default value is 0x0.  The SC-QAM is always reported as
            the default value.";
          smiv2:max-access "read-only";
          smiv2:oid "1.3.6.1.4.1.4491.2.1.28.1.2.1.2";
        }
      }
    }

    container docsIf31CmtsCmUsOfdmaChannelStatusTable {
      description
       "This object defines current status information of the CM
        on each OFDMA upstream channel, as reported by the CMTS.";
      smiv2:oid "1.3.6.1.4.1.4491.2.1.28.1.4";

      list docsIf31CmtsCmUsOfdmaChannelStatusEntry {
        key "docsIf3CmtsCmRegStatusId ifIndex";
        description
         "The conceptual row of docsIf31CmtsCmUsOfdmaChannelStatusTable.
          A separate entry exists for every OFDMA channel of every CM
          currently assigned to an OFDMA channel.";
        smiv2:oid "1.3.6.1.4.1.4491.2.1.28.1.4.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf ifIndex {
          type leafref {
            path "/if-mib:IF-MIB/if-mib:ifTable/if-mib:ifEntry/if-mib:ifIndex";
          }
        }

        leaf docsIf31CmtsCmUsOfdmaChannelRxPower {
          type docs-if:TenthdBmV;
          description
           "This attribute is the total received power in a specified
            OFDMA channel, normalized to power in a 1.6 MHz bandwidth, at
            the RF input port of the CMTS for a given CM.";
          reference
           "DOCSIS 3.1 Physical layer Specification CM-SP-PHYv3.1-I03-140610,
            Upstream Channel Power section.";
          smiv2:max-access "read-only";
          smiv2:oid "1.3.6.1.4.1.4491.2.1.28.1.4.1.1";
        }

        leaf docsIf31CmtsCmUsOfdmaChannelMeanRxMer {
          type DOCS-IF31-MIB:HundredthdB;
          description
           "This attribute is the mean of the dB values of the RxMER
            measurements of all active subcarriers. The mean is computed
            directly on the dB values as follows:
            
            Mean = sum of (RxMER dB values) / number of RxMER values";
          reference
           "DOCSIS 3.1 Physical layer Specification CM-SP-PHYv3.1-I03-140610,
            Upstream Receive Modulation Error Ratio (RxMER) Per Subcarrier
            section.";
          smiv2:max-access "read-only";
          smiv2:oid "1.3.6.1.4.1.4491.2.1.28.1.4.1.2";
        }

        leaf docsIf31CmtsCmUsOfdmaChannelStdDevRxMer {
          type DOCS-IF31-MIB:HundredthdB;
          description
           "This attribute is the standard deviation of the dB values of
            the RxMER measurements of all active subcarriers. The standard
            deviation is computed directly on the dB values as follows:
            
            StdDev = sqrt(sum of (RxMER dB vals - RxMER_mean)^2 / # RxMER vals)";
          smiv2:max-access "read-only";
          smiv2:oid "1.3.6.1.4.1.4491.2.1.28.1.4.1.3";
        }

        leaf docsIf31CmtsCmUsOfdmaChannelRxMerThreshold {
          type uint32;
          units "percentile";
          description
           "This attribute specifies the percentile (such as 2nd percentile
            or 5th percentile) of all active subcarriers in an OFDM channel
            at which the ThresholdRxMerValue occurs. That is, (Percentile) %
            of the subcarriers have RxMER <= ThresholdRxMerValue.";
          smiv2:defval "2";
          smiv2:max-access "read-write";
          smiv2:oid "1.3.6.1.4.1.4491.2.1.28.1.4.1.4";
        }

        leaf docsIf31CmtsCmUsOfdmaChannelThresholdRxMerValue {
          type DOCS-IF31-MIB:HundredthdB;
          description
           "This attribute is the RxMER value corresponding to the specified
            docsIf31CmtsCmUsOfdmaChannelRxMerThreshold percentile value. The
            CCAP sorts the subcarriers in ascending order of RxMER, resulting
            in a post-sorting subcarrier index ranging from 1 to the number of
            active subcarriers. If the percentile value corresponds to a non-
            integer post-sorting subcarrier index, the post-sorting index is
            truncated (floor function is applied); that is, the post-sorting
            index is selected which is the greatest integer less than or equal
            to the corresponding percentile value. For example, if there are
            3677 active subcarriers and the 2nd percentile is specified, the
            CCAP computes floor(3677*0.02) = 73.  That is, the RxMER value of
            the 73rd subcarrier in the sorted list is associated with the 2nd
            percentile.
            This is displayed in hundredth of a dB, but is only accurate to
            a quarter dB.";
          smiv2:max-access "read-only";
          smiv2:oid "1.3.6.1.4.1.4491.2.1.28.1.4.1.5";
        }

        leaf docsIf31CmtsCmUsOfdmaChannelThresholdRxMerHighestFreq {
          type uint32;
          units "Hz";
          description
           "This attribute is the frequency in Hz of the highest-frequency
            subcarrier having RxMER = ThresholdRxMer value.";
          smiv2:max-access "read-only";
          smiv2:oid "1.3.6.1.4.1.4491.2.1.28.1.4.1.6";
        }

        leaf docsIf31CmtsCmUsOfdmaChannelMicroreflections {
          type uint32;
          units "dBc";
          description
           "This attribute represents microreflections received on this
            upstream channel in dBc.";
          smiv2:max-access "read-only";
          smiv2:oid "1.3.6.1.4.1.4491.2.1.28.1.4.1.7";
        }

        leaf docsIf31CmtsCmUsOfdmaChannelHighResolutionTimingOffset {
          type int32;
          units "time tick/(64*256)";
          description
           "This attribute represents the current measured round trip
            time on this CM's upstream channel in units of
            (6.25 microseconds/(64*256)).
            This attribute returns zero if the value is unknown.";
          smiv2:max-access "read-only";
          smiv2:oid "1.3.6.1.4.1.4491.2.1.28.1.4.1.8";
        }

        leaf docsIf31CmtsCmUsOfdmaChannelIsMuted {
          type boolean;
          description
           "This attribute has a value 'true' to indicate that the CM's
            upstream channel has been muted via CM-CTRL-REQ/CM-CTRL-RSP
            message exchange.";
          smiv2:max-access "read-only";
          smiv2:oid "1.3.6.1.4.1.4491.2.1.28.1.4.1.9";
        }

        leaf docsIf31CmtsCmUsOfdmaChannelRangingStatus {
          type docs-if3:RangingState;
          description
           "This attribute denotes the ranging state of the CM.";
          smiv2:max-access "read-only";
          smiv2:oid "1.3.6.1.4.1.4491.2.1.28.1.4.1.10";
        }

        leaf docsIf31CmtsCmUsOfdmaChannelCurPartialSvcReasonCode {
          type DOCS-IF31-MIB:PartialSvcReasonType;
          description
           "This attribute returns the current CM-STATUS Event Code which
            indicates the reason that this CM is experiencing Partial Service
            with a bonding group utilizing this upstream OFDMA channel. A
            value of 0 indicates that the CM is not currently experiencing
            Partial Service involving this OFDMA channel.";
          smiv2:max-access "read-only";
          smiv2:oid "1.3.6.1.4.1.4491.2.1.28.1.4.1.11";
        }

        leaf docsIf31CmtsCmUsOfdmaChannelLastPartialSvcTime {
          type snmpv2-tc:DateAndTime;
          description
           "This attribute returns the date and time when the MAC indicated
            that this CM recovered from its most recent Partial Service
            incident on this upstream OFDMA channel.";
          smiv2:max-access "read-only";
          smiv2:oid "1.3.6.1.4.1.4491.2.1.28.1.4.1.12";
        }

        leaf docsIf31CmtsCmUsOfdmaChannelLastPartialSvcReasonCode {
          type DOCS-IF31-MIB:PartialSvcReasonType;
          description
           "This attribute returns the last CM-STATUS Event Code which
            indicates the reason that this CM was experiencing Partial
            Service on this upstream OFDMA channel. (Note: if the CM is
            currently experiencing Partial Service, this is the Event Code
            from the previous Partial Service event.) A value of 0 indicates
            that the CM has not experienced Partial Service involving this
            OFDMA channel during the CCAP's history of this CM.";
          smiv2:max-access "read-only";
          smiv2:oid "1.3.6.1.4.1.4491.2.1.28.1.4.1.13";
        }

        leaf docsIf31CmtsCmUsOfdmaChannelNumPartialSvcIncidents {
          type yang:counter32;
          description
           "This attribute returns the number of Partial Service incidents
            the MAC layer has reported for this CM on this upstream OFDMA
            channel.";
          smiv2:max-access "read-only";
          smiv2:oid "1.3.6.1.4.1.4491.2.1.28.1.4.1.14";
        }
      }
    }

    container docsIf31CmtsCmUsOfdmaProfileStatusTable {
      description
       "This object defines current status information of the CM on
        each OFDMA upstream channel profile, as reported by the CMTS.";
      smiv2:oid "1.3.6.1.4.1.4491.2.1.28.1.5";

      list docsIf31CmtsCmUsOfdmaProfileStatusEntry {
        key "docsIf3CmtsCmRegStatusId ifIndex docsIf31CmtsUsOfdmaStatsIuc";
        description
         "The conceptual row of docsIf31CmtsCmUsOfdmaProfileStatusTable.
          A separate entry exists for every Data IUC assigned to the CM
          for every OFDMA channel of every CM currently assigned to an
          OFDMA channel.";
        smiv2:oid "1.3.6.1.4.1.4491.2.1.28.1.5.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf ifIndex {
          type leafref {
            path "/if-mib:IF-MIB/if-mib:ifTable/if-mib:ifEntry/if-mib:ifIndex";
          }
        }

        leaf docsIf31CmtsUsOfdmaStatsIuc {
          type leafref {
            path "/DOCS-IF31-MIB:DOCS-IF31-MIB/DOCS-IF31-MIB:docsIf31CmtsUsOfdmaDataIucStatsTable/DOCS-IF31-MIB:docsIf31CmtsUsOfdmaDataIucStatsEntry/DOCS-IF31-MIB:docsIf31CmtsUsOfdmaStatsIuc";
          }
        }

        leaf docsIf31CmtsCmUsOfdmaProfileTotalCodewords {
          type yang:counter64;
          description
           "This attribute represents the count of the total number
            of FEC codewords received from the CM on this Profile/Data
            IUC for this upstream OFDMA channel.
            
            Discontinuities in the value of this counter can occur at
            re-initialization of the managed system, and at other times
            as indicated by the value of ifCounterDiscontinuityTime for
            the associated upstream OFDMA channel";
          smiv2:max-access "read-only";
          smiv2:oid "1.3.6.1.4.1.4491.2.1.28.1.5.1.1";
        }

        leaf docsIf31CmtsCmUsOfdmaProfileCorrectedCodewords {
          type yang:counter64;
          description
           "This attribute represents the count of codewords received
            that failed the pre-decoding syndrome check, but passed the
            post-decoding syndrome check from the CM on this Profile/Data
            IUC for this upstream OFDMA channel.
            
            Discontinuities in the value of this counter can occur at
            re-initialization of the managed system, and at other times
            as indicated by the value of ifCounterDiscontinuityTime for
            the associated upstream OFDMA channel.";
          smiv2:max-access "read-only";
          smiv2:oid "1.3.6.1.4.1.4491.2.1.28.1.5.1.2";
        }

        leaf docsIf31CmtsCmUsOfdmaProfileUnreliableCodewords {
          type yang:counter64;
          description
           "This attribute represents the count of codewords that
            failed the post-decoding syndrome check received from the
            CM on this Profile/Data IUC for this upstream OFDMA channel.
            
            Discontinuities in the value of this counter can occur at
            re-initialization of the managed system, and at other times
            as indicated by the value of ifCounterDiscontinuityTime for
            the associated upstream OFDMA channel.";
          smiv2:max-access "read-only";
          smiv2:oid "1.3.6.1.4.1.4491.2.1.28.1.5.1.3";
        }
      }
    }

    container docsIf31CmtsCmDsOfdmChannelStatusTable {
      description
       "This object defines current status information of the CM
        on each OFDM downstream channel, as reported by the CMTS.
        A separate entry exists for every OFDM channel of every CM
        currently assigned to an OFDM channel.";
      smiv2:oid "1.3.6.1.4.1.4491.2.1.28.1.6";

      list docsIf31CmtsCmDsOfdmChannelStatusEntry {
        key "docsIf3CmtsCmRegStatusId ifIndex";
        description
         "The conceptual row of docsIf31CmtsCmDsOfdmChannelStatusTable.
          If the CM has never experienced a partial service or partial
          channel event with respect to this channel since the last CCAP
          reinitialization, no entry should exist in this table.";
        smiv2:oid "1.3.6.1.4.1.4491.2.1.28.1.6.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf ifIndex {
          type leafref {
            path "/if-mib:IF-MIB/if-mib:ifTable/if-mib:ifEntry/if-mib:ifIndex";
          }
        }

        leaf docsIf31CmtsCmDsOfdmChannelCurPartialSvcReasonCode {
          type DOCS-IF31-MIB:PartialSvcReasonType;
          description
           "This attribute returns the current CM-STATUS Event Code
            which indicates the reason that this CM is experiencing
            Partial Service with a bonding group utilizing this downstream
            OFDM channel. A value of 0 indicates that the CM is not
            currently experiencing Partial Service involving this OFDM channel.";
          smiv2:max-access "read-only";
          smiv2:oid "1.3.6.1.4.1.4491.2.1.28.1.6.1.1";
        }

        leaf docsIf31CmtsCmDsOfdmChannelLastPartialSvcTime {
          type snmpv2-tc:DateAndTime;
          description
           "This attribute returns the date and time when the MAC
            indicated that this CM recovered from its most recent
            Partial Service incident on this downstream OFDM channel.";
          smiv2:max-access "read-only";
          smiv2:oid "1.3.6.1.4.1.4491.2.1.28.1.6.1.2";
        }

        leaf docsIf31CmtsCmDsOfdmChannelLastPartialSvcReasonCode {
          type DOCS-IF31-MIB:PartialSvcReasonType;
          description
           "This attribute returns the last CM-STATUS Event Code which
            indicates the reason that this CM was experiencing Partial
            Service on this downstream OFDM channel. (Note: if the CM is
            currently experiencing Partial Service, this is the Event Code
            from the previous Partial Service event.)
            
            A value of 0 indicates that the CM has not experienced Partial
            Service involving this OFDM channel during the CCAP's history
            of this CM.";
          smiv2:max-access "read-only";
          smiv2:oid "1.3.6.1.4.1.4491.2.1.28.1.6.1.3";
        }

        leaf docsIf31CmtsCmDsOfdmChannelNumPartialSvcIncidents {
          type yang:counter32;
          description
           "This attribute returns the number of Partial Service incidents
            the MAC layer has reported for this CM on this downstream OFDM
            channel";
          smiv2:max-access "read-only";
          smiv2:oid "1.3.6.1.4.1.4491.2.1.28.1.6.1.4";
        }

        leaf docsIf31CmtsCmDsOfdmChannelNumPartialChanIncidents {
          type yang:counter32;
          description
           "This attribute returns the number of Partial Channel incidents
            the MAC layer has reported for this CM on this downstream OFDM
            channel";
          smiv2:max-access "read-only";
          smiv2:oid "1.3.6.1.4.1.4491.2.1.28.1.6.1.5";
        }
      }
    }

    container docsIf31CmtsCmDsOfdmProfileStatusTable {
      description
       "This object defines current status information of the CM on
        each OFDM downstream channel profile, as reported by the CMTS.";
      smiv2:oid "1.3.6.1.4.1.4491.2.1.28.1.7";

      list docsIf31CmtsCmDsOfdmProfileStatusEntry {
        key "docsIf3CmtsCmRegStatusId ifIndex docsIf31CmtsDsOfdmStatsProfId";
        description
         "The conceptual row of docsIf31CmtsCmDsOfdmProfileStatusTable.
          A separate entry exists for every Profile assigned to the CM
          for every OFDM channel of every CM currently assigned to an
          OFDM channel.
          If the CM has never experienced a partial channel event with
          respect to this profile since the last CCAP reinitialization,
          no entry should exist in the table.";
        smiv2:oid "1.3.6.1.4.1.4491.2.1.28.1.7.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf ifIndex {
          type leafref {
            path "/if-mib:IF-MIB/if-mib:ifTable/if-mib:ifEntry/if-mib:ifIndex";
          }
        }

        leaf docsIf31CmtsDsOfdmStatsProfId {
          type leafref {
            path "/DOCS-IF31-MIB:DOCS-IF31-MIB/DOCS-IF31-MIB:docsIf31CmtsDsOfdmProfileStatsTable/DOCS-IF31-MIB:docsIf31CmtsDsOfdmProfileStatsEntry/DOCS-IF31-MIB:docsIf31CmtsDsOfdmStatsProfId";
          }
        }

        leaf docsIf31CmtsCmDsOfdmProfilePartialChanReasonCode {
          type DOCS-IF31-MIB:PartialChanReasonType;
          description
           "This attribute returns the current CM-STATUS Event Code
            which indicates the reason that this CM is in a Partial
            Channel state utilizing this Profile on this downstream
            OFDM channel. A value of 0 indicates that the CM is not
            currently experiencing Partial Channel involving this
            Profile on this OFDM channel.";
          smiv2:max-access "read-only";
          smiv2:oid "1.3.6.1.4.1.4491.2.1.28.1.7.1.1";
        }

        leaf docsIf31CmtsCmDsOfdmProfileLastPartialChanTime {
          type snmpv2-tc:DateAndTime;
          description
           "This attribute returns the date and time when the MAC
            indicated that this CM recovered from its most recent
            Partial Channel incident for this Profile on this downstream
            OFDM channel.";
          smiv2:max-access "read-only";
          smiv2:oid "1.3.6.1.4.1.4491.2.1.28.1.7.1.2";
        }

        leaf docsIf31CmtsCmDsOfdmProfileLastPartialChanReasonCode {
          type DOCS-IF31-MIB:PartialChanReasonType;
          description
           "This attribute returns the last CM-STATUS Event Code
            which indicates the reason that this CM was experiencing
            a Partial Channel event for this Profile on this downstream
            OFDM channel. A value of 0 indicates that the CM has not
            experienced a Partial Channel incident involving this Profile
            on this OFDM channel during the CCAP's history of this CM.";
          smiv2:max-access "read-only";
          smiv2:oid "1.3.6.1.4.1.4491.2.1.28.1.7.1.3";
        }
      }
    }

    container docsIf31CmtsCmEmStatsTable {
      description
       "This table defines Energy Management mode statistics for the
        CM as reported by the CMTS.  For example, such metrics can
        provide insight into configuration of appropriate EM 1x1 Mode
        Activity Detection thresholds on the CM and/or to get feedback
        on how/if the current thresholds are working well or are
        causing user experience issues.";
      smiv2:oid "1.3.6.1.4.1.4491.2.1.28.1.8";

      list docsIf31CmtsCmEmStatsEntry {
        key "docsIf3CmtsCmRegStatusId";
        description
         "The conceptual row of docsIf31CmtsCmEmStatsTable.
          
          A row exists in this table for every CM capable of
          Energy Management (either 1x1 or DLS).";
        smiv2:oid "1.3.6.1.4.1.4491.2.1.28.1.8.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf docsIf31CmtsCmEmStatsEm1x1ModeTotalDuration {
          type uint32;
          units "seconds";
          description
           "This attribute indicates the total time duration, in seconds
            since registration, the CM identified by
            docsIf3CmtsCmRegStatusId has been in Energy Management 1x1
            mode, as controlled by the DBC-REQ Energy Management 1x1
            Mode Indicator TLV.";
          smiv2:max-access "read-only";
          smiv2:oid "1.3.6.1.4.1.4491.2.1.28.1.8.1.1";
        }

        leaf docsIf31CmtsCmEmStatsDlsModeTotalDuration {
          type uint32;
          units "seconds";
          description
           "This attribute indicates the total time duration, in seconds
            since registration, the CM identified by
            docsIf3CmtsCmRegStatusId has been in DLS mode.";
          smiv2:max-access "read-only";
          smiv2:oid "1.3.6.1.4.1.4491.2.1.28.1.8.1.2";
        }

        leaf docsIf31CmtsCmEmStatsLastDlsTime {
          type snmpv2-tc:DateAndTime;
          description
           "This attribute indicates the time of the last DLS wakeup
            event for this CM. If this CM is currently in DLS mode, then
            this attribute returns 0.";
          smiv2:max-access "read-only";
          smiv2:oid "1.3.6.1.4.1.4491.2.1.28.1.8.1.3";
        }

        leaf docsIf31CmtsCmEmStatsDlsWakeupEvents {
          type yang:counter32;
          description
           "This attribute indicates the total number of wakeup events
            that this CM has experienced over the CCAP's history for this CM.";
          smiv2:max-access "read-only";
          smiv2:oid "1.3.6.1.4.1.4491.2.1.28.1.8.1.4";
        }
      }
    }

    container docsIf31CmDsOfdmChanTable {
      description
       "This table describes the CM's downstream OFDM channels.";
      smiv2:oid "1.3.6.1.4.1.4491.2.1.28.1.9";

      list docsIf31CmDsOfdmChanEntry {
        key "ifIndex";
        description
         "The conceptual row of docsIf31CmDsOfdmChanTable.
          
          An entry exists in this table for each ifEntry with an
          ifType value of docsOfdmDownstream(277).";
        smiv2:oid "1.3.6.1.4.1.4491.2.1.28.1.9.1";

        leaf ifIndex {
          type leafref {
            path "/if-mib:IF-MIB/if-mib:ifTable/if-mib:ifEntry/if-mib:ifIndex";
          }
        }

        leaf docsIf31CmDsOfdmChanChannelId {
          type int32 {
            range "0..255";
          }
          description
           "The Cable Modem identification of the OFDM downstream channel
            within this particular MAC interface. If the interface is down,
            the object returns the most current value.  If the downstream
            channel ID is unknown, this object returns a value of 0.";
          smiv2:max-access "read-only";
          smiv2:oid "1.3.6.1.4.1.4491.2.1.28.1.9.1.1";
        }

        leaf docsIf31CmDsOfdmChanChanIndicator {
          type DOCS-IF31-MIB:PrimaryDsIndicatorType;
          description
           "This attribute is used to identify the OFDM downstream channel
            as primary, backup primary or non-primary. A value of
            'primary(2)' indicates that OFDM channel is assigned to be the
            CM's primary downstream channel. A value of 'backupPrimary(3)'
            indicates that the OFDM channel is assigned to be the CM's
            backup primary downstream channel. A value of 'nonPrimary(4)'
            indicates the OFDM channel is not assigned to be CM's primary
            or backup primary downstream channel.";
          smiv2:max-access "read-only";
          smiv2:oid "1.3.6.1.4.1.4491.2.1.28.1.9.1.2";
        }

        leaf docsIf31CmDsOfdmChanSubcarrierZeroFreq {
          type uint32;
          units "Hz";
          description
           "This attribute specifies the center frequency of the
            subcarrier 0 of the OFDM transmission. Note that since
            subcarrier 0 is always excluded, it will actually be below the
            allowed downstream spectrum band. This is the frequency of
            subcarrier X(0) in the definition of the DFT.";
          smiv2:max-access "read-only";
          smiv2:oid "1.3.6.1.4.1.4491.2.1.28.1.9.1.3";
        }

        leaf docsIf31CmDsOfdmChanFirstActiveSubcarrierNum {
          type uint32;
          description
           "This attribute corresponds to the number of the first
            non-excluded subcarrier. The valid range is 148 to 7895";
          smiv2:max-access "read-only";
          smiv2:oid "1.3.6.1.4.1.4491.2.1.28.1.9.1.4";
        }

        leaf docsIf31CmDsOfdmChanLastActiveSubcarrierNum {
          type uint32;
          description
           "This attribute corresponds to the number of the last
            non-excluded subcarrier. The valid range is 148 to 7895";
          smiv2:max-access "read-only";
          smiv2:oid "1.3.6.1.4.1.4491.2.1.28.1.9.1.5";
        }

        leaf docsIf31CmDsOfdmChanNumActiveSubcarriers {
          type uint32;
          description
           "This attribute represents the number of active data
            subcarriers within the OFDM downstream channel (i.e. this
            exclude subcarriers for continuous pilots and the PLC).
            For 4K FFT mode, the maximum number of subcarriers including
            continuous pilots and the PLC cannot exceed 3800, and for
            8K FFT mode, the maximum number of active subcarriers including
            continuous pilots and the PLC cannot be greater than 7600.
            
            However, there are a minimum of 56 continuous pilots in a 192MHz
            channel that has no exclusions, and the size of the PLC is
            8 subcarriers for 4K FFT mode and 16 subcarriers for 8K FFT mode.
            Therefore the maximum value of NumActiveSubcarriers is 3736
            (or 3800 - 56 - 8) for 4K FFT mode and 7528 (or 7600 - 56 - 16)
            for 8K FFT mode.";
          smiv2:max-access "read-only";
          smiv2:oid "1.3.6.1.4.1.4491.2.1.28.1.9.1.6";
        }

        leaf docsIf31CmDsOfdmChanSubcarrierSpacing {
          type DOCS-IF31-MIB:SubcarrierSpacingType;
          units "kHz";
          description
           "This attribute defines the subcarrier spacing associated with
            a particular FFT mode configured on the OFDM downstream
            channel. If it is 4K mode, then the subcarrier spacing is
            50kHz. If it is 8K mode, then the subcarrier spacing is
            25kHz.";
          smiv2:max-access "read-only";
          smiv2:oid "1.3.6.1.4.1.4491.2.1.28.1.9.1.7";
        }

        leaf docsIf31CmDsOfdmChanCyclicPrefix {
          type DOCS-IF31-MIB:DsOfdmCyclicPrefix;
          units "number of samples";
          description
           "Cyclic prefix enables the receiver to overcome the effects of
            inter-symbol-interference and intercarrier-interference caused
            by micro-reflections in the channel. There are five possible
            values for the length of the CP and the choice depends on the
            delay spread of the channel - a longer delay spread requires a
            longer cyclic prefix. The cyclic prefix (in usec) are converted
            into samples using the sample rate of 204.8 Msamples/s and is
            an integer multiple of: 1/64 * 20 us.";
          smiv2:max-access "read-only";
          smiv2:oid "1.3.6.1.4.1.4491.2.1.28.1.9.1.8";
        }

        leaf docsIf31CmDsOfdmChanRollOffPeriod {
          type DOCS-IF31-MIB:DsOfdmRollOffPeriod;
          units "number of samples";
          description
           "Roll off period maximizes channel capacity by sharpening the
            edges of the spectrum of the OFDM signal. For windowing
            purposes another segment at the start of the IDFT output is
            appended to the end of the IDFT output - the roll-off postfix
            (RP). There are five possible values for the (RP), and the
            choice depends on the bandwidth of the channel and the number
            of exclusion bands within the channel. A larger RP provides
            sharper edges in the spectrum of the OFDM signal; however,
            there is a time vs. frequency trade-off. Larger RP values
            reduce the efficiency of transmission in the time domain,
            but because the spectral edges are sharper, more useful
            subcarriers appear in the frequency domain. There is an
            optimum value for the RP that maximizes capacity for a given
            bandwidth and/or exclusion band scenario.";
          smiv2:max-access "read-only";
          smiv2:oid "1.3.6.1.4.1.4491.2.1.28.1.9.1.9";
        }

        leaf docsIf31CmDsOfdmChanPlcFreq {
          type uint32;
          units "Hz";
          description
           "This is the PHY Link Channel (PLC) frequency. It is the center
            frequency of the lowest frequency subcarrier of the PLC. The
            aim of the PLC is for the CMTS to convey to the CM the
            physical properties of the OFDM channel.";
          smiv2:max-access "read-only";
          smiv2:oid "1.3.6.1.4.1.4491.2.1.28.1.9.1.10";
        }

        leaf docsIf31CmDsOfdmChanNumPilots {
          type uint32;
          description
           "This attribute indicates the number of continuous pilots configured
            for the OFDM downstream channel as received in the OCD message.";
          smiv2:max-access "read-only";
          smiv2:oid "1.3.6.1.4.1.4491.2.1.28.1.9.1.11";
        }

        leaf docsIf31CmDsOfdmChanTimeInterleaverDepth {
          type DOCS-IF31-MIB:TimeInterleaverDepth;
          units "symbols";
          description
           "The time interleaving used for this downstream channel as
            received in the OCD message.";
          smiv2:max-access "read-only";
          smiv2:oid "1.3.6.1.4.1.4491.2.1.28.1.9.1.12";
        }

        leaf docsIf31CmDsOfdmChanPlcTotalCodewords {
          type yang:counter64;
          description
           "This attribute represents the total number of PLC codewords
            received by the CM.";
          smiv2:max-access "read-only";
          smiv2:oid "1.3.6.1.4.1.4491.2.1.28.1.9.1.13";
        }

        leaf docsIf31CmDsOfdmChanPlcUnreliableCodewords {
          type yang:counter64;
          description
           "This attribute represents the total number of PLC codewords
            which failed post-decoding LDPC syndrome check.";
          smiv2:max-access "read-only";
          smiv2:oid "1.3.6.1.4.1.4491.2.1.28.1.9.1.14";
        }

        leaf docsIf31CmDsOfdmChanNcpTotalFields {
          type yang:counter64;
          description
           "This attribute represents the total number of NCP fields
            received by the CM.";
          smiv2:max-access "read-only";
          smiv2:oid "1.3.6.1.4.1.4491.2.1.28.1.9.1.15";
        }

        leaf docsIf31CmDsOfdmChanNcpFieldCrcFailures {
          type yang:counter64;
          description
           "This attribute represents the total number of NCP fields
            received by the CM which failed the CRC check.";
          smiv2:max-access "read-only";
          smiv2:oid "1.3.6.1.4.1.4491.2.1.28.1.9.1.16";
        }
      }
    }

    container docsIf31CmDsOfdmProfileStatsTable {
      description
       "This CM table specifies the attributes of the Downstream
        profile assigned to an OFDM downstream channel.
        This table is not applicable to NCP profiles.";
      smiv2:oid "1.3.6.1.4.1.4491.2.1.28.1.10";

      list docsIf31CmDsOfdmProfileStatsEntry {
        key "ifIndex docsIf31CmDsOfdmProfileStatsProfileId";
        description
         "The conceptual row of docsIf31CmDsOfdmProfileStatsTable.
          
          An entry exists in this table for each DS Profile assigned to
          this CM on channels with an ifType value of
          docsOfdmDownstream(277).
          A row entry is created when a profile is assigned. The row
          entry is deleted when a profile id becomes unassigned.";
        smiv2:oid "1.3.6.1.4.1.4491.2.1.28.1.10.1";

        leaf ifIndex {
          type leafref {
            path "/if-mib:IF-MIB/if-mib:ifTable/if-mib:ifEntry/if-mib:ifIndex";
          }
        }

        leaf docsIf31CmDsOfdmProfileStatsProfileId {
          type uint32 {
            range "0..255";
          }
          description
           "This attribute is the unique identifier of the downstream
            profile associated with the OFDM downstream channel. Profile ID
            with a value of 255 corresponds to NCP profile.";
          reference
           "DOCSIS 3.1 MAC and Upper Layer Protocols Interface Specification
            CM-SP-MULPIv3.1-I03-140610, Downstream Profile Descriptor.";
          smiv2:max-access "not-accessible";
          smiv2:oid "1.3.6.1.4.1.4491.2.1.28.1.10.1.1";
        }

        leaf docsIf31CmDsOfdmProfileStatsConfigChangeCt {
          type uint32 {
            range "0..255";
          }
          description
           "This attribute contains the value of the Configuration Change
            Count field in the Downstream Profile Descriptor (DPD) MAC
            Management Message corresponding to this profile.";
          smiv2:max-access "read-only";
          smiv2:oid "1.3.6.1.4.1.4491.2.1.28.1.10.1.2";
        }

        leaf docsIf31CmDsOfdmProfileStatsTotalCodewords {
          type yang:counter64;
          description
           "This attribute defines the total number of codewords
            (including full-length and shortened) measured on this profile.";
          smiv2:max-access "read-only";
          smiv2:oid "1.3.6.1.4.1.4491.2.1.28.1.10.1.3";
        }

        leaf docsIf31CmDsOfdmProfileStatsCorrectedCodewords {
          type yang:counter64;
          description
           "This attribute defines the number of codewords measured on this
            profile that failed pre-decoding LDPC syndrome check and passed
            BCH decoding.";
          smiv2:max-access "read-only";
          smiv2:oid "1.3.6.1.4.1.4491.2.1.28.1.10.1.4";
        }

        leaf docsIf31CmDsOfdmProfileStatsUncorrectableCodewords {
          type yang:counter64;
          description
           "This attribute defines the number of codewords measured on this
            profile that failed BCH decoding.";
          smiv2:max-access "read-only";
          smiv2:oid "1.3.6.1.4.1.4491.2.1.28.1.10.1.5";
        }

        leaf docsIf31CmDsOfdmProfileStatsInOctets {
          type yang:counter64;
          description
           "This attribute is the count of MAC-layer octets received
            by the CM on this Profile. This value is the size of all
            unicast, multicast or broadcast frames (including all MAC-
            layer framing) delivered from the Phy to the MAC; this
            includes user data, DOCSIS MAC Management Messages, etc.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.6";
        }

        leaf docsIf31CmDsOfdmProfileStatsInUnicastOctets {
          type yang:counter64;
          description
           "This attribute is the count of MAC-layer unicast octets received
            by the CM on this profile. This value is the size of all unicast
            frames (including all MAC-layer framing) delivered from the Phy
            to the MAC; this includes user data, DOCSIS MAC Management
            Messages, etc.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.7";
        }

        leaf docsIf31CmDsOfdmProfileStatsInMulticastOctets {
          type yang:counter64;
          description
           "This attribute is the count of MAC-layer multicast and broadcast
            octets received by the CM on this profile. This value is the size
            of all frames (including all MAC-layer framing) delivered from the
            Phy to the MAC and addressed to a multicast MAC address;
            this includes user data, DOCSIS MAC Management Messages, etc.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.8";
        }

        leaf docsIf31CmDsOfdmProfileStatsInFrames {
          type yang:counter64;
          description
           "This attribute is the count of frames received by the CM
            on this profile. This value is the count of all unicast,
            multicast or broadcast frames delivered from the Phy to the MAC;
            this includes user data, DOCSIS MAC Management Messages, etc.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.9";
        }

        leaf docsIf31CmDsOfdmProfileStatsInUnicastFrames {
          type yang:counter64;
          description
           "This attribute is the count of frames received by the CM
            on this profile. This value is the count of all unicast,
            multicast or broadcast frames delivered from the Phy to the MAC;
            this includes user data, DOCSIS MAC Management Messages, etc.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.10";
        }

        leaf docsIf31CmDsOfdmProfileStatsInMulticastFrames {
          type yang:counter64;
          description
           "This attribute is the count of multicast frames received
            by the CM on this profile. This value is the count of all
            frames delivered from the Phy to the MAC and addressed to a
            multicast MAC address; this includes user data, DOCSIS MAC
            Management Messages, etc., but excludes frames sent to a
            broadcast address.
            
            Discontinuities in the value of this counter can occur at
            reinitialization of the managed system, and at other times as
            indicated by the value of docsIf31CmDsOfdmProfileStats-
            CtrDiscontinuityTime.";
          smiv2:max-access "read-only";
          smiv2:oid "1.3.6.1.4.1.4491.2.1.28.1.10.1.11";
        }

        leaf docsIf31CmDsOfdmProfileStatsInFrameCrcFailures {
          type yang:counter64;
          description
           "This attribute defines the number of MAC frames measured on
            this profile that failed the MAC frame CRC check.";
          smiv2:max-access "read-only";
          smiv2:oid "1.3.6.1.4.1.4491.2.1.28.1.10.1.12";
        }

        leaf docsIf31CmDsOfdmProfileStatsCtrDiscontinuityTime {
          type yang:timestamp;
          description
           "This attribute is the value of sysUpTime on the most recent
            occasion at which any one or more of this entry's counters
            suffered a discontinuity. If no such discontinuities have
            occurred since the last re-initialization of the local
            management subsystem, then this attribute contains a zero value.";
          smiv2:max-access "read-only";
          smiv2:oid "1.3.6.1.4.1.4491.2.1.28.1.10.1.13";
        }
      }
    }

    container docsIf31CmDsOfdmChannelPowerTable {
      description
       "This CM object provides measurements of the channel power
        in 6 MHz wide bands at the F connector input of the CM.";
      smiv2:oid "1.3.6.1.4.1.4491.2.1.28.1.11";

      list docsIf31CmDsOfdmChannelPowerEntry {
        key "ifIndex docsIf31CmDsOfdmChannelBandIndex";
        description
         "The conceptual row of docsIf31CmDsOfdmChannelPowerTable.";
        smiv2:oid "1.3.6.1.4.1.4491.2.1.28.1.11.1";

        leaf ifIndex {
          type leafref {
            path "/if-mib:IF-MIB/if-mib:ifTable/if-mib:ifEntry/if-mib:ifIndex";
          }
        }

        leaf docsIf31CmDsOfdmChannelBandIndex {
          type uint32;
          description
           "This attribute is a unique index used by the CM to identify
            each of the 6 MHz bands of a given OFDM downstream channel
            (from the lowest 6MHz band of the Occupied Bandwidth to the
            highest 6MHz band of the Occupied Bandwidth). The CM assigns
            indices in frequency order from the OFDM channel's lowest to
            highest 6 MHz frequency band for each of the 6 MHz bands of
            the channel, using an index of 1 to represent the lowest frequency
            band of the Occupied Bandwidth. Thus, an index of 33 represents
            the highest possible 6 MHz frequency band of the Occupied Bandwidth
            of a DOCSIS 3.1 OFDM channel. The CM also provides the power of the
            PLC channel and utilize a value of 0 to represent the PLC
            channel in this table.";
          smiv2:max-access "not-accessible";
          smiv2:oid "1.3.6.1.4.1.4491.2.1.28.1.11.1.1";
        }

        leaf docsIf31CmDsOfdmChannelPowerCenterFrequency {
          type uint32;
          units "Hz";
          description
           "This attribute corresponds to the center frequency of the 6 MHz
            band the CM measured the average channel power.
            
            See Reference for specific details on this attribute.";
          reference
           "DOCSIS 3.1 CM Operations Support System Interface
            Specification CM-SP-CM OSSIv3.1-I03-15MMDD,
            CenterFrequency";
          smiv2:max-access "read-only";
          smiv2:oid "1.3.6.1.4.1.4491.2.1.28.1.11.1.2";
        }

        leaf docsIf31CmDsOfdmChannelPowerRxPower {
          type docs-if:TenthdBmV;
          units "TenthdBmV";
          description
           "This attribute provides an estimate of the average power measured
            at the F connector input of the CM in the receive downstream channel
            set for this 6 MHz band.
            
            If the band index is 0, then this attribute provides an
            estimate of the average power measured at the F connector input
            of the CM for a 6 MHz encompassed spectrum containing the
            DOCSIS 3.1 PLC at its center.";
          smiv2:max-access "read-only";
          smiv2:oid "1.3.6.1.4.1.4491.2.1.28.1.11.1.3";
        }
      }
    }

    container docsIf31CmStatusOfdmaUsTable {
      description
       "This object defines PHY and MAC information about
        the CM's upstream channels operating in OFDMA mode.
        This object provides per-CM Upstream channel information
        previously available in the table docsIf3CmStatusTable.";
      smiv2:oid "1.3.6.1.4.1.4491.2.1.28.1.12";

      list docsIf31CmStatusOfdmaUsEntry {
        key "ifIndex";
        description
         "The conceptual row of docsIf31CmStatusOfdmaUsTable.
          An instance exist for each of the CM's OFDMA upstream channels
          which are configured for data transmission.";
        smiv2:oid "1.3.6.1.4.1.4491.2.1.28.1.12.1";

        leaf ifIndex {
          type leafref {
            path "/if-mib:IF-MIB/if-mib:ifTable/if-mib:ifEntry/if-mib:ifIndex";
          }
        }

        leaf docsIf31CmStatusOfdmaUsT3Timeouts {
          type yang:counter32;
          units "timeouts";
          description
           "This attribute denotes the number of times counter
            T3 expired in the CM for this upstream channel. Discontinuities
            in the value of this counter can occur at
            re-initialization of the managed system, and at other
            times as indicated by the value of ifCounterDiscontinuityTime
            for the associated upstream channel.";
          reference
           "RFC 2863.";
          smiv2:max-access "read-only";
          smiv2:oid "1.3.6.1.4.1.4491.2.1.28.1.12.1.2";
        }

        leaf docsIf31CmStatusOfdmaUsT4Timeouts {
          type yang:counter32;
          units "timeouts";
          description
           "This attribute denotes the number of times counter
            T4 expired in the CM for this upstream channel. Discontinuities
            in the value of this counter can occur at
            re-initialization of the managed system, and at other
            times as indicated by the value of ifCounterDiscontinuityTime
            for the associated upstream channel.";
          reference
           "RFC 2863.";
          smiv2:max-access "read-only";
          smiv2:oid "1.3.6.1.4.1.4491.2.1.28.1.12.1.3";
        }

        leaf docsIf31CmStatusOfdmaUsRangingAborteds {
          type yang:counter32;
          units "attempts";
          description
           "This attribute denotes the number of times the ranging
            process was aborted by the CMTS. Discontinuities
            in the value of this counter can occur at re-initialization
            of the managed system, and at other times as
            indicated by the value of ifCounterDiscontinuityTime
            ([RFC2863]) for the associated upstream channel.";
          reference
           "RFC 2863.";
          smiv2:max-access "read-only";
          smiv2:oid "1.3.6.1.4.1.4491.2.1.28.1.12.1.4";
        }

        leaf docsIf31CmStatusOfdmaUsT3Exceededs {
          type yang:counter32;
          units "timeouts";
          description
           "This attribute denotes the number of times for excessive
            T3 timeouts. Discontinuities in the value of
            this counter can occur at re-initialization of the managed
            system, and at other times as indicated by the
            value of ifCounterDiscontinuityTime for the associated
            upstream channel.";
          reference
           "RFC 2863.";
          smiv2:max-access "read-only";
          smiv2:oid "1.3.6.1.4.1.4491.2.1.28.1.12.1.5";
        }

        leaf docsIf31CmStatusOfdmaUsIsMuted {
          type boolean;
          description
           "This attribute denotes whether the upstream
            channel is muted.";
          reference
           "DOCSIS 3.1 MAC and Upper Layer Protocols Interface
            Specification CM-SP-MULPIv3.1-I03-140610 CM Control
            Request section.";
          smiv2:max-access "read-only";
          smiv2:oid "1.3.6.1.4.1.4491.2.1.28.1.12.1.6";
        }

        leaf docsIf31CmStatusOfdmaUsRangingStatus {
          type docs-if3:RangingState;
          description
           "This attribute denotes the ranging state of the CM.";
          reference
           "DOCSIS 3.1 MAC and Upper Layer Protocols Interface
            Specification CM-SP-MULPIv3.1-I03-140610 Ranging section.";
          smiv2:max-access "read-only";
          smiv2:oid "1.3.6.1.4.1.4491.2.1.28.1.12.1.7";
        }
      }
    }

    container docsIf31CmUsOfdmaChanTable {
      description
       "This object specifies the CM upstream OFDMA channel.";
      smiv2:oid "1.3.6.1.4.1.4491.2.1.28.1.13";

      list docsIf31CmUsOfdmaChanEntry {
        key "ifIndex";
        description
         "The conceptual row of docsIf31CmUsOfdmaChanTable.
          An instance exist for the CM OFDMA upstream interface.";
        smiv2:oid "1.3.6.1.4.1.4491.2.1.28.1.13.1";

        leaf ifIndex {
          type leafref {
            path "/if-mib:IF-MIB/if-mib:ifTable/if-mib:ifEntry/if-mib:ifIndex";
          }
        }

        leaf docsIf31CmUsOfdmaChanConfigChangeCt {
          type uint32 {
            range "0..255";
          }
          description
           "This attribute contains the value of the Configuration Change
            Count field in the Upstream Channel Descriptor (UCD) MAC
            Management Message corresponding to this OFDMA channel.";
          smiv2:max-access "read-only";
          smiv2:oid "1.3.6.1.4.1.4491.2.1.28.1.13.1.1";
        }

        leaf docsIf31CmUsOfdmaChanSubcarrierZeroFreq {
          type uint32;
          units "Hz";
          description
           "This attribute defines the lower edge frequency of the OFDMA
            upstream channel";
          smiv2:max-access "read-only";
          smiv2:oid "1.3.6.1.4.1.4491.2.1.28.1.13.1.2";
        }

        leaf docsIf31CmUsOfdmaChanFirstActiveSubcarrierNum {
          type uint32;
          description
           "This attribute defines the upper edge of the OFDMA upstream
            channel. The minimum channel width for an OFDMA upstream
            channel is 6.4 MHz in 4K mode and 10MHz in 2K mode. The valid
            range is 74 to 3947.";
          smiv2:max-access "read-only";
          smiv2:oid "1.3.6.1.4.1.4491.2.1.28.1.13.1.3";
        }

        leaf docsIf31CmUsOfdmaChanLastActiveSubcarrierNum {
          type uint32;
          description
           "This attribute defines the last active subcarrier number.
            The valid range is 74 to 3947.";
          smiv2:max-access "read-only";
          smiv2:oid "1.3.6.1.4.1.4491.2.1.28.1.13.1.4";
        }

        leaf docsIf31CmUsOfdmaChanNumActiveSubcarriers {
          type uint32;
          description
           "This attribute defines the number of active subcarriers within
            the OFDMA upstream channel. The valid range is 1 to 3800.";
          smiv2:max-access "read-only";
          smiv2:oid "1.3.6.1.4.1.4491.2.1.28.1.13.1.5";
        }

        leaf docsIf31CmUsOfdmaChanSubcarrierSpacing {
          type DOCS-IF31-MIB:SubcarrierSpacingType;
          units "kHz";
          description
           "This attribute defines the subcarrier spacing associated with
            a particular FFT mode configured on the OFDMA upstream
            channel. If it is 2K mode, then the subcarrier spacing is 50kHz.
            If it is 4K mode, then the subcarrier spacing is 25kHz.";
          smiv2:max-access "read-only";
          smiv2:oid "1.3.6.1.4.1.4491.2.1.28.1.13.1.6";
        }

        leaf docsIf31CmUsOfdmaChanCyclicPrefix {
          type DOCS-IF31-MIB:UsOfdmaCyclicPrefix;
          units "number of samples";
          description
           "Cyclic prefix is added in order to enable the receiver to
            overcome the effects of inter-symbol interference (ISI) and
            inter-carrier interference caused by microreflections in the
            channel. The cyclic prefix (in usec) is converted into samples
            using the sample rate of 102.4 Msamples/s. There are eleven
            values for the length of the CP and the choice depends on the
            delay spread of the channel; a longer delay spread requires a
            longer cyclic prefix.";
          smiv2:max-access "read-only";
          smiv2:oid "1.3.6.1.4.1.4491.2.1.28.1.13.1.7";
        }

        leaf docsIf31CmUsOfdmaChanRollOffPeriod {
          type DOCS-IF31-MIB:UsOfdmaRollOffPeriod;
          units "number of samples";
          description
           "Windowing is applied in order to maximize channel capacity
            by sharpening the edges of the spectrum of the OFDMA signal.
            Windowing is applied in the time domain by tapering (or
            rolling off) the edges using a raised cosine function. There
            are eight possible values of roll-off prefix. The Roll-Off
            Period is given in us and in number of samples using the
            sample rate of 102.4 Msamples/s. The configuration where
            Roll-off prefix value is greater than or equal to cyclic
            prefix value is considered invalid.";
          smiv2:max-access "read-only";
          smiv2:oid "1.3.6.1.4.1.4491.2.1.28.1.13.1.8";
        }

        leaf docsIf31CmUsOfdmaChanNumSymbolsPerFrame {
          type uint32;
          description
           "This attribute is the number of symbol periods per frame.
            For channel bandwidth greater than 72MHz, the maximum number
            of symbol periods per frame is 18 for 2K mode and 9 for 4K
            mode. For channel bandwidth less than 72 MHz but greater than
            48MHz, the maximum number of symbols per frame is 24 for 2K
            mode and 12 for 4K mode. For channel bandwidth less than
            48MHz, the maximum number of symbol periods is 36 for 2K mode
            and 18 for 4K mode. The minimum number of symbol periods per
            frame is 6 for both the FFT modes and is independent of the
            channel bandwidth.";
          smiv2:max-access "read-only";
          smiv2:oid "1.3.6.1.4.1.4491.2.1.28.1.13.1.9";
        }

        leaf docsIf31CmUsOfdmaChanTxPower {
          type uint32;
          units "QuarterdBmV";
          description
           "This attribute represents the operational transmit power for
            the associated OFDMA upstream channel.The CM reports its Target
            Power, P1.6r_n as described in [PHYv3.1]. Valid values for this
            object are 68 to (213 + (4*(Pmax - 65 dBmV))), since 68 quarter dBmV
            represents the lowest Tx power value 17 dBmV and 213 represents the
            nearest quarter dBmV to the highest Tx power value 53.2 dBmV.";
          smiv2:max-access "read-only";
          smiv2:oid "1.3.6.1.4.1.4491.2.1.28.1.13.1.10";
        }

        leaf docsIf31CmUsOfdmaChanPreEqEnabled {
          type boolean;
          description
           "This attribute defines whether pre-equalization is enabled on
            the associated OFDMA upstream channel.";
          smiv2:max-access "read-only";
          smiv2:oid "1.3.6.1.4.1.4491.2.1.28.1.13.1.11";
        }

        leaf docsIf31CmUsOfdmaChanChannelId {
          type uint32 {
            range "0..255";
          }
          description
           "The Cable Modem identification of the OFDMA upstream channel
            within this particular MAC interface. If the interface is down,
            the object returns the most current value.  If the upstream
            channel ID is unknown, this object returns a value of 0.";
          smiv2:max-access "read-only";
          smiv2:oid "1.3.6.1.4.1.4491.2.1.28.1.13.1.12";
        }
      }
    }

    container docsIf31CmUsOfdmaProfileStatsTable {
      description
       "This CM object specifies the attributes of the Upstream
        profile assigned to an OFDM upstream channel.";
      smiv2:oid "1.3.6.1.4.1.4491.2.1.28.1.14";

      list docsIf31CmUsOfdmaProfileStatsEntry {
        key "ifIndex docsIf31CmUsOfdmaProfileStatsIuc";
        description
         "The conceptual row of docsIf31CmUsOfdmaProfileStatsTable.
          An instance exist for each profile associated with the OFDMA
          upstream interface.";
        smiv2:oid "1.3.6.1.4.1.4491.2.1.28.1.14.1";

        leaf ifIndex {
          type leafref {
            path "/if-mib:IF-MIB/if-mib:ifTable/if-mib:ifEntry/if-mib:ifIndex";
          }
        }

        leaf docsIf31CmUsOfdmaProfileStatsIuc {
          type uint32;
          description
           "This attribute is the unique identifier of the upstream
            profile/IUC associated with the OFDMA upstream channel. It
            is a key defined to provide an index into the table. In
            DOCSIS 3.1 the valid Data Profile IUCs are: 5, 6, 9, 10,
            11, 12 and 13.";
          reference
           "DOCSIS 3.1 MAC and Upper Layer Protocols Interface
            Specification CM-SP-MULPIv3.1-I03-140610,
            Required Burst Attributes on OFDMA Channels.";
          smiv2:max-access "not-accessible";
          smiv2:oid "1.3.6.1.4.1.4491.2.1.28.1.14.1.1";
        }

        leaf docsIf31CmUsOfdmaProfileStatsOutOctets {
          type yang:counter64;
          description
           "This attribute is the count of MAC-layer octets transmitted by
            the CM using this Data IUC profile. This value is the size of
            all unicast, multicast or broadcast frames (including all MAC-
            layer framing) delivered from the MAC to the Phy -- this includes
            user data, DOCSIS MAC Management Messages, etc.
            
            Discontinuities in the value of this counter can occur at
            reinitialization of the managed system, and at other times as
            indicated by the value of docsIf31CmUsOfdmaProfileStats-
            CtrDiscontinuityTime.";
          smiv2:max-access "read-only";
          smiv2:oid "1.3.6.1.4.1.4491.2.1.28.1.14.1.2";
        }

        leaf docsIf31CmUsOfdmaProfileStatsCtrDiscontinuityTime {
          type yang:timestamp;
          description
           "This attribute is the value of sysUpTime on the most recent
            occasion at which any one or more of this entry's counters
            suffered a discontinuity. If no such discontinuities have
            occurred since the last re-initialization of the local
            management subsystem, then this attribute contains a zero value.";
          smiv2:max-access "read-only";
          smiv2:oid "1.3.6.1.4.1.4491.2.1.28.1.14.1.3";
        }
      }
    }

    container docsIf31CmUsOfdmaMinislotCfgStateTable {
      description
       "This CM object specifies the attributes of the minislot
        configuration associated with a OFDMA upstream channel.";
      smiv2:oid "1.3.6.1.4.1.4491.2.1.28.1.15";

      list docsIf31CmUsOfdmaMinislotCfgStateEntry {
        key "ifIndex docsIf31CmUsOfdmaProfileStatsIuc docsIf31CmUsOfdmaMinislotCfgStateStartMinislotNum";
        description
         "The conceptual row of docsIf31CmUsOfdmaMinislotCfgStateTable.
          An instance exists for each OFDMA minislot.";
        smiv2:oid "1.3.6.1.4.1.4491.2.1.28.1.15.1";

        leaf ifIndex {
          type leafref {
            path "/if-mib:IF-MIB/if-mib:ifTable/if-mib:ifEntry/if-mib:ifIndex";
          }
        }

        leaf docsIf31CmUsOfdmaProfileStatsIuc {
          type leafref {
            path "/DOCS-IF31-MIB:DOCS-IF31-MIB/DOCS-IF31-MIB:docsIf31CmUsOfdmaProfileStatsTable/DOCS-IF31-MIB:docsIf31CmUsOfdmaProfileStatsEntry/DOCS-IF31-MIB:docsIf31CmUsOfdmaProfileStatsIuc";
          }
        }

        leaf docsIf31CmUsOfdmaMinislotCfgStateStartMinislotNum {
          type uint32;
          description
           "This attribute is the unique identifier of the starting
            minislot in the group of consecutive minislots. The
            valid range is 1 to 240.";
          smiv2:max-access "not-accessible";
          smiv2:oid "1.3.6.1.4.1.4491.2.1.28.1.15.1.1";
        }

        leaf docsIf31CmUsOfdmaMinislotCfgStateFirstSubcarrierId {
          type uint32;
          description
           "This attribute is subcarrier identifier of the first
            subcarrier in the minislot. The valid range is 0 to 4095.";
          smiv2:max-access "read-only";
          smiv2:oid "1.3.6.1.4.1.4491.2.1.28.1.15.1.2";
        }

        leaf docsIf31CmUsOfdmaMinislotCfgStateNumConsecutiveMinislots {
          type uint32;
          description
           "This attribute defines the number of continuous minislots
            which have the same bit loading, starting with the StartMinislotNum,
            defined in the associated upstream profile. The valid range
            is 1 to 237.";
          smiv2:max-access "read-only";
          smiv2:oid "1.3.6.1.4.1.4491.2.1.28.1.15.1.3";
        }

        leaf docsIf31CmUsOfdmaMinislotCfgStateMinislotPilotPattern {
          type uint32;
          description
           "This attribute specifies the id of the pilot pattern used for
            the minislot.  The actual range varies depending on the FFT
            size in use, either 1-8 for 2K or 1-14 for 4K mode. The valid
            range is 1 to 14.";
          smiv2:max-access "read-only";
          smiv2:oid "1.3.6.1.4.1.4491.2.1.28.1.15.1.4";
        }

        leaf docsIf31CmUsOfdmaMinislotCfgStateDataSymbolModulation {
          type DOCS-IF31-MIB:UsOfdmaModulationType;
          description
           "This attribute defines the bit loading of the data
            subcarriers in the minislot.";
          smiv2:max-access "read-only";
          smiv2:oid "1.3.6.1.4.1.4491.2.1.28.1.15.1.5";
        }
      }
    }

    container docsIf31CmEmDlsStatsTable {
      description
       "This CM object provides statistics on the DLS feature, when
        enabled.";
      smiv2:oid "1.3.6.1.4.1.4491.2.1.28.1.16";

      list docsIf31CmEmDlsStatsEntry {
        key "ifIndex";
        description
         "The conceptual row of docsIf31CmEmDlsStatsTable. An
          instance exists for each of the Cable Modem's MAC Domains.
          It is indexed by the ifIndex of the corresponding MAC Domain.";
        smiv2:oid "1.3.6.1.4.1.4491.2.1.28.1.16.1";

        leaf ifIndex {
          type leafref {
            path "/if-mib:IF-MIB/if-mib:ifTable/if-mib:ifEntry/if-mib:ifIndex";
          }
        }

        leaf docsIf31CmEmDlsStatsNumberTimesCrossedBelowUsEntryThrshlds {
          type uint32;
          description
           "This attribute indicates the number of times since
            registration the CM crossed below the upstream entry bitrate
            threshold for a number of consecutive seconds equal to or
            exceeding the upstream entry time threshold.";
          smiv2:max-access "read-only";
          smiv2:oid "1.3.6.1.4.1.4491.2.1.28.1.16.1.1";
        }

        leaf docsIf31CmEmDlsStatsNumberTimesCrossedBelowDsEntryThrshlds {
          type uint32;
          description
           "This attribute indicates the number of times since
            registration the CM crossed below the downstream entry
            bitrate threshold for a number of consecutive seconds equal
            to or exceeding the downstream entry time threshold.";
          smiv2:max-access "read-only";
          smiv2:oid "1.3.6.1.4.1.4491.2.1.28.1.16.1.2";
        }

        leaf docsIf31CmEmDlsStatsTotalDuration {
          type uint32;
          units "seconds";
          description
           "This attribute indicates the total time duration, in seconds
            since registration, the CM has been in Energy Management DLS
            mode, as controlled by the DBC-REQ Energy Management DLS Mode
            Indicator TLV. This attribute differs from
            docsIf31CmEmDlsStatsTotalDurationBelowUsDsThrshlds because it
            is dependent on effects of the Energy Management Cycle
            Period, and processing of EM-REQ/EM-RSP messages and DBC
            messages that specifically indicate entry into or exit from
            Energy Management DLS mode.";
          smiv2:max-access "read-only";
          smiv2:oid "1.3.6.1.4.1.4491.2.1.28.1.16.1.3";
        }

        leaf docsIf31CmEmDlsStatsTotalDurationBelowUsThrshlds {
          type uint32;
          units "seconds";
          description
           "This attribute indicates the total time duration, in seconds
            since registration, the CM satisfied upstream conditions for
            entry into or remaining in Energy Management DLS mode.";
          smiv2:max-access "read-only";
          smiv2:oid "1.3.6.1.4.1.4491.2.1.28.1.16.1.4";
        }

        leaf docsIf31CmEmDlsStatsTotalDurationBelowDsThrshlds {
          type uint32;
          units "seconds";
          description
           "This attribute indicates the total time duration, in seconds
            since registration, the CM satisfied downstream conditions for
            entry into or remaining in Energy Management DLS mode.";
          smiv2:max-access "read-only";
          smiv2:oid "1.3.6.1.4.1.4491.2.1.28.1.16.1.5";
        }

        leaf docsIf31CmEmDlsStatsTotalDurationBelowUsDsThrshlds {
          type uint32;
          units "seconds";
          description
           "This attribute indicates the total time duration, in seconds
            since registration, the CM, with respect to both upstream and
            downstream entry and exit thresholds, satisfied conditions for
            entry into and remaining in Energy Management DLS mode.  This
            attribute differs from docsIf31CmEmDlsStatsTotalDuration
            because it is not dependent on effects of the Energy
            Management Cycle Period or processing of EM-REQ/EM-RSP
            messages and DBC messages that specifically indicate entry
            into or exit from Energy Management DLS mode.";
          smiv2:max-access "read-only";
          smiv2:oid "1.3.6.1.4.1.4491.2.1.28.1.16.1.6";
        }

        leaf docsIf31CmEmDlsStatsNumSleepLatencyTriggers {
          type yang:counter32;
          description
           "This attribute indicates the number of times since
            registration the CM transitioned to the DLS wake state
            due to the DLS Maximum Sleep Latency being exceeded.";
          smiv2:max-access "read-only";
          smiv2:oid "1.3.6.1.4.1.4491.2.1.28.1.16.1.7";
        }

        leaf docsIf31CmEmDlsStatsNumSleepByteCtTriggers {
          type yang:counter32;
          description
           "This attribute indicates the number of times since
            registration the CM transitioned to the DLS wake state
            due to the DLS Maximum Byte Count being exceeded.";
          smiv2:max-access "read-only";
          smiv2:oid "1.3.6.1.4.1.4491.2.1.28.1.16.1.8";
        }
      }
    }

    container docsIf31CmEmDlsStatusTable {
      description
       "This CM object provides statistics on the DLS feature, when
        enabled.";
      smiv2:oid "1.3.6.1.4.1.4491.2.1.28.1.17";

      list docsIf31CmEmDlsStatusEntry {
        key "ifIndex";
        description
         "The conceptual row of docsIf31CmEmDlsStatusTable. An
          instance exists for each of the Cable Modem's MAC Domains.
          It is indexed by the ifIndex of the corresponding MAC Domain.";
        smiv2:oid "1.3.6.1.4.1.4491.2.1.28.1.17.1";

        leaf ifIndex {
          type leafref {
            path "/if-mib:IF-MIB/if-mib:ifTable/if-mib:ifEntry/if-mib:ifIndex";
          }
        }

        leaf docsIf31CmEmDlsStatusAssignedEmIds {
          type DOCS-IF31-MIB:EmIdList;
          description
           "This attribute reports the set of CMTS-assigned EM-IDs for this CM.
            This attribute is encoded as an array 16-bit binary values with up
            to 3 elements. The broadcast EM-ID is not included in the list";
          smiv2:max-access "read-only";
          smiv2:oid "1.3.6.1.4.1.4491.2.1.28.1.17.1.1";
        }

        leaf docsIf31CmEmDlsStatusReceiveTimer {
          type uint32;
          description
           "This attribute specifies how long the CM is required to
            continue listening on the downstream for traffic, after
            reception of the EMM with Sleep Time with a non-zero value.
            The CMTS communicates the EM Receive Timer to the CM during
            registration or in DBC message. The DLS Receive Timer is
            specified in units of PLC frame intervals. The valid range
            is 0 - 2.";
          smiv2:max-access "read-only";
          smiv2:oid "1.3.6.1.4.1.4491.2.1.28.1.17.1.2";
        }

        leaf docsIf31CmEmDlsStatusMaxSleepLatency {
          type uint32 {
            range "1..255";
          }
          units "milliseconds";
          description
           "This attribute specifies the amount of time the CM would allow
            an upstream channel to queue the packets without transitioning
            to DLS wake state. The Max Sleep Latency is specified in msec.";
          smiv2:max-access "read-only";
          smiv2:oid "1.3.6.1.4.1.4491.2.1.28.1.17.1.3";
        }

        leaf docsIf31CmEmDlsStatusMaxSleepBytes {
          type uint32 {
            range "1..65535";
          }
          description
           "This attribute specifies the maximum number of bytes a CM would
            allow an upstream service flow to enqueue without transitioning
            to DLS wake state. The MaxSleepBytes is specified in bytes.";
          smiv2:max-access "read-only";
          smiv2:oid "1.3.6.1.4.1.4491.2.1.28.1.17.1.4";
        }
      }
    }

    container docsIf31CmtsDsOfdmChanTable {
      description
       "This CMTS object reports the status of the downstream OFDM channels.";
      smiv2:oid "1.3.6.1.4.1.4491.2.1.28.1.19";

      list docsIf31CmtsDsOfdmChanEntry {
        key "ifIndex";
        description
         "The conceptual row of docsIf31CmtsDsOfdmTable.
          An instance exists for each downstream OFDM channel.";
        smiv2:oid "1.3.6.1.4.1.4491.2.1.28.1.19.1";

        leaf ifIndex {
          type leafref {
            path "/if-mib:IF-MIB/if-mib:ifTable/if-mib:ifEntry/if-mib:ifIndex";
          }
        }

        leaf docsIf31CmtsDsOfdmChanChannelId {
          type int32 {
            range "0..255";
          }
          description
           "The Cable Modem Termination System identification of the
            OFDM downstream channel within this particular MAC interface.
            if the interface is down, the object returns the most
            current value.  If the downstream channel ID is unknown,
            this object returns a value of 0.";
          smiv2:max-access "read-only";
          smiv2:oid "1.3.6.1.4.1.4491.2.1.28.1.19.1.1";
        }

        leaf docsIf31CmtsDsOfdmChanLowerBdryFreq {
          type uint32;
          units "Hz";
          description
           "This attribute represents either the lower boundary frequency
            of the lower guardband or (if no guardband is defined) the
            lower boundary frequency of the lowest active subcarrier of the
            OFDM downstream channel.";
          smiv2:max-access "read-only";
          smiv2:oid "1.3.6.1.4.1.4491.2.1.28.1.19.1.2";
        }

        leaf docsIf31CmtsDsOfdmChanUpperBdryFreq {
          type uint32;
          units "Hz";
          description
           "This attribute represents either the upper boundary frequency
            of the upper guardband or (if no guardband is defined) the
            upper boundary frequency of the highest active subcarrier of the
            OFDM downstream channel.";
          smiv2:max-access "read-only";
          smiv2:oid "1.3.6.1.4.1.4491.2.1.28.1.19.1.3";
        }

        leaf docsIf31CmtsDsOfdmChanLowerBdryEncompSpectrum {
          type uint32;
          units "Hz";
          description
           "This attribute represents the lower boundary frequency
            of the encompassed spectrum.";
          smiv2:max-access "read-only";
          smiv2:oid "1.3.6.1.4.1.4491.2.1.28.1.19.1.4";
        }

        leaf docsIf31CmtsDsOfdmChanUpperBdryEncompSpectrum {
          type uint32;
          units "Hz";
          description
           "This attribute represents the upper boundary frequency
            of the encompassed spectrum.";
          smiv2:max-access "read-only";
          smiv2:oid "1.3.6.1.4.1.4491.2.1.28.1.19.1.5";
        }

        leaf docsIf31CmtsDsOfdmChanPlcFreq {
          type uint32;
          units "Hz";
          description
           "This is the PHY Link Channel (PLC) frequency. It is the center
            frequency of the lowest frequency subcarrier of the PLC. The
            aim of the PLC is for the CMTS to convey to the CM the
            physical properties of the OFDM channel.";
          smiv2:max-access "read-only";
          smiv2:oid "1.3.6.1.4.1.4491.2.1.28.1.19.1.6";
        }

        leaf docsIf31CmtsDsOfdmChanSubcarrierZeroFreq {
          type uint32;
          units "Hz";
          description
           "This attribute specifies the center frequency of the
            subcarrier 0 of the OFDM transmission. Note that since
            subcarrier 0 is always excluded, it will actually be below the
            allowed downstream spectrum band. This is the frequency of
            subcarrier X(0) in the definition of the DFT.";
          smiv2:max-access "read-only";
          smiv2:oid "1.3.6.1.4.1.4491.2.1.28.1.19.1.7";
        }

        leaf docsIf31CmtsDsOfdmChanFirstActiveSubcarrierNum {
          type uint32;
          description
           "This attribute corresponds to the number of the first
            non-excluded subcarrier. The valid range is 148 to 7895.";
          smiv2:max-access "read-only";
          smiv2:oid "1.3.6.1.4.1.4491.2.1.28.1.19.1.8";
        }

        leaf docsIf31CmtsDsOfdmChanLastActiveSubcarrierNum {
          type uint32;
          description
           "This attribute corresponds to the number of the last
            non-excluded subcarrier. The valid range is 148 to 7895";
          smiv2:max-access "read-only";
          smiv2:oid "1.3.6.1.4.1.4491.2.1.28.1.19.1.9";
        }

        leaf docsIf31CmtsDsOfdmChanNumActiveSubcarriers {
          type uint32;
          description
           "This attribute represents the number of active data
            subcarriers within the OFDM downstream channel (i.e. this
            exclude subcarriers for continuous pilots and the PLC).
            For 4K FFT mode, the maximum number of subcarriers including
            continuous pilots and the PLC cannot exceed 3800, and for
            8K FFT mode, the maximum number of active subcarriers including
            continuous pilots and the PLC cannot be greater than 7600.
            
            However, there are a minimum of 56 continuous pilots in a 192MHz
            channel that has no exclusions, and the size of the PLC is
            8 subcarriers for 4K FFT mode and 16 subcarriers for 8K FFT mode.
            Therefore the maximum value of NumActiveSubcarriers is 3736
            (or 3800 - 56 - 8) for 4K FFT mode and 7528 (or 7600 - 56 - 16)
            for 8K FFT mode.";
          smiv2:max-access "read-only";
          smiv2:oid "1.3.6.1.4.1.4491.2.1.28.1.19.1.10";
        }

        leaf docsIf31CmtsDsOfdmChanSubcarrierSpacing {
          type DOCS-IF31-MIB:SubcarrierSpacingType;
          units "kHz";
          description
           "This attribute defines the subcarrier spacing associated with
            a particular FFT mode configured on the OFDM downstream
            channel. If it is 4K mode, then the subcarrier spacing is
            50kHz. If it is 8K mode, then the subcarrier spacing is
            25kHz.";
          smiv2:max-access "read-only";
          smiv2:oid "1.3.6.1.4.1.4491.2.1.28.1.19.1.11";
        }

        leaf docsIf31CmtsDsOfdmChanLowerGuardbandWidth {
          type uint32;
          description
           "This attribute is the width in Hertz of the lower guard
            band of the OFDM channel. The valid range is 0 or
            1MHz to 1.77GHz.";
          smiv2:max-access "read-only";
          smiv2:oid "1.3.6.1.4.1.4491.2.1.28.1.19.1.12";
        }

        leaf docsIf31CmtsDsOfdmChanUpperGuardbandWidth {
          type uint32;
          description
           "This attribute is the width in Hertz of the upper guard
            band of the OFDM channel. The valid range is 0 or
            1MHz to 1.77GHz";
          smiv2:max-access "read-only";
          smiv2:oid "1.3.6.1.4.1.4491.2.1.28.1.19.1.13";
        }

        leaf docsIf31CmtsDsOfdmChanCyclicPrefix {
          type DOCS-IF31-MIB:DsOfdmCyclicPrefix;
          units "number of samples";
          description
           "Cyclic prefix enables the receiver to overcome the effects of
            inter-symbol-interference and intercarrier-interference caused
            by micro-reflections in the channel. There are five possible
            values for the length of the CP and the choice depends on the
            delay spread of the channel - a longer delay spread requires a
            longer cyclic prefix. The cyclic prefix (in usec) are converted
            into samples using the sample rate of 204.8 Msamples/s and is
            an integer multiple of: 1/64 * 20 us.";
          smiv2:max-access "read-only";
          smiv2:oid "1.3.6.1.4.1.4491.2.1.28.1.19.1.14";
        }

        leaf docsIf31CmtsDsOfdmChanRollOffPeriod {
          type DOCS-IF31-MIB:DsOfdmRollOffPeriod;
          units "number of samples";
          description
           "Roll off period maximizes channel capacity by sharpening the
            edges of the spectrum of the OFDM signal. For windowing
            purposes another segment at the start of the IDFT output is
            appended to the end of the IDFT output - the roll-off postfix
            (RP). There are five possible values for the (RP), and the
            choice depends on the bandwidth of the channel and the number
            of exclusion bands within the channel. A larger RP provides
            sharper edges in the spectrum of the OFDM signal; however,
            there is a time vs. frequency trade-off. Larger RP values
            reduce the efficiency of transmission in the time domain,
            but because the spectral edges are sharper, more useful
            subcarriers appear in the frequency domain. There is an
            optimum value for the RP that maximizes capacity for a given
            bandwidth and/or exclusion band scenario.";
          smiv2:max-access "read-only";
          smiv2:oid "1.3.6.1.4.1.4491.2.1.28.1.19.1.15";
        }

        leaf docsIf31CmtsDsOfdmChanTimeInterleaverDepth {
          type DOCS-IF31-MIB:TimeInterleaverDepth;
          units "symbols";
          description
           "This attribute represents the number of samples for the
            OFDM Downstream channel. This is limited to 16 samples for
            and 32 samples for 50 kHz and 25 kHz Subcarrier Spacing,
            respectively.";
          smiv2:max-access "read-only";
          smiv2:oid "1.3.6.1.4.1.4491.2.1.28.1.19.1.16";
        }

        leaf docsIf31CmtsDsOfdmChanNumPilots {
          type uint32;
          description
           "This attribute is the number of continuous pilots
            for the OFDM downstream channel.";
          smiv2:max-access "read-only";
          smiv2:oid "1.3.6.1.4.1.4491.2.1.28.1.19.1.17";
        }

        leaf docsIf31CmtsDsOfdmChanPilotScaleFactor {
          type uint32;
          description
           "This attribute represents the scale factor for calculating
            the number of continuous pilots. ";
          smiv2:max-access "read-only";
          smiv2:oid "1.3.6.1.4.1.4491.2.1.28.1.19.1.18";
        }

        leaf docsIf31CmtsDsOfdmChanNcpModulation {
          type DOCS-IF31-MIB:DsOfdmModulationType;
          description
           "This attribute represents the modulation of all subcarriers in
            the NCP channel. Valid values are qpsk, qam16 and qam64.";
          smiv2:max-access "read-only";
          smiv2:oid "1.3.6.1.4.1.4491.2.1.28.1.19.1.19";
        }

        leaf docsIf31CmtsDsOfdmChanUtilization {
          type uint32 {
            range "0..100";
          }
          units "percent";
          description
           "The utilization for this OFDM downstream channel, accurate as
            of the most recent docsIfCmtsChannelUtilizationInterval.
            
            See Reference for specific details on this attribute.";
          reference
           "DOCSIS 3.1 CCAP Operations Support System Interface
            Specification CM-SP-CCAP OSSIv3.1-I04-15MMDD,
            OfdmChannelUtilization.";
          smiv2:max-access "read-only";
          smiv2:oid "1.3.6.1.4.1.4491.2.1.28.1.19.1.20";
        }
      }
    }

    container docsIf31CmtsDsOfdmProfileStatsTable {
      description
       "This CMTS table provides DS OFDM statistics on a per Profile basis.";
      smiv2:oid "1.3.6.1.4.1.4491.2.1.28.1.20";

      list docsIf31CmtsDsOfdmProfileStatsEntry {
        key "ifIndex docsIf31CmtsDsOfdmStatsProfId";
        description
         "The conceptual row of docsIf31CmtsDsOfdmProfileStatsTable.
          An instance exists for each Profile Id on a given DS OFDM channel.";
        smiv2:oid "1.3.6.1.4.1.4491.2.1.28.1.20.1";

        leaf ifIndex {
          type leafref {
            path "/if-mib:IF-MIB/if-mib:ifTable/if-mib:ifEntry/if-mib:ifIndex";
          }
        }

        leaf docsIf31CmtsDsOfdmStatsProfId {
          type uint32 {
            range "0..255";
          }
          description
           "This attribute is the identifier of a profile associated
            with the OFDM downstream channel. The value of this attribute
            is zero-based due to constraints of the definition of Profile Id.";
          reference
           "DOCSIS 3.1 MAC and Upper Layer Protocols Interface Specification
            CM-SP-MULPIv3.1-I03-140610, Downstream Profile Descriptor.";
          smiv2:max-access "not-accessible";
          smiv2:oid "1.3.6.1.4.1.4491.2.1.28.1.20.1.1";
        }

        leaf docsIf31CmtsDsOfdmProfileStatsConfigChangeCt {
          type uint32 {
            range "0..255";
          }
          description
           "This attribute contains the value of the Configuration Change
            Count field in the Downstream Profile Descriptor (DPD) MAC
            Management Message corresponding to this profile.";
          smiv2:max-access "read-only";
          smiv2:oid "1.3.6.1.4.1.4491.2.1.28.1.20.1.2";
        }

        leaf docsIf31CmtsDsOfdmProfileStatsFullChannelSpeed {
          type yang:gauge64;
          description
           "This attribute is the speed of the associated channel in bps
            if this were the only profile and 100% of data-capable subcarriers
            were utilized to transmit MAC frames in full codewords.
            
            See Reference for specific details on this attribute.";
          reference
           "DOCSIS 3.1 CCAP Operations Support System Interface
            Specification CM-SP-CCAP OSSIv3.1-I03-15MMDD,
            ProfileFullChannelSpeed.";
          smiv2:max-access "read-only";
          smiv2:oid "1.3.6.1.4.1.4491.2.1.28.1.20.1.3";
        }

        leaf docsIf31CmtsDsOfdmProfileStatsOutOctets {
          type yang:counter64;
          description
           "This attribute is the count of MAC-layer octets transmitted
            by the CCAP using this profile. This value is the size of all
            unicast, multicast or broadcast frames (including all MAC-layer
            framing) delivered from the MAC to the Phy -- this includes user
            data, DOCSIS MAC Management Messages, etc.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.4";
        }

        leaf docsIf31CmtsDsOfdmProfileStatsOutUnicastOctets {
          type yang:counter64;
          description
           "This attribute is the count of MAC-layer Unicast octets transmitted
            by the CCAP using this profile. This value is the size of all unicast
            frames (including all MAC-layer framing) delivered from the
            MAC to the Phy -- this includes user data, DOCSIS MAC Management
            Messages, etc.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.5";
        }

        leaf docsIf31CmtsDsOfdmProfileStatsOutMulticastOctets {
          type yang:counter64;
          description
           "This attribute is the count of MAC-layer Multicast and broadcast
            octets transmitted by the CCAP using this profile. This value is
            the size of all frames (including all MAC-layer framing) delivered
            from the MAC to the Phy and addressed to a multicast MAC address
            -- this includes user data, DOCSIS MAC Management Messages, etc.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.6";
        }

        leaf docsIf31CmtsDsOfdmProfileStatsOutFrames {
          type yang:counter64;
          description
           "This attribute is the count of frames transmitted by the CCAP
            using this profile. This value is the count of all unicast,
            multicast or broadcast frames delivered from the MAC to the Phy
            -- this includes user data, DOCSIS MAC Management Messages, etc.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.7";
        }

        leaf docsIf31CmtsDsOfdmProfileStatsOutUnicastFrames {
          type yang:counter64;
          description
           "This attribute is the count of unicast frames transmitted by
            the CCAP using this profile. This value is the count of all
            frames delivered from the MAC to the Phy and addressed to a
            unicast MAC address -- this include user data, DOCSIS MAC Management
            Messages, etc.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.8";
        }

        leaf docsIf31CmtsDsOfdmProfileStatsOutMulticastFrames {
          type yang:counter64;
          description
           "This attribute is the count of multicast frames transmitted
            by the CCAP using this profile. This value is the count of all
            frames delivered from the MAC to the Phy and addressed to a
            multicast MAC address -- this include user data, DOCSIS MAC
            Management Messages, etc, but excludes frames sent to a broadcast
            address.
            
            Discontinuities in the value of this counter can occur at
            reinitialization of the managed system, and at other times as
            indicated by the value of docsIf31CmtsDsOfdmProfileStats-
            CtrDiscontinuityTime.";
          smiv2:max-access "read-only";
          smiv2:oid "1.3.6.1.4.1.4491.2.1.28.1.20.1.9";
        }

        leaf docsIf31CmtsDsOfdmProfileStatsCtrDiscontinuityTime {
          type yang:timestamp;
          description
           "This attribute is the value of sysUpTime on the most recent
            occasion at which any one or more of this entry's counters
            suffered a discontinuity. If no such discontinuities have
            occurred since the last re-initialization of the local
            management subsystem, then this attribute contains a zero value.";
          smiv2:max-access "read-only";
          smiv2:oid "1.3.6.1.4.1.4491.2.1.28.1.20.1.10";
        }

        leaf docsIf31CmtsDsOfdmProfileStatsAssignedCmCt {
          type uint32;
          description
           "This attribute is the count of CMs currently assigned to
            this profile.";
          smiv2:max-access "read-only";
          smiv2:oid "1.3.6.1.4.1.4491.2.1.28.1.20.1.11";
        }
      }
    }

    container docsIf31CmtsDsOfdmSubcarrierStatusTable {
      description
       "This CMTS object provides the status of each of the OFDM subcarriers
        which comprise this OFDM channel.";
      smiv2:oid "1.3.6.1.4.1.4491.2.1.28.1.21";

      list docsIf31CmtsDsOfdmSubcarrierStatusEntry {
        key "ifIndex docsIf31CmtsDsOfdmStatsProfId docsIf31CmtsDsOfdmSubcarrierStatusStartId";
        description
         "The conceptual row of docsIf31CmtsDsOfdmSubcarrierStatusTable.
          An instance exists for each Profile on a given OFDM downstream.";
        smiv2:oid "1.3.6.1.4.1.4491.2.1.28.1.21.1";

        leaf ifIndex {
          type leafref {
            path "/if-mib:IF-MIB/if-mib:ifTable/if-mib:ifEntry/if-mib:ifIndex";
          }
        }

        leaf docsIf31CmtsDsOfdmStatsProfId {
          type leafref {
            path "/DOCS-IF31-MIB:DOCS-IF31-MIB/DOCS-IF31-MIB:docsIf31CmtsDsOfdmProfileStatsTable/DOCS-IF31-MIB:docsIf31CmtsDsOfdmProfileStatsEntry/DOCS-IF31-MIB:docsIf31CmtsDsOfdmStatsProfId";
          }
        }

        leaf docsIf31CmtsDsOfdmSubcarrierStatusStartId {
          type uint32;
          description
           "This attribute is an identifier for the first subcarrier
            in the range of active subcarriers with the same modulation.";
          smiv2:max-access "not-accessible";
          smiv2:oid "1.3.6.1.4.1.4491.2.1.28.1.21.1.1";
        }

        leaf docsIf31CmtsDsOfdmSubcarrierStatusEndId {
          type uint32;
          description
           "This attribute is the subcarrier number of the last subcarrier
            in the group.";
          smiv2:max-access "read-only";
          smiv2:oid "1.3.6.1.4.1.4491.2.1.28.1.21.1.2";
        }

        leaf docsIf31CmtsDsOfdmSubcarrierStatusMainModulation {
          type DOCS-IF31-MIB:DsOfdmModulationType;
          description
           "This attribute indicates the main modulation order of the
            subcarriers in the range. In case of skip modulation enabled
            the MainModulation is the modulation order of the first, the
            third, the fifth, etc. subcarriers in the range.";
          smiv2:max-access "read-only";
          smiv2:oid "1.3.6.1.4.1.4491.2.1.28.1.21.1.3";
        }

        leaf docsIf31CmtsDsOfdmSubcarrierStatusSkip {
          type int32 {
            range "0..2";
          }
          description
           "This attribute indicates whether the skip modulation method
            is used. If true the modulation order of the subcarriers in
            the range is alternating between the MainModulation and
            SkipModulation.";
          smiv2:max-access "read-only";
          smiv2:oid "1.3.6.1.4.1.4491.2.1.28.1.21.1.4";
        }

        leaf docsIf31CmtsDsOfdmSubcarrierStatusSkipModulation {
          type DOCS-IF31-MIB:DsOfdmModulationType;
          description
           "This attribute indicates the modulation order for every other
            subcarrier in the range.";
          smiv2:max-access "read-only";
          smiv2:oid "1.3.6.1.4.1.4491.2.1.28.1.21.1.5";
        }
      }
    }

    container docsIf31CmtsDsOfdmChanPowerTable {
      description
       "This object provides measurements of the downstream OFDM channel
        power in 6 MHz-wide bands at the output of the CCAP.";
      smiv2:oid "1.3.6.1.4.1.4491.2.1.28.1.22";

      list docsIf31CmtsDsOfdmChanPowerEntry {
        key "ifIndex docsIf31CmtsDsOfdmChanPowerBandIndex";
        description
         "The conceptual row of the docsIf31CmtsDsOfdmChanPowerTable.";
        smiv2:oid "1.3.6.1.4.1.4491.2.1.28.1.22.1";

        leaf ifIndex {
          type leafref {
            path "/if-mib:IF-MIB/if-mib:ifTable/if-mib:ifEntry/if-mib:ifIndex";
          }
        }

        leaf docsIf31CmtsDsOfdmChanPowerBandIndex {
          type uint32;
          description
           "This attribute is a unique index used by the CCAP to
            identify each of the 6 MHz bands of a given OFDM downstream
            channel (from the lowest 6MHz band of the Occupied Bandwidth
            to the highest 6MHz band of the Occupied Bandwidth). The CCAP
            assigns indices in frequency order from the OFDM channel's
            lowest to highest 6 MHz frequency band for each of the 6 MHz
            bands of the channel, using an index of 1 to represent the lowest
            frequency band of the Occupied Bandwidth.  Thus, an index of 33
            represents the highest possible 6 MHz frequency band of the
            Occupied Bandwidth of an OFDM channel.
            
            The CCAP also provides the power of the PLC channel and utilizes
            a value of 0 to represent the PLC channel in this table. ";
          smiv2:max-access "not-accessible";
          smiv2:oid "1.3.6.1.4.1.4491.2.1.28.1.22.1.1";
        }

        leaf docsIf31CmtsDsOfdmChanPowerCenterFrequency {
          type uint32;
          units "Hz";
          description
           "This attribute corresponds to the center frequency of the 6 MHz
            band the CM measured the average channel power.
            
            See Reference for specific details on this attribute.";
          reference
           "DOCSIS 3.1 CCAP Operations Support System Interface
            Specification CM-SP-CCAP OSSIv3.1-I04-15MMDD,
            CenterFrequency";
          smiv2:max-access "read-only";
          smiv2:oid "1.3.6.1.4.1.4491.2.1.28.1.22.1.2";
        }

        leaf docsIf31CmtsDsOfdmChanPowerTxPower {
          type docs-if:TenthdBmV;
          units "TenthdBmV";
          description
           "This attribute provides an estimate of the average power
            measured at the output of the CCAP in the downstream channel
            set for this 6 MHz band.
            
            If the docsIf31CmtsDsOfdmChanPowerBandIndex is 0, then this
            attribute provides an estimate of the average power measured
            at the output of the CCAP for a 6 MHz encompassed spectrum
            containing the DOCSIS 3.1 PLC at its center.";
          smiv2:max-access "read-only";
          smiv2:oid "1.3.6.1.4.1.4491.2.1.28.1.22.1.3";
        }
      }
    }

    container docsIf31CmtsUsOfdmaChanTable {
      description
       "This object provides channel-level visibility into Upstream
        OFDMA channel configuration and status.";
      smiv2:oid "1.3.6.1.4.1.4491.2.1.28.1.23";

      list docsIf31CmtsUsOfdmaChanEntry {
        key "ifIndex";
        description
         "The conceptual row of docsIf31CmtsUsOfdmaChanTable.";
        smiv2:oid "1.3.6.1.4.1.4491.2.1.28.1.23.1";

        leaf ifIndex {
          type leafref {
            path "/if-mib:IF-MIB/if-mib:ifTable/if-mib:ifEntry/if-mib:ifIndex";
          }
        }

        leaf docsIf31CmtsUsOfdmaChanTemplateIndex {
          type uint32;
          description
           "The index of the UsOfdmaModulationTemplate object which the
            CMTS/CCAP utilized when configuring this channel.";
          smiv2:max-access "read-only";
          smiv2:oid "1.3.6.1.4.1.4491.2.1.28.1.23.1.1";
        }

        leaf docsIf31CmtsUsOfdmaChanConfigChangeCt {
          type uint32 {
            range "0..255";
          }
          description
           "This attribute contains the value of the Configuration
            Change Count field in the Upstream Channel Descriptor (UCD) MAC
            Management Message currently in use on this channel.";
          smiv2:max-access "read-only";
          smiv2:oid "1.3.6.1.4.1.4491.2.1.28.1.23.1.2";
        }

        leaf docsIf31CmtsUsOfdmaChanTargetRxPower {
          type docs-if:TenthdBmV;
          units "TenthdBmV";
          description
           "This attribute provides the power of the expected commanded
            received signal in the channel, referenced to the CCAP input.
            The value represents the power spectral density in an
            equivalent 1.6 MHz spectrum.";
          smiv2:max-access "read-only";
          smiv2:oid "1.3.6.1.4.1.4491.2.1.28.1.23.1.3";
        }

        leaf docsIf31CmtsUsOfdmaChanLowerBdryFreq {
          type uint32;
          units "Hz";
          description
           "This attribute provides the lower frequency for the OFDMA US
            channel.";
          smiv2:max-access "read-only";
          smiv2:oid "1.3.6.1.4.1.4491.2.1.28.1.23.1.4";
        }

        leaf docsIf31CmtsUsOfdmaChanUpperBdryFreq {
          type uint32;
          units "Hz";
          description
           "This attribute provides the upper frequency for the OFDMA US
            channel.";
          smiv2:max-access "read-only";
          smiv2:oid "1.3.6.1.4.1.4491.2.1.28.1.23.1.5";
        }

        leaf docsIf31CmtsUsOfdmaChanSubcarrierSpacing {
          type DOCS-IF31-MIB:SubcarrierSpacingType;
          units "kHz";
          description
           "This attribute defines the subcarrier spacing associated with
            a particular FFT mode configured on the OFDMA upstream channel.";
          smiv2:max-access "read-only";
          smiv2:oid "1.3.6.1.4.1.4491.2.1.28.1.23.1.6";
        }

        leaf docsIf31CmtsUsOfdmaChanCyclicPrefix {
          type DOCS-IF31-MIB:UsOfdmaCyclicPrefix;
          units "number of samples";
          description
           "The cyclic prefix assigned to this channel for mitigating
            interference due to microreflections.";
          smiv2:max-access "read-only";
          smiv2:oid "1.3.6.1.4.1.4491.2.1.28.1.23.1.7";
        }

        leaf docsIf31CmtsUsOfdmaChanNumSymbolsPerFrame {
          type uint32;
          description
           "This attribute is the number of symbol periods per frame.";
          smiv2:max-access "read-only";
          smiv2:oid "1.3.6.1.4.1.4491.2.1.28.1.23.1.8";
        }

        leaf docsIf31CmtsUsOfdmaChanRollOffPeriod {
          type DOCS-IF31-MIB:UsOfdmaRollOffPeriod;
          units "number of samples";
          description
           "This attribute is the windowing roll-off period.";
          smiv2:max-access "read-only";
          smiv2:oid "1.3.6.1.4.1.4491.2.1.28.1.23.1.9";
        }

        leaf docsIf31CmtsUsOfdmaChanPreEqEnable {
          type boolean;
          description
           "This attribute indicates pre-equalization is enabled on the
            OFDMA upstream channel when its value is true, or disabled when
            its value is false.";
          smiv2:max-access "read-only";
          smiv2:oid "1.3.6.1.4.1.4491.2.1.28.1.23.1.10";
        }

        leaf docsIf31CmtsUsOfdmaChanFineRngGuardband {
          type uint32;
          units "Hz";
          description
           "This attribute is the sum of the upper and lower guard
            bands for fine ranging in Hz.";
          smiv2:max-access "read-only";
          smiv2:oid "1.3.6.1.4.1.4491.2.1.28.1.23.1.11";
        }

        leaf docsIf31CmtsUsOfdmaChanFineRngNumSubcarriers {
          type uint32;
          description
           "This attribute is the maximum number of subcarriers for
            fine ranging.";
          smiv2:max-access "read-only";
          smiv2:oid "1.3.6.1.4.1.4491.2.1.28.1.23.1.12";
        }

        leaf docsIf31CmtsUsOfdmaChanFineRngPreambleLen {
          type uint32;
          units "bits";
          description
           "This attribute is the length of the OFDMA fine ranging IUC
            preamble in bits.";
          smiv2:max-access "read-only";
          smiv2:oid "1.3.6.1.4.1.4491.2.1.28.1.23.1.13";
        }

        leaf docsIf31CmtsUsOfdmaChanInitRngGuardband {
          type uint32;
          units "Hz";
          description
           "This attribute is the sum of the upper and lower guard bands
            for initial ranging in Hz.";
          smiv2:max-access "read-only";
          smiv2:oid "1.3.6.1.4.1.4491.2.1.28.1.23.1.14";
        }

        leaf docsIf31CmtsUsOfdmaChanInitRngNumSubcarriers {
          type uint32;
          description
           "This attribute is the maximum number of subcarriers for
            initial ranging.";
          smiv2:max-access "read-only";
          smiv2:oid "1.3.6.1.4.1.4491.2.1.28.1.23.1.15";
        }

        leaf docsIf31CmtsUsOfdmaChanInitRngPreambleLen {
          type uint32;
          units "bits";
          description
           "This attribute is the maximum number of subcarriers for
            initial ranging.";
          smiv2:max-access "read-only";
          smiv2:oid "1.3.6.1.4.1.4491.2.1.28.1.23.1.16";
        }

        leaf docsIf31CmtsUsOfdmaChanProvAttribMask {
          type docs-if3:AttributeMask;
          description
           "This attribute provides the Provisioned Attribute Mask for
            the OFDMA upstream channel.";
          smiv2:max-access "read-only";
          smiv2:oid "1.3.6.1.4.1.4491.2.1.28.1.23.1.17";
        }

        leaf docsIf31CmtsUsOfdmaChanTxBackoffStart {
          type int32 {
            range "0..16";
          }
          description
           "The initial random backoff window to use when retrying
            transmissions.  Expressed as a power of 2.  A value of 16
            at the CMTS indicates that a proprietary adaptive retry
            mechanism is to be used.";
          smiv2:max-access "read-only";
          smiv2:oid "1.3.6.1.4.1.4491.2.1.28.1.23.1.18";
        }

        leaf docsIf31CmtsUsOfdmaChanTxBackoffEnd {
          type int32 {
            range "0..16";
          }
          description
           "The final random backoff window to use when retrying
            transmissions.  Expressed as a power of 2.  A value of 16
            at the CMTS indicates that a proprietary adaptive retry
            mechanism is to be used.";
          smiv2:max-access "read-only";
          smiv2:oid "1.3.6.1.4.1.4491.2.1.28.1.23.1.19";
        }

        leaf docsIf31CmtsUsOfdmaChanRangingBackoffStart {
          type int32 {
            range "0..16";
          }
          description
           "The initial random backoff window to use when retrying
            Ranging Requests.  Expressed as a power of 2.  A value of
            16 at the CMTS indicates that a proprietary adaptive retry
            mechanism is to be used.";
          smiv2:max-access "read-only";
          smiv2:oid "1.3.6.1.4.1.4491.2.1.28.1.23.1.20";
        }

        leaf docsIf31CmtsUsOfdmaChanRangingBackoffEnd {
          type int32 {
            range "0..16";
          }
          description
           "The final random backoff window to use when retrying
            Ranging Requests.  Expressed as a power of 2.  A value of
            16 at the CMTS indicates that a proprietary adaptive retry
            mechanism is to be used.";
          smiv2:max-access "read-only";
          smiv2:oid "1.3.6.1.4.1.4491.2.1.28.1.23.1.21";
        }

        leaf docsIf31CmtsUsOfdmaChanUtilization {
          type uint32 {
            range "0..100";
          }
          units "percent";
          description
           "The calculated and truncated utilization for this physical
            upstream channel, accurate as of the most recent
            docsIfCmtsChannelUtilizationInterval.
            
            The upstream channel utilization is expressed as a percentage
            of minislots utilized on the physical channel, regardless of
            burst type.
            
            The utilization calculation can be expressed by the
            following equation:
            
            Utilization = MinislotsUtilized/MinislotsAllocated * 100%
            
            For an Initial Maintenance region, the minislots for the
            complete region are considered utilized if the CMTS received
            an upstream burst within the region from any CM on the physical
            channel. For contention REQ and REQ/DATA regions, the minislots
            for a transmission opportunity within the region are considered
            utilized if the CMTS received an upstream burst within the
            opportunity from any CM on the physical channel. For all other
            regions, utilized minislots are those in which the CMTS granted
            bandwidth to any unicast SID on the physical channel.
            
            For an upstream interface that has multiple logical upstream
            channels enabled, the utilization index is a weighted sum of
            utilization indices for the logical channels. The weight for
            each utilization index is the percentage of upstream mini-slots
            allocated for the corresponding logical channel.
            
            Example:
            If 75% of bandwidth is allocated to the first logical channel
            and 25% to the second, and the utilization for each are 60 and 40,
            respectively, the utilization for the upstream physical channel is
            (60 * 0.75) + (40 * 0.25) = 55. This figure applies to the most
            recent utilization interval.";
          smiv2:max-access "read-only";
          smiv2:oid "1.3.6.1.4.1.4491.2.1.28.1.23.1.22";
        }

        leaf docsIf31CmtsUsOfdmaChanId {
          type int32;
          description
           "This attribute is the upstream Channel Id signaled in the
            DOCSIS protocol for the OFDMA upstream channel. The Channel
            Id is unique within the associated MacDomain.";
          smiv2:max-access "read-only";
          smiv2:oid "1.3.6.1.4.1.4491.2.1.28.1.23.1.23";
        }
      }
    }

    container docsIf31CmtsUsOfdmaDataIucStatsTable {
      description
       "This CMTS table provides DS OFDM statistics on a per Profile basis.";
      smiv2:oid "1.3.6.1.4.1.4491.2.1.28.1.24";

      list docsIf31CmtsUsOfdmaDataIucStatsEntry {
        key "ifIndex docsIf31CmtsUsOfdmaStatsIuc";
        description
         "The conceptual row of docsIf31CmtsUsOfdmaDataIucStatsTable.
          An instance exists for each Data IUC profile on a given
          US OFDMA channel.";
        smiv2:oid "1.3.6.1.4.1.4491.2.1.28.1.24.1";

        leaf ifIndex {
          type leafref {
            path "/if-mib:IF-MIB/if-mib:ifTable/if-mib:ifEntry/if-mib:ifIndex";
          }
        }

        leaf docsIf31CmtsUsOfdmaStatsIuc {
          type uint32;
          description
           "This attribute represents the OFDMA Data IUC that these
            statistics correspond to.";
          smiv2:max-access "not-accessible";
          smiv2:oid "1.3.6.1.4.1.4491.2.1.28.1.24.1.1";
        }

        leaf docsIf31CmtsUsOfdmaDataIucStatsMinislotPilotPattern {
          type uint32;
          description
           "This attribute contains the identifier for the default pilot
            pattern specified in the template for minislots using this
            Data IUC. The valid range is 1 - 14.";
          smiv2:max-access "read-only";
          smiv2:oid "1.3.6.1.4.1.4491.2.1.28.1.24.1.2";
        }

        leaf docsIf31CmtsUsOfdmaDataIucStatsMinislotModulation {
          type DOCS-IF31-MIB:UsOfdmaModulationType;
          description
           "This attribute contains the default modulation order specified
            in the template for minislots using this Data IUC.";
          smiv2:max-access "read-only";
          smiv2:oid "1.3.6.1.4.1.4491.2.1.28.1.24.1.3";
        }

        leaf docsIf31CmtsUsOfdmaDataIucStatsTotalCodewords {
          type yang:counter64;
          description
           "This attribute contains the count of the total number of
            FEC codewords received on this channel using this Data IUC.
            
            Discontinuities in the value of this counter can occur at
            reinitialization of the managed system, and at other times as
            indicated by the value of docsIf31CmtsUsOfdmaDataIucStats-
            CtrDiscontinuityTime.";
          smiv2:max-access "read-only";
          smiv2:oid "1.3.6.1.4.1.4491.2.1.28.1.24.1.4";
        }

        leaf docsIf31CmtsUsOfdmaDataIucStatsCorrectedCodewords {
          type yang:counter64;
          description
           "This attribute contains the count of codewords received
            on this channel using this Data IUC that failed the pre-decoding
            syndrome check, but passed the post-decoding syndrome check.
            
            Discontinuities in the value of this counter can occur at
            reinitialization of the managed system, and at other times as
            indicated by the value of docsIf31CmtsUsOfdmaDataIucStats-
            CtrDiscontinuityTime.";
          smiv2:max-access "read-only";
          smiv2:oid "1.3.6.1.4.1.4491.2.1.28.1.24.1.5";
        }

        leaf docsIf31CmtsUsOfdmaDataIucStatsUnreliableCodewords {
          type yang:counter64;
          description
           "This attribute contains the count of codewords received on
            this channel using this Data IUC that failed the post-decoding
            syndrome check.
            
            Discontinuities in the value of this counter can occur at
            reinitialization of the managed system, and at other times as
            indicated by the value of docsIf31CmtsUsOfdmaDataIucStats-
            CtrDiscontinuityTime.";
          smiv2:max-access "read-only";
          smiv2:oid "1.3.6.1.4.1.4491.2.1.28.1.24.1.6";
        }

        leaf docsIf31CmtsUsOfdmaDataIucStatsInOctets {
          type yang:counter64;
          description
           "This attribute is the count of MAC-layer octets received
            by the CCAP on this Data IUC. This value is the size of all
            unicast, multicast or broadcast octets (including all MAC-
            layer framing) and CCF PMD overhead (segment headers and
            stuffing bytes) delivered from the Phy to the MAC; this
            includes user data, DOCSIS MAC Management Messages, etc.
            
            Discontinuities in the value of this counter can occur at
            reinitialization of the managed system, and at other times as
            indicated by the value of docsIf31CmtsUsOfdmaDataIucStats-
            CtrDiscontinuityTime.";
          smiv2:max-access "read-only";
          smiv2:oid "1.3.6.1.4.1.4491.2.1.28.1.24.1.7";
        }

        leaf docsIf31CmtsUsOfdmaDataIucStatsCtrDiscontinuityTime {
          type yang:timestamp;
          description
           "This attribute is the value of sysUpTime on the most recent
            occasion at which any one or more of this entry's counters
            suffered a discontinuity. If no such discontinuities have
            occurred since the last re-initialization of the local
            management subsystem, then this attribute contains a zero value.";
          smiv2:max-access "read-only";
          smiv2:oid "1.3.6.1.4.1.4491.2.1.28.1.24.1.8";
        }

        leaf docsIf31CmtsUsOfdmaDataIucStatsAssignedCmCt {
          type uint32;
          description
           "This attribute is the count of CMs currently assigned to
            this Data IUC.";
          smiv2:max-access "read-only";
          smiv2:oid "1.3.6.1.4.1.4491.2.1.28.1.24.1.9";
        }
      }
    }

    container docsIf31CmtsUsOfdmaDataIucDetailStatusTable {
      description
       "This CMTS table provides exceptions to the US channel template
        for this Data IUC.";
      smiv2:oid "1.3.6.1.4.1.4491.2.1.28.1.25";

      list docsIf31CmtsUsOfdmaDataIucDetailStatusEntry {
        key "ifIndex docsIf31CmtsUsOfdmaStatsIuc docsIf31CmtsUsOfdmaDataIucDetailStatusLowerFreq";
        description
         "The conceptual row of docsIf31CmtsUsOfdmaDataIucDetailStatusTable.
          An instance exists for each exception to the template for a Data
          IUC profile on a given US OFDMA channel.";
        smiv2:oid "1.3.6.1.4.1.4491.2.1.28.1.25.1";

        leaf ifIndex {
          type leafref {
            path "/if-mib:IF-MIB/if-mib:ifTable/if-mib:ifEntry/if-mib:ifIndex";
          }
        }

        leaf docsIf31CmtsUsOfdmaStatsIuc {
          type leafref {
            path "/DOCS-IF31-MIB:DOCS-IF31-MIB/DOCS-IF31-MIB:docsIf31CmtsUsOfdmaDataIucStatsTable/DOCS-IF31-MIB:docsIf31CmtsUsOfdmaDataIucStatsEntry/DOCS-IF31-MIB:docsIf31CmtsUsOfdmaStatsIuc";
          }
        }

        leaf docsIf31CmtsUsOfdmaDataIucDetailStatusLowerFreq {
          type uint32;
          units "Hz";
          description
           "This attribute indicates the lower frequency where the
            minislots will use the pilot pattern and modulation";
          smiv2:max-access "not-accessible";
          smiv2:oid "1.3.6.1.4.1.4491.2.1.28.1.25.1.1";
        }

        leaf docsIf31CmtsUsOfdmaDataIucDetailStatusUpperFreq {
          type uint32;
          units "Hz";
          description
           "This attribute indicates the upper frequency where the
            minislots will use the pilot pattern and modulation";
          smiv2:max-access "read-only";
          smiv2:oid "1.3.6.1.4.1.4491.2.1.28.1.25.1.2";
        }

        leaf docsIf31CmtsUsOfdmaDataIucDetailStatusMinislotPilotPattern {
          type uint32;
          description
           "This attribute contains the identifier for the pilot
            pattern this frequency range. All minislots in the frequency
            range have this pilot pattern. The valid range is 1 - 14.";
          smiv2:max-access "read-only";
          smiv2:oid "1.3.6.1.4.1.4491.2.1.28.1.25.1.3";
        }

        leaf docsIf31CmtsUsOfdmaDataIucDetailStatusMinislotModulation {
          type DOCS-IF31-MIB:UsOfdmaModulationType;
          description
           "This attribute contains the modulation order for this
            frequency range. All minislots in the frequency range have
            this modulation.";
          smiv2:max-access "read-only";
          smiv2:oid "1.3.6.1.4.1.4491.2.1.28.1.25.1.4";
        }
      }
    }

    container docsIf31CmtsUsOfdmaRangingIucStatusTable {
      description
       "This CMTS table provides details on status of ranging IUCs.";
      smiv2:oid "1.3.6.1.4.1.4491.2.1.28.1.26";

      list docsIf31CmtsUsOfdmaRangingIucStatusEntry {
        key "ifIndex docsIf31CmtsUsOfdmaRangingIucStatusIuc";
        description
         "The conceptual row of docsIf31CmtsUsOfdmaRangingIucStatusTable.
          An instance exists for each Ranging IUC profile on a given
          US OFDMA channel.";
        smiv2:oid "1.3.6.1.4.1.4491.2.1.28.1.26.1";

        leaf ifIndex {
          type leafref {
            path "/if-mib:IF-MIB/if-mib:ifTable/if-mib:ifEntry/if-mib:ifIndex";
          }
        }

        leaf docsIf31CmtsUsOfdmaRangingIucStatusIuc {
          type uint32;
          description
           "This attribute indicates the OFDMA Ranging IUC that this
            status information corresponds to.";
          smiv2:max-access "not-accessible";
          smiv2:oid "1.3.6.1.4.1.4491.2.1.28.1.26.1.1";
        }

        leaf docsIf31CmtsUsOfdmaRangingIucStatusGuardband {
          type uint32;
          units "Hz";
          description
           "This attribute is the sum of the upper and lower guard bands
            for this ranging IUC in Hz. ";
          smiv2:max-access "read-only";
          smiv2:oid "1.3.6.1.4.1.4491.2.1.28.1.26.1.2";
        }

        leaf docsIf31CmtsUsOfdmaRangingIucStatusNumSubcarriers {
          type uint32;
          description
           "This attribute indicates the maximum number of subcarriers
            for this ranging IUC.";
          smiv2:max-access "read-only";
          smiv2:oid "1.3.6.1.4.1.4491.2.1.28.1.26.1.3";
        }
      }
    }

    container docsIf31CmtsDsOfdmSubcarrierTypeTable {
      description
       "This object specifies the subcarrier type for a group of subcarriers
        in the active spectrum of this OFDM channel. Groups of subcarriers of
        the same type are presented together; non-data subcarriers in these
        ranges are ignored.";
      smiv2:oid "1.3.6.1.4.1.4491.2.1.28.1.27";

      list docsIf31CmtsDsOfdmSubcarrierTypeEntry {
        key "ifIndex docsIf31CmtsDsOfdmSubcarrierTypeStartSubcarrierId";
        description
         "The conceptual row of docsIf31CmtsDsOfdmSubcarrierTypeTable.
          An instance exists for each OFDM downstream channel.";
        smiv2:oid "1.3.6.1.4.1.4491.2.1.28.1.27.1";

        leaf ifIndex {
          type leafref {
            path "/if-mib:IF-MIB/if-mib:ifTable/if-mib:ifEntry/if-mib:ifIndex";
          }
        }

        leaf docsIf31CmtsDsOfdmSubcarrierTypeStartSubcarrierId {
          type uint32;
          description
           "This attribute is a key defined to provide an index into the table
            and represents the subcarrier number of the first subcarrier in the
            group. ";
          smiv2:max-access "not-accessible";
          smiv2:oid "1.3.6.1.4.1.4491.2.1.28.1.27.1.1";
        }

        leaf docsIf31CmtsDsOfdmSubcarrierTypeEndSubcarrierId {
          type uint32;
          description
           "This attribute is the subcarrier number of the last subcarrier in
            the group. ";
          smiv2:max-access "read-only";
          smiv2:oid "1.3.6.1.4.1.4491.2.1.28.1.27.1.2";
        }

        leaf docsIf31CmtsDsOfdmSubcarrierTypeSubcarrierType {
          type enumeration {
            enum "data" {
              value "1";
            }
            enum "plc" {
              value "2";
            }
            enum "continuousPilot" {
              value "3";
            }
            enum "excluded" {
              value "4";
            }
          }
          description
           "This attribute specifies which type of subcarrier is represented in
            this group.";
          smiv2:max-access "read-only";
          smiv2:oid "1.3.6.1.4.1.4491.2.1.28.1.27.1.3";
        }
      }
    }

    container docsIf31CmtsUsOfdmaSubcarrierTypeTable {
      description
       "This object specifies the subcarrier type for a group of subcarriers
        in the active spectrum of this OFDMA channel. Groups of subcarriers of
        the same type are presented together; non-data subcarriers in these
        ranges are ignored.";
      smiv2:oid "1.3.6.1.4.1.4491.2.1.28.1.28";

      list docsIf31CmtsUsOfdmaSubcarrierTypeEntry {
        key "ifIndex docsIf31CmtsUsOfdmaSubcarrierTypeStartSubcarrierId";
        description
         "The conceptual row of docsIf31CmtsUsOfdmaSubcarrierStatusTable.
          An instance exists for each Profile on a given OFDMA upstream.";
        smiv2:oid "1.3.6.1.4.1.4491.2.1.28.1.28.1";

        leaf ifIndex {
          type leafref {
            path "/if-mib:IF-MIB/if-mib:ifTable/if-mib:ifEntry/if-mib:ifIndex";
          }
        }

        leaf docsIf31CmtsUsOfdmaSubcarrierTypeStartSubcarrierId {
          type uint32;
          description
           "This attribute is a key defined to provide an index into the table
            and represents the subcarrier number of the first subcarrier in the
            group. ";
          smiv2:max-access "not-accessible";
          smiv2:oid "1.3.6.1.4.1.4491.2.1.28.1.28.1.1";
        }

        leaf docsIf31CmtsUsOfdmaSubcarrierTypeEndSubcarrierId {
          type uint32;
          description
           "This attribute is the subcarrier number of the last subcarrier in
            the group. ";
          smiv2:max-access "read-only";
          smiv2:oid "1.3.6.1.4.1.4491.2.1.28.1.28.1.2";
        }

        leaf docsIf31CmtsUsOfdmaSubcarrierTypeSubcarrierType {
          type enumeration {
            enum "data" {
              value "1";
            }
            enum "excluded" {
              value "2";
            }
            enum "unused" {
              value "3";
            }
          }
          description
           "This attribute specifies which type of subcarrier is represented in
            this group.";
          smiv2:max-access "read-only";
          smiv2:oid "1.3.6.1.4.1.4491.2.1.28.1.28.1.3";
        }
      }
    }

    container docsIf31CmStatusTable {
      description
       "This object defines attributes of the CM status.
        This object is an extension to the SNMP table
        docsIf3CmStatusTable.";
      smiv2:oid "1.3.6.1.4.1.4491.2.1.28.1.29";

      list docsIf31CmStatusEntry {
        key "ifIndex";
        description
         "The conceptual row of docsIf31CmStatusTable.
          An instance exist for the CM MAC Domain Interface.";
        smiv2:oid "1.3.6.1.4.1.4491.2.1.28.1.29.1";

        leaf ifIndex {
          type leafref {
            path "/if-mib:IF-MIB/if-mib:ifTable/if-mib:ifEntry/if-mib:ifIndex";
          }
        }

        leaf docsIf31CmStatusEmDlsOperStatus {
          type boolean;
          description
           "This attribute indicates whether the CM is currently operating
            in Energy Management DLS Mode. If this attribute returns true,
            the CM is operating in Energy Management DLS Mode.";
          reference
           "DOCSIS 3.1 MAC and Upper Layer Protocols Interface
            Specification CM-SP-MULPIv3.1-I08-151210,
            Energy Management Mode Indicator section.";
          smiv2:max-access "read-only";
          smiv2:oid "1.3.6.1.4.1.4491.2.1.28.1.29.1.1";
        }
      }
    }

    container docsIf31CmEmDlsCfgTable {
      description
       "This object provides configuration state information
        on the CM for the Energy Management 1x1 Mode feature.";
      reference
       "DOCSIS 3.1 MAC and Upper Layer Protocols Interface
        Specification CM-SP-MULPIv3.1-I08-151210,
        Energy Management DLS Encodings section.";
      smiv2:oid "1.3.6.1.4.1.4491.2.1.28.1.30";

      list docsIf31CmEmDlsCfgEntry {
        key "docsIf31CmEmDlsCfgDirection";
        description
         "The conceptual row of docsIf31CmEmDlsCfgTable.";
        smiv2:oid "1.3.6.1.4.1.4491.2.1.28.1.30.1";

        leaf docsIf31CmEmDlsCfgDirection {
          type docs-if3:IfDirection;
          description
           "This index indicates whether the threshold applies to the
            upstream or downstream.";
          smiv2:max-access "not-accessible";
          smiv2:oid "1.3.6.1.4.1.4491.2.1.28.1.30.1.1";
        }

        leaf docsIf31CmEmDlsCfgEntryBitrateThrshld {
          type uint32;
          units "bps";
          description
           "This attribute specifies the upstream or downstream bitrate
            threshold (in bps) below which the CM will request to enter
            Energy Management DLS Mode operation.";
          smiv2:max-access "read-write";
          smiv2:oid "1.3.6.1.4.1.4491.2.1.28.1.30.1.2";
        }

        leaf docsIf31CmEmDlsCfgEntryTimeThrshld {
          type uint32 {
            range "1..65535";
          }
          units "seconds";
          description
           "This attribute specifies the number of consecutive seconds
            that the upstream or downstream data rate needs to remain below
            the Upstream or Downstream Entry Bitrate Threshold in order to
            determine that a transition to Energy Management DLS Mode is
            required.";
          smiv2:max-access "read-write";
          smiv2:oid "1.3.6.1.4.1.4491.2.1.28.1.30.1.3";
        }

        leaf docsIf31CmEmDlsCfgExitBitrateThrshld {
          type uint32;
          units "bps";
          description
           "This attribute specifies the upstream or downstream bitrate
            threshold (in bps) above which the CM will request to leave
            Energy Management DLS Mode operation.";
          smiv2:max-access "read-write";
          smiv2:oid "1.3.6.1.4.1.4491.2.1.28.1.30.1.4";
        }

        leaf docsIf31CmEmDlsCfgExitTimeThrshld {
          type uint32 {
            range "1..65535";
          }
          units "seconds";
          description
           "This attribute specifies the number of consecutive seconds
            that the upstream or downstream data rate needs to remain above
            the Upstream or Downstream Exit Bitrate Threshold in order to
            determine that a transition out of Energy Management DLS Mode
            is required.";
          smiv2:max-access "read-write";
          smiv2:oid "1.3.6.1.4.1.4491.2.1.28.1.30.1.5";
        }
      }
    }
  }

  smiv2:alias "docsIf31CmtsCmRegStatusTable" {
    description
     "This object defines attributes that represent the CM's
      registration status as tracked by the CMTS.
      Refer to the individual attribute definitions for
      applicability to 3.0 and 3.1 Cable Modems.
      
      This extends the DOCS-IF3-MIB's docsIf3CmtsCmRegStatusTable.";
    smiv2:oid "1.3.6.1.4.1.4491.2.1.28.1.3";
  }

  smiv2:alias "docsIf31CmtsCmRegStatusEntry" {
    description
     "The conceptual row of docsIf31CmtsCmRegStatusTable.";
    smiv2:oid "1.3.6.1.4.1.4491.2.1.28.1.3.1";
  }

  augment "/docs-if3:DOCS-IF3-MIB/docs-if3:docsIf3CmtsCmRegStatusTable/docs-if3:docsIf3CmtsCmRegStatusEntry" {
    description
     "The conceptual row of docsIf31CmtsCmRegStatusTable.";
    smiv2:oid "1.3.6.1.4.1.4491.2.1.28.1.3.1";

    leaf docsIf31CmtsCmRegStatusAssignedEmIds {
      type DOCS-IF31-MIB:EmIdList;
      description
       "This attribute reports the set of CMTS-assigned EM-IDs for
        this CM. This attribute is encoded as an array 16-bit binary
        values with up to 3 elements. The broadcast EM-ID is not
        included in the list.
        If the EM-ID is unknown the CMTS returns a zero length string.
        This object is applicable to DOCSIS 3.1 modems but not to prior
        versions of DOCSIS modems. If the CM is a pre-DOCSIS 3.1 modem,
        the CMTS returns a zero length string.";
      smiv2:max-access "read-only";
      smiv2:oid "1.3.6.1.4.1.4491.2.1.28.1.3.1.1";
    }

    leaf docsIf31CmtsCmRegStatusDsProfileIdList {
      type binary {
        length "0|6..72";
      }
      description
       "This attribute is a variable length series of hexadecimal
        octets where each series entry consists of the following fields
        (encoded in the following order):
        
        - The ifIndex (4 octets) of the OFDM channel where the
        downstream Profile IDs are assigned.
        
        - The number or count of Profile IDs (1 octet with valid values
        of 1-4) assigned to the CM on that channel.
        
        - The list of Profile IDs (1 octet each with valid values of
        0-15) assigned to this CM on that channel. Profile ID 0 is
        commonly referred to as Profile A.  Likewise, Profile IDs 1,
        2 and 3 are commonly referred to as Profiles B, C and D.
        
        The CCAP encodes each OFDM channel in a CM's RCS as a separate
        n-octet entry in the ProfileIdList.
        
        Examples: a CM with a single OFDM channel (ifIndex 34) and
        four assigned profiles (Profile IDs 0, 8, 9 and 10) would
        have a ProfileIdList value of 0x00000022040008090A. A CM with a
        2 OFDM channel bonding group each with two assigned profiles
        (Profile IDs 0 and 15 on channel with ifIndex 34 and Profile IDs
        0 and 14 on channel with ifIndex 35) would have a ProfileIdList
        value of 0x0000002202000F0000002302000E).
        
        Note: the CCAP must not include the transitional profile or
        test profile in the ProfileIdList.
        
        Note that octet string lengths greater than 18 are optional.
        
        This object is applicable to DOCSIS 3.1 modems but not to prior
        versions of DOCSIS modems. If the CM is a pre-DOCSIS 3.1 modem,
        the CMTS returns a zero length octet string.";
      smiv2:max-access "read-only";
      smiv2:oid "1.3.6.1.4.1.4491.2.1.28.1.3.1.2";
    }

    leaf docsIf31CmtsCmRegStatusUsProfileIucList {
      type binary {
        length "0|6..72";
      }
      description
       "This attribute is a variable length series of hexadecimal
        octets where each series entry consists of the following fields
        (encoded in the following order):
        
        - The ifIndex (4 octets) of the OFDMA channel where the
        Profile IUCs are assigned.
        
        - The number or count of Data IUCs (1 octet with valid values
        of 1-2) assigned to this CM on that channel.
        
        - The list of Data IUCs (1 octet each with valid values of
        5, 6, 9-13) assigned to this CM on that channel.
        
        The CCAP encodes each OFDMA channel in a CM's TCS as a separate
        n-octet entry in the UsProfileIucList.
        
        Examples: a CM with a single OFDMA channel (ifIndex 36) and two
        assigned Data IUCs (5 and 6) would have a ProfileIdList value of
        0x00000024020506. A CM with a 2 OFDMA channel bonding group each
        with one assigned Data IUC (IUC 5 on channel with ifIndex 34 and
        IUC 13 on channel with ifIndex 35) would have a UsProfileIucList
        value of 0x00000022010500000023010D).
        
        Note: the CCAP MUST NOT include transitional IUCs or test IUCs in
        the UsProfileIucList.
        
        Note that octet string lengths greater than 18 are optional.
        
        This object is applicable to DOCSIS 3.1 modems but not to prior
        versions of DOCSIS modems. If the CM is a pre-DOCSIS 3.1 modem,
        the CMTS returns a zero length octet string.";
      smiv2:max-access "read-only";
      smiv2:oid "1.3.6.1.4.1.4491.2.1.28.1.3.1.3";
    }

    leaf docsIf31CmtsCmRegStatusTcsPhigh {
      type uint32 {
        range "0|68..320";
      }
      description
       "This attribute reports the P1.6hi value for the CM's Transmit
        Channel Set.
        This object is applicable to DOCSIS 3.1 modems but not to prior
        versions of DOCSIS modems. If the CM is a pre-DOCSIS 3.1 modem,
        the CMTS returns zero.";
      smiv2:max-access "read-only";
      smiv2:oid "1.3.6.1.4.1.4491.2.1.28.1.3.1.4";
    }

    leaf docsIf31CmtsCmRegStatusTcsDrwTop {
      type uint32;
      units "dBmV";
      description
       "This attribute reports the level of the top of the Dynamic Range
        Window. The value is expressed in dBmV and is the result of a
        calculation equal to P1.6hi - P1.6load_min_set.
        This object is applicable to DOCSIS 3.1 modems but not to prior
        versions of DOCSIS modems. If the CM is a pre-DOCSIS 3.1 modem,
        the CMTS returns zero.";
      smiv2:max-access "read-only";
      smiv2:oid "1.3.6.1.4.1.4491.2.1.28.1.3.1.5";
    }

    leaf docsIf31CmtsCmRegStatusMinUsableDsFreq {
      type uint32;
      units "Hz";
      description
       "This attribute is the higher of the CCAP's minimum supported
        downstream frequency and the CM's minimum supported downstream
        frequency. It indicates the lowest downstream frequency the
        CCAP can use to communicate with this CM taking into account
        the capabilities of both devices.
        This object is applicable to DOCSIS 3.1 modems but not to prior
        versions of DOCSIS modems. If the CM is a pre-DOCSIS 3.1 modem,
        the CMTS returns zero.";
      smiv2:max-access "read-only";
      smiv2:oid "1.3.6.1.4.1.4491.2.1.28.1.3.1.6";
    }

    leaf docsIf31CmtsCmRegStatusMaxUsableDsFreq {
      type uint32;
      units "Hz";
      description
       "This attribute is the lower of the CCAP's maximum supported
        downstream frequency and the CM's maximum supported downstream
        frequency. It indicates the highest downstream frequency the
        CCAP can use to communicate with this CM taking into account
        the capabilities of both devices.
        This object is applicable to DOCSIS 3.1 modems but not to prior
        versions of DOCSIS modems. If the CM is a pre-DOCSIS 3.1 modem,
        the CMTS returns zero.";
      smiv2:max-access "read-only";
      smiv2:oid "1.3.6.1.4.1.4491.2.1.28.1.3.1.7";
    }

    leaf docsIf31CmtsCmRegStatusMaxUsableUsFreq {
      type uint32;
      units "Hz";
      description
       "This attribute is the lower of the CCAP's maximum supported
        upstream frequency and the CM's maximum supported upstream
        frequency. It indicates the highest upstream frequency the CCAP
        can use to receive signals from this CM taking into account the
        capabilities of both devices.
        
        Note: there is no minimum usable upstream frequency attribute as
        this is 5MHz for both CCAP and CM devices.
        
        This object is applicable to DOCSIS 3.1 modems but not to prior
        versions of DOCSIS modems. If the CM is a pre-DOCSIS 3.1 modem,
        the CMTS returns zero.";
      smiv2:max-access "read-only";
      smiv2:oid "1.3.6.1.4.1.4491.2.1.28.1.3.1.8";
    }

    leaf docsIf31CmtsCmRegStatusPartialSvcState {
      type DOCS-IF31-MIB:PartialServiceType;
      description
       "This attribute indicates the type of 'bonding group' issue
        that this CM is experiencing, based on what the MAC-layer
        shows. See PartialServiceType for further detail.
        This object is applicable to DOCSIS 3.1 modems but not to prior
        versions of DOCSIS modems. If the CM is a pre-DOCSIS 3.1 modem,
        the CMTS returns 'other'.";
      smiv2:max-access "read-only";
      smiv2:oid "1.3.6.1.4.1.4491.2.1.28.1.3.1.9";
    }

    leaf docsIf31CmtsCmRegStatusPartialChanState {
      type DOCS-IF31-MIB:PartialChannelType;
      description
       "This attribute is a bit-field which indicates the type of OFDM
        channel issue that this CM is experiencing, based on what the
        MAC-layer shows. See PartialChannelType for further detail.
        This object is applicable to DOCSIS 3.1 modems but not to prior
        versions of DOCSIS modems. If the CM is a pre-DOCSIS 3.1 modem,
        the CMTS returns 0x0 (no bits set).";
      smiv2:max-access "read-only";
      smiv2:oid "1.3.6.1.4.1.4491.2.1.28.1.3.1.10";
    }
  }

  smiv2:alias "docsIf31CmUsScQamChanTable" {
    description
     "This table describes the attributes of attached upstream
      SC-QAM channels for the CM.
      
      This extends the DOCS-IF-MIB's docsIfUpstreamChannelTable.";
    smiv2:oid "1.3.6.1.4.1.4491.2.1.28.1.31";
  }

  smiv2:alias "docsIf31CmUsScQamChanEntry" {
    description
     "The conceptual row of docsIf31CmUsScQamChanTable.
      For DOCSIS 3.1 CMs, an entry in this table exists for each
      ifEntry with an ifType of docsCableUpstream (129).";
    smiv2:oid "1.3.6.1.4.1.4491.2.1.28.1.31.1";
  }

  augment "/docs-if:DOCS-IF-MIB/docs-if:docsIfUpstreamChannelTable/docs-if:docsIfUpstreamChannelEntry" {
    description
     "The conceptual row of docsIf31CmUsScQamChanTable.
      For DOCSIS 3.1 CMs, an entry in this table exists for each
      ifEntry with an ifType of docsCableUpstream (129).";
    smiv2:oid "1.3.6.1.4.1.4491.2.1.28.1.31.1";

    leaf docsIf31CmUsScQamChanTxPsd {
      type uint32;
      units "QuarterdBmV";
      description
       "This attribute represents P1.6r_n, the power spectral density
        in 1.6 MHz, for the associated SC-QAM upstream channel.";
      smiv2:max-access "read-only";
      smiv2:oid "1.3.6.1.4.1.4491.2.1.28.1.31.1.1";
    }
  }

  smiv2:alias "docsIf31Mib" {
    smiv2:oid "1.3.6.1.4.1.4491.2.1.28";
  }

  smiv2:alias "docsIf31Notifications" {
    smiv2:oid "1.3.6.1.4.1.4491.2.1.28.0";
  }

  smiv2:alias "docsIf31MibObjects" {
    smiv2:oid "1.3.6.1.4.1.4491.2.1.28.1";
  }

  smiv2:alias "docsIf31CmSystemCfgState" {
    smiv2:oid "1.3.6.1.4.1.4491.2.1.28.1.18";
  }

  smiv2:alias "docsIf31MibConformance" {
    smiv2:oid "1.3.6.1.4.1.4491.2.1.28.2";
  }

  smiv2:alias "docsIf31MibCompliances" {
    smiv2:oid "1.3.6.1.4.1.4491.2.1.28.2.1";
  }

  smiv2:alias "docsIf31MibGroups" {
    smiv2:oid "1.3.6.1.4.1.4491.2.1.28.2.2";
  }

}
