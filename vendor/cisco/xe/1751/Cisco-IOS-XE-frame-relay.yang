module Cisco-IOS-XE-frame-relay {
  namespace "http://cisco.com/ns/yang/Cisco-IOS-XE-frame-relay";
  prefix ios-frame-relay;

  import cisco-semver {
    prefix cisco-semver;
  }
  import ietf-inet-types {
    prefix inet;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native frame-relay Yang Model.
     Copyright (c) 2016-2020 by Cisco Systems, Inc.
     All rights reserved.";

  revision 2020-07-01 {
    description
      "Initial revision";
    cisco-semver:module-version "1.0.0";
  }

  grouping config-global-frame-relay-grouping {
    leaf switching {
      description
        "enable frame relay pvc switching";
      type empty;
    }
  }

  grouping frame-relay-switch-interface-grouping {
    choice interface-choice {
      leaf Serial {
        description
          "Serial interface";
        type string;
      }
      leaf Tunnel {
        description
          "Tunnel interface";
        type uint32;
      }
      leaf MFR {
        description
          "MFR interface";
        type uint32 {
          range "0..2147483647";
        }
      }
    }
  }

  grouping config-interface-serial-frame-relay-grouping {
    container frame-relay {
      description
        "Set frame relay parameters";
      when "../ios:encapsulation/ios:frame-relay";
      leaf lmi-type {
        description
          "Use CISCO-ANSI-CCITT type LMI";
        type enumeration {
          enum "ansi";
        }
      }
      leaf intf-type {
        description
          "Configure a FR DTE/DCE/NNI interface";
        type enumeration {
          enum "dce";
          enum "dte";
        }
        default "dte";
      }
      list interface-dlci {
        key "name";
        leaf name {
          description
            "Define a DLCI on an interface/subinterface";
          type uint16 {
            range "16..1007";
          }
        }
      }
      list route {
        description
          "frame relay route for pvc switching";
        key "name";
        leaf name {
          description
            "input dlci to be switched";
          type uint16 {
            range "16..1007";
          }
        }
        container interface {
          description
            "outgoing interface for pvc switching";
          uses frame-relay-switch-interface-grouping;
          leaf dlci-number {
            description
              "output dlci to use when switching";
            type uint16 {
              range "16..1007";
            }
          }
        }
      }
    }
  }

  grouping config-MFR-bandwidth-grouping {
    container frame-relay {
      description
        "Set frame relay parameters";
      container multilink {
        description
          "Set Multilink FR parameters";
        container bandwidth-class {
          description
            "Multilink Frame Relay bandwidth class";
          choice class-choice {
            leaf a {
              description
                "Bandwidth class A";
              type empty;
            }
            leaf b {
              description
                "Bandwidth class B";
              type empty;
            }
            leaf c {
              description
                "Bandwidth class C";
              type uint16 {
                range "1..65535";
              }
            }
          }
        }
      }
      leaf intf-type {
        description
          "Configure a FR DTE/DCE/NNI interface";
        type enumeration {
          enum "dce";
          enum "dte";
        }
        default "dte";
      }
      list interface-dlci {
        key "name";
        leaf name {
          description
            "Define a DLCI on an interface/subinterface";
          type uint16 {
            range "16..1007";
          }
        }
      }
      leaf lmi-type {
        type enumeration {
          enum "ansi";
        }
      }
      container map {
        description
          "Map a protocol address to a DLCI address";
        list ip {
          description
            "ip";
          key "name";
          leaf name {
            description
              "Protocol specific address";
            type inet:ipv4-address;
          }
          leaf dlci-number {
            description
              "DLCI";
            type uint16 {
              range "16..1007";
            }
          }
        }
      }
    }
  }

  grouping config-interface-dlci-grouping {
    container frame-relay {
      description
        "Set frame relay parameters";
      container interface-dlci {
        leaf name {
          description
            "Define a DLCI on an interface/subinterface";
          type uint16 {
            range "16..1007";
          }
        }
      }
    }
  }

  grouping config-frame-relay-grouping {
    container frame-relay {
      description
        "Set frame relay parameters";
      leaf encapsulation {
        description
          "Frame Relay networks";
        type empty;
      }
      leaf intf-type {
        description
          "Configure a FR DTE/DCE/NNI interface";
        type enumeration {
          enum "dce";
          enum "dte";
        }
      }
    }
  }

  augment "/ios:native/ios:interface/ios:Serial" {
    uses config-interface-serial-frame-relay-grouping;
  }
  augment "/ios:native/ios:interface/ios:MFR" {
    uses config-MFR-bandwidth-grouping;
  }
  augment "/ios:native/ios:interface/ios:Serial-subinterface/ios:Serial" {
    uses config-interface-dlci-grouping;
  }
  augment "/ios:native/ios:interface/ios:MFR-subinterface/ios:MFR" {
    uses config-interface-dlci-grouping;
  }
  augment "/ios:native/ios:frame-relay" {
    uses config-global-frame-relay-grouping;
  }
}
