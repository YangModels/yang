module Cisco-IOS-XE-nwpi-types {
  yang-version 1;
  namespace "http://cisco.com/ns/yang/Cisco-IOS-XE-nwpi-types";
  prefix Cisco-IOS-XE-nwpi-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Network Wide Path Insight Types.
     Copyright (c) 2020 by Cisco Systems, Inc.
     All rights reserved.";

  revision 2020-11-01 {
    description
      "Initial revision";
    reference
      "1.0.0";
    cisco-semver:module-version "1.0.0";
  }

  typedef nwpi-action-type {
    type enumeration {
      enum action-start-trace {
        value 0;
        description
          "Start trace";
      }
      enum action-stop-trace {
        value 1;
        description
          "Stop trace";
      }
      enum action-clear-trace {
        value 2;
        description
          "Clear trace data";
      }
      enum action-enable-nwpi {
        value 3;
        description
          "Enable Network Wide Path Insight";
      }
      enum action-disable-nwpi {
        value 4;
        description
          "Disable Network Wide Path Insight";
      }
    }
    description
      "Network Wide Path Insight action type";
  }

  typedef nwpi-target-type {
    type enumeration {
      enum target-vpn-id {
        value 0;
        description
          "SD-WAN VPN identifier type";
      }
      enum target-vrf-name {
        value 1;
        description
          "VRF name type";
      }
    }
    description
      "Network Wide Path Insight target type";
  }
}
