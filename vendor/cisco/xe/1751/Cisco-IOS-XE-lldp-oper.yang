module Cisco-IOS-XE-lldp-oper {
  yang-version 1;
  namespace "http://cisco.com/ns/yang/Cisco-IOS-XE-lldp-oper";
  prefix lldp-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of Link Layer Discovery Protocol state information.
     Copyright (c) 2016-2017, 2019-2020 by Cisco Systems, Inc.
     All rights reserved.";

  revision 2020-07-01 {
    description
      "-Added Time to live leaf for the neighbor entry
       -Added new mgmt-type enum value mgmt-not-advertised indicating that a
        management address is not advertised
       -Added system cookie leaf for the neighbor entry";
    reference
      "1.5.0";
    cisco-semver:module-version "1.5.0";
  }
  revision 2020-03-01 {
    description
      "Added transmission and reception state details, neighboring device
       physical media capabilities and failure counters";
    reference
      "1.4.0";
    cisco-semver:module-version "1.4.0";
  }
  revision 2019-05-01 {
    description
      "Added semantic version";
    reference
      "1.3.0";
    cisco-semver:module-version "1.3.0";
  }
  revision 2018-11-05 {
    description
      "- Adding port VLAN ID, power details,
         media attachment unit, and auto negotiation details.
       - Cleaned up spelling errors in descriptions.";
    reference
      "1.2.0";
    cisco-semver:module-version "1.2.0";
  }
  revision 2018-06-27 {
    description
      "Entries to support open config LLDP are added";
    reference
      "1.1.0";
    cisco-semver:module-version "1.1.0";
  }
  revision 2017-02-07 {
    description
      "Initial revision";
    reference
      "1.0.0";
    cisco-semver:module-version "1.0.0";
  }

  typedef lldp-pwr-pair-type {
    type enumeration {
      enum power-pair-signal {
        value 1;
        description
          "LLDP power pair is Signal";
      }
      enum power-pair-spare {
        value 2;
        description
          "LLDP power pair is Spare";
      }
    }
    description
      "LLDP Power pair type";
  }

  typedef lldp-pwr-class-type {
    type enumeration {
      enum power-class-0 {
        value 1;
        description
          "LLDP power class 0";
      }
      enum power-class-1 {
        value 2;
        description
          "LLDP power class 1";
      }
      enum power-class-2 {
        value 3;
        description
          "LLDP power class 2";
      }
      enum power-class-3 {
        value 4;
        description
          "LLDP power class 3";
      }
      enum power-class-4 {
        value 5;
        description
          "LLDP power class 4";
      }
    }
    description
      "LLDP Power class type";
  }

  typedef lldp-pwr-device-type {
    type enumeration {
      enum power-device-type-2-pse {
        value 1;
        description
          "LLDP power device type is TYPE 2 PSE";
      }
      enum power-device-type-2-pd {
        value 2;
        description
          "LLDP power device type is TYPE 2 PD";
      }
      enum power-device-type-1-pse {
        value 3;
        description
          "LLDP power device type is TYPE 1 PSE";
      }
      enum power-device-type-1-pd {
        value 4;
        description
          "LLDP power device type is TYPE 1 PD";
      }
    }
    description
      "LLDP Power device type";
  }

  typedef lldp-pwr-source-type {
    type enumeration {
      enum power-source-pse-and-local {
        value 1;
        description
          "LLDP power source as PSE and Local";
      }
      enum power-source-reserved {
        value 2;
        description
          "LLDP power source as Reserved";
      }
      enum power-source-pse {
        value 3;
        description
          "LLDP power source as PSE";
      }
      enum power-source-unknown {
        value 4;
        description
          "LLDP power source as Unknown";
      }
    }
    description
      "LLDP Power source";
  }

  typedef lldp-pwr-priority-type {
    type enumeration {
      enum power-priority-unknown {
        value 1;
        description
          "LLDP power priority as Unknown";
      }
      enum power-priority-critical {
        value 2;
        description
          "LLDP power source as Critical";
      }
      enum power-prioirty-high {
        value 3;
        description
          "LLDP power source as High";
      }
      enum power-priority-low {
        value 4;
        description
          "LLDP power source as Low";
      }
    }
    description
      "LLDP Power priority";
  }

  typedef chid-subtype {
    type enumeration {
      enum chassis-entphyalias {
        value 1;
        description
          "chassis id sub type holds the value of entity
           MIB physical alias";
      }
      enum chassis-ifalias {
        value 2;
        description
          "chassis id subtype with value Interface alias";
      }
      enum chassis-portentphyalias {
        value 3;
        description
          "chassis id subtype with port component";
      }
      enum chassis-mac {
        value 4;
        description
          "chassis id sub type with MAC address";
      }
      enum chassis-net {
        value 5;
        description
          "chassis id sub type with Network address";
      }
      enum chassis-ifname {
        value 6;
        description
          "chassis id sub type with interface name";
      }
      enum chassis-local {
        value 7;
        description
          "chassis id subtype with locally assigned
           identifier";
      }
    }
    description
      "Chassis id sub-type";
  }

  typedef poid-type {
    type enumeration {
      enum port-ifalias {
        value 1;
        description
          "port id subtype with interface alias";
      }
      enum port-portphyalias {
        value 2;
        description
          "port id subtype with port component";
      }
      enum port-mac {
        value 3;
        description
          "Port id subtype with MAC address";
      }
      enum port-net {
        value 4;
        description
          "Port id subtype with network address";
      }
      enum port-ifname {
        value 5;
        description
          "Port id sub type with interface name";
      }
      enum port-ckt {
        value 6;
        description
          "Port id sub type with circuit";
      }
      enum port-local {
        value 7;
        description
          "Port id sub type with local";
      }
    }
    description
      "port id subtype";
  }

  typedef mgmt-type {
    type enumeration {
      enum mgmt-ip {
        value 1;
        description
          "specifies if the type of management address is
           IPv4";
      }
      enum mgmt-ipv6 {
        value 2;
        description
          "Specifies ipv6 address";
      }
      enum mgmt-decnet {
        value 3;
        description
          "Specifies decnet phase four address";
      }
      enum mgmt-ipx {
        value 4;
        description
          "Specifies ipx address";
      }
      enum mgmt-bv {
        value 5;
        description
          "Specifies banyan vine address type";
      }
      enum mgmt-at {
        value 6;
        description
          "Specifies apple talk address type";
      }
      enum mgmt-not-advertised {
        value 7;
        description
          "Indicates that the management address field is
           not advertised";
      }
    }
    description
      "Types of management address";
  }

  typedef rx-state {
    type enumeration {
      enum wait-port-oper {
        value 0;
        description
          "Transmission waits for port operation to come up";
      }
      enum tx-init {
        value 1;
        description
          "Reception is initialized";
      }
      enum wait-for-frame {
        value 2;
        description
          "Transmission waits for frame";
      }
      enum rx-frame {
        value 3;
        description
          "Transmission waits for receive frame";
      }
      enum update-info {
        value 4;
        description
          "Updates peer LLDP information for port";
      }
      enum delete-info {
        value 5;
        description
          "Deletes Peer lldp info on TTL timeout when Port
           is active";
      }
      enum delete-aged-info {
        value 6;
        description
          "Deletes Peer lldp info on TTL timeout when Port is
           NOT enabled";
      }
    }
    description
      "Reception states available in LLDP";
  }

  typedef tx-state {
    type enumeration {
      enum rx-init {
        value 0;
        description
          "LLDP Transmission is initialized";
      }
      enum idle {
        value 1;
        description
          "Reception is in IDLE state";
      }
      enum info-frame {
        value 2;
        description
          "Information frame is received";
      }
      enum shutdown-frame {
        value 3;
        description
          "Shutdown frame is received";
      }
    }
    description
      "Transmission states available in LLDP";
  }

  typedef phy-media-cap {
    type enumeration {
      enum unknown {
        value 0;
        description
          "Advertised value is not known";
      }
      enum 10baset {
        value 1;
        description
          "10 Base-T half duplex mode is advertised";
      }
      enum 10baset-fd {
        value 2;
        description
          "10 Base-T full duplex mode is advertised";
      }
      enum 100baset4 {
        value 3;
        description
          "10 Base-T4 mode is advertised";
      }
      enum 100basetx {
        value 4;
        description
          "100 Base-TX half duplex mode is advertised";
      }
      enum 100basetx-fd {
        value 5;
        description
          "100 Base-TX full duplex mode is advertised";
      }
      enum 100baset2 {
        value 6;
        description
          "100 Base-T2 half duplex mode is advertised";
      }
      enum 100baset2-fd {
        value 7;
        description
          "100 Base-T2 full duplex mode is advertised";
      }
      enum pause-fd {
        value 8;
        description
          "Pause for full duplex mode is advertised";
      }
      enum asym-pause-fd {
        value 9;
        description
          "Asymmetric pause for full duplex mode is advertised";
      }
      enum sym-pause-fd {
        value 10;
        description
          "Symmetric pause for full duplex mode is advertised";
      }
      enum symm-asym-pause-fd {
        value 11;
        description
          "Symmetric pause for full duplex mode is advertised";
      }
      enum 1000basex-hd {
        value 12;
        description
          "1000 BASE-X, -LX, -SX, -CX half duplex mode is
           advertised";
      }
      enum 1000basex-fd {
        value 13;
        description
          "1000 BASE-X, -LX, -SX, -CX full duplex mode is
           advertised";
      }
      enum 1000base-t-hd {
        value 14;
        description
          "1000 Base-T half duplex mode is advertised";
      }
      enum 1000baset-fd {
        value 15;
        description
          "1000 Base-T full duplex mode is advertised";
      }
    }
    description
      "Physical media capabilities is advertised";
  }

  grouping lldp-capabilities {
    description
      "LLDP device type";
    leaf repeater {
      type empty;
      description
        "Repeater";
    }
    leaf bridge {
      type empty;
      description
        "Bridge";
    }
    leaf access-point {
      type empty;
      description
        "Access point";
    }
    leaf router {
      type empty;
      description
        "Router";
    }
    leaf telephone {
      type empty;
      description
        "Phone";
    }
    leaf docsis {
      type empty;
      description
        "Docsis";
    }
    leaf station {
      type empty;
      description
        "Station";
    }
    leaf other {
      type empty;
      description
        "Other";
    }
  }

  grouping lldp-auto-negotiation {
    description
      "LLDP Auto Negotiation";
    leaf enabled {
      type empty;
      description
        "Auto Negotiation is enabled";
    }
    leaf supported {
      type empty;
      description
        "Auto Negotiation is supported";
    }
  }

  grouping lldp-pwr-via-mdi {
    description
      "Holds details for LLDP Power-via-MDI";
    leaf power-pair {
      type lldp-ios-xe-oper:lldp-pwr-pair-type;
      description
        "Power pair details";
    }
    leaf power-class {
      type lldp-ios-xe-oper:lldp-pwr-class-type;
      description
        "Power class details";
    }
    leaf power-device-type {
      type lldp-ios-xe-oper:lldp-pwr-device-type;
      description
        "Power device type details";
    }
    leaf power-source {
      type lldp-ios-xe-oper:lldp-pwr-source-type;
      description
        "Power source details";
    }
    leaf power-priority {
      type lldp-ios-xe-oper:lldp-pwr-priority-type;
      description
        "Power priority details";
    }
    leaf power-requested {
      type uint32;
      units "milliWatts";
      description
        "Power requested by peer device";
    }
    leaf power-allocated {
      type uint32;
      units "milliWatts";
      description
        "Power allocated to peer device";
    }
  }

  grouping lldp-pwrt {
    description
      "LLDP Power type";
    leaf is-drawing-power {
      type empty;
      description
        "Power is drawn from the device";
    }
    container power-details {
      when 'boolean(../is-drawing-power)';
      description
        "LLDP Power-via-MDI details";
      uses lldp-ios-xe-oper:lldp-pwr-via-mdi;
    }
  }

  grouping lldp-entry-key {
    description
      "Unique LLDP entry identifier";
    leaf device-id {
      type string;
      description
        "Device ID of the link";
    }
    leaf local-interface {
      type string;
      description
        "Name of the local interface on the current device";
    }
    leaf connecting-interface {
      type string;
      description
        "Name of the connected interface to 'local-interface'";
    }
  }

  grouping lldp-entry {
    description
      "LLDP entry details";
    leaf ttl {
      type uint32;
      description
        "TTL denoting hold-time of this link entry";
    }
    container capabilities {
      description
        "LLD device capabilities";
      uses lldp-ios-xe-oper:lldp-capabilities;
    }
    leaf port-vlan-id {
      type uint32;
      description
        "LLDP port VLAN ID";
    }
    leaf mau-type {
      type uint32;
      description
        "Media attachment unit type for LLDP";
    }
    container auto-neg {
      description
        "LLDP auto negotiation details";
      uses lldp-ios-xe-oper:lldp-auto-negotiation;
    }
    container power {
      description
        "LLDP Power-via-MDI details";
      uses lldp-ios-xe-oper:lldp-pwrt;
    }
  }

  grouping lldp-state-entry {
    description
      "LLDP state entry details";
    leaf enabled {
      type boolean;
      description
        "Provides the state of LLDP";
    }
    leaf hello-timer {
      type uint64;
      description
        "Denotes the time between advertisement packets";
    }
    leaf system-name {
      type string;
      description
        "Provides the name of the system";
    }
    leaf system-desc {
      type string;
      description
        "Provides system related information";
    }
    leaf chassis-id {
      type string;
      description
        "Provides information about the chassis";
    }
    leaf chassis-id-type {
      type lldp-ios-xe-oper:chid-subtype;
      description
        "Provides information about the subtype of
         chassis ID";
    }
    leaf frame-in {
      type uint64;
      description
        "Denotes the number of input frames";
    }
    leaf frame-out {
      type uint64;
      description
        "Denotes the number of output frames";
    }
    leaf frame-error-in {
      type uint64;
      description
        "Denotes the number of input frames containing errors";
    }
    leaf frame-discard {
      type uint64;
      description
        "Denotes the number of discarded frames";
    }
    leaf tlv-discard {
      type uint64;
      description
        "Denotes the number of discarded TLVs";
    }
    leaf tlv-unknown {
      type uint64;
      description
        "Denotes the number of unknown TLVs";
    }
    leaf entries-aged-out {
      type uint64;
      description
        "Number of aged out entries";
    }
    leaf mem-failures {
      type uint64;
      description
        "Number of memory allocation failures";
    }
    leaf encap-failures {
      type uint64;
      description
        "Number of encapsulation failures";
    }
    leaf inqueue-overflow {
      type uint64;
      description
        "Number of queue overflow failures";
    }
    leaf table-overflow {
      type uint64;
      description
        "Number of table failures";
    }
  }

  grouping lldp-intf-entry {
    description
      "LLDP entry details for interface";
    leaf if-name {
      type string;
      description
        "Denotes the interface name";
    }
    leaf isenabled {
      type boolean;
      description
        "provides state of LLDP on the interface";
    }
    list lldp-neighbor-details {
      key "identifier";
      description
        "Holds neighbor information";
      uses lldp-ios-xe-oper:lldp-neighbor-entry;
    }
    leaf tx {
      type lldp-ios-xe-oper:tx-state;
      description
        "LLDP transmission state on the interface";
    }
    leaf rx {
      type lldp-ios-xe-oper:rx-state;
      description
        "LLDP reception state on the interface";
    }
  }

  grouping lldp-mgmt {
    description
      "Holds lldp's management address";
    leaf mgmt-addr {
      type string;
      description
        "Denotes the management ip address";
    }
    leaf mgmt-addr-type {
      type lldp-ios-xe-oper:mgmt-type;
      description
        "Denotes the type of management ip address";
    }
  }

  grouping lldp-neighbor-entry {
    description
      "Holds LLDP device neighbor entry";
    leaf identifier {
      type string;
      description
        "Provides information about the system generated id";
    }
    leaf chassis-id {
      type string;
      description
        "Provides information about the chassis";
    }
    leaf chassis-id-type {
      type lldp-ios-xe-oper:chid-subtype;
      description
        "Provides information about the subtype of
         chassis ID";
    }
    leaf port-id {
      type string;
      description
        "Provides information about the port id";
    }
    leaf port-id-type {
      type lldp-ios-xe-oper:poid-type;
      description
        "Provides information about the port id's type";
    }
    leaf port-desc {
      type string;
      description
        "Provides information about the port's description";
    }
    leaf system-name {
      type string;
      description
        "Provides the name of the system";
    }
    leaf system-desc {
      type string;
      description
        "Provides system related information";
    }
    leaf time-remaining {
      type uint32;
      units "seconds";
      description
        "Specifies the timing of next advertisement";
    }
    leaf age {
      type uint32;
      units "seconds";
      description
        "Denotes the age of the current state";
    }
    leaf time-since-last-update {
      type uint32;
      units "seconds";
      description
        "Denotes the time since last update";
    }
    list mgmt-addrs {
      description
        "Denotes the management ip address";
      uses lldp-ios-xe-oper:lldp-mgmt;
    }
    container system-capabilities {
      description
        "Provides LLDP device system capabilities";
      uses lldp-ios-xe-oper:lldp-capabilities;
    }
    container enabled-capabilities {
      description
        "Provides LLDP device enabled capabilities";
      uses lldp-ios-xe-oper:lldp-capabilities;
    }
    leaf media-caps {
      type lldp-ios-xe-oper:phy-media-cap;
      description
        "Physical media capabilities of peer device";
    }
    leaf ttl {
      type uint32;
      units "seconds";
      description
        "The time-to-live (TTL) is a mandatory TLV which
         indicates how long information from the neighbor should be
         considered valid";
    }
    list orgtlv-detail {
      key "platform-id";
      description
        "Holds LLDP org specific TLV information";
      uses lldp-ios-xe-oper:lldp-orgtlv-entry;
    }
  }

  grouping lldp-orgtlv-entry {
    description
      "Holds LLDP org specific TLV entry";
    leaf platform-id {
      type string;
      description
        "Provides information about the platform identifier";
    }
    leaf system-cookie {
      type string;
      description
        "Provides system cookie - the info string for
         an LLDP org specific TLV (Type=127, Subtype=1)";
    }
  }

  container lldp-entries {
    config false;
    description
      "Data nodes for LLDP entries";
    list lldp-entry {
      key "device-id local-interface connecting-interface";
      description
        "The list of LLDP entries";
      uses lldp-ios-xe-oper:lldp-entry-key;
      uses lldp-ios-xe-oper:lldp-entry;
    }
    container lldp-state-details {
      presence "lldp-state-details";
      description
        "The list of LLDP state entries";
      uses lldp-ios-xe-oper:lldp-state-entry;
    }
    list lldp-intf-details {
      key "if-name";
      description
        "The list of LLDP interface entries";
      uses lldp-ios-xe-oper:lldp-intf-entry;
    }
  }
}
