module Cisco-IOS-XE-vservice {
  namespace "http://cisco.com/ns/yang/Cisco-IOS-XE-vservice";
  prefix ios-vservice;

  import ietf-inet-types {
    prefix inet;
  }

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Virtual Service Yang model.
     Copyright (c) 2016 by Cisco Systems, Inc.
     All rights reserved.";

  // =========================================================================
  // REVISION
  // =========================================================================
  revision 2017-02-07 {
    description
      "Initial revision";
  }

  grouping config-vservice-grouping {
    container ip {
      description
        "ip configured virtual service";
      container shared {
        description
          "Ip shared host-interface";
        container host-interface {
          description
            "Ip shared host-interface";
          leaf FastEthernet {
            description
              "FastEthernet IEEE 802.3";
            type string;
          }
          leaf TenGigabitEthernet {
            description
              "Ten Gigabit Ethernet";
            type string;
          }
          leaf Loopback {
            description
              "Loopback interface";
            type uint64 {
              range "0..2147483647";
            }
          }
          leaf Vlan {
            description
              "Vlan interface number";
            type uint16 {
              range "1..4094";
            }
          }
        }
      }
    }
    leaf activate {
      description
        "Activate configured virtual service";
      type empty;
    }
    leaf profile {
      type string;
    }
    container vnic {
      description
        "Guest vnic configuration";
      container gateway {
        description
          "Gateway interface to connect to the guest vnic";
        list VirtualPortGroup {
          description
            "Virtual Port Group";
          key "number";
          leaf number {
            type uint16 {
              range "0..31";
            }
          }
          container guest {
            description
              "Configure guest vnic address";
            choice ip-address {
              case ipv4-case {
                container ip {
                  description
                    "Guest vnic IP address";
                  leaf address {
                    description
                      "Set the IP address of virtual interface on guest";
                    type inet:ipv4-address;
                  }
                }
              }
              case ipv6-case {
                container ipv6 {
                  description
                    "Guest vnic IPv6 address";
                  leaf address {
                    description
                      "Set the IPv6 address of virtual interface on guest";
                    type inet:ipv6-address;
                  }
                }
              }
            }
          }
        }
      }
      container management {
        description
          "Gateway interface to connect to the guest vnic";
        leaf GigabitEthernet0 {
          description
            "Management Ethernet Interface";
          type empty;
        }
        container guest {
          description
            "Configure guest vnic address";
          choice ip-address {
            case ipv4-case {
              container ip {
                description
                  "Guest vnic IP address";
                leaf address {
                  description
                    "Set the IP address of virtual interface on guest";
                  type inet:ipv4-address;
                }
              }
            }
            case ipv6-case {
              container ipv6 {
                description
                  "Guest vnic IPv6 address";
                leaf address {
                  description
                    "Set the IPv6 address of virtual interface on guest";
                  type inet:ipv6-address;
                }
              }
            }
          }
        }
      }
    }
  }

  /////////////////////////////////////////////////////////
  // native / virtual-service
  /////////////////////////////////////////////////////////
  augment "/ios:native/ios:virtual-service" {
    uses config-vservice-grouping;
  } //augment
} //module
