/*
 * Generated by confdc --mib2yang-std
 * Source: mgmt/dmi/model/common/mib-source/CISCO-OSPF-MIB.mib
 */
/*
 * This YANG module has been generated by smidump 0.5.0:
 *
 *      smidump -f yang CISCO-OSPF-MIB
 *
 * Do not edit. Edit the source file instead!
 */

module CISCO-OSPF-MIB {

  namespace "urn:ietf:params:xml:ns:yang:smiv2:CISCO-OSPF-MIB";
  prefix CISCO-OSPF-MIB;

  import IF-MIB {
    prefix "if-mib";
  }

  import INET-ADDRESS-MIB {
    prefix "inet-address";
  }

  import OSPF-MIB {
    prefix "ospf-mib";
  }

  import ietf-inet-types {
    prefix "inet";
  }

  import ietf-yang-smiv2 {
    prefix "smiv2";
  }

  import ietf-yang-types {
    prefix "yang";
  }

  organization
   "Cisco Systems, Inc.";

  contact
   "       Cisco Systems
    Customer Service
    
    Postal: 170 W. Tasman Drive
    San Jose, CA  95134
    USA
    
    Tel: +1 800 553-NETS
    
    E-mail: cs-ospf@cisco.com";

  description
   "An extension to the MIB module defined in
    RFC 1850 for managing OSPF implimentation. 
    Most of the MIB definitions are based on
    the IETF draft 
    < draft-ietf-ospf-mib-update-05.txt > . 
    Support for OSPF Sham link is also added";

  revision 2003-07-18 {
    description
     "+Deprecated cospfShamLinkTable.
      +Added cospfShamLinksTable.
      +Added cospfShamLinkNbrTable.
      +Fixed indentation and spelling.";
  }

  revision 2003-01-28 {
    description
     "Initial version of the MIB module.";
  }


  container CISCO-OSPF-MIB {
    config false;

    container cospfGeneralGroup {
      smiv2:oid "1.3.6.1.4.1.9.10.99.1";

      leaf cospfRFC1583Compatibility {
        type boolean;
        description
         "Indicates metrics used to choose among multiple AS-
          external-LSAs. When cospfRFC1583Compatibility is set to
          enabled, only cost will be used when choosing among
          multiple AS-external-LSAs advertising the same
          destination. When cospfRFC1583Compatibility is set to
          disabled, preference will be driven first by type of
          path using cost only to break ties.";
        reference
         "OSPF Version 2, Section 16.4.1 External path preferences";
        smiv2:max-access "read-only";
        smiv2:oid "1.3.6.1.4.1.9.10.99.1.1";
      }

      leaf cospfOpaqueLsaSupport {
        type boolean;
        description
         "The router's support for Opaque LSA types.";
        reference
         "The OSPF Opaque LSA Option";
        smiv2:max-access "read-only";
        smiv2:oid "1.3.6.1.4.1.9.10.99.1.2";
      }

      leaf cospfTrafficEngineeringSupport {
        type boolean;
        description
         "The router's support for OSPF traffic engineering.";
        smiv2:max-access "read-only";
        smiv2:oid "1.3.6.1.4.1.9.10.99.1.3";
      }

      leaf cospfOpaqueASLsaCount {
        type yang:gauge32;
        description
         "The total number of Opaque AS link-state
          advertisements in the link state database.";
        reference
         "The OSPF Opaque LSA Option (RFC 2370)";
        smiv2:max-access "read-only";
        smiv2:oid "1.3.6.1.4.1.9.10.99.1.4";
      }

      leaf cospfOpaqueASLsaCksumSum {
        type uint32 {
          range "0..4294967295";
        }
        description
         "The 32-bit unsigned sum of the Opaque AS 
          link-state advertisements' LS checksums contained
          link state database.";
        reference
         "The OSPF Opaque LSA Option (RFC 2370)";
        smiv2:max-access "read-only";
        smiv2:oid "1.3.6.1.4.1.9.10.99.1.5";
      }
    }

    container cospfLsdbTable {
      description
       "The OSPF Process's Link State Database. This 
        table is meant for Opaque LSA's";
      reference
       "OSPF Version 2, Section 12 Link State Advertisements";
      smiv2:oid "1.3.6.1.4.1.9.10.99.3";

      list cospfLsdbEntry {
        key "ospfLsdbAreaId cospfLsdbType ospfLsdbLsid ospfLsdbRouterId";
        description
         "A single Link State Advertisement.";
        smiv2:oid "1.3.6.1.4.1.9.10.99.3.1";

        leaf ospfLsdbAreaId {
          type leafref {
            path "/ospf-mib:OSPF-MIB/ospf-mib:ospfLsdbTable/ospf-mib:ospfLsdbEntry/ospf-mib:ospfLsdbAreaId";
          }
        }

        leaf ospfLsdbLsid {
          type leafref {
            path "/ospf-mib:OSPF-MIB/ospf-mib:ospfLsdbTable/ospf-mib:ospfLsdbEntry/ospf-mib:ospfLsdbLsid";
          }
        }

        leaf ospfLsdbRouterId {
          type leafref {
            path "/ospf-mib:OSPF-MIB/ospf-mib:ospfLsdbTable/ospf-mib:ospfLsdbEntry/ospf-mib:ospfLsdbRouterId";
          }
        }

        leaf cospfLsdbType {
          type enumeration {
            enum "areaOpaqueLink" {
              value "10";
            }
            enum "asOpaqueLink" {
              value "11";
            }
          }
          description
           "The type of the link state advertisement.
            Each link state type has a separate advertisement format.";
          reference
           "OSPF Version 2, Appendix A.4.1 The  Link  State
            Advertisement header
            The OSPF Opaque LSA Option (RFC 2370)";
          smiv2:max-access "not-accessible";
          smiv2:oid "1.3.6.1.4.1.9.10.99.3.1.1";
        }

        leaf cospfLsdbSequence {
          type int32 {
            range "1..147483647";
          }
          description
           "The sequence number field is a  signed  32-bit
            integer.   It  is used to detect old and duplicate
            link state advertisements.  The  space  of
            sequence  numbers  is  linearly  ordered.   The
            larger the sequence number the more recent  the
            advertisement.";
          reference
           "OSPF Version  2,  Section  12.1.6  LS  sequence
            number";
          smiv2:max-access "read-only";
          smiv2:oid "1.3.6.1.4.1.9.10.99.3.1.2";
        }

        leaf cospfLsdbAge {
          type int32 {
            range "0..2147483647";
          }
          description
           "This field is the age of the link state advertisement in
            seconds.";
          reference
           "OSPF Version 2, Section 12.1.1 LS age";
          smiv2:max-access "read-only";
          smiv2:oid "1.3.6.1.4.1.9.10.99.3.1.3";
        }

        leaf cospfLsdbChecksum {
          type int32 {
            range "0..2147483647";
          }
          description
           "This field is the  checksum  of  the  complete
            contents  of  the  advertisement, excepting the
            age field.  The age field is excepted  so  that
            an   advertisement's  age  can  be  incremented
            without updating the  checksum.   The  checksum
            used  is  the same that is used for ISO connectionless
            datagrams; it is commonly referred  to
            as the Fletcher checksum.";
          reference
           "OSPF Version 2, Section 12.1.7 LS checksum";
          smiv2:max-access "read-only";
          smiv2:oid "1.3.6.1.4.1.9.10.99.3.1.4";
        }

        leaf cospfLsdbAdvertisement {
          type binary {
            length "1..65535";
          }
          description
           "The entire Link State Advertisement, including
            its header.";
          reference
           "OSPF Version 2, Section 12  Link  State  Adverisements";
          smiv2:max-access "read-only";
          smiv2:oid "1.3.6.1.4.1.9.10.99.3.1.5";
        }
      }
    }

    container cospfShamLinkTable {
      status deprecated;
      description
       "Information about this router's sham links";
      reference
       "IETF draft draft-rosen-vpns-ospf-bgp-mpls-05.txt";
      smiv2:oid "1.3.6.1.4.1.9.10.99.6";

      list cospfShamLinkEntry {
        key "cospfShamLinkAreaId cospfShamLinkLocalIpAddress cospfShamLinkNeighborId";
        status deprecated;
        description
         "Information about a single sham link";
        smiv2:oid "1.3.6.1.4.1.9.10.99.6.1";

        leaf cospfShamLinkAreaId {
          type ospf-mib:AreaID;
          status deprecated;
          description
           "The  Transit  Area  that  the   Virtual   Link
            traverses.  By definition, this is not 0.0.0.0";
          smiv2:max-access "not-accessible";
          smiv2:oid "1.3.6.1.4.1.9.10.99.6.1.1";
        }

        leaf cospfShamLinkLocalIpAddress {
          type inet:ipv4-address;
          status deprecated;
          description
           "The Local IP address of the sham link.";
          smiv2:max-access "not-accessible";
          smiv2:oid "1.3.6.1.4.1.9.10.99.6.1.2";
        }

        leaf cospfShamLinkNeighborId {
          type ospf-mib:RouterID;
          status deprecated;
          description
           "The Router ID of the other end router of the sham
            link.";
          smiv2:max-access "not-accessible";
          smiv2:oid "1.3.6.1.4.1.9.10.99.6.1.3";
        }

        leaf cospfShamLinkRetransInterval {
          type ospf-mib:UpToMaxAge;
          status deprecated;
          description
           "The number of seconds between  link-state  advertisement
            retransmissions,  for  adjacencies
            belonging to this  link.   This  value  is also
            used when retransmitting database description  
            and  link-state  request  packets. This value  
            should  be well over the expected round trip
            time.";
          smiv2:defval "5";
          smiv2:max-access "read-only";
          smiv2:oid "1.3.6.1.4.1.9.10.99.6.1.4";
        }

        leaf cospfShamLinkHelloInterval {
          type ospf-mib:HelloRange;
          status deprecated;
          description
           "The length of time, in  seconds,  between  the
            Hello  packets that the router sends on the sham
            link.";
          smiv2:defval "10";
          smiv2:max-access "read-only";
          smiv2:oid "1.3.6.1.4.1.9.10.99.6.1.5";
        }

        leaf cospfShamLinkRtrDeadInterval {
          type ospf-mib:PositiveInteger;
          status deprecated;
          description
           "The number of seconds that  a  router's  Hello
            packets  have  not been seen before it's neighbors
            declare the router down.  This  should  be
            some  multiple  of  the  Hello  interval.";
          smiv2:defval "40";
          smiv2:max-access "read-only";
          smiv2:oid "1.3.6.1.4.1.9.10.99.6.1.6";
        }

        leaf cospfShamLinkState {
          type enumeration {
            enum "down" {
              value "1";
            }
            enum "pointToPoint" {
              value "4";
            }
          }
          status deprecated;
          description
           "OSPF sham link states.";
          smiv2:defval "down";
          smiv2:max-access "read-only";
          smiv2:oid "1.3.6.1.4.1.9.10.99.6.1.7";
        }

        leaf cospfShamLinkEvents {
          type yang:counter32;
          status deprecated;
          description
           "The number of state changes or error events on
            this sham link";
          smiv2:max-access "read-only";
          smiv2:oid "1.3.6.1.4.1.9.10.99.6.1.8";
        }

        leaf cospfShamLinkMetric {
          type ospf-mib:Metric;
          status deprecated;
          description
           "The Metric to be advertised.";
          smiv2:max-access "read-only";
          smiv2:oid "1.3.6.1.4.1.9.10.99.6.1.9";
        }
      }
    }

    container cospfLocalLsdbTable {
      description
       "The OSPF Process's Link-Local Link State Database
        for non-virtual links.";
      reference
       "OSPF Version 2, Section 12 Link State Advertisements 
        and The OSPF Opaque LSA Option";
      smiv2:oid "1.3.6.1.4.1.9.10.99.7";

      list cospfLocalLsdbEntry {
        key "cospfLocalLsdbIpAddress cospfLocalLsdbAddressLessIf cospfLocalLsdbType cospfLocalLsdbLsid cospfLocalLsdbRouterId";
        description
         "A single Link State Advertisement.";
        smiv2:oid "1.3.6.1.4.1.9.10.99.7.1";

        leaf cospfLocalLsdbIpAddress {
          type inet:ipv4-address;
          description
           "The IP Address of the interface from
            which the LSA was received if the interface is
            numbered.";
          reference
           "OSPF Version 2, Appendix C.3 Interface parameters";
          smiv2:max-access "not-accessible";
          smiv2:oid "1.3.6.1.4.1.9.10.99.7.1.1";
        }

        leaf cospfLocalLsdbAddressLessIf {
          type if-mib:InterfaceIndexOrZero;
          description
           "The Interface Index of the interface from
            which the LSA was received if the interface is
            unnumbered.";
          reference
           "OSPF Version 2, Appendix C.3 Interface parameters";
          smiv2:max-access "not-accessible";
          smiv2:oid "1.3.6.1.4.1.9.10.99.7.1.2";
        }

        leaf cospfLocalLsdbType {
          type enumeration {
            enum "localOpaqueLink" {
              value "9";
            }
          }
          description
           "The type of the link state advertisement.
            Each link state type has a separate advertisement format.";
          reference
           "OSPF Version 2, Appendix A.4.1 The  Link  State
            Advertisement header and ";
          smiv2:max-access "not-accessible";
          smiv2:oid "1.3.6.1.4.1.9.10.99.7.1.3";
        }

        leaf cospfLocalLsdbLsid {
          type inet:ipv4-address;
          description
           "The Link State ID is an LS Type Specific field
            containing a 32 bit identifier in IP address format;
            it identifies the piece of the routing domain
            that is being described by the advertisement.";
          reference
           "OSPF Version 2, Section 12.1.4 Link State ID";
          smiv2:max-access "not-accessible";
          smiv2:oid "1.3.6.1.4.1.9.10.99.7.1.4";
        }

        leaf cospfLocalLsdbRouterId {
          type ospf-mib:RouterID;
          description
           "The 32 bit number that uniquely identifies the
            originating router in the Autonomous System.";
          reference
           "OSPF Version 2, Appendix C.1 Global parameters";
          smiv2:max-access "not-accessible";
          smiv2:oid "1.3.6.1.4.1.9.10.99.7.1.5";
        }

        leaf cospfLocalLsdbSequence {
          type int32 {
            range "-2147483647..2147483647";
          }
          description
           "The sequence number field is a signed 32-bit
            integer. It is used to detect old and duplicate link
            state advertisements. The space of
            sequence numbers is linearly ordered. The
            larger the sequence number the more recent the
            advertisement.";
          reference
           "OSPF Version 2, Section 12.1.6 LS sequence
            number";
          smiv2:max-access "read-only";
          smiv2:oid "1.3.6.1.4.1.9.10.99.7.1.6";
        }

        leaf cospfLocalLsdbAge {
          type int32 {
            range "0..3600";
          }
          description
           "This field is the age of the link state advertisement 
            in seconds.";
          reference
           "OSPF Version 2, Section 12.1.1 LS age";
          smiv2:max-access "read-only";
          smiv2:oid "1.3.6.1.4.1.9.10.99.7.1.7";
        }

        leaf cospfLocalLsdbChecksum {
          type uint32 {
            range "0..4294967295";
          }
          description
           "This field is the checksum of the complete
            contents of the advertisement, excepting the
            age field. The age field is excepted so that
            an advertisement's age can be incremented
            without updating the checksum. The checksum
            used is the same that is used for ISO connectionless
            datagrams; it is commonly referred  to
            as the Fletcher checksum.";
          reference
           "OSPF Version 2, Section 12.1.7 LS checksum";
          smiv2:max-access "read-only";
          smiv2:oid "1.3.6.1.4.1.9.10.99.7.1.8";
        }

        leaf cospfLocalLsdbAdvertisement {
          type binary {
            length "1..65535";
          }
          description
           "The entire Link State Advertisement, including
            its header.";
          reference
           "OSPF Version 2, Section 12 Link State Advertisements";
          smiv2:max-access "read-only";
          smiv2:oid "1.3.6.1.4.1.9.10.99.7.1.9";
        }
      }
    }

    container cospfVirtLocalLsdbTable {
      description
       "The OSPF Process's Link-Local Link State Database
        for virtual links.";
      reference
       "OSPF Version 2, Section 12 Link State Advertisements 
        and The OSPF Opaque LSA Option";
      smiv2:oid "1.3.6.1.4.1.9.10.99.8";

      list cospfVirtLocalLsdbEntry {
        key "cospfVirtLocalLsdbTransitArea cospfVirtLocalLsdbNeighbor cospfVirtLocalLsdbType cospfVirtLocalLsdbLsid cospfVirtLocalLsdbRouterId";
        description
         "A single Link State Advertisement.";
        smiv2:oid "1.3.6.1.4.1.9.10.99.8.1";

        leaf cospfVirtLocalLsdbTransitArea {
          type ospf-mib:AreaID;
          description
           "The Transit Area that the Virtual Link
            traverses. By definition, this is not 0.0.0.0";
          reference
           "OSPF Version 2, Appendix C.3 Interface parameters";
          smiv2:max-access "not-accessible";
          smiv2:oid "1.3.6.1.4.1.9.10.99.8.1.1";
        }

        leaf cospfVirtLocalLsdbNeighbor {
          type ospf-mib:RouterID;
          description
           "The Router ID of the Virtual Neighbor.";
          reference
           "OSPF Version 2, Appendix C.3 Interface parameters";
          smiv2:max-access "not-accessible";
          smiv2:oid "1.3.6.1.4.1.9.10.99.8.1.2";
        }

        leaf cospfVirtLocalLsdbType {
          type enumeration {
            enum "localOpaqueLink" {
              value "9";
            }
          }
          description
           "The type of the link state advertisement.
            Each  link state type has a separate advertisement format.";
          reference
           "OSPF Version 2, Appendix A.4.1 The  Link  State
            Advertisement header and ";
          smiv2:max-access "not-accessible";
          smiv2:oid "1.3.6.1.4.1.9.10.99.8.1.3";
        }

        leaf cospfVirtLocalLsdbLsid {
          type inet:ipv4-address;
          description
           "The Link State ID is an LS Type Specific field
            containing a 32 bit identifier in IP address format;
            it identifies the piece of the routing domain
            that is being described by the advertisement.";
          reference
           "OSPF Version 2, Section 12.1.4 Link State ID";
          smiv2:max-access "not-accessible";
          smiv2:oid "1.3.6.1.4.1.9.10.99.8.1.4";
        }

        leaf cospfVirtLocalLsdbRouterId {
          type ospf-mib:RouterID;
          description
           "The 32 bit number that uniquely identifies the
            originating router in the Autonomous System.";
          reference
           "OSPF Version 2, Appendix C.1 Global parameters";
          smiv2:max-access "not-accessible";
          smiv2:oid "1.3.6.1.4.1.9.10.99.8.1.5";
        }

        leaf cospfVirtLocalLsdbSequence {
          type int32 {
            range "-2147483647..2147483647";
          }
          description
           "The sequence number field is a  signed  32-bit
            integer. It is used to detect old and duplicate
            link state advertisements. The space of
            sequence numbers is linearly ordered. The
            larger the sequence number the more recent the
            advertisement.";
          reference
           "OSPF Version 2, Section 12.1.6 LS sequence
            number";
          smiv2:max-access "read-only";
          smiv2:oid "1.3.6.1.4.1.9.10.99.8.1.6";
        }

        leaf cospfVirtLocalLsdbAge {
          type int32 {
            range "0..3600";
          }
          description
           "This field is the age of the link state advertisement
            in seconds.";
          reference
           "OSPF Version 2, Section 12.1.1 LS age";
          smiv2:max-access "read-only";
          smiv2:oid "1.3.6.1.4.1.9.10.99.8.1.7";
        }

        leaf cospfVirtLocalLsdbChecksum {
          type uint32 {
            range "0..4294967295";
          }
          description
           "This field is the checksum of the complete
            contents of the advertisement, excepting the
            age field. The age field is excepted so that
            an advertisement's age can be incremented
            without updating the checksum. The checksum
            used is the same that is used for ISO connectionless
            datagrams; it is commonly referred  to
            as the Fletcher checksum.";
          reference
           "OSPF Version 2, Section 12.1.7 LS checksum";
          smiv2:max-access "read-only";
          smiv2:oid "1.3.6.1.4.1.9.10.99.8.1.8";
        }

        leaf cospfVirtLocalLsdbAdvertisement {
          type binary {
            length "1..65535";
          }
          description
           "The entire Link State Advertisement, including
            its header.";
          reference
           "OSPF Version 2, Section 12 Link State Advertisements";
          smiv2:max-access "read-only";
          smiv2:oid "1.3.6.1.4.1.9.10.99.8.1.9";
        }
      }
    }

    container cospfShamLinkNbrTable {
      description
       "A table of sham link neighbor information.";
      reference
       "IETF draft draft-rosen-vpns-ospf-bgp-mpls-05.txt";
      smiv2:oid "1.3.6.1.4.1.9.10.99.10";

      list cospfShamLinkNbrEntry {
        key "cospfShamLinksLocalIpAddrType cospfShamLinksLocalIpAddr cospfShamLinkNbrArea cospfShamLinkNbrIpAddrType cospfShamLinkNbrIpAddr";
        description
         "Sham link neighbor information.";
        smiv2:oid "1.3.6.1.4.1.9.10.99.10.1";

        leaf cospfShamLinksLocalIpAddrType {
          type leafref {
            path "/CISCO-OSPF-MIB:CISCO-OSPF-MIB/CISCO-OSPF-MIB:cospfShamLinksTable/CISCO-OSPF-MIB:cospfShamLinksEntry/CISCO-OSPF-MIB:cospfShamLinksLocalIpAddrType";
          }
        }

        leaf cospfShamLinksLocalIpAddr {
          type leafref {
            path "/CISCO-OSPF-MIB:CISCO-OSPF-MIB/CISCO-OSPF-MIB:cospfShamLinksTable/CISCO-OSPF-MIB:cospfShamLinksEntry/CISCO-OSPF-MIB:cospfShamLinksLocalIpAddr";
          }
        }

        leaf cospfShamLinkNbrArea {
          type ospf-mib:AreaID;
          description
           "The area to which the sham link is part of.";
          smiv2:max-access "not-accessible";
          smiv2:oid "1.3.6.1.4.1.9.10.99.10.1.1";
        }

        leaf cospfShamLinkNbrIpAddrType {
          type inet-address:InetAddressType;
          description
           "The type of internet address of this sham link neighbor's
            IP address.";
          smiv2:max-access "not-accessible";
          smiv2:oid "1.3.6.1.4.1.9.10.99.10.1.2";
        }

        leaf cospfShamLinkNbrIpAddr {
          type inet-address:InetAddress;
          description
           "The IP address this sham link neighbor is using.";
          smiv2:max-access "not-accessible";
          smiv2:oid "1.3.6.1.4.1.9.10.99.10.1.3";
        }

        leaf cospfShamLinkNbrRtrId {
          type ospf-mib:RouterID;
          description
           "A 32-bit integer uniquely identifying the neighboring
            router.";
          smiv2:max-access "read-only";
          smiv2:oid "1.3.6.1.4.1.9.10.99.10.1.4";
        }

        leaf cospfShamLinkNbrOptions {
          type int32 {
            range "0..255";
          }
          description
           "A Bit Mask corresponding to the neighbor's options
            field.
            
            Bit 1, if set, indicates that the  system  will
            operate  on  Type of Service metrics other than
            TOS 0.  If zero, the neighbor will  ignore  all
            metrics except the TOS 0 metric.
            
            Bit 2, if set, indicates  that  the  system  is
            Network  Multicast  capable; ie, that it implements 
            OSPF Multicast Routing.";
          smiv2:max-access "read-only";
          smiv2:oid "1.3.6.1.4.1.9.10.99.10.1.5";
        }

        leaf cospfShamLinkNbrState {
          type enumeration {
            enum "down" {
              value "1";
            }
            enum "attempt" {
              value "2";
            }
            enum "init" {
              value "3";
            }
            enum "twoWay" {
              value "4";
            }
            enum "exchangeStart" {
              value "5";
            }
            enum "exchange" {
              value "6";
            }
            enum "loading" {
              value "7";
            }
            enum "full" {
              value "8";
            }
          }
          description
           "The state of this sham link neighbor relation-
            ship.";
          reference
           "OSPF Version 2, Section 10.1 Neighbor states.";
          smiv2:max-access "read-only";
          smiv2:oid "1.3.6.1.4.1.9.10.99.10.1.6";
        }

        leaf cospfShamLinkNbrEvents {
          type yang:counter32;
          description
           "The number of  times  this sham link has changed
            state or an error has occurred.";
          smiv2:max-access "read-only";
          smiv2:oid "1.3.6.1.4.1.9.10.99.10.1.7";
        }

        leaf cospfShamLinkNbrLsRetransQLen {
          type yang:gauge32;
          description
           "The  current  length  of  the   retransmission
            queue. The retransmission queue is maintained for
            LSAs that have been flooded but not acknowledged
            on this adjacency.";
          reference
           "OSPF Version 2, Section 13.6 Retransmitting LSAs.";
          smiv2:max-access "read-only";
          smiv2:oid "1.3.6.1.4.1.9.10.99.10.1.8";
        }

        leaf cospfShamLinkNbrHelloSuppressed {
          type boolean;
          description
           "Indicates whether Hellos are being  suppressed
            to the neighbor.";
          smiv2:max-access "read-only";
          smiv2:oid "1.3.6.1.4.1.9.10.99.10.1.9";
        }
      }
    }

    container cospfShamLinksTable {
      description
       "Information about this router's sham links.";
      reference
       "IETF draft draft-rosen-vpns-ospf-bgp-mpls-05.txt";
      smiv2:oid "1.3.6.1.4.1.9.10.99.11";

      list cospfShamLinksEntry {
        key "cospfShamLinksAreaId cospfShamLinksLocalIpAddrType cospfShamLinksLocalIpAddr cospfShamLinksRemoteIpAddrType cospfShamLinksRemoteIpAddr";
        description
         "Information about a single sham link.";
        smiv2:oid "1.3.6.1.4.1.9.10.99.11.1";

        leaf cospfShamLinksAreaId {
          type ospf-mib:AreaID;
          description
           "The area that this sham link is part of.";
          smiv2:max-access "not-accessible";
          smiv2:oid "1.3.6.1.4.1.9.10.99.11.1.1";
        }

        leaf cospfShamLinksLocalIpAddrType {
          type inet-address:InetAddressType;
          description
           "The type of internet address of this sham link's local IP
            address.";
          smiv2:max-access "not-accessible";
          smiv2:oid "1.3.6.1.4.1.9.10.99.11.1.2";
        }

        leaf cospfShamLinksLocalIpAddr {
          type inet-address:InetAddress;
          description
           "The Local IP address of the sham link.";
          smiv2:max-access "not-accessible";
          smiv2:oid "1.3.6.1.4.1.9.10.99.11.1.3";
        }

        leaf cospfShamLinksRemoteIpAddrType {
          type inet-address:InetAddressType;
          description
           "The type of internet address of this sham link's remote IP
            address.";
          smiv2:max-access "not-accessible";
          smiv2:oid "1.3.6.1.4.1.9.10.99.11.1.4";
        }

        leaf cospfShamLinksRemoteIpAddr {
          type inet-address:InetAddress;
          description
           "The IP address of the other end router of the sham link.";
          smiv2:max-access "not-accessible";
          smiv2:oid "1.3.6.1.4.1.9.10.99.11.1.5";
        }

        leaf cospfShamLinksRetransInterval {
          type ospf-mib:UpToMaxAge;
          description
           "The number of seconds between  link-state  advertisement
            retransmissions, for adjacencies belonging to this link.
            This value is also used when retransmitting database 
            description and link-state request packets. This value
            should be well over the expected round trip time.";
          smiv2:defval "5";
          smiv2:max-access "read-only";
          smiv2:oid "1.3.6.1.4.1.9.10.99.11.1.6";
        }

        leaf cospfShamLinksHelloInterval {
          type ospf-mib:HelloRange;
          description
           "The length of time, in  seconds,  between  the
            Hello  packets that the router sends on the sham
            link.";
          smiv2:defval "10";
          smiv2:max-access "read-only";
          smiv2:oid "1.3.6.1.4.1.9.10.99.11.1.7";
        }

        leaf cospfShamLinksRtrDeadInterval {
          type ospf-mib:PositiveInteger;
          description
           "The number of seconds that  a  router's  Hello
            packets  have  not been seen before it's neighbors
            declare the router down.  This  should  be
            some  multiple  of  the  Hello  interval.";
          smiv2:defval "40";
          smiv2:max-access "read-only";
          smiv2:oid "1.3.6.1.4.1.9.10.99.11.1.8";
        }

        leaf cospfShamLinksState {
          type enumeration {
            enum "down" {
              value "1";
            }
            enum "pointToPoint" {
              value "4";
            }
          }
          description
           "OSPF sham link states.";
          smiv2:defval "down";
          smiv2:max-access "read-only";
          smiv2:oid "1.3.6.1.4.1.9.10.99.11.1.9";
        }

        leaf cospfShamLinksEvents {
          type yang:counter32;
          description
           "The number of state changes or error events on
            this sham link";
          smiv2:max-access "read-only";
          smiv2:oid "1.3.6.1.4.1.9.10.99.11.1.10";
        }

        leaf cospfShamLinksMetric {
          type ospf-mib:Metric;
          description
           "The Metric to be advertised.";
          smiv2:max-access "read-only";
          smiv2:oid "1.3.6.1.4.1.9.10.99.11.1.11";
        }
      }
    }
  }

  smiv2:alias "cospfAreaTable" {
    description
     "Information describing the configured parameters 
      and cumulative statistics of the router's attached 
      areas.";
    reference
     "OSPF Version 2, Section 6 The Area Data Structure";
    smiv2:oid "1.3.6.1.4.1.9.10.99.2";
  }

  smiv2:alias "cospfAreaEntry" {
    description
     "Information describing the configured parameters and 
      cumulative statistics of one of the router's attached 
      areas.";
    smiv2:oid "1.3.6.1.4.1.9.10.99.2.1";
  }

  augment "/ospf-mib:OSPF-MIB/ospf-mib:ospfAreaTable/ospf-mib:ospfAreaEntry" {
    description
     "Information describing the configured parameters and 
      cumulative statistics of one of the router's attached 
      areas.";
    smiv2:oid "1.3.6.1.4.1.9.10.99.2.1";

    leaf cospfOpaqueAreaLsaCount {
      type yang:gauge32;
      description
       "The total number of Opaque Area and AS link-state 
        advertisements in the link state database of this
        area.";
      reference
       "The OSPF Opaque LSA Option (RFC 2370)";
      smiv2:max-access "read-only";
      smiv2:oid "1.3.6.1.4.1.9.10.99.2.1.1";
    }

    leaf cospfOpaqueAreaLsaCksumSum {
      type uint32 {
        range "0..4294967295";
      }
      description
       "The 32-bit unsigned sum of the Opaque Area and AS 
        link-state advertisements' LS checksums contained 
        link state database of this area.  The sum can be 
        used to determine if there has been a change in the 
        link state database for Opaque Area and AS link-state
        advertisements";
      reference
       "The OSPF Opaque LSA Option (RFC 2370)";
      smiv2:max-access "read-only";
      smiv2:oid "1.3.6.1.4.1.9.10.99.2.1.2";
    }

    leaf cospfAreaNssaTranslatorRole {
      type enumeration {
        enum "always" {
          value "1";
        }
        enum "candidate" {
          value "2";
        }
      }
      description
       "Indicates an NSSA Border router's ability to
        perform NSSA translation of type-7 LSAs into
        type-5 LSAs.";
      smiv2:defval "candidate";
      smiv2:max-access "read-only";
      smiv2:oid "1.3.6.1.4.1.9.10.99.2.1.3";
    }

    leaf cospfAreaNssaTranslatorState {
      type enumeration {
        enum "enabled" {
          value "1";
        }
        enum "elected" {
          value "2";
        }
        enum "disabled" {
          value "3";
        }
      }
      description
       "Indicates if and how an NSSA Border router is
        performing NSSA translation of type-7 LSAs into type-5
        LSAs. When this object set to enabled, the NSSA Border
        router's cospfAreaNssaExtTranslatorRole has been set to
        always. When this object is set to elected, a candidate
        NSSA Border router is Translating type-7 LSAs into type-5.
        When this object is set to disabled, a candidate NSSA
        Border router is NOT translating type-7 LSAs into type-5.";
      smiv2:max-access "read-only";
      smiv2:oid "1.3.6.1.4.1.9.10.99.2.1.4";
    }

    leaf cospfAreaNssaTranslatorEvents {
      type yang:counter32;
      description
       "Indicates the number of Translator State changes
        that have occurred since the last boot-up.";
      smiv2:max-access "read-only";
      smiv2:oid "1.3.6.1.4.1.9.10.99.2.1.5";
    }
  }

  smiv2:alias "cospfIfTable" {
    description
     "The OSPF Interface Table describes the inter-
      faces from the viewpoint of OSPF.";
    reference
     "OSPF Version 2, Appendix C.3  Router interface
      parameters";
    smiv2:oid "1.3.6.1.4.1.9.10.99.4";
  }

  smiv2:alias "cospfIfEntry" {
    description
     "The OSPF Interface Entry describes one inter-
      face from the viewpoint of OSPF.";
    smiv2:oid "1.3.6.1.4.1.9.10.99.4.1";
  }

  augment "/ospf-mib:OSPF-MIB/ospf-mib:ospfIfTable/ospf-mib:ospfIfEntry" {
    description
     "The OSPF Interface Entry describes one inter-
      face from the viewpoint of OSPF.";
    smiv2:oid "1.3.6.1.4.1.9.10.99.4.1";

    leaf cospfIfLsaCount {
      type yang:gauge32;
      description
       "The total number of link-local link state advertisements
        in this interface's link-local link state database.";
      reference
       "The OSPF Opaque LSA Option (RFC 2370)";
      smiv2:max-access "read-only";
      smiv2:oid "1.3.6.1.4.1.9.10.99.4.1.1";
    }

    leaf cospfIfLsaCksumSum {
      type uint32 {
        range "0..4294967295";
      }
      description
       "The 32-bit unsigned sum of the link-state advertisements'
        LS checksums contained in this interface's link-local link 
        state database. The sum can be used to determine if there has
        been a change in the interface's link state database, and to
        compare the interface link-state database of routers 
        attached to the same subnet.";
      reference
       "The OSPF Opaque LSA Option (RFC 2370)";
      smiv2:max-access "read-only";
      smiv2:oid "1.3.6.1.4.1.9.10.99.4.1.2";
    }
  }

  smiv2:alias "cospfVirtIfTable" {
    description
     "Information about this router's virtual inter-
      faces.";
    reference
     "OSPF Version 2, Appendix C.4  Virtual link
      parameters";
    smiv2:oid "1.3.6.1.4.1.9.10.99.5";
  }

  smiv2:alias "cospfVirtIfEntry" {
    description
     "Information about a single Virtual Interface.";
    smiv2:oid "1.3.6.1.4.1.9.10.99.5.1";
  }

  augment "/ospf-mib:OSPF-MIB/ospf-mib:ospfVirtIfTable/ospf-mib:ospfVirtIfEntry" {
    description
     "Information about a single Virtual Interface.";
    smiv2:oid "1.3.6.1.4.1.9.10.99.5.1";

    leaf cospfVirtIfLsaCount {
      type yang:gauge32;
      description
       "The total number of link-local link state advertisements
        in this virtual interface's link-local link state database.";
      reference
       "The OSPF Opaque LSA Option (RFC 2370)";
      smiv2:max-access "read-only";
      smiv2:oid "1.3.6.1.4.1.9.10.99.5.1.1";
    }

    leaf cospfVirtIfLsaCksumSum {
      type uint32 {
        range "0..4294967295";
      }
      description
       "The 32-bit unsigned sum of the link-state advertisements'
        LS checksums contained in this
        virtual interface's link-local link state database.
        The sum can be used to determine if there has
        been a change in the virtual interface's link state database,
        and to compare the virtual interface link-state
        database of the virtual neighbors.";
      reference
       "The OSPF Opaque LSA Option (RFC 2370)";
      smiv2:max-access "read-only";
      smiv2:oid "1.3.6.1.4.1.9.10.99.5.1.2";
    }
  }

  smiv2:alias "cospf" {
    smiv2:oid "1.3.6.1.4.1.9.10.99";
  }

  smiv2:alias "cospfGeneralGroup" {
    smiv2:oid "1.3.6.1.4.1.9.10.99.1";
  }

  smiv2:alias "cospfConformance" {
    smiv2:oid "1.3.6.1.4.1.9.10.99.9";
  }

  smiv2:alias "cospfGroups" {
    smiv2:oid "1.3.6.1.4.1.9.10.99.9.1";
  }

  smiv2:alias "cospfCompliances" {
    smiv2:oid "1.3.6.1.4.1.9.10.99.9.2";
  }

}
