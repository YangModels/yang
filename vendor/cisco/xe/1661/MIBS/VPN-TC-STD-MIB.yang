/*
 * Generated by confdc --mib2yang-std
 * Source: mgmt/dmi/model/common/mib-source/VPN-TC-STD-MIB.mib
 */
/*
 * This YANG module has been generated by smidump 0.5.0:
 *
 *      smidump -f yang VPN-TC-STD-MIB
 *
 * Do not edit. Edit the source file instead!
 */

module VPN-TC-STD-MIB {

  namespace "urn:ietf:params:xml:ns:yang:smiv2:VPN-TC-STD-MIB";
  prefix VPN-TC-STD-MIB;

  import ietf-yang-smiv2 {
    prefix "smiv2";
  }

  organization
   "Layer 3 Virtual Private Networks (L3VPN) Working Group.";

  contact
   "Benson Schliesser
    bensons@savvis.net
    
    Thomas D. Nadeau
    tnadeau@cisco.com
    
    This TC MIB is a product of the PPVPN
    http://www.ietf.org/html.charters/ppvpn-charter.html
    and subsequently the L3VPN
    http://www.ietf.org/html.charters/l3vpn-charter.html
    working groups.
    
    Comments and discussion should be directed to
    l3vpn@ietf.org";

  description
   "This MIB contains TCs for VPNs.
    
    Copyright (C) The Internet Society (2005).  This version
    of this MIB module is part of RFC 4265;  see the RFC
    itself for full legal notices.";

  revision 2005-11-15 {
    description
     "Initial version, published as RFC 4265.";
  }

  typedef VPNId {
    type binary {
      length "7";
    }
    description
     "The purpose of a VPN-ID is to uniquely identify a VPN.
      The Global VPN Identifier format is:
      3 octet VPN Authority, Organizationally Unique Identifier
      followed by 4 octet VPN index identifying VPN according
      to OUI";
    reference
     "Fox, B. and Gleeson, B., 'Virtual Private Networks
      Identifier', RFC 2685, September 1999.";
  }

  typedef VPNIdOrZero {
    type binary {
      length "0|7";
    }
    description
     "This textual convention is an extension of the
      VPNId textual convention that defines a non-zero-length
      OCTET STRING to identify a physical entity.  This extension
      permits the additional value of a zero-length OCTET STRING.
      
      The semantics of the value zero-length OCTET STRING are
      object-specific and must therefore be defined
      as part of the description of any object that uses this
      syntax.  Examples of usage of this extension are
      situations where none or all VPN IDs need to be
      referenced.";
  }

  smiv2:alias "vpnTcMIB" {
    smiv2:oid "1.3.6.1.2.1.129";
  }

}
