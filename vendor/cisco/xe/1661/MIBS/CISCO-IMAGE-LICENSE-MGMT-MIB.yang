/*
 * Generated by confdc --mib2yang-std
 * Source: mgmt/dmi/model/common/mib-source/CISCO-IMAGE-LICENSE-MGMT-MIB.mib
 */
/*
 * This YANG module has been generated by smidump 0.5.0:
 *
 *      smidump -f yang CISCO-IMAGE-LICENSE-MGMT-MIB
 *
 * Do not edit. Edit the source file instead!
 */

module CISCO-IMAGE-LICENSE-MGMT-MIB {

  namespace "urn:ietf:params:xml:ns:yang:smiv2:CISCO-IMAGE-LICENSE-MGMT-MIB";
  prefix CISCO-IMAGE-LICENSE-MGMT-MIB;

  import ENTITY-MIB {
    prefix "entity-mib";
  }

  import SNMP-FRAMEWORK-MIB {
    prefix "snmp-framework";
  }

  import ietf-yang-smiv2 {
    prefix "smiv2";
  }

  organization
   "Cisco Systems Inc.";

  contact
   "Cisco Systems
    Customer Service
    Postal: 170 W Tasman Drive
    San Jose, CA  95134
    USA
    Tel: +1 800 553 -NETS
    E-mail: cs-snmp@cisco.com";

  description
   "The MIB module for managing the running image level
    of a Cisco device. Cisco's licensing mechanism provides
    flexibility to run a device on a chosen image level.
    This mechanism is referred to as image level licensing.
    Image level licensing leverages the universal image
    based licensing solution.
    
    The image level licensing mechanism works as follows - 
    
    A universal image that contains all levels of software
    packages is loaded on to the device. At boot time, the
    device determines the highest level of license and brings
    up the appropriate software features or subsystems.
    The user can configure the image level with which the
    device has to boot. The system will verify whether the
    appropriate license is available for the configured image
    level. The image level for the next boot will be determined
    based on the availability of the license. The following
    scenarios explains some use-cases of image level licensing:
    
    Scenario 1:
    - Customer selects advsecurityk9 based image.
    - Manufacturing installs advsecurity license on the device.
    - This device will run all features that are part of the
    base advsecurity license.
    - Customer upgrades to advipservicesk9 license.
    - The next boot level is set to advipservicesk9.
    - The device will run advsecurityk9 feature until the
    next reboot. After reboot the device will run 
    advipservicesk9 features.
    
    Scenario 2:
    - Customer selects advipservicesk9 based image.
    - Manufacturing installs advipservices and advsecurity
    license on the device.
    - This device will run all features that are part of the
    base advipservices license.
    - No upgrades available for advipservices license.
    
    The user has to accept the End User License Agreement(EULA)
    before using this MIB to configure the image level. 
    
    This MIB should be used in conjuntion with
    CISCO-LICENSE-MGMT-MIB module to achieve the image level
    licensing functionality.
    
    This MIB module defines objects which provides the different
    image levels supported by the device and the license required
    to enable a particular image level. It also defines objects
    to let the user configure the required image level. The MIB 
    module contains notification which will be triggered when
    the user changes the image level for next boot. 
    
    The CISCO-LICENSE-MGMT-MIB module should be used to export
    the EULA and to configure the required license.
    
    This MIB module is defined generically so it can be used for
    both stand-alone as well as stackable devices. The
    entPhysicalIndex imported from ENTITY-MIB is used to identify
    the device uniquely.";

  revision 2007-10-16 {
    description
     "Initial version of this MIB module.";
  }

  typedef BootImageLevel {
    type binary {
      length "0..255";
    }
    description
     "This textual convention is used to define
      the image level. 
      
      If the device is running at advipservices 
      image level, then the boot image level will
      be 'advipservices'.";
  }

  typedef LicenseNameList {
    type binary {
      length "0..255";
    }
    description
     "This textual convention is used to define
      the list of license names. If multiple licenses
      are present then this string will contain all
      the licenses seperated by the ',' character.
      
      If the license required to run a device at
      advipservices image level is advipservices and
      advsecurity, then the license name list will be
      'advipservices,advsecurity'.";
  }


  container CISCO-IMAGE-LICENSE-MGMT-MIB {
    config false;

    container ciscoImageLicenseMgmtMIBObjects {
      smiv2:oid "1.3.6.1.4.1.9.9.640.1";

      leaf cilmEULAAccepted {
        type boolean;
        description
         "This object when set to TRUE means that the user has
          accepted the END USER LICENSE AGREEMENT. This object
          has to be set to TRUE by the user before using the
          objects in the cilmBootImageLevelTable to configure
          the license.";
        smiv2:defval "false";
        smiv2:max-access "read-write";
        smiv2:oid "1.3.6.1.4.1.9.9.640.1.3";
      }
    }

    container cilmNotifCntl {
      smiv2:oid "1.3.6.1.4.1.9.9.640.1.4";

      leaf cilmImageLevelChangedNotif {
        type boolean;
        description
         "Specify whether or not a notification should be
          generated on the detection of change in next boot
          image level.
          
          If set to TRUE, cilmBootImageLevelChanged notification
          will be generated. It is the responsibility of the
          management entity to ensure that the SNMP administrative
          model is configured in such a way as to allow the 
          notification to be delivered.";
        reference
         "See also RFC3413 for explanation that notifications
          are under the ultimate control of the MIB module in
          this document.";
        smiv2:defval "false";
        smiv2:max-access "read-write";
        smiv2:oid "1.3.6.1.4.1.9.9.640.1.4.1";
      }
    }

    container cilmBootImageLevelTable {
      description
       "A table that contains the configuration information of
        current and next boot image level. This table contains
        entries for each software module running in an image 
        loaded in the device. The software module is identified by
        cilmModuleName and the device is identified by 
        entPhysicalIndex.";
      smiv2:oid "1.3.6.1.4.1.9.9.640.1.1";

      list cilmBootImageLevelEntry {
        key "entPhysicalIndex cilmModuleName";
        description
         "An entry in the table for each module containing the
          list of objects that define the configuration of next
          boot level. The following information is specified by
          the objects present in the table.
          
          - Current image level.
          - Configured image level for the next boot.
          - Actual image level for the next boot.
          - License store index for the current license.
          - License index of the current license.
          - License store index for the next boot license.
          - License index of the next boot license.";
        smiv2:oid "1.3.6.1.4.1.9.9.640.1.1.1";

        leaf entPhysicalIndex {
          type leafref {
            path "/entity-mib:ENTITY-MIB/entity-mib:entPhysicalTable/entity-mib:entPhysicalEntry/entity-mib:entPhysicalIndex";
          }
        }

        leaf cilmModuleName {
          type snmp-framework:SnmpAdminString;
          description
           "This object is used as one of the two indices in
            cilmBootImageLevelTable. This object indicates the module
            name of the software package. There can be multiple
            modules in an image performing specific functionality.
            For example, in a wireless image there can be two modules
            - a base image module and a wireless module.";
          smiv2:max-access "not-accessible";
          smiv2:oid "1.3.6.1.4.1.9.9.640.1.1.1.1";
        }

        leaf cilmCurrentImageLevel {
          type CISCO-IMAGE-LICENSE-MGMT-MIB:BootImageLevel;
          description
           "This object indicates the current image level that
            the module is running.";
          smiv2:max-access "read-only";
          smiv2:oid "1.3.6.1.4.1.9.9.640.1.1.1.2";
        }

        leaf cilmConfiguredBootImageLevel {
          type CISCO-IMAGE-LICENSE-MGMT-MIB:BootImageLevel;
          description
           "This object indicates the configured image level
            of the module for the next boot.
            
            Note: The configured next boot image level may not 
            be the actual next boot image level. The actual next
            boot image level is denoted by cilmNextBootImageLevel
            which is determined based on the license availability.";
          smiv2:max-access "read-write";
          smiv2:oid "1.3.6.1.4.1.9.9.640.1.1.1.3";
        }

        leaf cilmNextBootImageLevel {
          type CISCO-IMAGE-LICENSE-MGMT-MIB:BootImageLevel;
          description
           "This object indicates the next boot image level. The
            next boot image level can be different from configured
            level. The next boot image level is determined based
            on the availability of required license.";
          smiv2:max-access "read-only";
          smiv2:oid "1.3.6.1.4.1.9.9.640.1.1.1.4";
        }

        leaf cilmCurrentLicenseStoreIndex {
          type uint32;
          description
           "This object indicates the license store index where the
            currently used license is stored. This object has the same
            value as clmgmtLicenseStoreIndex object and uniquely
            identifies an entry in clmgmtLicenseStoreInfoTable in
            CISCO-LICENSE-MGMT-MIB.
            
            Note: The license store index can be '0' if no license is
            installed and device is running base image.";
          smiv2:max-access "read-only";
          smiv2:oid "1.3.6.1.4.1.9.9.640.1.1.1.5";
        }

        leaf cilmCurrentLicenseIndex {
          type uint32;
          description
           "This object indicates the license index of the currently used
            license. This object has the same value as clmgmtLicenseIndex and
            uniquely identifies an entry in clmgmtLicenseInfoTable in
            CISCO-LICENSE-MGMT-MIB.
            
            Note: The license index can be '0' if no license is
            installed and device is running base image.";
          smiv2:max-access "read-only";
          smiv2:oid "1.3.6.1.4.1.9.9.640.1.1.1.6";
        }

        leaf cilmNextBootLicenseStoreIndex {
          type uint32;
          description
           "This object indicates the license store index where the
            next boot license is stored. This object has the same
            value as clmgmtLicenseStoreIndex object and uniquely
            identifies an entry in clmgmtLicenseStoreInfoTable in
            CISCO-LICENSE-MGMT-MIB.
            
            Note: The license store index can be '0' if no license is
            installed for the next boot.";
          smiv2:max-access "read-only";
          smiv2:oid "1.3.6.1.4.1.9.9.640.1.1.1.7";
        }

        leaf cilmNextBootLicenseIndex {
          type uint32;
          description
           "This object indicates the license index of the next boot
            license. This object has the same value as clmgmtLicenseIndex
            and uniquely identifies an entry in clmgmtLicenseInfoTable in
            CISCO-LICENSE-MGMT-MIB.
            
            Note: The license index can be '0' if no license is
            installed for the next boot.";
          smiv2:max-access "read-only";
          smiv2:oid "1.3.6.1.4.1.9.9.640.1.1.1.8";
        }
      }
    }

    container cilmImageLevelToLicenseMapTable {
      description
       "This table contains the mapping between different
        image levels of each modules in the image and the
        license required to run the modules at a particular
        image level. This table can be used to identify the
        different image levels and the appropriate licenses 
        required for each.";
      smiv2:oid "1.3.6.1.4.1.9.9.640.1.2";

      list cilmImageLevelToLicenseMapEntry {
        key "entPhysicalIndex cilmModuleName cilmImageLicenseMapIndex";
        description
         "An entry in the table containing the following
          information.
          - The image levels at the which the modules can be run.
          - The license required to the run a module at a
          particular image level.
          - The priority of the license.";
        smiv2:oid "1.3.6.1.4.1.9.9.640.1.2.1";

        leaf entPhysicalIndex {
          type leafref {
            path "/entity-mib:ENTITY-MIB/entity-mib:entPhysicalTable/entity-mib:entPhysicalEntry/entity-mib:entPhysicalIndex";
          }
        }

        leaf cilmModuleName {
          type leafref {
            path "/CISCO-IMAGE-LICENSE-MGMT-MIB:CISCO-IMAGE-LICENSE-MGMT-MIB/CISCO-IMAGE-LICENSE-MGMT-MIB:cilmBootImageLevelTable/CISCO-IMAGE-LICENSE-MGMT-MIB:cilmBootImageLevelEntry/CISCO-IMAGE-LICENSE-MGMT-MIB:cilmModuleName";
          }
        }

        leaf cilmImageLicenseMapIndex {
          type uint32;
          description
           "This is a running index used to identify an entry
            of this table.";
          smiv2:max-access "not-accessible";
          smiv2:oid "1.3.6.1.4.1.9.9.640.1.2.1.1";
        }

        leaf cilmImageLicenseImageLevel {
          type CISCO-IMAGE-LICENSE-MGMT-MIB:BootImageLevel;
          description
           "This object indicates the image level at which
            a module can be run. A module can be run at
            different image levels. An entry will be created
            in this table for every module and image level
            combination.";
          smiv2:max-access "read-only";
          smiv2:oid "1.3.6.1.4.1.9.9.640.1.2.1.2";
        }

        leaf cilmImageLicenseName {
          type CISCO-IMAGE-LICENSE-MGMT-MIB:LicenseNameList;
          description
           "This object indicates the list of licenses needed to
            be installed for the module to run at the image level
            mentioned by cilmImageLicenseImageLevel object of this
            entry.";
          smiv2:max-access "read-only";
          smiv2:oid "1.3.6.1.4.1.9.9.640.1.2.1.3";
        }

        leaf cilmImageLicensePriority {
          type uint32 {
            range "1..255";
          }
          description
           "This object indicates the priority of the image level
            mentioned by cilmImageLicenseImageLevel object of this
            entry. The image level with the highest priority license
            will be considered as the default level in the absense of
            next boot image level configuration. For example if there
            are three licenses l1, l2 and l3 in the ascending order of
            priority, then by default l1 will be the level at which the
            module will be running. If the next boot level is configured
            then the configuration will override the priority. The highest
            priority license supports a feature set which is a super set of
            all other licenses.";
          smiv2:max-access "read-only";
          smiv2:oid "1.3.6.1.4.1.9.9.640.1.2.1.4";
        }
      }
    }
  }

  notification cilmBootImageLevelChanged {
    description
     "This notification is triggered when next boot image level
      is changed in the management entity. The current and 
      configured image level are indicated by cilmCurrentImageLevel
      and cilmConfiguredBootImageLevel objects respectively.";
    smiv2:oid "1.3.6.1.4.1.9.9.640.0.1";

    container object-1 {

      leaf entPhysicalIndex {
        type leafref {
          path "/entity-mib:ENTITY-MIB/entity-mib:entPhysicalTable/entity-mib:entPhysicalEntry/entity-mib:entPhysicalIndex";
        }
      }

      leaf cilmModuleName {
        type leafref {
          path "/CISCO-IMAGE-LICENSE-MGMT-MIB:CISCO-IMAGE-LICENSE-MGMT-MIB/CISCO-IMAGE-LICENSE-MGMT-MIB:cilmBootImageLevelTable/CISCO-IMAGE-LICENSE-MGMT-MIB:cilmBootImageLevelEntry/CISCO-IMAGE-LICENSE-MGMT-MIB:cilmModuleName";
        }
      }

      leaf cilmCurrentImageLevel {
        type leafref {
          path "/CISCO-IMAGE-LICENSE-MGMT-MIB:CISCO-IMAGE-LICENSE-MGMT-MIB/CISCO-IMAGE-LICENSE-MGMT-MIB:cilmBootImageLevelTable/CISCO-IMAGE-LICENSE-MGMT-MIB:cilmBootImageLevelEntry/CISCO-IMAGE-LICENSE-MGMT-MIB:cilmCurrentImageLevel";
        }
      }
    }

    container object-2 {

      leaf entPhysicalIndex {
        type leafref {
          path "/entity-mib:ENTITY-MIB/entity-mib:entPhysicalTable/entity-mib:entPhysicalEntry/entity-mib:entPhysicalIndex";
        }
      }

      leaf cilmModuleName {
        type leafref {
          path "/CISCO-IMAGE-LICENSE-MGMT-MIB:CISCO-IMAGE-LICENSE-MGMT-MIB/CISCO-IMAGE-LICENSE-MGMT-MIB:cilmBootImageLevelTable/CISCO-IMAGE-LICENSE-MGMT-MIB:cilmBootImageLevelEntry/CISCO-IMAGE-LICENSE-MGMT-MIB:cilmModuleName";
        }
      }

      leaf cilmConfiguredBootImageLevel {
        type leafref {
          path "/CISCO-IMAGE-LICENSE-MGMT-MIB:CISCO-IMAGE-LICENSE-MGMT-MIB/CISCO-IMAGE-LICENSE-MGMT-MIB:cilmBootImageLevelTable/CISCO-IMAGE-LICENSE-MGMT-MIB:cilmBootImageLevelEntry/CISCO-IMAGE-LICENSE-MGMT-MIB:cilmConfiguredBootImageLevel";
        }
      }
    }
  }

  smiv2:alias "ciscoImageLicenseMgmtMIB" {
    smiv2:oid "1.3.6.1.4.1.9.9.640";
  }

  smiv2:alias "ciscoImageLicenseMgmtMIBNotifs" {
    smiv2:oid "1.3.6.1.4.1.9.9.640.0";
  }

  smiv2:alias "ciscoImageLicenseMgmtMIBObjects" {
    smiv2:oid "1.3.6.1.4.1.9.9.640.1";
  }

  smiv2:alias "cilmNotifCntl" {
    smiv2:oid "1.3.6.1.4.1.9.9.640.1.4";
  }

  smiv2:alias "ciscoImageLicenseMgmtMIBConform" {
    smiv2:oid "1.3.6.1.4.1.9.9.640.2";
  }

  smiv2:alias "cilmModuleCompliances" {
    smiv2:oid "1.3.6.1.4.1.9.9.640.2.1";
  }

  smiv2:alias "cilmModuleGroups" {
    smiv2:oid "1.3.6.1.4.1.9.9.640.2.2";
  }

}
