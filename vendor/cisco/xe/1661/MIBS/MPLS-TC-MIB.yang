/*
 * Generated by confdc --mib2yang-std
 * Source: mgmt/dmi/model/common/mib-source/MPLS-TC-MIB.mib
 */
/*
 * This YANG module has been generated by smidump 0.5.0:
 *
 *      smidump -f yang MPLS-TC-MIB
 *
 * Do not edit. Edit the source file instead!
 */

module MPLS-TC-MIB {

  namespace "urn:ietf:params:xml:ns:yang:smiv2:MPLS-TC-MIB";
  prefix MPLS-TC-MIB;

  import ietf-yang-smiv2 {
    prefix "smiv2";
  }

  organization
   "Multiprotocol Label Switching (MPLS) Working Group";

  contact
   "        Thomas D. Nadeau
    Cisco Systems, Inc.
    tnadeau@cisco.com
    
    Joan Cucchiara
    Crescent Networks
    jcucchiara@crescentnetworks.com
    
    Cheenu Srinivasan
    Parama Networks, Inc.
    cheenu@paramanet.com
    
    Arun Viswanathan
    Force10 Networks, Inc.
    arun@force10networks.com
    
    Hans Sjostrand
    ipUnplugged
    hans@ipunplugged.com
    
    Email comments to the MPLS WG Mailing List at
    mpls@uu.net.";

  description
   "This MIB module defines Textual Conventions and
    OBJECT-IDENTITIES for use in documents defining
    management information bases (MIBs) for managing
    MPLS networks.";

  revision 2001-01-04 {
    description
     "Initial version published as part of RFC XXXX.";
  }

  revision 2001-01-04 {
    description
     "[Revision added by libsmi due to a LAST-UPDATED clause.]";
  }

  typedef MplsAtmVcIdentifier {
    type int32 {
      range "32..65535";
    }
    description
     "The VCI value for a VCL. The maximum VCI value
      cannot exceed the value allowable by
      atmInterfaceMaxVciBits defined in ATM-MIB. The
      minimum value is 32, values 0 to 31 are reserved
      for other uses by the ITU and ATM Forum.  32 is
      typically the  default value for the Control VC.";
    reference
     "Definitions of Textual Conventions and OBJECT-
      IDENTITIES for ATM Management, RFC 2514, Feb.
      1999.";
  }

  typedef MplsBitRate {
    type int32 {
      range "1..2147483647";
    }
    description
     "An estimate of bandwidth in units of 1,000 bits per
      second.  If this object reports a value of 'n' then
      the rate of the object is somewhere in the range of
      'n-500' to 'n+499'. For objects which do not vary
      in bit rate, or for those where no accurate
      estimation can be made, this object should contain
      the nominal bit rate.";
    smiv2:display-hint "d";
  }

  typedef MplsBurstSize {
    type uint32 {
      range "1..4294967295";
    }
    description
     "The number of octets of MPLS data that the stream
      may send back-to-back without concern for
      policing.";
    smiv2:display-hint "d";
  }

  typedef MplsExtendedTunnelId {
    type uint32;
    description
     "A unique identifier for an MPLS Tunnel. This MAY
      represent an IpV4 address of the ingress or egress
      LSR for the tunnel. This value is derived from the
      Extended Tunnel Id in RSVP or the Ingress Router ID
      for CR-LDP.";
    reference
     "1. Awduche, D., et al., RSVP-TE: Extensions to RSVP
      for LSP Tunnels,  RFC 3209, December 2001.
      2. Constraint-Based LSP Setup using LDP, Jamoussi,
      B., et al., draft-ietf-mpls-cr-ldp-06.txt, November
      2001.";
  }

  typedef MplsInitialCreationSource {
    type enumeration {
      enum "other" {
        value "1";
      }
      enum "snmp" {
        value "2";
      }
      enum "ldp" {
        value "3";
      }
      enum "rsvp" {
        value "4";
      }
      enum "crldp" {
        value "5";
      }
      enum "policyAgent" {
        value "6";
      }
      enum "unknown" {
        value "7";
      }
    }
    description
     "The entity that originally created the object in
      question. The values of this enumeration are
      defined as follows:
      
      other(1) - This is used when an entity which has not
      been enumerated in this textual convention but
      which is known by the agent.
      
      snmp(2) - The Simple Network Management Protocol was
      used to configure this object initially.
      
      ldp(3 - The Label Distribution Protocol was used to
      configure this object initially.
      
      rsvp(4) - The Resource Reservation Protocol was used
      to configure this object initially.
      
      crldp(5) - The Constraint-Based Label Distribution
      Protocol was used to configure this object
      initially.
      
      policyAgent(6) - A policy agent (perhaps in
      combination with one of the above protocols) was
      used to configure this object initially.
      
      unknown(7) - the agent cannot discern which
      component created the object.";
  }

  typedef MplsLSPID {
    type binary {
      length "0..31";
    }
    description
     "An identifier that is assigned to each LSP and is
      used to uniquely identify it.  This is assigned at
      the head end of the LSP and can be used by all LSRs
      to identify this LSP.  This value is piggybacked by
      the signaling protocol when this LSP is signaled
      
      
      within the network.  This identifier can then be
      used at each LSR to identify which labels are being
      swapped to other labels for this LSP.  For IPv4
      addresses this results in a 6-octet long cookie.";
  }

  typedef MplsLabel {
    type uint32 {
      range "0..4294967295";
    }
    description
     "This value represents an MPLS label as defined in
      [RFC3031],  [RFC3032], [RFC3034] and [RFC3035].";
    reference
     "1. Multiprotocol Label Switching Architecture, Rosen
      et al, RFC 3031, August 1999.
      2. MPLS Label Stack Encoding, Rosen et al, RFC 3032,
      January 2001.
      3. Use of Label Switching on Frame Relay Networks,
      Conta et al, RFC 3034, January 2001.
      4. MPLS using LDP and ATM VC switching, Davie et al,
      RFC 3035, January 2001.";
  }

  typedef MplsLdpGenAddr {
    type binary {
      length "0..64";
    }
    description
     "The value of an network layer or data link layer
      address.";
  }

  typedef MplsLdpIdentifier {
    type binary {
      length "6";
    }
    description
     "The LDP identifier is a six octet quantity which is
      used to identify an Label Switch Router (LSR) label
      space.
      
      The first four octets identify the LSR and must be a
      globally unique value, such as a 32-bit router ID
      assigned to the LSR, and the last two octets
      identify a specific label space within the LSR.";
  }

  typedef MplsLdpLabelTypes {
    type enumeration {
      enum "generic" {
        value "1";
      }
      enum "atm" {
        value "2";
      }
      enum "frameRelay" {
        value "3";
      }
    }
    description
     "The Layer 2 label types which are defined for MPLS
      LDP/CRLDP are generic(1), atm(2), or
      frameRelay(3).";
  }

  typedef MplsLsrIdentifier {
    type binary {
      length "4";
    }
    description
     "The Label Switch Router (LSR) identifier is the
      first 4 bytes of the Label Distribution Protocol
      (LDP) identifier.";
  }

  typedef MplsPathIndex {
    type uint32;
    description
     "A unique identifier used to identify a specific path
      used by a tunnel.";
  }

  typedef MplsPathIndexOrZero {
    type uint32;
    description
     "A unique identifier used to identify a specific path
      used by a tunnel. If this value is set to 0, it
      indicates that no path is in use.";
  }

  typedef MplsPortNumber {
    type int32 {
      range "0..65535";
    }
    description
     "A TCP or UDP port number. Along with an IP address
      identifies a stream of IP traffic uniquely.";
  }

  typedef MplsTunnelAffinity {
    type uint32;
    description
     "Include-any, include-all, or exclude-all constraint
      for link selection.";
  }

  typedef MplsTunnelIndex {
    type int32 {
      range "1..65535";
    }
    description
     "Index into mplsTunnelTable.";
  }

  typedef MplsTunnelInstanceIndex {
    type uint32 {
      range "0..65535";
    }
    description
     "Instance index into mplsTunnelTable.";
  }

  smiv2:alias "mplsMIB" {
    smiv2:oid "1.3.6.1.2.1.10.9999";
  }

  smiv2:alias "mplsTCMIB" {
    smiv2:oid "1.3.6.1.2.1.10.9999.1";
  }

}
