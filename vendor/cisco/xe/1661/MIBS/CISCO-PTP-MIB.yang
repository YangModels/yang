/*
 * Generated by confdc --mib2yang-std
 * Source: mgmt/dmi/model/common/mib-source/CISCO-PTP-MIB.mib
 */
/*
 * This YANG module has been generated by smidump 0.5.0:
 *
 *      smidump -f yang CISCO-PTP-MIB
 *
 * Do not edit. Edit the source file instead!
 */

module CISCO-PTP-MIB {

  namespace "urn:ietf:params:xml:ns:yang:smiv2:CISCO-PTP-MIB";
  prefix CISCO-PTP-MIB;

  import CISCO-TC {
    prefix "cisco-tc";
  }

  import INET-ADDRESS-MIB {
    prefix "inet-address";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-<list>@cisco.com";

  description
   "The MIB module for PTPv2 (IEEE1588 - 2008)
    
    Overview of PTPv2 (IEEE 1588-2008)
    
    This IEEE standard defines a protocol enabling precise
    synchronization of clocks in measurement and control systems
    implemented with packet-based networks, the IEEE Standard PTPv2
    1588 (2008). This MIB does not address the standard IEEE
    1588 (2002). The protocol is applicable to network elements
    communicating using IP. The protocol enables heterogeneous
    systems that include clocks of various inherent precision,
    resolution, and stability to synchronize to a grandmaster
    clock.
    The protocol supports system-wide synchronization accuracy in
    the sub-microsecond range with minimal network and local clock
    computing resources. The standard uses UDP/IP. It includes
    formal mechanisms for message extensions, higher sampling
    rates, correction for asymmetry, a clock type to reduce error
    accumulation in large topologies, and specifications on how to
    incorporate the resulting additional data into the
    synchronization protocol. The standard defines conformance and
    management capability also.
    
    MIB description
    
    This MIB is to support the Precision Timing Protocol (PTP)
    feature of Cisco System devices.
    
    Acronyms:
             ARB       arbitrary
             BMC       best master clock
             CAN       Controller Area Network
             CP        Communication Profile
                       [according to IEC 61784-1:200710]
             CPF       Communication Profile Family
                       [according to IEC 61784-1:2007]
             DS        Differentiated Service
             E2E       End-to-End
             E2ETC     End-to-End Transparent Clock
             EUI       Extended Unique Identifier.
             FFO       Fractional Frequency Offset
             GPS       Global Positioning System
             IANA      Internet Assigned Numbers Authority
             ICV       Integrity Check Value
             ID        Identification
             IPv4      Internet Protocol version 4
             IPv6      Internet Protocol version 6
             JD        Julian Date
             JDN       Julian Day Number
             MAC       Media Access Control
                       [according to IEEE Std 802.3-2005]
             MJD       Modified Julian Day
             NIST      National Institute of Standards and
    Technology                    (see www.nist.gov)
             NTP       Network Time Protocol (see IETF RFC 1305
    [B7])
             OUI       Organizational Unique Identifier(allocated
    by
    the IEEE)
             P2P       Peer-to-Peer
             P2PTC     Peer-To-Peer Transparent Clock
             PHY       physical layer [according to IEEE Std
    802.3-2005]
             POSIX     Portable Operating System Interface
                       (see ISO/IEC 9945:2003)
             PPS       Pulse per Second
             PTP       Precision Time Protocol
             SA        Security Associations
             SNTP      Simple Network Time Protocol
             SOF       Start of Frame
             TAI       International Atomic Time
             TC        Traffic Class
             TC        Transparent Clock
             TLV       Type, Length, Value [according to IEEE Std
    802.1AB]
             ToD       Time of Day Synchronization
             ToS       Type of Service
             UCMM      UnConnect Message Manager
             UDP/IP    User Datagram Protocol
             UTC       Coordinated Universal Time
    
    References:
       [1]  Precision clock synchronization protocol for networked
    measurement and control systems - IEC 61588 IEEE 1588(tm)
    Edition 2.0 2009-02
    
    
    Definitions from [1] section 3.1
    
    Accuracy:
    The mean of the time or frequency error between the clock under
    test and a perfect reference clock, over an ensemble of
    measurements.  Stability is a measure of how the mean varies
    with respect to variables such as time, temperature, and so on.
    
    The precision is a measure of the deviation of the error from
    the mean.
    
    Atomic process:
    A process is atomic if the values of all inputs to the process
    are not permitted to change until all of the results of the
    process are instantiated, and the outputs of the process are
    not visible to other processes until the processing of each
    output is complete.
    
    Boundary clock:
    A clock that has multiple Precision Time Protocol(PTP) ports in
    a domain and maintains the timescale used in the domain.  It
    may serve as the source of time, i.e., be a master clock, and
    may synchronize to another clock, i.e., be a slave clock.
    
    Boundary node clock:
    A clock that has multiple Precision Time Protocol(PTP) ports in
    a domain and maintains the timescale used in the domain. It
    differs from the boundary clock in that the clock roles can
    change.
    
    Clock:
    A node participating in the Precision Time Protocol (PTP) that
    is capable of providing a measurement of the passage of time
    since a defined epoch.
    
    Domain:
    A logical grouping of clocks that synchronize to each other
    using the protocol, but that are not necessarily synchronized
    to clocks in another domain.
    
    End-to-end transparent clock:
    A transparent clock that supports the use of the end-to-end
    delay measurement mechanism between slave clocks and the master
    clock.  Each node must measure the residence time of PTP event
    messages and accumulate it in Correction Field.
    
    Epoch:
    The origin of a timescale.
    
    Event:
    An abstraction of the mechanism by which signals or conditions
    are generated and represented.
    
    Foreign master:
    An ordinary or boundary clock sending Announce messages to
    another clock that is not the current master recognized by the
    other clock.
    
    Grandmaster clock:
    Within a domain, a clock that is the ultimate source of time
    for clock synchronization using the protocol.
    
    Holdover:
    A clock previously synchronized/syntonized to another clock
    (normally a primary reference or a master clock) but now
    free-running based on its own internal oscillator, whose
    frequency is being adjusted using data acquired while it had
    been synchronized/syntonized to the other clock.  It is said to
    be in holdover or in the holdover mode, as long as it is within
    its accuracy requirements.
    
    Link:
    A network segment between two Precision Time Protocol ports
    supporting the peer delay mechanism of this standard.  The peer
    delay mechanism is designed to measure the propagation time
    over such a link.
    
    Management node:
    A device that configures and monitors clocks.
    
    Master clock:
    In the context of a single Precision Time Protocol
    communication path, a clock that is the source of time to which
    all other clocks on that path synchronize.
    
    Message timestamp point:
    A point within a Precision Time Protocol event message serving
    as a reference point in the message.  A timestamp is defined by
    the instant a message timestamp point passes the reference
    plane of a clock.
    
    Multicast communication:
    A communication model in which each Precision Time Protocol
    message sent from any PTP port is capable of being received and
    processed by all PTP ports on the same PTP communication path.
    
    Node:
    A device that can issue or receive Precision Time Protocol
    communications on a network.
    
    One-step clock:
    A clock that provides time information using a single event
    message.
    
    On-pass support:
    Indicates that each node in the synchronization chain from
    master to slave can support IEEE-1588.
    
    Ordinary clock:
    A clock that has a single Precision Time Protocol port in a
    domain and maintains the timescale used in the domain.  It may
    serve as a source of time, i.e., be a master clock, or may
    synchronize to another clock, i.e., be a slave clock.
    
    Parent clock:
    The master clock to which a clock is synchronized.
    
    
    Peer-to-peer transparent clock:
    A transparent clock that, in addition to providing Precision
    Time Protocol event transit time information, also provides
    corrections for the propagation delay of the link connected to
    the port receiving the PTP event message.  In the presence of
    peer-to-peer transparent clocks, delay measurements between
    slave clocks and the master clock are performed using the
    peer-to-peer delay measurement mechanism.
    
    
    Phase change rate:
    The observed rate of change in the measured time with respect
    to the reference time.  The phase change rate is equal to the
    fractional frequency offset between the measured frequency and
    the reference frequency.
    
    PortNumber:
    An index identifying a specific Precision Time Protocol port on
    a PTP node.
    
    Primary reference:
    A source of time and or frequency that is traceable to
    international standards.
    
    Profile:
    The set of allowed Precision Time Protocol features applicable
    to a device.
    
    Precision Time Protocol communication:
    Information used in the operation of the protocol, transmitted
    in a PTP message over a PTP communication path.
    
    Precision Time Protocol communication path: The signaling path
    portion of a particular network enabling direct communication
    among ordinary and boundary clocks.
    
    Precision Time Protocol node:
    PTP ordinary, boundary, or transparent clock or a device that
    generates or parses PTP messages.
    
    Precision Time Protocol port:
    A logical access point of a clock for PTP communications to the
    communications network.
    
    Recognized standard time source:
    A recognized standard time source is a source external to
    Precision Time Protocol that provides time and/or frequency as
    appropriate that is traceable to the international standards
    laboratories maintaining clocks that form the basis for the
    International Atomic Time and Universal Coordinated Time
    timescales.  Examples of these are Global Positioning System,
    NTP, and National Institute of Standards and Technology (NIST)
    timeservers.
    
    Requestor:
    The port implementing the peer-to-peer delay mechanism that
    initiates the mechanism by sending a Pdelay_Req message.
    
    Responder:
    The port responding to the receipt of a Pdelay_Req message as
    part of the operation of the peer-to-peer delay mechanism.
    
    Synchronized clocks:
    Two clocks are synchronized to a specified uncertainty if they
    have the same  epoch and their measurements of the time of a
    single event at an arbitrary time differ by no more than that
    uncertainty.
    
    Syntonized clocks:
    Two clocks are syntonized if the duration of the second is the
    same on both, which means the time as measured by each advances
    at the same rate. They may or may not share the same epoch.
    
    Time of Day:
    
    
    Timeout:
    A mechanism for terminating requested activity that, at least
    from the requester's perspective, does not complete within the
    specified time.
    
    Timescale:
    A linear measure of time from an epoch.
    
    Traceability:
    A property of the result of a measurement or the value of a
    standard whereby it can be related to stated references,
    usually national or international standards, through an unbroken
    chain of comparisons all having stated uncertainties.
    
    Translation device:
    A boundary clock or, in some cases, a transparent clock that
    translates the protocol messages between regions implementing
    different transport and messaging protocols, between different
    versions of IEEE Std 1588-2008/IEC 61588:2009, or different
    Precision Time Protocol profiles.
    
    transparent clock:
    A device that measures the time taken for a Precision Time
    Protocol event message to transit the device and provides this
    information to clocks receiving this PTP event message.
    
    Two-step clock:
    A clock that provides time information using the combination of
    an event message and a subsequent general message.
    
    The below table specifies the object formats of the various
    textual conventions used.
    
    Data type mapping     Textual Convention  SYNTAX
    --------------------  ------------------  ---------------------
    5.3.2 TimeInterval    ClockTimeInterval   OCTET
    STRING(SIZE(1..255))
    5.3.3 Timestamp       ClockTimestamp      OCTET STRING(SIZE(6))
    5.3.4 ClockIdentity   ClockIdentity       OCTET
    STRING(SIZE(1..255))
    5.3.5 PortIdentity    ClockPortNumber     INTEGER(1..65535)
    5.3.7 ClockQuality    ClockQualityClassType
    
    Simple master-slave hierarchy [1] section 6.6.2.4
    
      ---------------
      - Ordinary    -
      - Clock(1)    -
      - GrandMaster -
      -------M-------
             |
             1
             |
      -------S-------------------------------
      - Boundary                            -
      - Clock(1)                            -
      --------------M------------------M-----
                    |                  |
                    2                  3
                    |                  |
               -----S------     -------S------------------
               - Ordinary -     - Boundary               -
               - Clock(2) -     - Clock(2)               -
               ------------     -----M-------------M------
                                     |             |
                                     4             5
                                     |             |
                                -----S------  -----S------
                                - Ordinary -  - Ordinary -
                                - Clock(3) -  - Clock(4) -
                                ------------  ------------
    
      Grandmaster
    
      Boundary Clock(0-N)   Ordinary Clocks(0-N)
      Ordinary Clocks(0-N)
    
    
     Relationship cardinality
        PTP system 1 : N PTP Clock
        PTP Clock 1 : 1 Domain
        PTP Clock 1 : N PTP Ports
        PTP Port N : N Physical Port (interface in IF-MIB)
    
    Transparent clock diagram from section 6.7.1.3 of [1]
    
    
              +----------------------------+
              |     Boundary clock - 1     |
              +----------------------------+
              |                       |
              |                       |
      +-- A --+                       B
      |                               |
    +---------------------+           |
    |   Ordinary clock - 1|           |
    +---------------------+           |
                                      +----------------------+
    +--------------+                  |      End-to-end      |
    |  Ordinary    |------------------|  transparent clock-  |
    |  clock 1-1   |                  |       1 - 1          |
    +--------------+                  +----------------------+
                                       |
                                       |
                                       C
                                       |
                                       |
                                      +----------------------+
    +--------------+                  |      End-to-end      |
    |  Ordinary    |------------------|  transparent clock-  |
    |  clock 1-2   |                  |       1 - 2          |
    +--------------+                  +----------------------+
    
    
    The MIB refers to the sections of the IEEE 1588 standard for
    reference. Throughout the MIB various secions from the standard
    are referenced";

  revision 2011-01-28 {
    description
     "Initial Version";
  }

  typedef ClockDomainType {
    type uint32 {
      range "0..255";
    }
    description
     "The Domain is identified by an integer, the domainNumber, in
      the range of 0 to 255. An integer value that is used to assign
      each PTP device to a particular domain. The following values
      define the valid domains. [1] Section 7.1 Domains Table 2
      
               Value       definition.
               ---------   -------------------
               0           Default domain
               1           Alternate domain 1
               2           Alternate domain 2
               3           Alternate domain 3
               4 - 127     User-defined domains
               128 - 255   Reserved";
    reference
     "Section 7.1 Domains and Table 2 of [1]";
    smiv2:display-hint "d";
  }

  typedef ClockIdentity {
    type binary {
      length "1..255";
    }
    description
     "The clock Identity is an 8-octet array and will be presented in
      the form of a character array. The value of the
      ClockIdentity should be taken from the IEEE EUI-64 individual
      assigned numbers as indicated in Section 7.5.2.2.2 of [1].  The
      EUI-64 address is divided into the following fields.
      
           OUI byte[0-2]
           Extension identifier bytes:[3-7]
      
      The clock identifier can be constructed from existing EUI-48
      assignments and here is an abbreviated example extracted from
      section 7.5.2.2.2 [1].
      
           Company EUI-48 = 0xACDE4823456716
           EUI-64 = ACDE48FFFE23456716
      
      It is important to note the IEEE Registration Authority has
      deprecated the use of MAC-48 in any new design.";
    reference
     "Section 7.5.2.2.1 from [1]";
  }

  typedef ClockIntervalBase2 {
    type int32 {
      range "-128..127";
    }
    description
     "The interval included in message types Announce, Sync,
      Delay_Req, and Pdelay_Req as indicated in section 7.7.2.1 of
      [1].
      
      The mean time interval between successive messages shall be
      represented as the logarithm to the base 2 of this time
      interval measured in seconds on the local clock of the device
      sending the message. The values of these logarithmic attributes
      shall be selected from integers in the range -128 to 127 subject
      to further limits established in an applicable PTP profile.";
    reference
     "Section 7.7.2.1 General interval specification of [1]";
    smiv2:display-hint "d";
  }

  typedef ClockMechanismType {
    type enumeration {
      enum "e2e" {
        value "1";
      }
      enum "p2p" {
        value "2";
      }
      enum "disabled" {
        value "254";
      }
    }
    description
     "The clock type based on whether End to End or peer to peer
      mechanisms are used. The mechanism used to calculate the Mean
      Path Delay as indicated in Table 9 of IEEE 1588-2008.
      
      Delay mechanism       Value(hex) Specification
      E2E                    01        The port is configured to use
                                       the delay request-response
                                       mechanism.
      
      P2P                    02        The port is configured to use
                                       the peer delay mechanism.
      
      DISABLED               FE        The port does not implement
                                       the delay mechanism.";
    reference
     "Sections 8.2.5.4.4, 6.6.4 and 7.4.2 of [1].";
  }

  typedef ClockInstanceType {
    type uint32 {
      range "0..255";
    }
    description
     "The instance of the Clock of a given clock type in a given
      domain.";
    smiv2:display-hint "d";
  }

  typedef ClockPortNumber {
    type uint32 {
      range "0..65535";
    }
    description
     "An index identifying a specific Precision Time Protocol (PTP)
      port on a PTP node.";
    reference
     "Section 7.5.2.3 Port Number and 5.3.5 of [1]";
    smiv2:display-hint "d";
  }

  typedef ClockPortState {
    type enumeration {
      enum "initializing" {
        value "1";
      }
      enum "faulty" {
        value "2";
      }
      enum "disabled" {
        value "3";
      }
      enum "listening" {
        value "4";
      }
      enum "preMaster" {
        value "5";
      }
      enum "master" {
        value "6";
      }
      enum "passive" {
        value "7";
      }
      enum "uncalibrated" {
        value "8";
      }
      enum "slave" {
        value "9";
      }
    }
    description
     "This is the value of the current state of the protocol engine
      associated with this port.
      Port state      Value     Description
      -----------------------------------------------------------
      initializing      1       In this state a port initializes
                                its data sets, hardware, and
                                communication facilities.
      faulty            2       The fault state of the protocol.
      disabled          3       The port shall not place any
                                messages on its communication path.
      listening         4       The port is waiting for the
                                announceReceiptTimeout to expire or
                                to receive an Announce message from
                                a master.
      preMaster         5       The port shall behave in all respects
                                as though it were in the MASTER state
                                except that it shall not place any
                                messages on its communication path
                                except for Pdelay_Req, Pdelay_Resp,
                                Pdelay_Resp_Follow_Up, signaling, or
                                management messages.
      master            6       The port is behaving as a master
                                port. 
      passive           7       The port shall not place any
                                messages on its communication path
                                except for Pdelay_Req, Pdelay_Resp,
                                Pdelay_Resp_Follow_Up, or signaling
                                messages, or management messages
                                that are a required response to
                                another management message
      uncalibrated      8       The local port is preparing to
                                synchronize to the master port.
      slave             9       The port is synchronizing to the
                                selected master port.";
    reference
     "Section 8.2.5.3.1 portState and 9.2.5 of [1]";
  }

  typedef ClockProfileType {
    type enumeration {
      enum "default" {
        value "1";
      }
      enum "telecom" {
        value "2";
      }
      enum "vendorspecific" {
        value "3";
      }
    }
    description
     "Clock Profile used. From [1] section 3.1.30, Profile is the set
      of allowed Precision Time Protocol (PTP) features applicable to
      a device.";
    reference
     "Section 3.1.30 and 19.3 PTP profiles of [1]";
  }

  typedef ClockQualityAccuracyType {
    type enumeration {
      enum "reserved00" {
        value "1";
      }
      enum "nanoSecond25" {
        value "32";
      }
      enum "nanoSecond100" {
        value "33";
      }
      enum "nanoSecond250" {
        value "34";
      }
      enum "microSec1" {
        value "35";
      }
      enum "microSec2dot5" {
        value "36";
      }
      enum "microSec10" {
        value "37";
      }
      enum "microSec25" {
        value "38";
      }
      enum "microSec100" {
        value "39";
      }
      enum "microSec250" {
        value "40";
      }
      enum "milliSec1" {
        value "41";
      }
      enum "milliSec2dot5" {
        value "42";
      }
      enum "milliSec10" {
        value "43";
      }
      enum "milliSec25" {
        value "44";
      }
      enum "milliSec100" {
        value "45";
      }
      enum "milliSec250" {
        value "46";
      }
      enum "second1" {
        value "47";
      }
      enum "second10" {
        value "48";
      }
      enum "secondGreater10" {
        value "49";
      }
      enum "unknown" {
        value "254";
      }
      enum "reserved255" {
        value "255";
      }
    }
    description
     "The ClockQuality as specified in section 5.3.7, 7.6.2.5 and
      Table 6 of [1].
      
      The following values are not represented in the enumerated
      values.
      
               0x01-0x1F Reserved
               0x32-0x7F Reserved
      
      It is important to note that section 7.1.1 RFC2578 allows for
      gaps and enumerate values to start with zero when indicated by
      the protocol.";
    reference
     "Section 5.3.7, 7.6.2.5 and Table 6 of [1]";
  }

  typedef ClockQualityClassType {
    type uint32 {
      range "0..255";
    }
    description
     "The ClockQuality as specified in section 5.3.7, 7.6.2.4 and
      Table 5 of [1].
      
       Value    Description
       ------
      ----------------------------------------------------------
             0  Reserved to enable compatibility with future
                versions.
           1-5  Reserved
             6  Shall designate a clock that is synchronized
                to a primary reference time source.  The
                timescale distributed shall be PTP.  A
                clockClass 6 clock shall not be a slave to
                another clock in the domain.
             7  Shall designate a clock that has previously
                been designated as clockClass 6 but that has
                lost the ability to synchronize to a primary
                reference time source and is in holdover mode
                and within holdover specifications. The
                timescale distributed shall be PTP.  A
                clockClass 7 clock shall not be a slave to
                another clock in the domain.
             8  Reserved.
          9-10  Reserved to enable compatibility with future
                versions.
         11-12  Reserved.
            13  Shall designate a clock that is synchronized
                to an application-specific source of time.
                The timescale distributed shall be ARB.  A
                clockClass 13 clock shall not be a slave to
                another clock in the domain.
            14  Shall designate a clock that has previously
                been designated as clockClass 13 but that
                has lost the ability to synchronize to an
                application-specific source of time and is
                in holdover mode and within holdover
                specifications. The timescale distributed
                shall be ARB.  A clockClass 14 clock shall
                not be a slave to another clock in the domain.
         15-51  Reserved.
            52  Degradation alternative A for a clock of
                clockClass 7 that is not within holdover
                specification.  A clock of clockClass 52
                shall not be a slave to another clock in
                the domain.
         53-57  Reserved.
            58  Degradation alternative A for a clock of
                clockClass 14 that is not within holdover
                specification. A clock of clockClass 58 shall
                not be a slave to another clock in the domain.
         59-67  Reserved.
        68-122  For use by alternate PTP profiles.
       123-127  Reserved.
       128-132  Reserved.
       133-170  For use by alternate PTP profiles.
       171-186  Reserved.
      
           187  Degradation alternative B for a clock of
                clockClass 7 that is not within holdover
                specification. A clock of clockClass 187 may
                be a slave to another clock in the domain.
       188-192 Reserved.
           193 Degradation alternative B for a clock of
               clockClass 14 that is not within holdover
               specification. A clock of clockClass 193 may
               be a slave to another clock in the domain.
       194-215 Reserved.
       216-232 For use by alternate PTP profiles.
       233-247 Reserved.
           248 Default. This clockClass shall be used if
               none of the other clockClass definitions apply.
       249-250 Reserved.
           251 Reserved for version 1 compatibility; see Clause 18.
       252-254 Reserved.
           255 Shall be the clockClass of a slave-only clock; see
      9.2.2.";
    reference
     "section 5.3.7, 7.6.2.4 and Table 5 of [1].";
    smiv2:display-hint "d";
  }

  typedef ClockRoleType {
    type enumeration {
      enum "master" {
        value "1";
      }
      enum "slave" {
        value "2";
      }
    }
    description
     "The Clock Role. The protocol generates a Master Slave
      relationship among the clocks in the system.
      
      Clock Role      Value     Description
      --------------------------------------------------------------
      Master clock     1        A clock that is the source of
                                time to which all other clocks on
                                that path synchronize.
      
      Slave clock       2       A clock which synchronizes to
                                another clock (master).";
  }

  typedef ClockStateType {
    type enumeration {
      enum "freerun" {
        value "1";
      }
      enum "holdover" {
        value "2";
      }
      enum "acquiring" {
        value "3";
      }
      enum "frequencyLocked" {
        value "4";
      }
      enum "phaseAligned" {
        value "5";
      }
    }
    description
     "The clock state returned by PTP engine.
      
      Clock State      Value   Description
      --------------------------------------------------------------
      Freerun state       1   Applies to a slave device that is not
                              locked to a master. This is the initial
                              state a slave starts out with when it
                              is not getting any PTP packets from the
                              master or because of some other input
                              error (erroneous packets, etc).
      
      Holdover state      2  In this state the slave device is
                              locked to a master but communication
                              with the master is lost or the
                              timestamps in the ptp packets are
                              incorrect. But since the slave was
                              locked to the master, it can run with
                              the same accuracy for sometime. The
                              slave can continue to operate in this
                              state for some time. If communication
                              with the master is not restored for a
                              while, the device is moved to the
                              FREERUN state.
      
      Acquiring state     3   The slave device is receiving packets
                              from a master and is trying to acquire
                              a lock.
      
      Freq_locked state   4   Slave device is locked to the Master
                              with respect to frequency, but not phase
                              aligned
      
      Phase_aligned state 5   Locked to the master with respect to
                              frequency and phase.";
  }

  typedef ClockTimeSourceType {
    type enumeration {
      enum "atomicClock" {
        value "16";
      }
      enum "gps" {
        value "32";
      }
      enum "terrestrialRadio" {
        value "48";
      }
      enum "ptp" {
        value "64";
      }
      enum "ntp" {
        value "80";
      }
      enum "handSet" {
        value "96";
      }
      enum "other" {
        value "144";
      }
      enum "internalOsillator" {
        value "160";
      }
    }
    description
     "The ClockQuality as specified in section 5.3.7, 7.6.2.6 and
      Table 7 of [1].
      
      The following values are not represented in the enumerated
      values.
      
      0xF0-0xFE  For use by alternate PTP profiles
      0xFF       Reserved
      
      It is important to note that section 7.1.1 RFC2578 allows for
      gaps and enumerate values to start with zero when indicated by
      the protocol.";
    reference
     "section 5.3.7, 7.6.2.6 and Table 7 of [1].";
  }

  typedef ClockTimeInterval {
    type binary {
      length "1..255";
    }
    description
     "This textual convention corresponds to the TimeInterval
      structure indicated in section 5.3.2 of [1]. It will be
      presented in the form of a character array.
      
      The TimeInterval type represents time intervals.
      
           struct TimeInterval
           {
                Integer64 scaledNanoseconds;
           };
      
      The scaledNanoseconds member is the time interval expressed in
      units of nanoseconds and multiplied by 2**16.
      
      Positive or negative time intervals outside the maximum range
      of this data type shall be encoded as the largest positive and
      negative values of the data type, respectively.
      
      For example, 2.5 ns is expressed as 0000 0000 0002 8000 in
      Base16.";
    reference
     "Section 5.3.2 and setion 7.7.2.1 Timer interval
      specification of [1]";
  }

  typedef ClockTxModeType {
    type enumeration {
      enum "unicast" {
        value "1";
      }
      enum "multicast" {
        value "2";
      }
      enum "multicastmix" {
        value "3";
      }
    }
    description
     "Transmission mode.
      
      unicast. Using unicast commnuication channel.
      
      multicast. Using Multicast communication channel.
      
      multicast-mix. Using multicast-unicast communication channel";
  }

  typedef ClockType {
    type enumeration {
      enum "ordinaryClock" {
        value "1";
      }
      enum "boundaryClock" {
        value "2";
      }
      enum "transparentClock" {
        value "3";
      }
      enum "boundaryNode" {
        value "4";
      }
    }
    description
     "The clock types as defined in the MIB module description.";
    reference
     "section 6.5.1 of [1].";
  }


  container CISCO-PTP-MIB {
    config false;

    container ciscoPtpMIBSystemInfo {
      smiv2:oid "1.3.6.1.4.1.9.9.760.1.1";

      leaf cPtpSystemProfile {
        type CISCO-PTP-MIB:ClockProfileType;
        description
         "This object specifies the PTP Profile implemented on the
          system.";
        reference
         "Section 19.3 PTP profiles of [1]";
        smiv2:max-access "read-only";
        smiv2:oid "1.3.6.1.4.1.9.9.760.1.1.4";
      }
    }

    container cPtpSystemTable {
      description
       "Table of count information about the PTP system for all
        domains.";
      smiv2:oid "1.3.6.1.4.1.9.9.760.1.1.1";

      list cPtpSystemEntry {
        key "cPtpDomainIndex cPtpInstanceIndex";
        description
         "An entry in the table, containing count information about a
          single domain. New row entries are added when the PTP clock for
          this domain is configured, while the unconfiguration of the PTP
          clock removes it.";
        smiv2:oid "1.3.6.1.4.1.9.9.760.1.1.1.1";

        leaf cPtpDomainIndex {
          type CISCO-PTP-MIB:ClockDomainType;
          description
           "This object specifies the domain number used to create logical
            group of PTP devices. The Clock Domain is a logical group of
            clocks and devices that synchronize with each other using the
            PTP protocol.
            
            
            0           Default domain
            1           Alternate domain 1
            2           Alternate domain 2
            3           Alternate domain 3
            4 - 127     User-defined domains
            128 - 255   Reserved";
          smiv2:max-access "not-accessible";
          smiv2:oid "1.3.6.1.4.1.9.9.760.1.1.1.1.1";
        }

        leaf cPtpInstanceIndex {
          type CISCO-PTP-MIB:ClockInstanceType {
            range "0..255";
          }
          description
           "This object specifies the instance of the Clock for this
            domain.";
          smiv2:max-access "not-accessible";
          smiv2:oid "1.3.6.1.4.1.9.9.760.1.1.1.1.2";
        }

        leaf cPtpDomainClockPortsTotal {
          type yang:gauge32;
          units "ptp ports";
          description
           "This object specifies the total number of clock ports
            configured within a domain.";
          smiv2:max-access "read-only";
          smiv2:oid "1.3.6.1.4.1.9.9.760.1.1.1.1.3";
        }

        leaf cPtpDomainClockPortPhysicalInterfacesTotal {
          type yang:gauge32;
          units "physical ports";
          description
           "This object specifies the total number of clock port Physical
            interfaces configured within a domain instance for PTP
            communications.";
          smiv2:max-access "read-only";
          smiv2:oid "1.3.6.1.4.1.9.9.760.1.1.1.1.4";
        }
      }
    }

    container cPtpSystemDomainTable {
      description
       "Table of information about the PTP system for all clock modes
        -- ordinary, boundary or transparent.";
      smiv2:oid "1.3.6.1.4.1.9.9.760.1.1.2";

      list cPtpSystemDomainEntry {
        key "cPtpSystemDomainClockTypeIndex";
        description
         "An entry in the table, containing information about a single
          clock mode for the PTP system. A row entry gets added when PTP
          clocks are configured on the router.";
        smiv2:oid "1.3.6.1.4.1.9.9.760.1.1.2.1";

        leaf cPtpSystemDomainClockTypeIndex {
          type CISCO-PTP-MIB:ClockType;
          description
           "This object specifies the clock type as defined in the
            Textual convention description.";
          smiv2:max-access "not-accessible";
          smiv2:oid "1.3.6.1.4.1.9.9.760.1.1.2.1.1";
        }

        leaf cPtpSystemDomainTotals {
          type yang:gauge32;
          units "domains";
          description
           "This object specifies the  total number of PTP domains for this
            particular clock type configured in this node.";
          smiv2:max-access "read-only";
          smiv2:oid "1.3.6.1.4.1.9.9.760.1.1.2.1.2";
        }
      }
    }

    container cPtpClockNodeTable {
      description
       "Table of information about the PTP system for a given domain.";
      smiv2:oid "1.3.6.1.4.1.9.9.760.1.1.3";

      list cPtpClockNodeEntry {
        key "cPtpClockDomainIndex cPtpClockTypeIndex cPtpClockInstanceIndex";
        description
         "An entry in the table, containing information about a single
          domain. A entry is added when a new PTP clock domain is
          configured on the router.";
        smiv2:oid "1.3.6.1.4.1.9.9.760.1.1.3.1";

        leaf cPtpClockDomainIndex {
          type CISCO-PTP-MIB:ClockDomainType;
          description
           "This object specifies the  domain number used to create logical
            group of PTP devices.";
          smiv2:max-access "not-accessible";
          smiv2:oid "1.3.6.1.4.1.9.9.760.1.1.3.1.1";
        }

        leaf cPtpClockTypeIndex {
          type CISCO-PTP-MIB:ClockType;
          description
           "This object specifies the clock type as defined in the
            Textual convention description.";
          smiv2:max-access "not-accessible";
          smiv2:oid "1.3.6.1.4.1.9.9.760.1.1.3.1.2";
        }

        leaf cPtpClockInstanceIndex {
          type CISCO-PTP-MIB:ClockInstanceType {
            range "0..255";
          }
          description
           "This object specifies the instance of the Clock for this clock
            type for the given domain.";
          smiv2:max-access "not-accessible";
          smiv2:oid "1.3.6.1.4.1.9.9.760.1.1.3.1.3";
        }

        leaf cPtpClockInput1ppsEnabled {
          type boolean;
          description
           "This object specifies whether the node is enabled for PTP input
            clocking using the 1pps interface.";
          smiv2:max-access "read-only";
          smiv2:oid "1.3.6.1.4.1.9.9.760.1.1.3.1.4";
        }

        leaf cPtpClockInputFrequencyEnabled {
          type boolean;
          description
           "This object specifies whether enabled for Frequency input using
            the 1.544 Mhz, 2.048 Mhz, or 10Mhz timing interface.";
          smiv2:max-access "read-only";
          smiv2:oid "1.3.6.1.4.1.9.9.760.1.1.3.1.5";
        }

        leaf cPtpClockTODEnabled {
          type boolean;
          description
           "This object specifies whether the node is enabled for TOD.";
          smiv2:max-access "read-only";
          smiv2:oid "1.3.6.1.4.1.9.9.760.1.1.3.1.6";
        }

        leaf cPtpClockOutput1ppsEnabled {
          type boolean;
          description
           "This object specifies whether the node is enabled for PTP input
            clocking using the 1pps interface.";
          smiv2:max-access "read-only";
          smiv2:oid "1.3.6.1.4.1.9.9.760.1.1.3.1.7";
        }

        leaf cPtpClockOutput1ppsOffsetEnabled {
          type boolean;
          description
           "This object specifies whether an offset is configured in order
            to compensate for a known phase error such as network
            asymmetry.";
          reference
           "section 11 Clock offset, path delay, residence time, and
            asymmetry corrections of [1]";
          smiv2:max-access "read-only";
          smiv2:oid "1.3.6.1.4.1.9.9.760.1.1.3.1.8";
        }

        leaf cPtpClockOutput1ppsOffsetValue {
          type uint32;
          description
           "This object specifies the fixed offset value configured to be
            added for the 1pps output.";
          smiv2:max-access "read-only";
          smiv2:oid "1.3.6.1.4.1.9.9.760.1.1.3.1.9";
        }

        leaf cPtpClockOutput1ppsOffsetNegative {
          type boolean;
          description
           "This object specifies whether the added (fixed) offset to the
            1pps output is negative or not.  When object returns TRUE the
            offset is negative and when object returns FALSE the offset is
            positive.";
          smiv2:max-access "read-only";
          smiv2:oid "1.3.6.1.4.1.9.9.760.1.1.3.1.10";
        }

        leaf cPtpClockInput1ppsInterface {
          type snmpv2-tc:DisplayString;
          description
           "This object specifies the 1pps interface used for PTP input
            clocking.";
          smiv2:max-access "read-only";
          smiv2:oid "1.3.6.1.4.1.9.9.760.1.1.3.1.11";
        }

        leaf cPtpClockOutput1ppsInterface {
          type snmpv2-tc:DisplayString;
          description
           "This object specifies the 1pps interface used for PTP output
            clocking.";
          smiv2:max-access "read-only";
          smiv2:oid "1.3.6.1.4.1.9.9.760.1.1.3.1.12";
        }

        leaf cPtpClockTODInterface {
          type snmpv2-tc:DisplayString;
          description
           "This object specifies the interface used for PTP TOD.";
          smiv2:max-access "read-only";
          smiv2:oid "1.3.6.1.4.1.9.9.760.1.1.3.1.13";
        }
      }
    }

    container cPtpClockCurrentDSTable {
      description
       "Table of information about the PTP clock Current Datasets for
        all domains.";
      smiv2:oid "1.3.6.1.4.1.9.9.760.1.2.1";

      list cPtpClockCurrentDSEntry {
        key "cPtpClockCurrentDSDomainIndex cPtpClockCurrentDSClockTypeIndex cPtpClockCurrentDSInstanceIndex";
        description
         "An entry in the table, containing information about a single
          PTP clock Current Datasets for a domain.";
        reference
         "1588 Version 2.0 Section 8.2.2 currentDS data set member
          specifications of [1]";
        smiv2:oid "1.3.6.1.4.1.9.9.760.1.2.1.1";

        leaf cPtpClockCurrentDSDomainIndex {
          type CISCO-PTP-MIB:ClockDomainType;
          description
           "This object specifies the domain number used to create logical
            group of PTP devices.";
          smiv2:max-access "not-accessible";
          smiv2:oid "1.3.6.1.4.1.9.9.760.1.2.1.1.1";
        }

        leaf cPtpClockCurrentDSClockTypeIndex {
          type CISCO-PTP-MIB:ClockType;
          description
           "This object specifies the clock type as defined in the
            Textual convention description.";
          smiv2:max-access "not-accessible";
          smiv2:oid "1.3.6.1.4.1.9.9.760.1.2.1.1.2";
        }

        leaf cPtpClockCurrentDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.1.1.3";
        }

        leaf cPtpClockCurrentDSStepsRemoved {
          type yang:counter32;
          units "steps";
          description
           "The current clock dataset StepsRemoved value.
            
            This object specifies the distance measured by the number of
            Boundary clocks between the local clock and the Foreign master
            as indicated in the stepsRemoved field of Announce messages.";
          reference
           "1588 Version 2.0 Section 8.2.2.2 stepsRemoved";
          smiv2:max-access "read-only";
          smiv2:oid "1.3.6.1.4.1.9.9.760.1.2.1.1.4";
        }

        leaf cPtpClockCurrentDSOffsetFromMaster {
          type CISCO-PTP-MIB:ClockTimeInterval;
          units "Time Interval";
          description
           "This object specifies the current clock dataset ClockOffset
            value. The value of the computation of the offset in time
            between
            a slave and a master clock.";
          reference
           "1588 Version 2.0 Section 8.2.2.3 of [1]";
          smiv2:max-access "read-only";
          smiv2:oid "1.3.6.1.4.1.9.9.760.1.2.1.1.5";
        }

        leaf cPtpClockCurrentDSMeanPathDelay {
          type CISCO-PTP-MIB:ClockTimeInterval;
          description
           "This object specifies the current clock dataset
            MeanPathDelay value.
            
            The mean path delay between a pair of ports as measure by the
            delay request-response mechanism.";
          reference
           "1588 Version 2.0 Section 8.2.2.4 mean path delay";
          smiv2:max-access "read-only";
          smiv2:oid "1.3.6.1.4.1.9.9.760.1.2.1.1.6";
        }
      }
    }

    container cPtpClockParentDSTable {
      description
       "Table of information about the PTP clock Parent Datasets for
        all domains.";
      smiv2:oid "1.3.6.1.4.1.9.9.760.1.2.2";

      list cPtpClockParentDSEntry {
        key "cPtpClockParentDSDomainIndex cPtpClockParentDSClockTypeIndex cPtpClockParentDSInstanceIndex";
        description
         "An entry in the table, containing information about a single
          PTP clock Parent Datasets for a domain.";
        reference
         "Section 8.2.3 parentDS data set member specifications of
          [1]";
        smiv2:oid "1.3.6.1.4.1.9.9.760.1.2.2.1";

        leaf cPtpClockParentDSDomainIndex {
          type CISCO-PTP-MIB:ClockDomainType;
          description
           "This object specifies the domain number used to create logical
            group of PTP devices.";
          smiv2:max-access "not-accessible";
          smiv2:oid "1.3.6.1.4.1.9.9.760.1.2.2.1.1";
        }

        leaf cPtpClockParentDSClockTypeIndex {
          type CISCO-PTP-MIB:ClockType;
          description
           "This object specifies the clock type as defined in the
            Textual convention description.";
          smiv2:max-access "not-accessible";
          smiv2:oid "1.3.6.1.4.1.9.9.760.1.2.2.1.2";
        }

        leaf cPtpClockParentDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.2.1.3";
        }

        leaf cPtpClockParentDSParentPortIdentity {
          type binary;
          description
           "This object specifies the value of portIdentity of the port on
            the master that issues the Sync messages used in synchronizing
            this clock.";
          reference
           "section 8.2.3.2 parentDS.parentPortIdentity of [1]";
          smiv2:max-access "read-only";
          smiv2:oid "1.3.6.1.4.1.9.9.760.1.2.2.1.4";
        }

        leaf cPtpClockParentDSParentStats {
          type boolean;
          description
           "This object specifies the Parent Dataset ParentStats value.
            
            This value indicates whether the values of ParentDSOffset
            and ParentDSClockPhChRate have been measured and are valid.
            A TRUE value shall indicate valid data.";
          reference
           "section 8.2.3.3 parentDS.parentStats of [1]";
          smiv2:max-access "read-only";
          smiv2:oid "1.3.6.1.4.1.9.9.760.1.2.2.1.5";
        }

        leaf cPtpClockParentDSOffset {
          type CISCO-PTP-MIB:ClockIntervalBase2 {
            range "-128..127";
          }
          description
           "This object specifies the Parent Dataset
            ParentOffsetScaledLogVariance value.
            
            This value is the variance of the parent clocks phase as
            measured by the local clock.";
          reference
           "section 8.2.3.4
            parentDS.observedParentOffsetScaledLogVariance [1]";
          smiv2:max-access "read-only";
          smiv2:oid "1.3.6.1.4.1.9.9.760.1.2.2.1.6";
        }

        leaf cPtpClockParentDSClockPhChRate {
          type int32;
          description
           "This object specifies the clock's parent dataset
            ParentClockPhaseChangeRate value.
            
            This value is an estimate of the parent clocks phase change
            rate as measured by the slave clock.";
          reference
           "section 8.2.3.5
            parentDS.observedParentClockPhaseChangeRate of [1]";
          smiv2:max-access "read-only";
          smiv2:oid "1.3.6.1.4.1.9.9.760.1.2.2.1.7";
        }

        leaf cPtpClockParentDSGMClockIdentity {
          type CISCO-PTP-MIB:ClockIdentity;
          description
           "This object specifies the parent dataset Grandmaster clock
            identity.";
          reference
           "section  8.2.3.6 parentDS.grandmasterIdentity of [1]";
          smiv2:max-access "read-only";
          smiv2:oid "1.3.6.1.4.1.9.9.760.1.2.2.1.8";
        }

        leaf cPtpClockParentDSGMClockPriority1 {
          type int32;
          description
           "This object specifies the parent dataset Grandmaster clock
            priority1.";
          reference
           "section 8.2.3.8 parentDS.grandmasterPriority1 of [1]";
          smiv2:max-access "read-only";
          smiv2:oid "1.3.6.1.4.1.9.9.760.1.2.2.1.9";
        }

        leaf cPtpClockParentDSGMClockPriority2 {
          type int32;
          description
           "This object specifies the parent dataset grandmaster clock
            priority2.";
          reference
           "section 8.2.3.9 parentDS.grandmasterPriority2 of [1]";
          smiv2:max-access "read-only";
          smiv2:oid "1.3.6.1.4.1.9.9.760.1.2.2.1.10";
        }

        leaf cPtpClockParentDSGMClockQualityClass {
          type CISCO-PTP-MIB:ClockQualityClassType {
            range "0..255";
          }
          description
           "This object specifies the parent dataset grandmaster clock
            quality class.";
          reference
           "section 8.2.3.7 parentDS.grandmasterClockQuality of [1]";
          smiv2:max-access "read-only";
          smiv2:oid "1.3.6.1.4.1.9.9.760.1.2.2.1.11";
        }

        leaf cPtpClockParentDSGMClockQualityAccuracy {
          type CISCO-PTP-MIB:ClockQualityAccuracyType;
          description
           "This object specifies the parent dataset grandmaster clock
            quality accuracy.";
          reference
           "section 8.2.3.7 parentDS.grandmasterClockQuality of [1]";
          smiv2:max-access "read-only";
          smiv2:oid "1.3.6.1.4.1.9.9.760.1.2.2.1.12";
        }

        leaf cPtpClockParentDSGMClockQualityOffset {
          type uint32;
          description
           "This object specifies the parent dataset grandmaster clock
            quality offset.";
          reference
           "section 8.2.3.7 parentDS.grandmasterClockQuality of [1]";
          smiv2:max-access "read-only";
          smiv2:oid "1.3.6.1.4.1.9.9.760.1.2.2.1.13";
        }
      }
    }

    container cPtpClockDefaultDSTable {
      description
       "Table of information about the PTP clock Default Datasets for
        all domains.";
      smiv2:oid "1.3.6.1.4.1.9.9.760.1.2.3";

      list cPtpClockDefaultDSEntry {
        key "cPtpClockDefaultDSDomainIndex cPtpClockDefaultDSClockTypeIndex cPtpClockDefaultDSInstanceIndex";
        description
         "An entry in the table, containing information about a single
          PTP clock Default Datasets for a domain.";
        smiv2:oid "1.3.6.1.4.1.9.9.760.1.2.3.1";

        leaf cPtpClockDefaultDSDomainIndex {
          type CISCO-PTP-MIB:ClockDomainType;
          description
           "This object specifies the domain number used to create logical
            group of PTP devices.";
          smiv2:max-access "not-accessible";
          smiv2:oid "1.3.6.1.4.1.9.9.760.1.2.3.1.1";
        }

        leaf cPtpClockDefaultDSClockTypeIndex {
          type CISCO-PTP-MIB:ClockType;
          description
           "This object specifies the clock type as defined in the
            Textual convention description.";
          smiv2:max-access "not-accessible";
          smiv2:oid "1.3.6.1.4.1.9.9.760.1.2.3.1.2";
        }

        leaf cPtpClockDefaultDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.3.1.3";
        }

        leaf cPtpClockDefaultDSTwoStepFlag {
          type boolean;
          description
           "This object specifies whether the Two Step process is used.";
          smiv2:max-access "read-only";
          smiv2:oid "1.3.6.1.4.1.9.9.760.1.2.3.1.4";
        }

        leaf cPtpClockDefaultDSClockIdentity {
          type CISCO-PTP-MIB:ClockIdentity;
          description
           "This object specifies the default Datasets clock identity.";
          smiv2:max-access "read-only";
          smiv2:oid "1.3.6.1.4.1.9.9.760.1.2.3.1.5";
        }

        leaf cPtpClockDefaultDSPriority1 {
          type int32;
          description
           "This object specifies the default Datasets clock Priority1.";
          smiv2:max-access "read-only";
          smiv2:oid "1.3.6.1.4.1.9.9.760.1.2.3.1.6";
        }

        leaf cPtpClockDefaultDSPriority2 {
          type int32;
          description
           "This object specifies the default Datasets clock Priority2.";
          smiv2:max-access "read-only";
          smiv2:oid "1.3.6.1.4.1.9.9.760.1.2.3.1.7";
        }

        leaf cPtpClockDefaultDSSlaveOnly {
          type boolean;
          description
           "Whether the SlaveOnly flag is set.";
          smiv2:max-access "read-only";
          smiv2:oid "1.3.6.1.4.1.9.9.760.1.2.3.1.8";
        }

        leaf cPtpClockDefaultDSQualityClass {
          type CISCO-PTP-MIB:ClockQualityClassType {
            range "0..255";
          }
          description
           "This object specifies the default dataset Quality Class.";
          smiv2:max-access "read-only";
          smiv2:oid "1.3.6.1.4.1.9.9.760.1.2.3.1.9";
        }

        leaf cPtpClockDefaultDSQualityAccuracy {
          type CISCO-PTP-MIB:ClockQualityAccuracyType;
          description
           "This object specifies the default dataset Quality Accurarcy.";
          smiv2:max-access "read-only";
          smiv2:oid "1.3.6.1.4.1.9.9.760.1.2.3.1.10";
        }

        leaf cPtpClockDefaultDSQualityOffset {
          type int32;
          description
           "This object specifies the default dataset Quality offset.";
          smiv2:max-access "read-only";
          smiv2:oid "1.3.6.1.4.1.9.9.760.1.2.3.1.11";
        }
      }
    }

    container cPtpClockRunningTable {
      description
       "Table of information about the PTP clock Running Datasets for
        all domains.";
      smiv2:oid "1.3.6.1.4.1.9.9.760.1.2.4";

      list cPtpClockRunningEntry {
        key "cPtpClockRunningDomainIndex cPtpClockRunningClockTypeIndex cPtpClockRunningInstanceIndex";
        description
         "An entry in the table, containing information about a single
          PTP clock running Datasets for a domain.";
        smiv2:oid "1.3.6.1.4.1.9.9.760.1.2.4.1";

        leaf cPtpClockRunningDomainIndex {
          type CISCO-PTP-MIB:ClockDomainType;
          description
           "This object specifies the domain number used to create logical
            group of PTP devices.";
          smiv2:max-access "not-accessible";
          smiv2:oid "1.3.6.1.4.1.9.9.760.1.2.4.1.1";
        }

        leaf cPtpClockRunningClockTypeIndex {
          type CISCO-PTP-MIB:ClockType;
          description
           "This object specifies the clock type as defined in the
            Textual convention description.";
          smiv2:max-access "not-accessible";
          smiv2:oid "1.3.6.1.4.1.9.9.760.1.2.4.1.2";
        }

        leaf cPtpClockRunningInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.4.1.3";
        }

        leaf cPtpClockRunningState {
          type CISCO-PTP-MIB:ClockStateType;
          description
           "This object specifies the Clock state returned by PTP engine
            which was described earlier.
            
            Freerun state. Applies to a slave device that is not locked to
            a master. This is the initial state a slave starts out with
            when
            it is not getting any PTP packets from the master or because of
            some other input error (erroneous packets, etc).
            
            Holdover state. In this state the slave device is locked to a
            master but communication with the master is lost or the
            timestamps in the ptp packets are incorrect. But since the
            slave was locked to the master, it can run with the same
            accuracy for
            sometime. The slave can continue to operate in this state for
            some time. If communication with the master is not restored for
            a while, the device is moved to the FREERUN state.
            
            Acquiring state. The slave device is receiving packets from a
            master and is trying to acquire a lock.
            
            Freq_locked state. Slave device is locked to the Master with
            respect to frequency, but not phase aligned
            
            Phase_aligned state. Locked to the master with respect to
            frequency and phase.";
          smiv2:max-access "read-only";
          smiv2:oid "1.3.6.1.4.1.9.9.760.1.2.4.1.4";
        }

        leaf cPtpClockRunningPacketsSent {
          type yang:counter64;
          description
           "This object specifies the total number of all packet Unicast
            and multicast that have been sent out for this clock in this
            domain for this type.";
          smiv2:max-access "read-only";
          smiv2:oid "1.3.6.1.4.1.9.9.760.1.2.4.1.5";
        }

        leaf cPtpClockRunningPacketsReceived {
          type yang:counter64;
          description
           "This object specifies the total number of all packet Unicast
            and multicast that have been received for this clock in this
            domain for this type.";
          smiv2:max-access "read-only";
          smiv2:oid "1.3.6.1.4.1.9.9.760.1.2.4.1.6";
        }
      }
    }

    container cPtpClockTimePropertiesDSTable {
      description
       "Table of information about the PTP clock Timeproperties
        Datasets for all domains.";
      smiv2:oid "1.3.6.1.4.1.9.9.760.1.2.5";

      list cPtpClockTimePropertiesDSEntry {
        key "cPtpClockTimePropertiesDSDomainIndex cPtpClockTimePropertiesDSClockTypeIndex cPtpClockTimePropertiesDSInstanceIndex";
        description
         "An entry in the table, containing information about a single
          PTP clock timeproperties Datasets for a domain.";
        reference
         "Section 8.2.4 of [1]";
        smiv2:oid "1.3.6.1.4.1.9.9.760.1.2.5.1";

        leaf cPtpClockTimePropertiesDSDomainIndex {
          type CISCO-PTP-MIB:ClockDomainType;
          description
           "This object specifies the domain number used to create logical
            group of PTP devices.";
          smiv2:max-access "not-accessible";
          smiv2:oid "1.3.6.1.4.1.9.9.760.1.2.5.1.1";
        }

        leaf cPtpClockTimePropertiesDSClockTypeIndex {
          type CISCO-PTP-MIB:ClockType;
          description
           "This object specifies the clock type as defined in the
            Textual convention description.";
          smiv2:max-access "not-accessible";
          smiv2:oid "1.3.6.1.4.1.9.9.760.1.2.5.1.2";
        }

        leaf cPtpClockTimePropertiesDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.5.1.3";
        }

        leaf cPtpClockTimePropertiesDSCurrentUTCOffsetValid {
          type boolean;
          description
           "This object specifies the timeproperties dataset value of
            whether current UTC offset is valid.";
          reference
           "Section 8.2.4.2 of [1]";
          smiv2:max-access "read-only";
          smiv2:oid "1.3.6.1.4.1.9.9.760.1.2.5.1.4";
        }

        leaf cPtpClockTimePropertiesDSCurrentUTCOffset {
          type int32;
          description
           "This object specifies the timeproperties dataset value of
            current UTC offset.
            
            In PTP systems whose epoch is the PTP epoch, the value of
            timePropertiesDS.currentUtcOffset is the offset
            between TAI and UTC; otherwise the value has no meaning. The
            value shall be in units of seconds.
            The initialization value shall be selected as follows:
            a) If the timePropertiesDS.ptpTimescale (see 8.2.4.8) is TRUE,
            the value is the value obtained from a
            primary reference if the value is known at the time of
            initialization, else.
            b) The value shall be the current number of leap seconds (7.2.3)
            when the node is designed.";
          reference
           "Section 8.2.4.3 of [1]";
          smiv2:max-access "read-only";
          smiv2:oid "1.3.6.1.4.1.9.9.760.1.2.5.1.5";
        }

        leaf cPtpClockTimePropertiesDSLeap59 {
          type boolean;
          description
           "This object specifies the Leap59 value in the clock Current
            Dataset.";
          reference
           "Section 8.2.4.4 of [1]";
          smiv2:max-access "read-only";
          smiv2:oid "1.3.6.1.4.1.9.9.760.1.2.5.1.6";
        }

        leaf cPtpClockTimePropertiesDSLeap61 {
          type boolean;
          description
           "This object specifies the Leap61 value in the clock Current
            Dataset.";
          reference
           "Section 8.2.4.5 of [1]";
          smiv2:max-access "read-only";
          smiv2:oid "1.3.6.1.4.1.9.9.760.1.2.5.1.7";
        }

        leaf cPtpClockTimePropertiesDSTimeTraceable {
          type boolean;
          description
           "This object specifies the Timetraceable value in the clock
            Current Dataset.";
          reference
           "Section 8.2.4.6 of [1]";
          smiv2:max-access "read-only";
          smiv2:oid "1.3.6.1.4.1.9.9.760.1.2.5.1.8";
        }

        leaf cPtpClockTimePropertiesDSFreqTraceable {
          type boolean;
          description
           "This object specifies the Frequency Traceable value in the
            clock Current Dataset.";
          reference
           "Section 8.2.4.7 of [1]";
          smiv2:max-access "read-only";
          smiv2:oid "1.3.6.1.4.1.9.9.760.1.2.5.1.9";
        }

        leaf cPtpClockTimePropertiesDSPTPTimescale {
          type boolean;
          description
           "This object specifies the PTP Timescale value in the clock
            Current Dataset.";
          reference
           "Section 8.2.4.8 of [1]";
          smiv2:max-access "read-only";
          smiv2:oid "1.3.6.1.4.1.9.9.760.1.2.5.1.10";
        }

        leaf cPtpClockTimePropertiesDSSource {
          type CISCO-PTP-MIB:ClockTimeSourceType;
          description
           "This object specifies the Timesource value in the clock Current
            Dataset.";
          reference
           "Section 8.2.4.9 of [1]";
          smiv2:max-access "read-only";
          smiv2:oid "1.3.6.1.4.1.9.9.760.1.2.5.1.11";
        }
      }
    }

    container cPtpClockTransDefaultDSTable {
      description
       "Table of information about the PTP Transparent clock Default
        Datasets for all domains.";
      smiv2:oid "1.3.6.1.4.1.9.9.760.1.2.6";

      list cPtpClockTransDefaultDSEntry {
        key "cPtpClockTransDefaultDSDomainIndex cPtpClockTransDefaultDSInstanceIndex";
        description
         "An entry in the table, containing information about a single
          PTP Transparent clock Default Datasets for a domain.";
        reference
         "Section 8.3.2 of [1]";
        smiv2:oid "1.3.6.1.4.1.9.9.760.1.2.6.1";

        leaf cPtpClockTransDefaultDSDomainIndex {
          type CISCO-PTP-MIB:ClockDomainType;
          description
           "This object specifies the domain number used to create logical
            group of PTP devices.";
          smiv2:max-access "not-accessible";
          smiv2:oid "1.3.6.1.4.1.9.9.760.1.2.6.1.1";
        }

        leaf cPtpClockTransDefaultDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.6.1.2";
        }

        leaf cPtpClockTransDefaultDSClockIdentity {
          type CISCO-PTP-MIB:ClockIdentity;
          description
           "This object specifies the value of the clockIdentity attribute
            of the local clock.";
          reference
           "Section 8.3.2.2.1 of [1]";
          smiv2:max-access "read-only";
          smiv2:oid "1.3.6.1.4.1.9.9.760.1.2.6.1.3";
        }

        leaf cPtpClockTransDefaultDSNumOfPorts {
          type yang:counter32;
          description
           "This object specifies the number of PTP ports of the device.";
          reference
           "Section 8.3.2.2.2 of [1]";
          smiv2:max-access "read-only";
          smiv2:oid "1.3.6.1.4.1.9.9.760.1.2.6.1.4";
        }

        leaf cPtpClockTransDefaultDSDelay {
          type CISCO-PTP-MIB:ClockMechanismType;
          description
           "This object, if the transparent clock is an end-to-end
            transparent clock, has the value shall be E2E; If the
            transparent clock is a peer-to-peer transparent clock, the
            value
            shall be P2P.";
          reference
           "Section 8.3.2.3.1 of [1]";
          smiv2:max-access "read-only";
          smiv2:oid "1.3.6.1.4.1.9.9.760.1.2.6.1.5";
        }

        leaf cPtpClockTransDefaultDSPrimaryDomain {
          type int32;
          description
           "This object specifies the value of the primary syntonization
            domain. The initialization value shall be 0.";
          reference
           "Section 8.3.2.3.2 of [1]";
          smiv2:max-access "read-only";
          smiv2:oid "1.3.6.1.4.1.9.9.760.1.2.6.1.6";
        }
      }
    }

    container cPtpClockPortTable {
      description
       "Table of information about the clock ports for a particular
        domain.";
      smiv2:oid "1.3.6.1.4.1.9.9.760.1.2.7";

      list cPtpClockPortEntry {
        key "cPtpClockPortDomainIndex cPtpClockPortClockTypeIndex cPtpClockPortClockInstanceIndex cPtpClockPortTablePortNumberIndex";
        description
         "An entry in the table, containing information about a single
          clock port.";
        smiv2:oid "1.3.6.1.4.1.9.9.760.1.2.7.1";

        leaf cPtpClockPortDomainIndex {
          type CISCO-PTP-MIB:ClockDomainType;
          description
           "This object specifies the domain number used to create logical
            group of PTP devices.";
          smiv2:max-access "not-accessible";
          smiv2:oid "1.3.6.1.4.1.9.9.760.1.2.7.1.1";
        }

        leaf cPtpClockPortClockTypeIndex {
          type CISCO-PTP-MIB:ClockType;
          description
           "This object specifies the clock type as defined in the
            Textual convention description.";
          smiv2:max-access "not-accessible";
          smiv2:oid "1.3.6.1.4.1.9.9.760.1.2.7.1.2";
        }

        leaf cPtpClockPortClockInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.7.1.3";
        }

        leaf cPtpClockPortTablePortNumberIndex {
          type CISCO-PTP-MIB:ClockPortNumber {
            range "1..65535";
          }
          description
           "This object specifies the PTP Portnumber for this port.";
          smiv2:max-access "not-accessible";
          smiv2:oid "1.3.6.1.4.1.9.9.760.1.2.7.1.4";
        }

        leaf cPtpClockPortName {
          type snmpv2-tc:DisplayString {
            length "1..64";
          }
          description
           "This object specifies the PTP clock port name configured on the
            router.";
          smiv2:max-access "read-only";
          smiv2:oid "1.3.6.1.4.1.9.9.760.1.2.7.1.5";
        }

        leaf cPtpClockPortRole {
          type CISCO-PTP-MIB:ClockRoleType;
          description
           "This object describes the current role (slave/master) of the
            port.";
          smiv2:max-access "read-only";
          smiv2:oid "1.3.6.1.4.1.9.9.760.1.2.7.1.6";
        }

        leaf cPtpClockPortSyncOneStep {
          type boolean;
          description
           "This object specifies that one-step clock operation between
            the PTP master and slave device is enabled.";
          smiv2:max-access "read-only";
          smiv2:oid "1.3.6.1.4.1.9.9.760.1.2.7.1.7";
        }

        leaf cPtpClockPortCurrentPeerAddressType {
          type inet-address:InetAddressType;
          description
           "This object specifies the current peer's network address used
            for PTP communication. Based on the scenario and the setup
            involved, the values might look like these -
            Scenario                   Value
            -------------------   ----------------
            Single Master          master port
            Multiple Masters       selected master port
            Single Slave           slave port
            Multiple Slaves        <empty>
            
            (In relevant setups, information on available
            slaves and available masters will be available through 
            cPtpClockPortAssociateTable)";
          smiv2:max-access "read-only";
          smiv2:oid "1.3.6.1.4.1.9.9.760.1.2.7.1.8";
        }

        leaf cPtpClockPortCurrentPeerAddress {
          type inet-address:InetAddress;
          description
           "This object specifies the current peer's network address used
            for PTP communication. Based on the scenario and the setup
            involved, the values might look like these -
            Scenario                   Value
            -------------------   ----------------
            Single Master          master port
            Multiple Masters       selected master port
            Single Slave           slave port
            Multiple Slaves        <empty>
            
            (In relevant setups, information on available
            slaves and available masters will be available through 
            cPtpClockPortAssociateTable)";
          smiv2:max-access "read-only";
          smiv2:oid "1.3.6.1.4.1.9.9.760.1.2.7.1.9";
        }

        leaf cPtpClockPortNumOfAssociatedPorts {
          type yang:gauge32;
          description
           "This object specifies -
            For a master port - the number of PTP slave sessions (peers)
            associated with this PTP port.
            For a slave port - the number of masters available to this slave
            port (might or might not be peered).";
          smiv2:max-access "read-only";
          smiv2:oid "1.3.6.1.4.1.9.9.760.1.2.7.1.10";
        }
      }
    }

    container cPtpClockPortDSTable {
      description
       "Table of information about the clock ports dataset for a
        particular domain.";
      smiv2:oid "1.3.6.1.4.1.9.9.760.1.2.8";

      list cPtpClockPortDSEntry {
        key "cPtpClockPortDSDomainIndex cPtpClockPortDSClockTypeIndex cPtpClockPortDSClockInstanceIndex cPtpClockPortDSPortNumberIndex";
        description
         "An entry in the table, containing port dataset information for
          a single clock port.";
        smiv2:oid "1.3.6.1.4.1.9.9.760.1.2.8.1";

        leaf cPtpClockPortDSDomainIndex {
          type CISCO-PTP-MIB:ClockDomainType;
          description
           "This object specifies the domain number used to create logical
            group of PTP devices.";
          smiv2:max-access "not-accessible";
          smiv2:oid "1.3.6.1.4.1.9.9.760.1.2.8.1.1";
        }

        leaf cPtpClockPortDSClockTypeIndex {
          type CISCO-PTP-MIB:ClockType;
          description
           "This object specifies the clock type as defined in the
            Textual convention description.";
          smiv2:max-access "not-accessible";
          smiv2:oid "1.3.6.1.4.1.9.9.760.1.2.8.1.2";
        }

        leaf cPtpClockPortDSClockInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.8.1.3";
        }

        leaf cPtpClockPortDSPortNumberIndex {
          type CISCO-PTP-MIB:ClockPortNumber {
            range "1..65535";
          }
          description
           "This object specifies the PTP portnumber associated with this
            PTP port.";
          smiv2:max-access "not-accessible";
          smiv2:oid "1.3.6.1.4.1.9.9.760.1.2.8.1.4";
        }

        leaf cPtpClockPortDSName {
          type snmpv2-tc:DisplayString {
            length "1..64";
          }
          description
           "This object specifies the PTP clock port name.";
          smiv2:max-access "read-only";
          smiv2:oid "1.3.6.1.4.1.9.9.760.1.2.8.1.5";
        }

        leaf cPtpClockPortDSPortIdentity {
          type binary;
          description
           "This object specifies the PTP clock port Identity.";
          smiv2:max-access "read-only";
          smiv2:oid "1.3.6.1.4.1.9.9.760.1.2.8.1.6";
        }

        leaf cPtpClockPortDSAnnouncementInterval {
          type int32;
          description
           "This object specifies the Announce message transmission
            interval associated with this clock port.";
          smiv2:max-access "read-only";
          smiv2:oid "1.3.6.1.4.1.9.9.760.1.2.8.1.7";
        }

        leaf cPtpClockPortDSAnnounceRctTimeout {
          type int32;
          description
           "This object specifies the Announce receipt timeout associated
            with this clock port.";
          smiv2:max-access "read-only";
          smiv2:oid "1.3.6.1.4.1.9.9.760.1.2.8.1.8";
        }

        leaf cPtpClockPortDSSyncInterval {
          type int32;
          description
           "This object specifies the Sync message transmission interval.";
          smiv2:max-access "read-only";
          smiv2:oid "1.3.6.1.4.1.9.9.760.1.2.8.1.9";
        }

        leaf cPtpClockPortDSMinDelayReqInterval {
          type int32;
          description
           "This object specifies the Delay_Req message transmission
            interval.";
          smiv2:max-access "read-only";
          smiv2:oid "1.3.6.1.4.1.9.9.760.1.2.8.1.10";
        }

        leaf cPtpClockPortDSPeerDelayReqInterval {
          type int32;
          description
           "This object specifies the Pdelay_Req message transmission
            interval.";
          smiv2:max-access "read-only";
          smiv2:oid "1.3.6.1.4.1.9.9.760.1.2.8.1.11";
        }

        leaf cPtpClockPortDSDelayMech {
          type CISCO-PTP-MIB:ClockMechanismType;
          description
           "This object specifies the delay mechanism used. If the clock
            is an end-to-end clock, the value of the is e2e, else if the
            clock is a peer to-peer clock, the value shall be p2p.";
          smiv2:max-access "read-only";
          smiv2:oid "1.3.6.1.4.1.9.9.760.1.2.8.1.12";
        }

        leaf cPtpClockPortDSPeerMeanPathDelay {
          type CISCO-PTP-MIB:ClockTimeInterval;
          description
           "This object specifies the peer meanPathDelay.";
          smiv2:max-access "read-only";
          smiv2:oid "1.3.6.1.4.1.9.9.760.1.2.8.1.13";
        }

        leaf cPtpClockPortDSGrantDuration {
          type uint32;
          description
           "This object specifies the grant duration allocated by the
            master.";
          smiv2:max-access "read-only";
          smiv2:oid "1.3.6.1.4.1.9.9.760.1.2.8.1.14";
        }

        leaf cPtpClockPortDSPTPVersion {
          type int32;
          description
           "This object specifies the PTP version being used.";
          smiv2:max-access "read-only";
          smiv2:oid "1.3.6.1.4.1.9.9.760.1.2.8.1.15";
        }
      }
    }

    container cPtpClockPortRunningTable {
      description
       "Table of information about the clock ports running dataset for
        a particular domain.";
      smiv2:oid "1.3.6.1.4.1.9.9.760.1.2.9";

      list cPtpClockPortRunningEntry {
        key "cPtpClockPortRunningDomainIndex cPtpClockPortRunningClockTypeIndex cPtpClockPortRunningClockInstanceIndex cPtpClockPortRunningPortNumberIndex";
        description
         "An entry in the table, containing runing dataset information
          about a single clock port.";
        smiv2:oid "1.3.6.1.4.1.9.9.760.1.2.9.1";

        leaf cPtpClockPortRunningDomainIndex {
          type CISCO-PTP-MIB:ClockDomainType;
          description
           "This object specifies the domain number used to create logical
            group of PTP devices.";
          smiv2:max-access "not-accessible";
          smiv2:oid "1.3.6.1.4.1.9.9.760.1.2.9.1.1";
        }

        leaf cPtpClockPortRunningClockTypeIndex {
          type CISCO-PTP-MIB:ClockType;
          description
           "This object specifies the clock type as defined in the
            Textual convention description.";
          smiv2:max-access "not-accessible";
          smiv2:oid "1.3.6.1.4.1.9.9.760.1.2.9.1.2";
        }

        leaf cPtpClockPortRunningClockInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.9.1.3";
        }

        leaf cPtpClockPortRunningPortNumberIndex {
          type CISCO-PTP-MIB:ClockPortNumber {
            range "1..65535";
          }
          description
           "This object specifies the PTP portnumber associated with this
            clock port.";
          smiv2:max-access "not-accessible";
          smiv2:oid "1.3.6.1.4.1.9.9.760.1.2.9.1.4";
        }

        leaf cPtpClockPortRunningName {
          type snmpv2-tc:DisplayString {
            length "1..64";
          }
          description
           "This object specifies the PTP clock port name.";
          smiv2:max-access "read-only";
          smiv2:oid "1.3.6.1.4.1.9.9.760.1.2.9.1.5";
        }

        leaf cPtpClockPortRunningState {
          type CISCO-PTP-MIB:ClockPortState;
          description
           "This object specifies the port state returned by PTP engine.
            
            initializing - In this state a port initializes
                           its data sets, hardware, and
                           communication facilities.
            faulty       - The fault state of the protocol.
            disabled     - The port shall not place any
                           messages on its communication path.
            listening    - The port is waiting for the
                           announceReceiptTimeout to expire or
                           to receive an Announce message from
                           a master.
            preMaster    - The port shall behave in all respects
                           as though it were in the MASTER state
                           except that it shall not place any
                           messages on its communication path
                           except for Pdelay_Req, Pdelay_Resp,
                           Pdelay_Resp_Follow_Up, signaling, or
                           management messages.
            master       - The port is behaving as a master port.           
            
            passive      - The port shall not place any
                           messages on its communication path
                           except for Pdelay_Req, Pdelay_Resp,
                           Pdelay_Resp_Follow_Up, or signaling
                           messages, or management messages
                           that are a required response to
                           another management message
            uncalibrated - The local port is preparing to
                           synchronize to the master port.
            slave        - The port is synchronizing to the
                           selected master port.";
          smiv2:max-access "read-only";
          smiv2:oid "1.3.6.1.4.1.9.9.760.1.2.9.1.6";
        }

        leaf cPtpClockPortRunningRole {
          type CISCO-PTP-MIB:ClockRoleType;
          description
           "This object specifies the Clock Role.";
          smiv2:max-access "read-only";
          smiv2:oid "1.3.6.1.4.1.9.9.760.1.2.9.1.7";
        }

        leaf cPtpClockPortRunningInterfaceIndex {
          type cisco-tc:InterfaceIndexOrZero;
          description
           "This object specifies the interface on the router being used by
            the PTP Clock for PTP communication.";
          smiv2:max-access "read-only";
          smiv2:oid "1.3.6.1.4.1.9.9.760.1.2.9.1.8";
        }

        leaf cPtpClockPortRunningIPversion {
          type int32;
          description
           "This object specifirst the IP version being used for PTP
            communication (the mapping used).";
          smiv2:max-access "read-only";
          smiv2:oid "1.3.6.1.4.1.9.9.760.1.2.9.1.9";
        }

        leaf cPtpClockPortRunningEncapsulationType {
          type int32;
          description
           "This object specifies the type of encapsulation if the
            interface is adding extra  layers (eg. VLAN, Pseudowire
            encapsulation...) for the PTP messages.";
          smiv2:max-access "read-only";
          smiv2:oid "1.3.6.1.4.1.9.9.760.1.2.9.1.10";
        }

        leaf cPtpClockPortRunningTxMode {
          type CISCO-PTP-MIB:ClockTxModeType;
          description
           "This object specifies the clock transmission mode as
            
            unicast:       Using unicast commnuication channel.
            multicast:     Using Multicast communication channel.
            multicast-mix: Using multicast-unicast communication channel";
          smiv2:max-access "read-only";
          smiv2:oid "1.3.6.1.4.1.9.9.760.1.2.9.1.11";
        }

        leaf cPtpClockPortRunningRxMode {
          type CISCO-PTP-MIB:ClockTxModeType;
          description
           "This object specifie the clock receive mode as
            
            unicast:       Using unicast commnuication channel.
            multicast:     Using Multicast communication channel.
            multicast-mix: Using multicast-unicast communication channel";
          smiv2:max-access "read-only";
          smiv2:oid "1.3.6.1.4.1.9.9.760.1.2.9.1.12";
        }

        leaf cPtpClockPortRunningPacketsReceived {
          type yang:counter64;
          units "packets";
          description
           "This object specifies the packets received on the clock port
            (cummulative).";
          smiv2:max-access "read-only";
          smiv2:oid "1.3.6.1.4.1.9.9.760.1.2.9.1.13";
        }

        leaf cPtpClockPortRunningPacketsSent {
          type yang:counter64;
          units "packets";
          description
           "This object specifies the packets sent on the clock port
            (cummulative).";
          smiv2:max-access "read-only";
          smiv2:oid "1.3.6.1.4.1.9.9.760.1.2.9.1.14";
        }
      }
    }

    container cPtpClockPortTransDSTable {
      description
       "Table of information about the Transparent clock ports running
        dataset for a particular domain.";
      smiv2:oid "1.3.6.1.4.1.9.9.760.1.2.10";

      list cPtpClockPortTransDSEntry {
        key "cPtpClockPortTransDSDomainIndex cPtpClockPortTransDSInstanceIndex cPtpClockPortTransDSPortNumberIndex";
        description
         "An entry in the table, containing clock port Transparent
          dataset information about a single clock port";
        smiv2:oid "1.3.6.1.4.1.9.9.760.1.2.10.1";

        leaf cPtpClockPortTransDSDomainIndex {
          type CISCO-PTP-MIB:ClockDomainType;
          description
           "This object specifies the domain number used to create logical
            group of PTP devices.";
          smiv2:max-access "not-accessible";
          smiv2:oid "1.3.6.1.4.1.9.9.760.1.2.10.1.1";
        }

        leaf cPtpClockPortTransDSInstanceIndex {
          type CISCO-PTP-MIB:ClockInstanceType {
            range "0..255";
          }
          description
           "This object specifies the instance of the clock for this clock
            type in the given domain.";
          smiv2:max-access "not-accessible";
          smiv2:oid "1.3.6.1.4.1.9.9.760.1.2.10.1.2";
        }

        leaf cPtpClockPortTransDSPortNumberIndex {
          type CISCO-PTP-MIB:ClockPortNumber {
            range "1..65535";
          }
          description
           "This object specifies the PTP port number associated with this
            port.";
          reference
           "Section 7.5.2 Port Identity of [1]";
          smiv2:max-access "not-accessible";
          smiv2:oid "1.3.6.1.4.1.9.9.760.1.2.10.1.3";
        }

        leaf cPtpClockPortTransDSPortIdentity {
          type CISCO-PTP-MIB:ClockIdentity;
          description
           "This object specifies the value of the PortIdentity
            attribute of the local port.";
          reference
           "Section 8.3.3.2.1 of [1]";
          smiv2:max-access "read-only";
          smiv2:oid "1.3.6.1.4.1.9.9.760.1.2.10.1.4";
        }

        leaf cPtpClockPortTransDSlogMinPdelayReqInt {
          type int32;
          description
           "This object specifies the value of the logarithm to the
            base 2 of the minPdelayReqInterval.";
          reference
           "Section 8.3.3.3.1 of [1]";
          smiv2:max-access "read-only";
          smiv2:oid "1.3.6.1.4.1.9.9.760.1.2.10.1.5";
        }

        leaf cPtpClockPortTransDSFaultyFlag {
          type boolean;
          description
           "This object specifies the value TRUE if the port is faulty
            and FALSE if the port is operating normally.";
          reference
           "Section 8.3.3.3.2 of [1]";
          smiv2:max-access "read-only";
          smiv2:oid "1.3.6.1.4.1.9.9.760.1.2.10.1.6";
        }

        leaf cPtpClockPortTransDSPeerMeanPathDelay {
          type CISCO-PTP-MIB:ClockTimeInterval;
          description
           "This object specifies, (if the delayMechanism used is P2P) the
            value is the estimate of the current one-way propagation delay,
            i.e., <meanPathDelay> on the link attached to this port
            computed
            using the peer delay mechanism. If the value of the
            delayMechanism
            used is E2E, then the value will be zero.";
          reference
           "Section 8.3.3.3.3 of [1]";
          smiv2:max-access "read-only";
          smiv2:oid "1.3.6.1.4.1.9.9.760.1.2.10.1.7";
        }
      }
    }

    container cPtpClockPortAssociateTable {
      description
       "Table of information about a given port's associated ports.
        
        For a master port - multiple slave ports which have established
        sessions with the current master port.  
        For a slave port - the list of masters available for a given
        slave port. 
        
        Session information (pkts, errors) to be displayed based on
        availability and scenario.";
      smiv2:oid "1.3.6.1.4.1.9.9.760.1.2.11";

      list cPtpClockPortAssociateEntry {
        key "cPtpClockPortCurrentDomainIndex cPtpClockPortCurrentClockTypeIndex cPtpClockPortCurrentClockInstanceIndex cPtpClockPortCurrentPortNumberIndex cPtpClockPortAssociatePortIndex";
        description
         "An entry in the table, containing information about a single
          associated port for the given clockport.";
        smiv2:oid "1.3.6.1.4.1.9.9.760.1.2.11.1";

        leaf cPtpClockPortCurrentDomainIndex {
          type CISCO-PTP-MIB:ClockDomainType;
          description
           "This object specifies the given port's domain number.";
          smiv2:max-access "not-accessible";
          smiv2:oid "1.3.6.1.4.1.9.9.760.1.2.11.1.1";
        }

        leaf cPtpClockPortCurrentClockTypeIndex {
          type CISCO-PTP-MIB:ClockType;
          description
           "This object specifies the given port's clock type.";
          smiv2:max-access "not-accessible";
          smiv2:oid "1.3.6.1.4.1.9.9.760.1.2.11.1.2";
        }

        leaf cPtpClockPortCurrentClockInstanceIndex {
          type CISCO-PTP-MIB:ClockInstanceType;
          description
           "This object specifies the instance of the clock for this clock
            type in the given domain.";
          smiv2:max-access "not-accessible";
          smiv2:oid "1.3.6.1.4.1.9.9.760.1.2.11.1.3";
        }

        leaf cPtpClockPortCurrentPortNumberIndex {
          type CISCO-PTP-MIB:ClockPortNumber;
          description
           "This object specifies the PTP Port Number for the given port.";
          smiv2:max-access "not-accessible";
          smiv2:oid "1.3.6.1.4.1.9.9.760.1.2.11.1.4";
        }

        leaf cPtpClockPortAssociatePortIndex {
          type uint32 {
            range "1..65535";
          }
          description
           "This object specifies the associated port's serial number in
            the current port's context.";
          smiv2:max-access "not-accessible";
          smiv2:oid "1.3.6.1.4.1.9.9.760.1.2.11.1.5";
        }

        leaf cPtpClockPortAssociateAddressType {
          type inet-address:InetAddressType;
          description
           "This object specifies the peer port's network address type used
            for PTP communication.";
          smiv2:max-access "read-only";
          smiv2:oid "1.3.6.1.4.1.9.9.760.1.2.11.1.6";
        }

        leaf cPtpClockPortAssociateAddress {
          type inet-address:InetAddress;
          description
           "This object specifies the peer port's network address used for
            PTP communication.";
          smiv2:max-access "read-only";
          smiv2:oid "1.3.6.1.4.1.9.9.760.1.2.11.1.7";
        }

        leaf cPtpClockPortAssociatePacketsSent {
          type yang:counter64;
          units "packets";
          description
           "The number of packets sent to this peer port from the current
            port.";
          smiv2:max-access "read-only";
          smiv2:oid "1.3.6.1.4.1.9.9.760.1.2.11.1.8";
        }

        leaf cPtpClockPortAssociatePacketsReceived {
          type yang:counter64;
          units "packets";
          description
           "The number of packets received from this peer port by the
            current port.";
          smiv2:max-access "read-only";
          smiv2:oid "1.3.6.1.4.1.9.9.760.1.2.11.1.9";
        }

        leaf cPtpClockPortAssociateInErrors {
          type yang:counter64;
          units "packets";
          description
           "This object specifies the input errors associated with the
            peer port.";
          smiv2:max-access "read-only";
          smiv2:oid "1.3.6.1.4.1.9.9.760.1.2.11.1.10";
        }

        leaf cPtpClockPortAssociateOutErrors {
          type yang:counter64;
          units "packets";
          description
           "This object specifies the output errors associated with the
            peer port.";
          smiv2:max-access "read-only";
          smiv2:oid "1.3.6.1.4.1.9.9.760.1.2.11.1.11";
        }
      }
    }
  }

  smiv2:alias "ciscoPtpMIB" {
    smiv2:oid "1.3.6.1.4.1.9.9.760";
  }

  smiv2:alias "ciscoPtpMIBNotifs" {
    smiv2:oid "1.3.6.1.4.1.9.9.760.0";
  }

  smiv2:alias "ciscoPtpMIBObjects" {
    smiv2:oid "1.3.6.1.4.1.9.9.760.1";
  }

  smiv2:alias "ciscoPtpMIBSystemInfo" {
    smiv2:oid "1.3.6.1.4.1.9.9.760.1.1";
  }

  smiv2:alias "ciscoPtpMIBClockInfo" {
    smiv2:oid "1.3.6.1.4.1.9.9.760.1.2";
  }

  smiv2:alias "ciscoPtpMIBConformance" {
    smiv2:oid "1.3.6.1.4.1.9.9.760.2";
  }

  smiv2:alias "ciscoPtpMIBCompliances" {
    smiv2:oid "1.3.6.1.4.1.9.9.760.2.1";
  }

  smiv2:alias "ciscoPtpMIBGroups" {
    smiv2:oid "1.3.6.1.4.1.9.9.760.2.2";
  }

}
