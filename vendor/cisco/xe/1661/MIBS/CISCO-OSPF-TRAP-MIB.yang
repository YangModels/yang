/*
 * Generated by confdc --mib2yang-std
 * Source: mgmt/dmi/model/common/mib-source/CISCO-OSPF-TRAP-MIB.mib
 */
/*
 * This YANG module has been generated by smidump 0.5.0:
 *
 *      smidump -f yang CISCO-OSPF-TRAP-MIB
 *
 * Do not edit. Edit the source file instead!
 */

module CISCO-OSPF-TRAP-MIB {

  namespace "urn:ietf:params:xml:ns:yang:smiv2:CISCO-OSPF-TRAP-MIB";
  prefix CISCO-OSPF-TRAP-MIB;

  import CISCO-OSPF-MIB {
    prefix "cisco-ospf";
  }

  import INET-ADDRESS-MIB {
    prefix "inet-address";
  }

  import OSPF-MIB {
    prefix "ospf-mib";
  }

  import ietf-inet-types {
    prefix "inet";
  }

  import ietf-yang-smiv2 {
    prefix "smiv2";
  }

  organization
   "Cisco Systems, Inc.";

  contact
   "       Cisco Systems
    Customer Service
    
    Postal: 170 W. Tasman Drive
    San Jose, CA  95134
    USA
    
    Tel: +1 800 553-NETS
    
    E-mail: cs-ospf@cisco.com";

  description
   "This MIB module describes new/modified notification
    objects/events, which are defined in the latest
    version for OSPF MIB IETF draft
    draftietf-ospf-mib-update-05.txt. Support for OSPF 
    Sham link is also added";

  revision 2003-07-18 {
    description
     "+Deprecated cospfShamLinkStateChange.
      +Added cospfShamLinksStateChange.
      +Added cospfShamLinkNbrStateChange.
      +Added cospfShamLinkConfigError.
      +Added cospfShamLinkAuthFailure.
      +Added cospfShamLinkRxBadPacket.
      +Added cospfShamLinkTxRetransmit.
      +Fixed indentation and spelling.";
  }

  revision 2003-02-27 {
    description
     "Initial version of the MIB module.";
  }


  container CISCO-OSPF-TRAP-MIB {
    config false;

    container cospfTrapControl {
      smiv2:oid "1.3.6.1.4.1.9.10.101.1.1";

      leaf cospfSetTrap {
        type bits {
          bit ifConfigError {
            position "0";
          }
          bit virtIfConfigError {
            position "1";
          }
          bit retransmit {
            position "2";
          }
          bit virtRetransmit {
            position "3";
          }
          bit originateLsa {
            position "4";
          }
          bit originateMaxAgeLsa {
            position "5";
          }
          bit nssaTranslatorStatusChange {
            position "6";
          }
          bit shamLinkStateChange {
            position "7";
          }
          bit shamLinkNbrStateChange {
            position "8";
          }
          bit shamLinkConfigError {
            position "9";
          }
          bit shamLinkAuthFailure {
            position "10";
          }
          bit shamLinkRxBadPacket {
            position "11";
          }
          bit shamLinkTxRetransmit {
            position "12";
          }
          bit shamLinksStateChange {
            position "13";
          }
        }
        description
         "An octet string serving as a bit  map  for
          the trap events defined by the OSPF traps in 
          this MIB. This object is used to enable and  
          disable  specific OSPF   traps   where  a  1  
          in  the  corresponding bit  field represents 
          enabled.";
        smiv2:max-access "read-write";
        smiv2:oid "1.3.6.1.4.1.9.10.101.1.1.1";
      }

      leaf cospfConfigErrorType {
        type enumeration {
          enum "badVersion" {
            value "1";
          }
          enum "areaMismatch" {
            value "2";
          }
          enum "unknownNbmaNbr" {
            value "3";
          }
          enum "unknownVirtualNbr" {
            value "4";
          }
          enum "authTypeMismatch" {
            value "5";
          }
          enum "authFailure" {
            value "6";
          }
          enum "netMaskMismatch" {
            value "7";
          }
          enum "helloIntervalMismatch" {
            value "8";
          }
          enum "deadIntervalMismatch" {
            value "9";
          }
          enum "optionMismatch" {
            value "10";
          }
          enum "mtuMismatch" {
            value "11";
          }
          enum "noError" {
            value "12";
          }
          enum "unknownShamLinkNbr" {
            value "13";
          }
        }
        description
         "Potential types of configuration conflicts.
          Used  by the cospfConfigError and cospfConfigVirtError
          traps. When the last value of a trap
          using this object is needed, but no traps of
          that type have been sent, this value pertaining
          to this object should be returned as noError.";
        smiv2:max-access "read-only";
        smiv2:oid "1.3.6.1.4.1.9.10.101.1.1.2";
      }

      leaf cospfPacketType {
        type enumeration {
          enum "hello" {
            value "1";
          }
          enum "dbDescript" {
            value "2";
          }
          enum "lsReq" {
            value "3";
          }
          enum "lsUpdate" {
            value "4";
          }
          enum "lsAck" {
            value "5";
          }
          enum "nullPacket" {
            value "6";
          }
        }
        description
         "OSPF packet types. When the last value of a trap
          using this object is needed, but no traps of
          that type have been sent, this value pertaining
          to this object should be returned as nullPacket.";
        smiv2:max-access "read-only";
        smiv2:oid "1.3.6.1.4.1.9.10.101.1.1.3";
      }

      leaf cospfPacketSrc {
        type inet:ipv4-address;
        description
         "The IP address of an inbound packet that can-
          not be identified by a neighbor instance. When
          the last value of a trap using this object is
          needed, but no traps of that type have been sent,
          this value pertaining to this object should
          be returned as 0.0.0.0.";
        smiv2:max-access "read-only";
        smiv2:oid "1.3.6.1.4.1.9.10.101.1.1.4";
      }
    }
  }

  notification cospfIfConfigError {
    description
     "A cospfIfConfigError  trap  signifies  that  a
      packet  with mismatched parameter MTU has been 
      received on a non-virtual interface  from  a  
      router.";
    smiv2:oid "1.3.6.1.4.1.9.10.101.0.1";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf cospfPacketSrc {
        type leafref {
          path "/CISCO-OSPF-TRAP-MIB:CISCO-OSPF-TRAP-MIB/CISCO-OSPF-TRAP-MIB:cospfTrapControl/CISCO-OSPF-TRAP-MIB:cospfPacketSrc";
        }
      }
    }

    container object-5 {

      leaf cospfConfigErrorType {
        type leafref {
          path "/CISCO-OSPF-TRAP-MIB:CISCO-OSPF-TRAP-MIB/CISCO-OSPF-TRAP-MIB:cospfTrapControl/CISCO-OSPF-TRAP-MIB:cospfConfigErrorType";
        }
      }
    }

    container object-6 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }
  }

  notification cospfVirtIfConfigError {
    description
     "A cospfVirtIfConfigError  trap  signifies  that  a
      packet  with mismatched parameter MTU has been received
      on a virtual interface  from  a router.";
    smiv2:oid "1.3.6.1.4.1.9.10.101.0.2";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf cospfConfigErrorType {
        type leafref {
          path "/CISCO-OSPF-TRAP-MIB:CISCO-OSPF-TRAP-MIB/CISCO-OSPF-TRAP-MIB:cospfTrapControl/CISCO-OSPF-TRAP-MIB:cospfConfigErrorType";
        }
      }
    }

    container object-5 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }
  }

  notification cospfTxRetransmit {
    description
     "A cospfTxRetransmit  trap  signifies  than  an
      OSPF  packet, which has been associated with 
      an Opaque LSA LSDB Entry, has  been retransmitted 
      on a non-virtual interface.";
    smiv2:oid "1.3.6.1.4.1.9.10.101.0.3";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRtrId {
        type leafref {
          path "/ospf-mib:OSPF-MIB/ospf-mib:ospfNbrTable/ospf-mib:ospfNbrEntry/ospf-mib:ospfNbrRtrId";
        }
      }
    }

    container object-5 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }

    container object-6 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-7 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-8 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification cospfVirtIfTxRetransmit {
    description
     "A cospfVirtTxRetransmit  trap  signifies  than  an
      OSPF  packet, which has been associated with 
      an Opaque LSA LSDB Entry, has  been retransmitted 
      on a non-virtual interface.";
    smiv2:oid "1.3.6.1.4.1.9.10.101.0.4";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-6 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-7 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification cospfOriginateLsa {
    description
     "A cospfOriginateLsa trap signifies that a  new
      Opaque LSA  has  been originated by this router.
      This trap should not be invoked for simple refreshes
      of  LSAs  (which happesn every 30 minutes), but
      instead will only be invoked  when  an  LSA  is
      (re)originated due to a topology change.  Additionally, 
      this trap does not include LSAs  that
      are  being  flushed  because  they have reached
      MaxAge.";
    smiv2:oid "1.3.6.1.4.1.9.10.101.0.5";

    container object-1 {

      leaf ospfRouterId {
        type leafref {
          path "/ospf-mib:OSPF-MIB/ospf-mib:ospfGeneralGroup/ospf-mib:ospfRouterId";
        }
      }
    }

    container object-2 {

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbAreaId {
        type leafref {
          path "/ospf-mib:OSPF-MIB/ospf-mib:ospfLsdbTable/ospf-mib:ospfLsdbEntry/ospf-mib:ospfLsdbAreaId";
        }
      }
    }

    container object-3 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-4 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification cospfMaxAgeLsa {
    description
     "A cospfMaxAgeLsa trap signifies  that  one  of
      the Opaque LSAs in the router's link-state database 
      has aged to MaxAge.";
    smiv2:oid "1.3.6.1.4.1.9.10.101.0.6";

    container object-1 {

      leaf ospfRouterId {
        type leafref {
          path "/ospf-mib:OSPF-MIB/ospf-mib:ospfGeneralGroup/ospf-mib:ospfRouterId";
        }
      }
    }

    container object-2 {

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbAreaId {
        type leafref {
          path "/ospf-mib:OSPF-MIB/ospf-mib:ospfLsdbTable/ospf-mib:ospfLsdbEntry/ospf-mib:ospfLsdbAreaId";
        }
      }
    }

    container object-3 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-4 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-6 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification cospfNssaTranslatorStatusChange {
    description
     "A cospfNssaTranslatorStatusChange trap indicates that there
      has been a change in the router's ability to translate OSPF
      type-7 LSAs into OSPF type-5 LSAs. This trap should be
      generated when the Translator Status transitions from or to
      any defined status on a per area basis.";
    smiv2:oid "1.3.6.1.4.1.9.10.101.0.7";

    container object-1 {

      leaf ospfRouterId {
        type leafref {
          path "/ospf-mib:OSPF-MIB/ospf-mib:ospfGeneralGroup/ospf-mib:ospfRouterId";
        }
      }
    }

    container object-2 {

      leaf ospfAreaId {
        type leafref {
          path "/ospf-mib:OSPF-MIB/ospf-mib:ospfAreaTable/ospf-mib:ospfAreaEntry/ospf-mib:ospfAreaId";
        }
      }
    }

    container object-3 {

      leaf ospfAreaId {
        type leafref {
          path "/ospf-mib:OSPF-MIB/ospf-mib:ospfAreaTable/ospf-mib:ospfAreaEntry/ospf-mib:ospfAreaId";
        }
      }

      leaf cospfAreaNssaTranslatorState {
        type leafref {
          path "/ospf-mib:OSPF-MIB/ospf-mib:ospfAreaTable/ospf-mib:ospfAreaEntry/cisco-ospf:cospfAreaNssaTranslatorState";
        }
      }
    }
  }

  notification cospfShamLinkStateChange {
    status deprecated;
    description
     "A ospfShamLinkStateChange trap signifies that 
      there has been a change in the state of a Sham
      Link OSPF interface. This trap should  be  generated
      when  the interface state regresses from  Point-to-Point
      to Down or progresses to Down to Point-to-Point. This
      trap has been deprecated by cospfShamLinksStateChange.";
    smiv2:oid "1.3.6.1.4.1.9.10.101.0.8";

    container object-1 {

      leaf ospfRouterId {
        type leafref {
          path "/ospf-mib:OSPF-MIB/ospf-mib:ospfGeneralGroup/ospf-mib:ospfRouterId";
        }
      }
    }

    container object-2 {

      leaf cospfShamLinkLocalIpAddress {
        type leafref {
          path "/cisco-ospf:CISCO-OSPF-MIB/cisco-ospf:cospfShamLinkTable/cisco-ospf:cospfShamLinkEntry/cisco-ospf:cospfShamLinkLocalIpAddress";
        }
        status deprecated;
      }

      leaf cospfShamLinkNeighborId {
        type leafref {
          path "/cisco-ospf:CISCO-OSPF-MIB/cisco-ospf:cospfShamLinkTable/cisco-ospf:cospfShamLinkEntry/cisco-ospf:cospfShamLinkNeighborId";
        }
        status deprecated;
      }

      leaf cospfShamLinkAreaId {
        type ospf-mib:AreaID;
        status deprecated;
        description
         "The  Transit  Area  that  the   Virtual   Link
          traverses.  By definition, this is not 0.0.0.0";
        smiv2:max-access "not-accessible";
        smiv2:oid "1.3.6.1.4.1.9.10.99.6.1.1";
      }
    }

    container object-3 {

      leaf cospfShamLinkAreaId {
        type leafref {
          path "/cisco-ospf:CISCO-OSPF-MIB/cisco-ospf:cospfShamLinkTable/cisco-ospf:cospfShamLinkEntry/cisco-ospf:cospfShamLinkAreaId";
        }
        status deprecated;
      }

      leaf cospfShamLinkNeighborId {
        type leafref {
          path "/cisco-ospf:CISCO-OSPF-MIB/cisco-ospf:cospfShamLinkTable/cisco-ospf:cospfShamLinkEntry/cisco-ospf:cospfShamLinkNeighborId";
        }
        status deprecated;
      }

      leaf cospfShamLinkLocalIpAddress {
        type inet:ipv4-address;
        status deprecated;
        description
         "The Local IP address of the sham link.";
        smiv2:max-access "not-accessible";
        smiv2:oid "1.3.6.1.4.1.9.10.99.6.1.2";
      }
    }

    container object-4 {

      leaf cospfShamLinkAreaId {
        type leafref {
          path "/cisco-ospf:CISCO-OSPF-MIB/cisco-ospf:cospfShamLinkTable/cisco-ospf:cospfShamLinkEntry/cisco-ospf:cospfShamLinkAreaId";
        }
        status deprecated;
      }

      leaf cospfShamLinkLocalIpAddress {
        type leafref {
          path "/cisco-ospf:CISCO-OSPF-MIB/cisco-ospf:cospfShamLinkTable/cisco-ospf:cospfShamLinkEntry/cisco-ospf:cospfShamLinkLocalIpAddress";
        }
        status deprecated;
      }

      leaf cospfShamLinkNeighborId {
        type ospf-mib:RouterID;
        status deprecated;
        description
         "The Router ID of the other end router of the sham
          link.";
        smiv2:max-access "not-accessible";
        smiv2:oid "1.3.6.1.4.1.9.10.99.6.1.3";
      }
    }

    container object-5 {

      leaf cospfShamLinkAreaId {
        type leafref {
          path "/cisco-ospf:CISCO-OSPF-MIB/cisco-ospf:cospfShamLinkTable/cisco-ospf:cospfShamLinkEntry/cisco-ospf:cospfShamLinkAreaId";
        }
        status deprecated;
      }

      leaf cospfShamLinkLocalIpAddress {
        type leafref {
          path "/cisco-ospf:CISCO-OSPF-MIB/cisco-ospf:cospfShamLinkTable/cisco-ospf:cospfShamLinkEntry/cisco-ospf:cospfShamLinkLocalIpAddress";
        }
        status deprecated;
      }

      leaf cospfShamLinkNeighborId {
        type leafref {
          path "/cisco-ospf:CISCO-OSPF-MIB/cisco-ospf:cospfShamLinkTable/cisco-ospf:cospfShamLinkEntry/cisco-ospf:cospfShamLinkNeighborId";
        }
        status deprecated;
      }

      leaf cospfShamLinkState {
        type leafref {
          path "/cisco-ospf:CISCO-OSPF-MIB/cisco-ospf:cospfShamLinkTable/cisco-ospf:cospfShamLinkEntry/cisco-ospf:cospfShamLinkState";
        }
        status deprecated;
      }
    }
  }

  notification cospfShamLinkNbrStateChange {
    description
     "A cospfShamLinkNbrStateChange trap signifies that
      there has been a change in the state of a sham link
      OSPF neighbor. This trap should be generated when 
      the neighbor state regresses (e.g., goes from 
      Attempt or Full to 1-Way or Down) or progresses to
      a terminal state (e.g., Full).";
    smiv2:oid "1.3.6.1.4.1.9.10.101.0.9";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinkNbrIpAddrType {
        type leafref {
          path "/cisco-ospf:CISCO-OSPF-MIB/cisco-ospf:cospfShamLinkNbrTable/cisco-ospf:cospfShamLinkNbrEntry/cisco-ospf:cospfShamLinkNbrIpAddrType";
        }
      }

      leaf cospfShamLinkNbrIpAddr {
        type leafref {
          path "/cisco-ospf:CISCO-OSPF-MIB/cisco-ospf:cospfShamLinkNbrTable/cisco-ospf:cospfShamLinkNbrEntry/cisco-ospf:cospfShamLinkNbrIpAddr";
        }
      }

      leaf cospfShamLinkNbrArea {
        type ospf-mib:AreaID;
        description
         "The area to which the sham link is part of.";
        smiv2:max-access "not-accessible";
        smiv2:oid "1.3.6.1.4.1.9.10.99.10.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinkNbrArea {
        type leafref {
          path "/cisco-ospf:CISCO-OSPF-MIB/cisco-ospf:cospfShamLinkNbrTable/cisco-ospf:cospfShamLinkNbrEntry/cisco-ospf:cospfShamLinkNbrArea";
        }
      }

      leaf cospfShamLinkNbrIpAddr {
        type leafref {
          path "/cisco-ospf:CISCO-OSPF-MIB/cisco-ospf:cospfShamLinkNbrTable/cisco-ospf:cospfShamLinkNbrEntry/cisco-ospf:cospfShamLinkNbrIpAddr";
        }
      }

      leaf cospfShamLinkNbrIpAddrType {
        type inet-address:InetAddressType;
        description
         "The type of internet address of this sham link neighbor's
          IP address.";
        smiv2:max-access "not-accessible";
        smiv2:oid "1.3.6.1.4.1.9.10.99.10.1.2";
      }
    }

    container object-6 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinkNbrArea {
        type leafref {
          path "/cisco-ospf:CISCO-OSPF-MIB/cisco-ospf:cospfShamLinkNbrTable/cisco-ospf:cospfShamLinkNbrEntry/cisco-ospf:cospfShamLinkNbrArea";
        }
      }

      leaf cospfShamLinkNbrIpAddrType {
        type leafref {
          path "/cisco-ospf:CISCO-OSPF-MIB/cisco-ospf:cospfShamLinkNbrTable/cisco-ospf:cospfShamLinkNbrEntry/cisco-ospf:cospfShamLinkNbrIpAddrType";
        }
      }

      leaf cospfShamLinkNbrIpAddr {
        type inet-address:InetAddress;
        description
         "The IP address this sham link neighbor is using.";
        smiv2:max-access "not-accessible";
        smiv2:oid "1.3.6.1.4.1.9.10.99.10.1.3";
      }
    }

    container object-7 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinkNbrArea {
        type leafref {
          path "/cisco-ospf:CISCO-OSPF-MIB/cisco-ospf:cospfShamLinkNbrTable/cisco-ospf:cospfShamLinkNbrEntry/cisco-ospf:cospfShamLinkNbrArea";
        }
      }

      leaf cospfShamLinkNbrIpAddrType {
        type leafref {
          path "/cisco-ospf:CISCO-OSPF-MIB/cisco-ospf:cospfShamLinkNbrTable/cisco-ospf:cospfShamLinkNbrEntry/cisco-ospf:cospfShamLinkNbrIpAddrType";
        }
      }

      leaf cospfShamLinkNbrIpAddr {
        type leafref {
          path "/cisco-ospf:CISCO-OSPF-MIB/cisco-ospf:cospfShamLinkNbrTable/cisco-ospf:cospfShamLinkNbrEntry/cisco-ospf:cospfShamLinkNbrIpAddr";
        }
      }

      leaf cospfShamLinkNbrRtrId {
        type leafref {
          path "/cisco-ospf:CISCO-OSPF-MIB/cisco-ospf:cospfShamLinkNbrTable/cisco-ospf:cospfShamLinkNbrEntry/cisco-ospf:cospfShamLinkNbrRtrId";
        }
      }
    }

    container object-8 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinkNbrArea {
        type leafref {
          path "/cisco-ospf:CISCO-OSPF-MIB/cisco-ospf:cospfShamLinkNbrTable/cisco-ospf:cospfShamLinkNbrEntry/cisco-ospf:cospfShamLinkNbrArea";
        }
      }

      leaf cospfShamLinkNbrIpAddrType {
        type leafref {
          path "/cisco-ospf:CISCO-OSPF-MIB/cisco-ospf:cospfShamLinkNbrTable/cisco-ospf:cospfShamLinkNbrEntry/cisco-ospf:cospfShamLinkNbrIpAddrType";
        }
      }

      leaf cospfShamLinkNbrIpAddr {
        type leafref {
          path "/cisco-ospf:CISCO-OSPF-MIB/cisco-ospf:cospfShamLinkNbrTable/cisco-ospf:cospfShamLinkNbrEntry/cisco-ospf:cospfShamLinkNbrIpAddr";
        }
      }

      leaf cospfShamLinkNbrState {
        type leafref {
          path "/cisco-ospf:CISCO-OSPF-MIB/cisco-ospf:cospfShamLinkNbrTable/cisco-ospf:cospfShamLinkNbrEntry/cisco-ospf:cospfShamLinkNbrState";
        }
      }
    }
  }

  notification cospfShamLinkConfigError {
    description
     "A cospfShamLinkConfigError signifies that a packet 
      has been received on a sham link from a router whose
      configuration parameters conflict with this router's
      configuration parameters.";
    smiv2:oid "1.3.6.1.4.1.9.10.101.0.10";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksAreaId {
        type ospf-mib:AreaID;
        description
         "The area that this sham link is part of.";
        smiv2:max-access "not-accessible";
        smiv2:oid "1.3.6.1.4.1.9.10.99.11.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksRemoteIpAddrType {
        type inet-address:InetAddressType;
        description
         "The type of internet address of this sham link's remote IP
          address.";
        smiv2:max-access "not-accessible";
        smiv2:oid "1.3.6.1.4.1.9.10.99.11.1.4";
      }
    }

    container object-6 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type inet-address:InetAddress;
        description
         "The IP address of the other end router of the sham link.";
        smiv2:max-access "not-accessible";
        smiv2:oid "1.3.6.1.4.1.9.10.99.11.1.5";
      }
    }

    container object-7 {

      leaf cospfConfigErrorType {
        type leafref {
          path "/CISCO-OSPF-TRAP-MIB:CISCO-OSPF-TRAP-MIB/CISCO-OSPF-TRAP-MIB:cospfTrapControl/CISCO-OSPF-TRAP-MIB:cospfConfigErrorType";
        }
      }
    }

    container object-8 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }
  }

  notification cospfShamLinkAuthFailure {
    description
     "A cospfShamLinkAuthFailure trap signifies that a 
      packet has been received on a sham link from a router
      whose authentication key or authentication type conflicts
      with this router's authentication key and authentication 
      type.";
    smiv2:oid "1.3.6.1.4.1.9.10.101.0.11";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksAreaId {
        type ospf-mib:AreaID;
        description
         "The area that this sham link is part of.";
        smiv2:max-access "not-accessible";
        smiv2:oid "1.3.6.1.4.1.9.10.99.11.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksRemoteIpAddrType {
        type inet-address:InetAddressType;
        description
         "The type of internet address of this sham link's remote IP
          address.";
        smiv2:max-access "not-accessible";
        smiv2:oid "1.3.6.1.4.1.9.10.99.11.1.4";
      }
    }

    container object-6 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type inet-address:InetAddress;
        description
         "The IP address of the other end router of the sham link.";
        smiv2:max-access "not-accessible";
        smiv2:oid "1.3.6.1.4.1.9.10.99.11.1.5";
      }
    }

    container object-7 {

      leaf cospfConfigErrorType {
        type leafref {
          path "/CISCO-OSPF-TRAP-MIB:CISCO-OSPF-TRAP-MIB/CISCO-OSPF-TRAP-MIB:cospfTrapControl/CISCO-OSPF-TRAP-MIB:cospfConfigErrorType";
        }
      }
    }

    container object-8 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }
  }

  notification cospfShamLinkRxBadPacket {
    description
     "A cospfShamLinkRxBadPacket trap signifies that an OSPF
      packet has been received on a sham link that cannot be 
      parsed.";
    smiv2:oid "1.3.6.1.4.1.9.10.101.0.12";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksAreaId {
        type ospf-mib:AreaID;
        description
         "The area that this sham link is part of.";
        smiv2:max-access "not-accessible";
        smiv2:oid "1.3.6.1.4.1.9.10.99.11.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksRemoteIpAddrType {
        type inet-address:InetAddressType;
        description
         "The type of internet address of this sham link's remote IP
          address.";
        smiv2:max-access "not-accessible";
        smiv2:oid "1.3.6.1.4.1.9.10.99.11.1.4";
      }
    }

    container object-6 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type inet-address:InetAddress;
        description
         "The IP address of the other end router of the sham link.";
        smiv2:max-access "not-accessible";
        smiv2:oid "1.3.6.1.4.1.9.10.99.11.1.5";
      }
    }

    container object-7 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }
  }

  notification cospfShamLinkTxRetransmit {
    description
     "A cospfShamLinkTxRetransmit trap signifies that an 
      OSPF packet has been retransmitted on a sham link. All 
      packets that may be retransmitted are associated with an 
      LSDB entry. The LS type, LS ID, and Router ID are used 
      identify the LSDB entry.";
    smiv2:oid "1.3.6.1.4.1.9.10.101.0.13";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksAreaId {
        type ospf-mib:AreaID;
        description
         "The area that this sham link is part of.";
        smiv2:max-access "not-accessible";
        smiv2:oid "1.3.6.1.4.1.9.10.99.11.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksRemoteIpAddrType {
        type inet-address:InetAddressType;
        description
         "The type of internet address of this sham link's remote IP
          address.";
        smiv2:max-access "not-accessible";
        smiv2:oid "1.3.6.1.4.1.9.10.99.11.1.4";
      }
    }

    container object-6 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type inet-address:InetAddress;
        description
         "The IP address of the other end router of the sham link.";
        smiv2:max-access "not-accessible";
        smiv2:oid "1.3.6.1.4.1.9.10.99.11.1.5";
      }
    }

    container object-7 {

      leaf cospfPacketType {
        type leafref {
          path "/CISCO-OSPF-TRAP-MIB:CISCO-OSPF-TRAP-MIB/CISCO-OSPF-TRAP-MIB:cospfTrapControl/CISCO-OSPF-TRAP-MIB:cospfPacketType";
        }
      }
    }

    container object-8 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf cospfLsdbType {
        type enumeration {
          enum "areaOpaqueLink" {
            value "10";
          }
          enum "asOpaqueLink" {
            value "11";
          }
        }
        description
         "The type of the link state advertisement.
          Each link state type has a separate advertisement format.";
        reference
         "OSPF Version 2, Appendix A.4.1 The  Link  State
          Advertisement header
          The OSPF Opaque LSA Option (RFC 2370)";
        smiv2:max-access "not-accessible";
        smiv2:oid "1.3.6.1.4.1.9.10.99.3.1.1";
      }
    }

    container object-9 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-10 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification cospfShamLinksStateChange {
    description
     "A ospfShamLinkStateChange trap signifies that 
      there has been a change in the state of a Sham
      Link OSPF interface. This trap should  be  generated
      when  the interface state regresses from  Point-to-Point
      to Down or progresses  to  Down to Point-to-Point.";
    smiv2:oid "1.3.6.1.4.1.9.10.101.0.14";

    container object-1 {

      leaf ospfRouterId {
        type leafref {
          path "/ospf-mib:OSPF-MIB/ospf-mib:ospfGeneralGroup/ospf-mib:ospfRouterId";
        }
      }
    }

    container object-2 {

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksAreaId {
        type ospf-mib:AreaID;
        description
         "The area that this sham link is part of.";
        smiv2:max-access "not-accessible";
        smiv2:oid "1.3.6.1.4.1.9.10.99.11.1.1";
      }
    }

    container object-3 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddrType {
        type inet-address:InetAddressType;
        description
         "The type of internet address of this sham link's local IP
          address.";
        smiv2:max-access "not-accessible";
        smiv2:oid "1.3.6.1.4.1.9.10.99.11.1.2";
      }
    }

    container object-4 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksLocalIpAddr {
        type inet-address:InetAddress;
        description
         "The Local IP address of the sham link.";
        smiv2:max-access "not-accessible";
        smiv2:oid "1.3.6.1.4.1.9.10.99.11.1.3";
      }
    }

    container object-5 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksRemoteIpAddrType {
        type inet-address:InetAddressType;
        description
         "The type of internet address of this sham link's remote IP
          address.";
        smiv2:max-access "not-accessible";
        smiv2:oid "1.3.6.1.4.1.9.10.99.11.1.4";
      }
    }

    container object-6 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type inet-address:InetAddress;
        description
         "The IP address of the other end router of the sham link.";
        smiv2:max-access "not-accessible";
        smiv2:oid "1.3.6.1.4.1.9.10.99.11.1.5";
      }
    }

    container object-7 {

      leaf cospfShamLinksAreaId {
        type leafref {
          path "/cisco-ospf:CISCO-OSPF-MIB/cisco-ospf:cospfShamLinksTable/cisco-ospf:cospfShamLinksEntry/cisco-ospf:cospfShamLinksAreaId";
        }
      }

      leaf cospfShamLinksLocalIpAddrType {
        type leafref {
          path "/cisco-ospf:CISCO-OSPF-MIB/cisco-ospf:cospfShamLinksTable/cisco-ospf:cospfShamLinksEntry/cisco-ospf:cospfShamLinksLocalIpAddrType";
        }
      }

      leaf cospfShamLinksLocalIpAddr {
        type leafref {
          path "/cisco-ospf:CISCO-OSPF-MIB/cisco-ospf:cospfShamLinksTable/cisco-ospf:cospfShamLinksEntry/cisco-ospf:cospfShamLinksLocalIpAddr";
        }
      }

      leaf cospfShamLinksRemoteIpAddrType {
        type leafref {
          path "/cisco-ospf:CISCO-OSPF-MIB/cisco-ospf:cospfShamLinksTable/cisco-ospf:cospfShamLinksEntry/cisco-ospf:cospfShamLinksRemoteIpAddrType";
        }
      }

      leaf cospfShamLinksRemoteIpAddr {
        type leafref {
          path "/cisco-ospf:CISCO-OSPF-MIB/cisco-ospf:cospfShamLinksTable/cisco-ospf:cospfShamLinksEntry/cisco-ospf:cospfShamLinksRemoteIpAddr";
        }
      }

      leaf cospfShamLinksState {
        type leafref {
          path "/cisco-ospf:CISCO-OSPF-MIB/cisco-ospf:cospfShamLinksTable/cisco-ospf:cospfShamLinksEntry/cisco-ospf:cospfShamLinksState";
        }
      }
    }
  }

  smiv2:alias "ciscoOspfTrapMIB" {
    smiv2:oid "1.3.6.1.4.1.9.10.101";
  }

  smiv2:alias "ciscoOspfTrapMIBNotifs" {
    smiv2:oid "1.3.6.1.4.1.9.10.101.0";
  }

  smiv2:alias "ciscoOspfTrapMIBObjects" {
    smiv2:oid "1.3.6.1.4.1.9.10.101.1";
  }

  smiv2:alias "cospfTrapControl" {
    smiv2:oid "1.3.6.1.4.1.9.10.101.1.1";
  }

  smiv2:alias "ciscoOspfTrapMIBConform" {
    smiv2:oid "1.3.6.1.4.1.9.10.101.2";
  }

  smiv2:alias "ciscoOspfTrapMIBGroups" {
    smiv2:oid "1.3.6.1.4.1.9.10.101.2.1";
  }

  smiv2:alias "ciscoOspfTrapMIBCompliances" {
    smiv2:oid "1.3.6.1.4.1.9.10.101.2.2";
  }

}
