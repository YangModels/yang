/*
 * Generated by confdc --mib2yang-std
 * Source: mgmt/dmi/model/common/mib-source/CISCO-ETHER-CFM-MIB.mib
 */
/*
 * This YANG module has been generated by smidump 0.5.0:
 *
 *      smidump -f yang CISCO-ETHER-CFM-MIB
 *
 * Do not edit. Edit the source file instead!
 */

module CISCO-ETHER-CFM-MIB {

  namespace "urn:ietf:params:xml:ns:yang:smiv2:CISCO-ETHER-CFM-MIB";
  prefix CISCO-ETHER-CFM-MIB;

  import Q-BRIDGE-MIB {
    prefix "q-bridge";
  }

  import SNMP-FRAMEWORK-MIB {
    prefix "snmp-framework";
  }

  import ietf-yang-smiv2 {
    prefix "smiv2";
  }

  import ietf-yang-types {
    prefix "yang";
  }

  organization
   "Cisco Systems, Inc.";

  contact
   "            Cisco Systems
    Customer Service
    Postal: 170 W Tasman Drive
    San Jose, CA 95134
    USA
    Tel: +1 800 553-NETS
    E-mail:  cs-ethermibs@cisco.com";

  description
   "This MIB module defines the managed objects 
    and notifications for Ethernet Connectivity 
    Fault Management (CFM).
    
    CFM is an end-to-end per service instance Ethernet layer 
    Operations, Administration and Management (OAM) protocol. 
    
    CFM events include: 
    
    - Maintenance End-Point (MEP) coming up: establishing 
      connectivity
    
    - Maintenance End-Point going down: losing connectivity
    
    - Maintenance End-Point unknown: unexpected
    
    - Maintenance End-Point missing: expected but not reachable
    
    - Continuity Check Configuration Error: collision in MEP IDs
    
    - Continuity Check Loop: forwarding loop in network
    
    - Continuity Check Cross-connect: cross-connected 
      forwarding path.
    
    The following acronyms are used in this module:
    
    - MEP: Maintenance End Point
    
    - MEPID: Maintenance End Point Identifier
    
    - CC: Continuity Check
    
    - CCDB: Continuity Check Database
    
    - SVLAN: Service Provider Virtual Local Area Network
    
    - VLAN: Virtual Local Area Network
    
    - CLI: Command Line Interface.
    
    - OAM: Operations Administration and Management.";

  revision 2004-12-28 {
    description
     "The initial revision of this MIB.";
  }

  typedef CfmMepid {
    type uint32 {
      range "0..8191";
    }
    description
     "The identifier of a maintenance end point.";
  }


  container CISCO-ETHER-CFM-MIB {
    config false;

    container cecCfmEvents {
      smiv2:oid "1.3.6.1.4.1.9.9.461.1.1";

      leaf cEtherCfmMaxEventIndex {
        type uint32 {
          range "1..4294967295";
        }
        description
         "This object specifies the maximum upper value supported 
          for the cEtherCfmEventIndex index by this agent.";
        smiv2:max-access "read-only";
        smiv2:oid "1.3.6.1.4.1.9.9.461.1.1.1";
      }
    }

    container cEtherCfmEventTable {
      description
       "This table contains a collection of Ethernet CFM notifications
        generated by the device. The notifications correspond to events
        recognized by the device and fall into the following classes:
        
        - MEP-Up
        
        - MEP-Down
        
        - Configuration Error
        
        - Forwarding Loop
        
        - Cross-connected Ethernet Connection
        
        - Crosscheck Missing MEP
        
        - Crosscheck Unknown MEP
        
        - Crosscheck Service Up
        
        A conceptual row is created in this table whenever the device 
        encounters one of the events listed above. Rows can only be
        created by the agent, and not at the request of the management
        station.
        
        Rows are deleted at the request of a management station by 
        setting the cEtherCfmEventDeleteRow object to 'delete'.
        Another way of deleting rows is through the CLI.
        
        Although this table may be indexed uniquely by the 
        cEtherCfmEventIndex index, the first two indices 
        (cEtherCfmEventDomainIndex and cEtherCfmEventSvlan) are used
        to speed-up queries per maintenance domain and per customer
        service instance. Furthermore, these two indices will help
        in defining the MIB views easily in order to restrict access
        to the MIB to particular entities (be it a service provider,
        or operator, or customer).";
      smiv2:oid "1.3.6.1.4.1.9.9.461.1.1.2";

      list cEtherCfmEventEntry {
        key "cEtherCfmEventDomainIndex cEtherCfmEventSvlan cEtherCfmEventIndex";
        description
         "An entry in this table is created for every event reported
          by Ethernet CFM.";
        smiv2:oid "1.3.6.1.4.1.9.9.461.1.1.2.1";

        leaf cEtherCfmEventDomainIndex {
          type uint32 {
            range "1..4294967295";
          }
          description
           "This object represents the ID which uniquely identifies 
            a CFM maintenance domain on the device. Every domain can
            be uniquely identified by its user-defined 
            name (cEtherCfmEventDomainName) or device-assigned ID (this
            object).";
          smiv2:max-access "not-accessible";
          smiv2:oid "1.3.6.1.4.1.9.9.461.1.1.2.1.1";
        }

        leaf cEtherCfmEventSvlan {
          type q-bridge:VlanId;
          description
           "The service VLAN identifier of the customer service 
            instance to which the event belongs.";
          smiv2:max-access "not-accessible";
          smiv2:oid "1.3.6.1.4.1.9.9.461.1.1.2.1.2";
        }

        leaf cEtherCfmEventIndex {
          type uint32 {
            range "1..4294967295";
          }
          description
           "A monotonically increasing integer for the sole purpose of
            indexing CFM events.  When it reaches the maximum value 
            supported by the agent, as defined in the 
            cEtherCfmMaxEventIndex object, the agent wraps the value
            back to 1 and may flush existing entries.";
          smiv2:max-access "not-accessible";
          smiv2:oid "1.3.6.1.4.1.9.9.461.1.1.2.1.3";
        }

        leaf cEtherCfmEventDomainName {
          type snmp-framework:SnmpAdminString;
          description
           "The name of the CFM maintenance domain.";
          smiv2:max-access "read-only";
          smiv2:oid "1.3.6.1.4.1.9.9.461.1.1.2.1.4";
        }

        leaf cEtherCfmEventType {
          type enumeration {
            enum "mepUp" {
              value "1";
            }
            enum "mepDown" {
              value "2";
            }
            enum "xconnect" {
              value "3";
            }
            enum "loop" {
              value "4";
            }
            enum "config" {
              value "5";
            }
            enum "xcheckMissing" {
              value "6";
            }
            enum "xcheckUnknown" {
              value "7";
            }
            enum "xcheckServiceUp" {
              value "8";
            }
          }
          description
           "This object informs the management station of how to interpret
            the rest of the objects within a row, as summarized in the 
            following table:
            
            Legend I: Ignored Object 
                   V: Valid Object
            
            Object                                 cEtherCfmEventType
                                           | 1 | 2 | 3 | 4 | 5 | 6 | 7 | 8
            ================================================================
                                           |   |   |   |   |   |   |   |
            cEtherCfmEventDomainIndex      | V | V | V | V | V | V | V | V
                                           |   |   |   |   |   |   |   |
            cEtherCfmEventSvlan            | V | V | V | V | V | V | V | V
                                           |   |   |   |   |   |   |   |
            cEtherCfmEventIndex            | V | V | V | V | V | V | V | V
                                           |   |   |   |   |   |   |   |
            cEtherCfmEventLastChange       | V | V | V | V | V | V | V | V
                                           |   |   |   |   |   |   |   |
            cEtherCfmEventServiceId        | V | V | V | V | V | V | V | V
                                           |   |   |   |   |   |   |   |
            cEtherCfmEventDomainName       | V | V | V | V | V | V | V | V
                                           |   |   |   |   |   |   |   |
            cEtherCfmEventLclMepid         | I | I | I | V | V | I | I | I
                                           |   |   |   |   |   |   |   |
            cEtherCfmEventLclMacAddress    | V | V | V | V | V | V | V | V
                                           |   |   |   |   |   |   |   |
            cEtherCfmEventLclMepCount      | V | V | I | I | I | I | I | I
                                           |   |   |   |   |   |   |   |
            cEtherCfmEventLclIfCount       | V | V | I | I | I | I | I | I
                                           |   |   |   |   |   |   |   |
            cEtherCfmEventRmtMepid         | V | V | V | I | I | V | V | I
                                           |   |   |   |   |   |   |   |
            cEtherCfmEventRmtMacAddress    | V | V | V | I | V | V | V | I
                                           |   |   |   |   |   |   |   |
            cEtherCfmEventRmtPortState     | V | I | I | I | I | I | I | I
                                           |   |   |   |   |   |   |   |
            cEtherCfmEventRmtServiceId     | I | I | V | I | I | I | I | I
                                           |   |   |   |   |   |   |   |
            cEtherCfmEventCode             | V | V | I | I | I | I | I | I
                                           |   |   |   |   |   |   |   |
            cEtherCfmEventDeleteRow        | V | V | V | V | V | V | V | V
                                           |   |   |   |   |   |   |   |
            
            Note: When reading any ignored object, a value of 0 will 
            be returned by the agent.";
          smiv2:max-access "read-only";
          smiv2:oid "1.3.6.1.4.1.9.9.461.1.1.2.1.5";
        }

        leaf cEtherCfmEventLastChange {
          type yang:timestamp;
          description
           "The value of sysUpTime at the time when this row was created.";
          smiv2:max-access "read-only";
          smiv2:oid "1.3.6.1.4.1.9.9.461.1.1.2.1.6";
        }

        leaf cEtherCfmEventServiceId {
          type snmp-framework:SnmpAdminString {
            length "1..100";
          }
          description
           "The customer service instance to which the event belongs.";
          smiv2:max-access "read-only";
          smiv2:oid "1.3.6.1.4.1.9.9.461.1.1.2.1.7";
        }

        leaf cEtherCfmEventLclMepid {
          type CISCO-ETHER-CFM-MIB:CfmMepid;
          description
           "The identifier of the local MEP impacted by the event.";
          smiv2:max-access "read-only";
          smiv2:oid "1.3.6.1.4.1.9.9.461.1.1.2.1.8";
        }

        leaf cEtherCfmEventLclMacAddress {
          type yang:mac-address;
          description
           "The MAC address of the device reporting the event.";
          smiv2:max-access "read-only";
          smiv2:oid "1.3.6.1.4.1.9.9.461.1.1.2.1.9";
        }

        leaf cEtherCfmEventLclMepCount {
          type yang:gauge32;
          description
           "The number of local MEPs affected by the event.";
          smiv2:max-access "read-only";
          smiv2:oid "1.3.6.1.4.1.9.9.461.1.1.2.1.10";
        }

        leaf cEtherCfmEventLclIfCount {
          type yang:gauge32;
          description
           "The number of local interfaces affected by the event.";
          smiv2:max-access "read-only";
          smiv2:oid "1.3.6.1.4.1.9.9.461.1.1.2.1.11";
        }

        leaf cEtherCfmEventRmtMepid {
          type CISCO-ETHER-CFM-MIB:CfmMepid;
          description
           "The maintenance end-point identifier of the remote 
            MEP causing the event entry to be logged.";
          smiv2:max-access "read-only";
          smiv2:oid "1.3.6.1.4.1.9.9.461.1.1.2.1.12";
        }

        leaf cEtherCfmEventRmtMacAddress {
          type yang:mac-address;
          description
           "The MAC address of the remote maintenance point for which
            the event entry is being logged.";
          smiv2:max-access "read-only";
          smiv2:oid "1.3.6.1.4.1.9.9.461.1.1.2.1.13";
        }

        leaf cEtherCfmEventRmtPortState {
          type enumeration {
            enum "up" {
              value "1";
            }
            enum "down" {
              value "2";
            }
            enum "adminDown" {
              value "3";
            }
            enum "test" {
              value "4";
            }
            enum "remoteExcessiveErrors" {
              value "5";
            }
            enum "localExcessiveErrors" {
              value "6";
            }
            enum "localNoData" {
              value "7";
            }
          }
          description
           "The operational state of the port on which the 
            remote MEP is configured. This information is 
            derived from the port-state as indicated in the 
            CC message. The possible values are:
            
            'up'                    - The port is operationally up.
            
            'down'                  - The port is operationally (but not
                                      administratively) down.
            
            'adminDown'             - The port is administratively down.
            
            'test'                  - The port is in test mode (perhaps 
                                      due to an IEEE Standard 802.3ah OAM
                                      intrusive loopback operation).
            
            'remoteExcessiveErrors' - 802.3ah OAM reports that the other 
                                      end of the link is receiving an 
                                      excessive number of invalid frames.
            
            'localExcessiveErrors'  - 802.3ah OAM reports that this end of
                                      the link is receiving an excessive 
                                      number of invalid frames.
            
            'localNoData'           - No data and no CFM messages have been
                                      received for an excessive length of 
                                      time.";
          reference
           "IEEE 802.1ag Draft 1.0: Section 19.4.9.1 and 
            IEEE 802.3ah-2004: Clause 57.";
          smiv2:max-access "read-only";
          smiv2:oid "1.3.6.1.4.1.9.9.461.1.1.2.1.14";
        }

        leaf cEtherCfmEventRmtServiceId {
          type snmp-framework:SnmpAdminString {
            length "1..100";
          }
          description
           "The ID that the remote device has configured for the 
            customer service instance (VLAN).";
          smiv2:max-access "read-only";
          smiv2:oid "1.3.6.1.4.1.9.9.461.1.1.2.1.15";
        }

        leaf cEtherCfmEventCode {
          type enumeration {
            enum "new" {
              value "1";
            }
            enum "returning" {
              value "2";
            }
            enum "portState" {
              value "3";
            }
            enum "lastGasp" {
              value "4";
            }
            enum "timeout" {
              value "5";
            }
            enum "configClear" {
              value "6";
            }
            enum "loopClear" {
              value "7";
            }
            enum "xconnectClear" {
              value "8";
            }
            enum "unknownClear" {
              value "9";
            }
          }
          description
           "This object is used in decoding 'mepUp' and 'mepDown' events. 
            
            ** For 'mepUp', the following codes are relevant:
            
                'new'           - This is the very first time the device 
                                  receives a CC message from the remote MEP.
            
                'returning'     - The device received a CC message from a 
                                  remote MEP for which it had an expired 
                                  CCDB entry.
            
                'portState'     - The device received a CC message from a 
                                  remote MEP for which it has a valid CCDB 
                                  entry, and the message indicates a port 
                                  status change.
            
            ** For 'mepDown', the following codes are relevant:
            
                'lastGasp'      - The device received a CC message from a
                                  remote MEP with zero lifetime.
            
                'timeout'       - The local CCDB entry for the remote MEP 
                                  expired.
            
                'configClear'   - A previous CC message from a MEP that
                                  triggered a configuration error event
                                  is cleared.
                
                'loopClear'     - A previous CC message from a MEP that
                                  triggered a loop error event is cleared.
            
                'xconnectClear' - A previous CC message from a MEP that
                                  triggered a crossconnect error event 
                                  is cleared.
            
                'unknownClear'  - A previous CC message from a MEP that
                                  triggered an unknown MEP event is 
                                  cleared.";
          smiv2:max-access "read-only";
          smiv2:oid "1.3.6.1.4.1.9.9.461.1.1.2.1.16";
        }

        leaf cEtherCfmEventDeleteRow {
          type enumeration {
            enum "noop" {
              value "1";
            }
            enum "delete" {
              value "2";
            }
          }
          description
           "This object allows the management station to 
            delete a row in the cEtherCfmEventTable in order
            to free system resources.
            
            When reading this object the value of 'noop' will be 
            returned. This object can only be set to 'delete'. 
            
            When this object is set to 'delete', the conceptual
            row corresponding to this object will be deleted to
            free system resources. This is equivalent to clearing
            the event log. Should the trigger that caused the event
            to be logged reoccur, the event will be re-asserted but
            in a different conceptual row.";
          smiv2:max-access "read-write";
          smiv2:oid "1.3.6.1.4.1.9.9.461.1.1.2.1.17";
        }
      }
    }
  }

  notification cEtherCfmCcMepUp {
    description
     "This notification is generated in the following cases:
      
      - when a remote MEP first comes up, that is when we receive 
      a CC message from that MEP for the first time.
      
      - when the device receives a CC message from a MEP for which 
      it has an expired CCDB entry.
      
      - when a CC message is received for a remote MEP for which
      the device already has a CCDB entry and the port-state in
      the received CC message is different from the cached 
      previous state.";
    smiv2:oid "1.3.6.1.4.1.9.9.461.0.0.1";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMepCount {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMepCount";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclIfCount {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclIfCount";
        }
      }
    }

    container object-5 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMepid";
        }
      }
    }

    container object-6 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }

    container object-7 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventCode {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventCode";
        }
      }
    }

    container object-8 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtPortState {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtPortState";
        }
      }
    }
  }

  notification cEtherCfmCcMepDown {
    description
     "This notification is generated when a remote MEP goes down; 
      i.e. the entry in CCDB corresponding to this MEP times out 
      or the device receives a CC message with zero hold-time.";
    smiv2:oid "1.3.6.1.4.1.9.9.461.0.0.2";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMepCount {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMepCount";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclIfCount {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclIfCount";
        }
      }
    }

    container object-5 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMepid";
        }
      }
    }

    container object-6 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }

    container object-7 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventCode {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventCode";
        }
      }
    }
  }

  notification cEtherCfmCcCrossconnect {
    description
     "This notification is generated when a device receives a CC
      message with the service ID not matching the one locally 
      configured for the VLAN in question.";
    smiv2:oid "1.3.6.1.4.1.9.9.461.0.0.3";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMepid";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }

    container object-5 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtServiceId";
        }
      }
    }
  }

  notification cEtherCfmCcLoop {
    description
     "This notification is generated when a device receives a CC
      message with the same MEPID and MAC address as those of
      the device itself, indicating that there is a forwarding
      loop and that the device is receiving its own CC messages.";
    smiv2:oid "1.3.6.1.4.1.9.9.461.0.0.4";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMepid";
        }
      }
    }
  }

  notification cEtherCfmCcConfigError {
    description
     "This notification is generated when a device receives a CC
      message with the same MEPID but different MAC address as 
      those of the device itself, indicating that there is a  
      mis-configuration in the network where a remote device
      has the same MEPID configured.";
    smiv2:oid "1.3.6.1.4.1.9.9.461.0.0.5";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMepid";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }
  }

  notification cEtherCfmXCheckMissing {
    description
     "This notification is generated when an expected 
      (configured) MEP does not come up during the cross-check
      start timeout interval.";
    smiv2:oid "1.3.6.1.4.1.9.9.461.0.0.6";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMepid";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }
  }

  notification cEtherCfmXCheckUnknown {
    description
     "This notification is generated when an unexpected MEP
      comes up.";
    smiv2:oid "1.3.6.1.4.1.9.9.461.0.0.7";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }

    container object-3 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMepid {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMepid";
        }
      }
    }

    container object-4 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventRmtMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventRmtMacAddress";
        }
      }
    }
  }

  notification cEtherCfmXCheckServiceUp {
    description
     "This notification is generated when all the MEPs belonging
      to a customer service instance come up before the expiration of
      the cross-check start timeout interval.";
    smiv2:oid "1.3.6.1.4.1.9.9.461.0.0.8";

    container object-1 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventServiceId {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventServiceId";
        }
      }
    }

    container object-2 {

      leaf cEtherCfmEventDomainIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventDomainIndex";
        }
      }

      leaf cEtherCfmEventSvlan {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventSvlan";
        }
      }

      leaf cEtherCfmEventIndex {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventIndex";
        }
      }

      leaf cEtherCfmEventLclMacAddress {
        type leafref {
          path "/CISCO-ETHER-CFM-MIB:CISCO-ETHER-CFM-MIB/CISCO-ETHER-CFM-MIB:cEtherCfmEventTable/CISCO-ETHER-CFM-MIB:cEtherCfmEventEntry/CISCO-ETHER-CFM-MIB:cEtherCfmEventLclMacAddress";
        }
      }
    }
  }

  smiv2:alias "ciscoEtherCfmMIB" {
    smiv2:oid "1.3.6.1.4.1.9.9.461";
  }

  smiv2:alias "ciscoEtherCfmMIBNotifs" {
    smiv2:oid "1.3.6.1.4.1.9.9.461.0";
  }

  smiv2:alias "ciscoEtherCfmNotificationPrefix" {
    smiv2:oid "1.3.6.1.4.1.9.9.461.0.0";
  }

  smiv2:alias "ciscoEtherCfmMIBObjects" {
    smiv2:oid "1.3.6.1.4.1.9.9.461.1";
  }

  smiv2:alias "cecCfmEvents" {
    smiv2:oid "1.3.6.1.4.1.9.9.461.1.1";
  }

  smiv2:alias "ciscoEtherCfmMIBConform" {
    smiv2:oid "1.3.6.1.4.1.9.9.461.2";
  }

  smiv2:alias "ciscoEtherCfmMIBCompliances" {
    smiv2:oid "1.3.6.1.4.1.9.9.461.2.1";
  }

  smiv2:alias "ciscoEtherCfmMIBGroups" {
    smiv2:oid "1.3.6.1.4.1.9.9.461.2.2";
  }

}
