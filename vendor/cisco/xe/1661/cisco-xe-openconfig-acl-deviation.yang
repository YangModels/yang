module cisco-xe-openconfig-acl-deviation{

  yang-version "1";

  // namespace
  namespace "http://cisco.com/ns/yang/cisco-xe-openconfig-acl-deviation";

  prefix "cisco-oc-acl-dev";

  import openconfig-acl { prefix oc-acl; }
  import cisco-xe-openconfig-acl-ext { prefix oc-acl-cisco; }
  import ietf-inet-types { prefix inet; }


  // import some basic types
  import openconfig-extensions { prefix oc-ext; }
  import tailf-common { prefix tailf; }


  // meta
  organization "Cisco";

  contact
    "www.cisco.com";

  description
    "Cisco deviation to oc-acl model to set acl-type mandatory.";

  oc-ext:openconfig-version "1.0.2";

  revision "2017-04-05" {
    description
      "Set range limit for sequence id";
  }

  deviation "/oc-acl:acl/oc-acl:acl-sets/oc-acl:acl-set" +
            "/oc-acl:acl-entries/oc-acl:acl-entry" + 
            "/oc-acl:l2" {
      deviate not-supported;
      description
        "L2 ACEs not supported in 16.6.1.";
  }

  deviation "/oc-acl:acl/oc-acl:acl-sets/oc-acl:acl-set" +
            "/oc-acl:config/oc-acl:description" {
      deviate not-supported;
      description
        "ACL description not supported in 16.6.1.";
  }

  deviation "/oc-acl:acl/oc-acl:acl-sets/oc-acl:acl-set" +
            "/oc-acl:state/oc-acl:description" {
      deviate not-supported;
      description
        "ACL description not supported in 16.6.1.";
  }

  deviation "/oc-acl:acl/oc-acl:acl-sets/oc-acl:acl-set" +
            "/oc-acl:acl-entries/oc-acl:acl-entry" + 
            "/oc-acl:config/oc-acl:description" {
      deviate not-supported;
      description
        "ACE description not supported in 16.6.1.";
  }

  deviation "/oc-acl:acl/oc-acl:acl-sets/oc-acl:acl-set" +
            "/oc-acl:acl-entries/oc-acl:acl-entry" + 
            "/oc-acl:state/oc-acl:description" {
      deviate not-supported;
      description
        "ACE description not supported in 16.6.1.";
  }

  deviation "/oc-acl:acl/oc-acl:acl-sets/oc-acl:acl-set" +
            "/oc-acl:acl-entries/oc-acl:acl-entry" + 
            "/oc-acl:actions/oc-acl:config"  +
            "/oc-acl:log-action" {
      deviate not-supported;
      description
        "ACE log-action not supported in 16.6.1.";
  }

  deviation "/oc-acl:acl/oc-acl:acl-sets/oc-acl:acl-set" +
            "/oc-acl:acl-entries/oc-acl:acl-entry" + 
            "/oc-acl:actions/oc-acl:state"  +
            "/oc-acl:log-action" {
      deviate not-supported;
      description
        "ACE log-action not supported in 16.6.1.";
  }

  // Deviate acl-type to make mandatory

//  deviation "/oc-acl:acl/oc-acl:acl-sets/oc-acl:acl-set" +
//            "/oc-acl:config/oc-acl-cisco:acl-type" {
//       deviate add {
//         mandatory true;
//      }
//  }
  // Deviate to add range limit for ace seq# to unit32 from oc-acl model

  deviation "/oc-acl:acl/oc-acl:acl-sets/oc-acl:acl-set" +
            "/oc-acl:acl-entries/oc-acl:acl-entry" + 
            "/oc-acl:config/oc-acl:sequence-id" {
      deviate replace {
         type uint32 {
          range "1..2147483647";
         }
      }
  }
}
