module Cisco-IOS-XE-power {
  namespace "http://cisco.com/ns/yang/Cisco-IOS-XE-power";
  prefix ios-power;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Power over Ethernet Yang (PoE) model.
     Copyright (c) 2016 by Cisco Systems, Inc.
     All rights reserved.";

  // =========================================================================
  // REVISION
  // =========================================================================
  revision 2017-02-07 {
    description
      "Initial revision";
  }


  grouping config-power-grouping {
    container power {
      description
        "Power configure";

            //  cycle            power cycle a module (deprecated)
            //  enable           module slot power control
      container inline {
            description "Inline power configuration";
            presence true;

            container consumption {
                description "Inline device power consumption";
                leaf default {
                    description "Inline device power consumption";
                    type uint16 {
                        range "4000..15400";
                    }
                }
             }

             container logging {
                description "Inline power logging messages";
                leaf global {
                    description "Enable global inline power logging messages";
                    type empty;
                }

             }

      }

      leaf redundancy-mode {
        description
          "set power supply redundancy mode";
        type enumeration {
          enum "combined";
          enum "redundant";
        }
      }
      leaf max-min {
        type enumeration {
          enum "max";
        }
      }
      leaf inputs {
        type uint8;
      }
    }
  }

  grouping config-interface-power-grouping {
    //unused /native/interface/power
    container power {
      container inline {
        leaf consumption {
          type uint16 {
            range "4000..15400";
          }
        }
        leaf never {
          type empty;
        }
        container auto{
          description
            "Automatically detect and power inline devices";
          presence true;
          leaf max {
            description
              "Maximum power allowed on this interface";
            type int32 {
               range "4000..60000";
            }
          }
        }
        container four-pair {
          description 
            "Four-pair PoE power";
          leaf forced {
	        description
              "Enable Four-pair PoE without L2 negotiation";
	        type empty;
          }
        }
        container police {
          description
            "Police the power drawn on the port";
          presence true;
          container action {
            description
              "Action to be taken when power is overdrawn on the port";
            leaf errdisable{
              description
                "Error-disable the port when power is overdrawn on the port";
              type empty;
            }
            leaf log {
              description
                "Log a message when power is overdrawn on the port";
              type empty;
            }
          }
        }
        container port {
          description 
            "Configure Port Power Level";
	      leaf poe-ha {
            description 
              "Apply poe-ha to the port";
	        type empty;
          }
          leaf two-event {
            description 
              "Enable 2-event classification";
	        type empty;
          }
        }
        container static {
          description
            "High priority inline power interface";
          presence true;
          leaf max {
            description
              "Maximum power allowed on this interface";
            type int32 {
               range "4000..60000";
            }
          }
        }
      }
    }
  }

  /////////////////////////////////////////////////////////
  // native / power
  /////////////////////////////////////////////////////////
  augment "/ios:native" {
    uses config-power-grouping;
  }

  /////////////////////////////////////////////////////////
  // native / interface FastEthernet * power
  /////////////////////////////////////////////////////////
  augment "/ios:native/ios:interface/ios:FastEthernet" {
    uses config-interface-power-grouping;
  }

  /////////////////////////////////////////////////////////
  // native / interface GigabitEthernet * power
  /////////////////////////////////////////////////////////
  augment "/ios:native/ios:interface/ios:GigabitEthernet" {
    uses config-interface-power-grouping;
  }

  /////////////////////////////////////////////////////////
  // native / interface TenGigabitEthernet * power
  /////////////////////////////////////////////////////////
  augment "/ios:native/ios:interface/ios:TenGigabitEthernet" {
    uses config-interface-power-grouping;
  }
} //module
