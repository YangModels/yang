module Cisco-IOS-XE-cts {
  namespace "http://cisco.com/ns/yang/Cisco-IOS-XE-cts";
  prefix ios-cts;

  import ietf-inet-types {
    prefix inet;
  }


  import Cisco-IOS-XE-native {
    prefix ios;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Cisco TrustSec (CTS) Yang model.
     Copyright (c) 2017 by Cisco Systems, Inc.
     All rights reserved.";

  // =========================================================================
  // REVISION
  // =========================================================================
  revision 2017-06-16 {
    description
      "Extension for model CTS role-based commands under interface";
  }
  revision 2017-04-28 {
    description
      "inet:ipv6-prefix changed to ios-types:ipv6-prefix";
  }
  revision 2017-03-23 {
    description
      "NED extension- Trustsec Routing - interface cts options";
  }

  revision 2017-03-07 {
    description
      "NED extension- Trustsec Routing - cts options";
  }

  revision 2017-02-07 {
    description
      "Initial revision";
  }

  grouping cts-server-grouping {
    leaf deadtime {
      description
        "Configure how long a server marked as dead should not be used";
      type uint32 {
        range "0..864000";
      }
    }
    leaf enable {
      description
        "Enable server liveness automated test";
      type boolean;
    }
    leaf idle-time {
      description
        "Configure how often to send an automated test message";
      type uint32 {
        range "0..14400";
      }
    }
  }

  grouping connection-vrf-grouping {
    leaf vrf {
      description "Name of the vrf this connection is in";
      type string;
    }
  }

  grouping cts-sxp-connection-mode-both-grouping {
    container both {
      description "Configure the mode as both";
      presence true;
      uses connection-vrf-grouping;
    }
  }

  grouping cts-sxp-connection-holdtime-min-grouping {
    container hold-time {
      description "Connection hold time period";
      leaf min-time {
        description "Enter minimum allowed Hold Time in seconds (0: apply global, 65535: no keepalive)";
        type uint16 {
          range "0..65535";
        }
      }
      uses connection-vrf-grouping;
    }
    uses connection-vrf-grouping;
  }

  grouping cts-sxp-connection-holdtime-min-max-grouping {
    container hold-time {
      description "Connection hold time period";
      leaf min-time {
        description 
          "Enter minimum allowed Hold Time in seconds (0: apply global, 65535: no keepalive)";
        type uint16 {
          range "0..65535";
        }
      }
      leaf max-time {
        description 
          "Enter maximum allowed Hold Time in seconds (0: apply global, 65535: no keepalive)";
        type uint16 {
          range "0..65535";
        }
      }
      uses connection-vrf-grouping;
    }
    uses connection-vrf-grouping;
  }

  grouping cts-sxp-connection-mode-local-grouping {
    container local {
      description "Configure the mode on the local device";
      presence true;

      uses cts-sxp-connection-mode-both-grouping;

      container listener {
        description "Receive SXP messages on the conn";
        presence true;
        uses cts-sxp-connection-holdtime-min-max-grouping;
      }
      container speaker {
        description "Send SXP messages on the conn";
        presence true;
        uses cts-sxp-connection-holdtime-min-grouping;
      }
    }
  }

  grouping cts-sxp-connection-mode-peer-grouping {
    container peer {
      description "Configure the mode on the peer device";
      presence true;

      uses cts-sxp-connection-mode-both-grouping;

      container listener {
        description "Receive SXP messages on the conn";
        presence true;
        uses cts-sxp-connection-holdtime-min-grouping;
      }
      container speaker {
        description "Send SXP messages on the conn";
        presence true;
        uses cts-sxp-connection-holdtime-min-max-grouping;
      }
    }
  }

  grouping cts-sxp-connection-peer-password-grouping {
    list password {
      max-elements "1";
      key "password-type";
      description "password details";
      leaf password-type {
        type enumeration {  
          enum "default";
          enum "none";
        }
      }
      container mode {
        description "Specify SXP connection mode";
        uses cts-sxp-connection-mode-local-grouping;
        uses cts-sxp-connection-mode-peer-grouping;
      }
    }
  }

  grouping config-cts-grouping {
    container cache {
      description "CTS cache configuration";
      leaf enable {
        description "Enable CTS cache support";
        type empty;
      }
      container nv-storage {
        description "CTS nv-storage options";
        leaf nv-storage {
          type enumeration {
            enum "bootflash:";
            enum "crashinfo:";
            enum "kinfo:";
            enum "slot0:";
            enum "usb0:";
          }
        }
      }
    }
    leaf critical-authentication-conf {
      // Note: Leaf and Container have the same name
      type empty;
    }
    container critical-authentication {
      description "Critical-Auth configuration commands";
      presence true;
      container default {
        description "Enter default value";
        container peer-sgt {
          description "Default Peer SGT value";
          list  range {
            key "range";
            leaf range {
              description "Enter default peer-sgt value";
              type uint16 {
                range "2..65519";
              }
            }
            leaf trusted {
              description "Trust the Source Group Tags that peer uses for sending";
                type empty;
            }
          }
        }
        container pmk {
          description "Default PMK value to be used for all SAP";
          leaf type {
            type enumeration {
              enum "0";
              enum "6";
            }
          }
          leaf secret {
            type string;
          }
        }
      }
      container fallback {
        description "Access policy to be applied in Critical-Auth";
        leaf Cached {
          description "Cached values to be used for existing sessions";
            type empty;
        }
        leaf default {
          description "Configured values to be applied for existing sessions";
            type empty;
        }
      }
    }

    container authorization {
      description
        "CTS global authorization configuration";
      leaf list {
        description
          "Local authorization list to use for CTS";
        type string;
      }
    }
    leaf dot1x-server-timeout {
      description
        "Timeout for Radius Retries";
      type uint16 {
        range "30..65535";
      }
    }
    leaf dot1x-supp-timeout {
      description
        "Timeout for supplicant reply";
      type uint16 {
        range "30..65535";
      }
    }
    leaf logging {
      description
        "Set logging parameters";
      type enumeration {
        enum "verbose";
      }
    }
    container role-based {
      description
        "Role-based Access Control configuration commands";
      leaf sgt-caching {
        description
          "Enable SGT caching";
        type empty;
      }
      container permissions {
        description "Permissions from a source group to a destination group";
        container default {
          description "Default Permission list";
          leaf name {
            description "Role-based Access-list name";
            type string;
          }
        }
        container from {
          description "Source Group Tag (SGT) of filtered traffic";
          list  range {
            key "range";
            leaf range {
              description "Security Group Tag";
              type uint16 {
                range "0..65519";
              }
            }
            container to {
              description "Destination Group Tag (DGT) of filtered traffic";
              list  range {
                key "range";
                leaf range {
                  description "Security Group Tag";
                  type uint16 {
                    range "0..65519";
                  }
                }

                leaf name {
                  type string;
                }
              }
            }
          }
        }
      }

      container enforcement {
        description 
          "Enable Role-based Access Control enforcement";
        presence true;
        leaf logging-interval {
          description
            "Configure sgacl logging interval";
          type uint32 {
            range "5..86400";
          }
        }
        list vlan-list {
          description 
            "VLANs on which Role-based ACLs are enforced";
          key "id";
          leaf id {
            description 
              "VLAN id";
            type union {
              type string;
              type enumeration {
                enum all;
              }  
            }
          }
        }
      }

      container monitor {
        description
          "Role-based Access List Monitor Commands";
        leaf all {
           description
             "Monitoring permissions for all source group to all destination group";
           type empty;
        }
      }

      list sgt-map {
        description
          "Assign Security Group Tag (SGT) to IP host or network address";
        key "ip sgt";
        leaf ip {
          type union {
            type inet:ipv4-address;
            type inet:ipv4-prefix;
            type inet:ipv6-address;
            type ios-types:ipv6-prefix;
          }
        }
        leaf sgt {
          description
            "Security Group Tag (SGT)";
          type uint16;
        }
        leaf vrf {
          description
            "Select VPN Routing/Forwarding instance for the binding";
          type string;
        }
        leaf host {
          type empty;
        }
      }

      container sgt-map-vlan-list {
        description 
          "VLANs on which Role-based ACLs are enforced";
        list sgt-map {
          key "vlan-list";
          leaf vlan-list {
            description 
              "VLANs id";
            type union {
              type string;
              type enumeration {
                enum all;
              }
            }  
          }             
          leaf sgt {
            description
              "Security Group Tag value";
            type int16;
          }  
        }
      }
    }
    container server {
      description
        "CTS server list configuration";
      leaf deadtime {
        description
          "Configure server group deadtime to specify how long a servermarked as dead should not be used";
        type uint32 {
          range "0..864000";
        }
      }
      container key-wrap {
        description
          "CTS key-wrap configuration";
        leaf enable {
          description
            "Enable CTS key-wrap for Private server-list";
          type empty;
        }
      }
      container load-balance {
        description
          "CTS Server group load-balancing options";
        container method {
          description
            "Method by which the next server will be picked";
          container least-outstanding {
            description
              "Pick the server with the least transactions outstanding";
            presence "true";
            leaf batch-size {
              description
                "Size of the transaction batch that should be load-balanced";
              type uint32 {
                range "1..2147483647";
              }
            }
            leaf ignore-preferred-server {
              description
                "Do not attempt to stick with the same server throughout a session";
              type empty;
            }
          }
        }
      }
      container test {
        description
          "Configure server automated test for liveness check";
        list server {
          key "ip";
          leaf ip {
            type inet:ipv4-address;
          }
          uses cts-server-grouping;
        }
        container all {
          description
            "Configure for all servers";
          uses cts-server-grouping;
        }
      }
    }
    leaf sgt {
      description
        "Local device security group";
      type uint16 {
        range "2..65519";
      }
    }

    leaf sg-epg {
      description
        "Security-Group and Endpoint-Group Configuration commands";
      type enumeration {
        enum "translation";
      }
    }

    container sxp {
      description "CTS sxp configuration";
      container default {
        description "Enter default value";
        container password {
          leaf type {
            type enumeration {
              enum "0";
              enum "6";
              enum "7";
            }
          }
          leaf secret {
            type string;
          }
        }
        leaf source-ip {
          description "Enter Source IPv4 Address";
          type inet:ipv4-address;
        }
      }
      container connection {
        description "CTS SXP Connection Configuration";
        container peer {
          description "SXP Peer IP address";
          list  ipv4 {
            key "ipv4";
            leaf ipv4 {
              description "Enter SXP Peer IP address (IPv4)";
              type inet:ipv4-address;
            }
            container source {
              description "Source IP address";
              list  ipv4 {
                key "ipv4";
                leaf ipv4 {
                  description "Enter SXP Source IP address (IPv4)";
                  type inet:ipv4-address;
                }
                uses cts-sxp-connection-peer-password-grouping;
              }
            }
            uses cts-sxp-connection-peer-password-grouping;
          }
        }
      }
      leaf enable {
        description "Enable CTS SXP support";
        type empty;
      }
    }
  }

  grouping interface-cts-manual-grouping {

    container manual {
      description
      "Supply local configuration for CTS parameters";
      presence true;
      container policy {
        description
        "CTS policy for manual mode";
        container static {
          description
          "Configure policy to be applied on the link";
          leaf sgt {
            description
            "Source Security Group Tag to apply to untagged or non-trusted 
             incoming traffic";
            type uint16 {
              range "2..65519";
            }
          }
          leaf trusted {
            description
              "Trust the Source Group Tags (SGT) that the peer uses for 
               sending";
            type empty;
          }
        }
      }
      container sap {
        description 
         "CTS SAP configuration for manual mode";
        list pmk {
          description 
            "Pre-Master Key (PMK) to use for CTS SAP";
          key "word";
          leaf word {
            type string;
          }
          container mode-list {
            description
              "List of advertised modes (prioritized from highest to lowest)";
            container gcm-encrypt {
              description 
                "GCM authentication, GCM encryption";
              presence true;
              container gmac {
                description 
                  "GCM authentication, no encryption";
                presence true;
                leaf null {
                  description 
                    "Encapsulation present, no authentication, 
                     no encryption";
                  type empty;
                }
              }
            }  
            container no-encap {
              description "No encapsulation";
              presence true;
              container gmac {
	        description
                  "GCM authentication, no encryption";
                presence true;
                leaf gcm-encrypt {
                  description
                    "GCM authentication, GCM encryption";
                  type empty;
                }
              }
            }
          }
        }  
      } 

      container propagate {
        description
          "CTS SGT Propagation configuration for manual mode";
        leaf sgt {
          description
            "CTS SGT Propagation configuration";
          type boolean;
        }
      }
    }
  }

  grouping interface-cts-role-based-grouping {
    container role-based {
      description
        "Role-based Access Control per-port config commands";
      leaf-list sgt-cache {
        description
          "Enable SGT caching on the interface";
        type enumeration {
          enum "egress";
          enum "ingress";
        }
      }
      // enforcement
      leaf enforcement {
        description 
          "Enable Role-based Access Control enforcement";
        type empty;
      }
      // sgt-map
      container sgt-map {
        description
          "Assign Security Group Tag (SGT) to IP host or network address";
        leaf security-group {
          description
            "Security Group Name";
          type string;
        }
        leaf sgt {
          description 
            "Security Group Tag (SGT)";
          type uint16 {
            range "2..65519";
          }
        }
      }
    }
  }
    
  grouping interface-cts-role-based-enforcement-grouping {
    container role-based {
      description
        "Role-based Access Control per-port config commands";
      leaf enforcement {
        description 
          "Enable Role-based Access Control enforcement";
        type empty;
      }
    }
  }       
 
  grouping interface-cts-sgt-grouping {
    leaf sgt {
      description
        "SGT command options";
      type enumeration {
        enum "inline";
      }
    }
  }

  grouping config-interface-cts-manual-grouping {
    container cts {
      description
        "Configure Cisco Trusted Security";
      uses interface-cts-manual-grouping;
    }
  }
  
  grouping config-interface-cts-manual-role-based-enforcement-grouping {
    container cts {
      description
        "Configure Cisco Trusted Security";
      uses interface-cts-manual-grouping;
      uses interface-cts-role-based-enforcement-grouping;
    }
  }
 
 grouping config-interface-cts-manual-role-based-grouping {
    container cts {
      description
        "Configure Cisco Trusted Security";
      uses interface-cts-manual-grouping;
      uses interface-cts-role-based-grouping;
    }
  }
  
  grouping config-interface-cts-manual-role-based-sgt-grouping {
    container cts {
      description
        "Configure Cisco Trusted Security";
      uses interface-cts-manual-grouping;
      uses interface-cts-role-based-grouping;
      uses interface-cts-sgt-grouping;

    }
  }

  /////////////////////////////////////////////////////////
  // native / cts
  /////////////////////////////////////////////////////////
  augment "/ios:native/ios:cts" {
    uses config-cts-grouping;
  }

  /////////////////////////////////////////////////////////
  // native / interface * / cts
  /////////////////////////////////////////////////////////
  augment "/ios:native/ios:interface/ios:FastEthernet" {
    uses config-interface-cts-manual-role-based-grouping;
  }

  augment "/ios:native/ios:interface/ios:GigabitEthernet" {
    uses config-interface-cts-manual-role-based-grouping;
  }

  augment "/ios:native/ios:interface/ios:TenGigabitEthernet" {
    uses config-interface-cts-manual-role-based-grouping;
  }

  augment "/ios:native/ios:interface/ios:FortyGigabitEthernet" {
    uses config-interface-cts-manual-role-based-enforcement-grouping;
  }

  augment "/ios:native/ios:interface/ios:Loopback" {
    uses config-interface-cts-manual-grouping;
  }

  augment "/ios:native/ios:interface/ios:Tunnel" {
    uses config-interface-cts-manual-role-based-sgt-grouping;
  }

  augment "/ios:native/ios:interface/ios:Port-channel" {
    uses config-interface-cts-manual-grouping;
  }

  augment "/ios:native/ios:interface/ios:Virtual-Template" {
    uses config-interface-cts-manual-grouping;
  }

  augment "/ios:native/ios:interface/ios:VirtualPortGroup" {
    uses config-interface-cts-manual-grouping;
  }

  augment "/ios:native/ios:interface/ios:Vlan" {
    uses config-interface-cts-manual-grouping;
  }
} //module
