module cisco-xe-ietf-event-notifications-deviation {
  namespace "http://cisco.com/ns/yang/cisco-xe-ietf-event-notifications-deviation";

  prefix notif-bis-devs;

  import ietf-event-notifications {
    prefix notif-bis;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for ietf-event-notifications
     module.
     Copyright (c) 2017 by Cisco Systems, Inc.
     All rights reserved.";

  revision 2017-02-22 {
    description
      "Initial Revision";

    reference
      "RFC 6020: YANG - A Data Modeling Language for the
       Network Configuration Protocol (NETCONF)";

  }

  deviation "/notif-bis:establish-subscription/notif-bis:input" +
            "/notif-bis:filter-type/notif-bis:by-reference" {
    deviate not-supported;
    description  "Currently not supported.";
  }

  deviation "/notif-bis:establish-subscription/notif-bis:input" +
            "/notif-bis:startTime" {
    deviate not-supported;
    description  "Currently not supported.";
  }

  deviation "/notif-bis:establish-subscription/notif-bis:input" +
            "/notif-bis:stopTime" {
    deviate not-supported;
    description  "Currently not supported.";
  }

}
