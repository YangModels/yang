module cisco-xe-openconfig-if-ethernet-ext{

  yang-version "1";

  // namespace
  namespace "http://cisco.com/ns/yang/cisco-xe-openconfig-if-ethernet-ext";

  prefix "cisco-if-eth";
  import openconfig-interfaces { prefix oc-if; }
  import openconfig-if-ethernet { prefix oc-if-eth; }


  // import some basic types
  import openconfig-extensions { prefix oc-ext; }
  import tailf-common { prefix tailf; }


  // meta
  organization "OpenConfig working group";

  contact
    "OpenConfig working group
    netopenconfig@googlegroups.com";

  description
    "Module to enable mapping for oc-interfaces.";

  oc-ext:openconfig-version "1.0.2";

  revision "2017-03-09" {
    description
      "Added identity for AUTO ethernet port speed for switches";
    reference "1.0.2";
  }

  revision "2017-02-25" {
    description
      "Initial version.  Add switchport leaf for controlling Cisco switchport configs";
    reference "1.0.2";
  }

  identity AUTO {
    base oc-if-eth:ETHERNET_SPEED;
    description "Enable auto port-speed negotiation for switches";
  }

  // Augment to add switchport leaf

  augment "/oc-if:interfaces/oc-if:interface" +
            "/oc-if-eth:ethernet/oc-if-eth:config" {
              leaf switchport {
                type boolean;
                description
                  "If false the switch port is a routed port and can have an ip address.";
             }
          }

}
