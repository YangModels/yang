module cisco-xe-openconfig-terminal-device-deviation {
  // namespace
  namespace "http://cisco.com/ns/yang/cisco-xe-openconfig-ternimal-device-deviation";

  prefix oc-opt-term-devs;

  import openconfig-terminal-device {
    prefix oc-opt-term;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-platform module.";

  revision 2017-04-18 {
    description
      "Initial draft";

    reference
      "RFC 6020: YANG - A Data Modeling Language for the
       Network Configuration Protocol (NETCONF)";
  }

  deviation "/oc-opt-term:terminal-device/oc-opt-term:logical-channels" +
            "/oc-opt-term:channel/oc-opt-term:ingress" +
            "/oc-opt-term:config/oc-opt-term:transceiver" {
      deviate replace {
        type string;
      }
      description
        "remove leafref. Use direct type.";
  }

  deviation "/oc-opt-term:terminal-device/oc-opt-term:logical-channels" +
            "/oc-opt-term:channel/oc-opt-term:logical-channel-assignments" +
            "/oc-opt-term:assignment/oc-opt-term:config" +
            "/oc-opt-term:optical-channel" {
      deviate replace {
        type string;
      }
      description
        "remove leafref. Use direct type.";
  }
}
