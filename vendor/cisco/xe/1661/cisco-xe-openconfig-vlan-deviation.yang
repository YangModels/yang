module cisco-xe-openconfig-vlan-deviation {

  namespace "http://cisco.com/ns/yang/cisco-xe-openconfig-vlan-deviation";

  prefix oc-vlan-devs;
  
  import openconfig-interfaces { 
    prefix oc-if; 
  }
 
  import openconfig-vlan { 
    prefix oc-vlan; 
  }

  organization "Cisco Systems";

  description
     "Deviation YANG module for Openconfig-vlan
      Copyright (c) 2017 by Cisco Systems, Inc.
      All rights reserved.";

  ////////////////////////////////////////////////////////////////////////////
  // REVISION
  ///////////////////////////////////////////////////////////////////////////
  revision 2017-03-17 {
     description "Initial revision";
  }

  ////////////////////////////////////////////////////////////////////////////////
  // DEVIATION
  ///////////////////////////////////////////////////////////////////////////////

  deviation "/oc-vlan:vlans/oc-vlan:vlan/oc-vlan:members" {
    deviate not-supported;
  }

  deviation "/oc-vlan:vlans/oc-vlan:vlan/oc-vlan:config/oc-vlan:tpid" {
    deviate not-supported;
  }

  deviation "/oc-vlan:vlans/oc-vlan:vlan/oc-vlan:state/oc-vlan:tpid" {
    deviate not-supported;
  }

  deviation "/oc-if:interfaces/oc-if:interface" +
            "/oc-if:subinterfaces/oc-if:subinterface/oc-vlan:vlan" {
    deviate not-supported;
  }
}
