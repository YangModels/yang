module cisco-nx-openconfig-vlan-deviations {

  namespace "http://openconfig.net/yang/vlan-deviations";

  prefix "oc-vlan-devs";

  import openconfig-vlan { prefix oc-vlan; }
  import openconfig-interfaces { prefix oc-if; }
  import openconfig-vlan-types { prefix oc-vlan-types; }
  import openconfig-network-instance { prefix oc-netinst; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-vlan module 
     set for Cisco NXOS.
     Copyright (c) 2015-2019 by Cisco Systems, Inc.
     All rights reserved.";

  revision "2018-05-14" {
    description
      "Initial revision applicable to NXOS";
  }

  deviation /oc-if:interfaces/oc-if:interface/oc-if:config/oc-vlan:tpid {
    deviate add {
      must "../oc-vlan:tpid='oc-vlan-types:TPID_0X8100' or ../oc-vlan:tpid='oc-vlan-types:TPID_0X9100'" {
  		error-message "Only supports TPID_0X8100, TPID_0X9100 on device model";
      }     
    }
  }
  deviation /oc-netinst:network-instances/oc-netinst:network-instance/oc-netinst:vlans/oc-netinst:vlan/oc-netinst:config/oc-netinst:name {
    deviate replace {
      type string {
        pattern "[^\s]*";
      }
    }
  }
}
