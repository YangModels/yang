module cisco-nx-openconfig-qos-deviations {

  namespace "http://openconfig.net/yang/qos-deviations";

  prefix "oc-qos-devs";

  import openconfig-qos { prefix oc-qos; }
  import openconfig-extensions { prefix oc-ext; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-qos module 
     set for Cisco NXOS.
     Copyright (c) 2015-2017, 2020 by Cisco Systems, Inc.
     All rights reserved.";

  revision "2020-03-05" {
    description
      "Initial revision applicable to NXOS";
  }

  deviation /oc-qos:qos/oc-qos:interfaces/oc-qos:interface/oc-qos:input/oc-qos:queues/oc-qos:queue/oc-qos:state/oc-qos:max-queue-len {
     deviate "not-supported";
  }
  deviation /oc-qos:qos/oc-qos:interfaces/oc-qos:interface/oc-qos:output/oc-qos:queues/oc-qos:queue/oc-qos:state/oc-qos:max-queue-len {
     deviate "not-supported";
  }
  deviation /oc-qos:qos/oc-qos:interfaces/oc-qos:interface/oc-qos:input/oc-qos:queues/oc-qos:queue/oc-qos:state/oc-qos:avg-queue-len {
     deviate "not-supported";
  }
  deviation /oc-qos:qos/oc-qos:interfaces/oc-qos:interface/oc-qos:output/oc-qos:queues/oc-qos:queue/oc-qos:state/oc-qos:avg-queue-len {
     deviate "not-supported";
  }
  deviation /oc-qos:qos/oc-qos:interfaces/oc-qos:interface/oc-qos:input/oc-qos:queues/oc-qos:queue/oc-qos:state/oc-qos:transmit-pkts {
     deviate "not-supported";
  }
  deviation /oc-qos:qos/oc-qos:interfaces/oc-qos:interface/oc-qos:input/oc-qos:queues/oc-qos:queue/oc-qos:state/oc-qos:transmit-octets {
     deviate "not-supported";
  }
  deviation /oc-qos:qos/oc-qos:interfaces/oc-qos:interface/oc-qos:input/oc-qos:scheduler-policy/oc-qos:schedulers/oc-qos:scheduler/oc-qos:state/oc-qos:conforming-pkts {
     deviate "not-supported";
  }
  deviation /oc-qos:qos/oc-qos:interfaces/oc-qos:interface/oc-qos:output/oc-qos:scheduler-policy/oc-qos:schedulers/oc-qos:scheduler/oc-qos:state/oc-qos:conforming-pkts {
     deviate "not-supported";
  }
  deviation /oc-qos:qos/oc-qos:interfaces/oc-qos:interface/oc-qos:input/oc-qos:scheduler-policy/oc-qos:schedulers/oc-qos:scheduler/oc-qos:state/oc-qos:exceeding-pkts {
     deviate "not-supported";
  }
  deviation /oc-qos:qos/oc-qos:interfaces/oc-qos:interface/oc-qos:output/oc-qos:scheduler-policy/oc-qos:schedulers/oc-qos:scheduler/oc-qos:state/oc-qos:exceeding-pkts {
     deviate "not-supported";
  }
  deviation /oc-qos:qos/oc-qos:interfaces/oc-qos:interface/oc-qos:output/oc-qos:scheduler-policy/oc-qos:schedulers/oc-qos:scheduler/oc-qos:state/oc-qos:exceeding-octets {
     deviate "not-supported";
  }
  deviation /oc-qos:qos/oc-qos:interfaces/oc-qos:interface/oc-qos:input/oc-qos:scheduler-policy/oc-qos:schedulers/oc-qos:scheduler/oc-qos:state/oc-qos:violating-pkts {
     deviate "not-supported";
  }
  deviation /oc-qos:qos/oc-qos:interfaces/oc-qos:interface/oc-qos:output/oc-qos:scheduler-policy/oc-qos:schedulers/oc-qos:scheduler/oc-qos:state/oc-qos:violating-pkts {
     deviate "not-supported";
  }
/* Mapped to device model
 *     Device Model Target: openconfig-qos/qos/interfaces/interface[interface-id]/input/scheduler-policy/schedulers/scheduler[sequence]
 * Transformation Function: oc_qos_in_intf_police_stats_cmapname
 */
  deviation /oc-qos:qos/oc-qos:interfaces/oc-qos:interface/oc-qos:input/oc-qos:scheduler-policy/oc-qos:schedulers/oc-qos:scheduler/oc-qos:sequence {
    deviate replace {
        type string {
            length "1..40";
      }
    }
  }
/* Mapped to device model
 *     Device Model Target: openconfig-qos/qos/interfaces/interface[interface-id]/input/scheduler-policy/schedulers/scheduler[sequence]
 * Transformation Function: oc_qos_in_intf_police_stats_cmapname
 */
  deviation /oc-qos:qos/oc-qos:interfaces/oc-qos:interface/oc-qos:input/oc-qos:scheduler-policy/oc-qos:schedulers/oc-qos:scheduler/oc-qos:state/oc-qos:sequence {
    deviate replace {
        type string {
            length "1..40";
      }
    }
  }

/* Mapped to device model
 *     Device Model Target: openconfig-qos/qos/interfaces/interface[interface-id]/output/scheduler-policy/schedulers/scheduler[sequence]
 * Transformation Function: oc_qos_out_intf_police_stats_cmapname
 */
  deviation /oc-qos:qos/oc-qos:interfaces/oc-qos:interface/oc-qos:output/oc-qos:scheduler-policy/oc-qos:schedulers/oc-qos:scheduler/oc-qos:sequence {
    deviate replace {
        type string {
            length "1..40";
      }
    }
  }
/* Mapped to device model
 *     Device Model Target: openconfig-qos/qos/interfaces/interface[interface-id]/output/scheduler-policy/schedulers/scheduler[sequence]
 * Transformation Function: oc_qos_out_intf_police_stats_cmapname
 */
  deviation /oc-qos:qos/oc-qos:interfaces/oc-qos:interface/oc-qos:output/oc-qos:scheduler-policy/oc-qos:schedulers/oc-qos:scheduler/oc-qos:state/oc-qos:sequence {
    deviate replace {
        type string {
            length "1..40";
      }
    }
  }
/* Mapped to device model
 *     Device Model Target: openconfig-qos/qos/interfaces/interface[interface-id]/input/classifiers/classifier/type[type]
 */
  deviation /oc-qos:qos/oc-qos:interfaces/oc-qos:interface/oc-qos:input/oc-qos:classifiers/oc-qos:classifier/oc-qos:type {
    deviate  replace {
      type string;
      }
      deviate add {
        must "../oc-qos:type='qos'" {
          error-message "Only supports qos on device model";
      }
    }
  } 
/* Mapped to device model
 *     Device Model Target: openconfig-qos/qos/interfaces/interface[interface-id]/output/classifiers/classifier/type[type]
 */
  deviation /oc-qos:qos/oc-qos:interfaces/oc-qos:interface/oc-qos:output/oc-qos:classifiers/oc-qos:classifier/oc-qos:type {
    deviate  replace {
      type string;
      }
      deviate add {
        must "../oc-qos:type='qos'" {
          error-message "Only supports qos on device model";
      }
    }
  }
  deviation /oc-qos:qos/oc-qos:interfaces/oc-qos:interface/oc-qos:input/oc-qos:classifiers/oc-qos:classifier/oc-qos:config/oc-qos:type {
     deviate "not-supported";
  }
  deviation /oc-qos:qos/oc-qos:interfaces/oc-qos:interface/oc-qos:output/oc-qos:classifiers/oc-qos:classifier/oc-qos:config/oc-qos:type {
     deviate "not-supported";
  }
  deviation /oc-qos:qos/oc-qos:interfaces/oc-qos:interface/oc-qos:input/oc-qos:classifiers/oc-qos:classifier/oc-qos:state/oc-qos:type {
    deviate  replace {
      type string;
      }
      deviate add {
        must "../oc-qos:type='qos'" {
          error-message "Only supports qos on device model";
      }
    }
  } 
  deviation /oc-qos:qos/oc-qos:interfaces/oc-qos:interface/oc-qos:output/oc-qos:classifiers/oc-qos:classifier/oc-qos:state/oc-qos:type {
    deviate  replace {
      type string;
      }
      deviate add {
        must "../oc-qos:type='qos'" {
          error-message "Only supports qos on device model";
      }
    }
  }
  
  deviation /oc-qos:qos/oc-qos:config {
     deviate "not-supported";
  }
  deviation /oc-qos:qos/oc-qos:classifiers {
     deviate "not-supported";
  }
  deviation /oc-qos:qos/oc-qos:scheduler-policies {
     deviate "not-supported";
  }
  deviation /oc-qos:qos/oc-qos:queues {
     deviate "not-supported";
  }
  deviation /oc-qos:qos/oc-qos:forwarding-groups {
     deviate "not-supported";
  }
  deviation /oc-qos:qos/oc-qos:interfaces/oc-qos:interface/oc-qos:config {
     deviate "not-supported";
  }
  deviation /oc-qos:qos/oc-qos:interfaces/oc-qos:interface/oc-qos:state {
     deviate "not-supported";
  }
  deviation /oc-qos:qos/oc-qos:interfaces/oc-qos:interface/oc-qos:interface-ref/oc-qos:config {
     deviate "not-supported";
  }

  deviation /oc-qos:qos/oc-qos:interfaces/oc-qos:interface/oc-qos:input/oc-qos:config {
     deviate "not-supported";
  }
  deviation /oc-qos:qos/oc-qos:interfaces/oc-qos:interface/oc-qos:input/oc-qos:state {
     deviate "not-supported";
  }
  deviation /oc-qos:qos/oc-qos:interfaces/oc-qos:interface/oc-qos:output/oc-qos:config {
     deviate "not-supported";
  }
  deviation /oc-qos:qos/oc-qos:interfaces/oc-qos:interface/oc-qos:output/oc-qos:state {
     deviate "not-supported";
  }

  deviation /oc-qos:qos/oc-qos:interfaces/oc-qos:interface/oc-qos:input/oc-qos:virtual-output-queues {
     deviate "not-supported";
  }
  deviation /oc-qos:qos/oc-qos:interfaces/oc-qos:interface/oc-qos:output/oc-qos:interface-ref {
     deviate "not-supported";
  }

  deviation /oc-qos:qos/oc-qos:interfaces/oc-qos:interface/oc-qos:input/oc-qos:classifiers/oc-qos:classifier/oc-qos:config {
     deviate "not-supported";
  }
  deviation /oc-qos:qos/oc-qos:interfaces/oc-qos:interface/oc-qos:output/oc-qos:classifiers/oc-qos:classifier/oc-qos:config {
     deviate "not-supported";
  }
  deviation /oc-qos:qos/oc-qos:interfaces/oc-qos:interface/oc-qos:input/oc-qos:queues/oc-qos:queue/oc-qos:config {
     deviate "not-supported";
  }
  deviation /oc-qos:qos/oc-qos:interfaces/oc-qos:interface/oc-qos:output/oc-qos:queues/oc-qos:queue/oc-qos:config {
     deviate "not-supported";
  }
  
  deviation /oc-qos:qos/oc-qos:interfaces/oc-qos:interface/oc-qos:input/oc-qos:scheduler-policy/oc-qos:config {
     deviate "not-supported";
  }
  deviation /oc-qos:qos/oc-qos:interfaces/oc-qos:interface/oc-qos:output/oc-qos:scheduler-policy/oc-qos:config {
     deviate "not-supported";
  }
  deviation /oc-qos:qos/oc-qos:buffer-allocation-profiles {
     deviate "not-supported";
  }
  deviation /oc-qos:qos/oc-qos:queue-management-profiles {
     deviate "not-supported";
  }
  deviation /oc-qos:qos/oc-qos:interfaces/oc-qos:interface/oc-qos:input/oc-qos:queues/oc-qos:queue/oc-qos:state/oc-qos:queue-management-profile {
     deviate "not-supported";
  }
  deviation /oc-qos:qos/oc-qos:interfaces/oc-qos:interface/oc-qos:output/oc-qos:queues/oc-qos:queue/oc-qos:state/oc-qos:queue-management-profile {
     deviate "not-supported";
  }
  deviation /oc-qos:qos/oc-qos:interfaces/oc-qos:interface/oc-qos:input/oc-qos:queues/oc-qos:queue/oc-qos:state/oc-qos:dropped-octets {
   deviate "not-supported";
  }
  deviation /oc-qos:qos/oc-qos:interfaces/oc-qos:interface/oc-qos:output/oc-qos:queues/oc-qos:queue/oc-qos:state/oc-qos:dropped-octets {
     deviate "not-supported";
  }
}
