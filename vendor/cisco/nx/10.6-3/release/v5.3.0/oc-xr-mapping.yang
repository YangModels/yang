module oc-xr-mapping {

  namespace "http://cisco.com/ns/yang/cisco-oc-xr-mapping";
  prefix "cisco";

  organization "Cisco Systems, Inc.";

  contact 
    "Cisco Systems, Inc.
     Customer Service

     Postal: 170 W Tasman Drive
     San Jose, CA 95134

     Tel: +1 1800 553-NETS

     E-mail: cs-yang@cisco.com";


  description       
    "This module contains a collection of IOS-XR derived YANG data 
     types.
    
     Copyright (c) 2013-2015, 2017-2018 by Cisco Systems, Inc.
     All rights reserved.";

  revision "2015-02-10" {
    description
      "Initial revision.";
  }

  extension mapping {
    description "Define basic information about mapping.";
  }

  extension model-id {
    description "Define model id used for a part of generated function name.";
    argument "model-id";
  }

  extension module-id {
    description "Define module id used for a part of generated source file name.";
    argument "module-id";
  }

  extension target {
    description "Define information of target model.";
  }

  extension namespace {
    description "namespace of the target model.";
    argument "ns";
  }

  extension default-prefix {
    description "Default namespace prefix used when path does not specify it.";
    argument "default-ns";
  }

  extension map-to {
    description "The oc-xr-map statement takes as an argument
                 relevant XR yang model node(s).";
  }

  extension from {
    description "In case the node is under group and there are multiple parent uses the same group";
  }

  extension parent {
    description "Parent path that this mapping should be used";
    argument "parent_path";
  }

  extension path {
    description "The path in XR model mapped for this node.";
    argument "xpath";
  }

  extension path-get {
    description "The path to node mapped for get operation.";
    argument "xpath";
  }
  
  extension path-set {
    description "The path to node mapped for set operation.";
    argument "xpath";
  }
  
  extension path-del {
    description "The path to node mapped to delete/remove operation.";
    argument "xpath";
  }

  extension function {
    description "The function called for mapping this node.";
    argument "name";
  }

  extension description {
    description "Instructions for mapping specific to this node.";
    argument "description";
  }
  
  extension dt-convert-to {
    description "The statement specifies that this leaf has data type 
                  conversion before being mapped";
    argument "dt-convert-to";
  }
  
  extension dt-case {
    description "This specifies the datatype conversion cases. 
                 The value maps to the datatype it should be converted to";
    argument "dt-case";
  }
 
  extension dt-value {
    description "This specifies the datatype conversion value.";
    argument "dt-value";
  }

  extension dt-action {
    description "This specifies the action for some datatype conversions";
    argument "dt-action";
  }
  
  extension if {
    description "Conditional mapping annotation";
    argument "if";
  } 

  extension data-split {
    description "If the input data has to be split into multiple
                 parts and sent to different xpaths";
    argument "data-split";
  }
 
  extension dt-convert-function {
    description "Function that needs to be invoked for datatype convertion";
    argument "name";
  }

  extension category {
    description "Function category for the manual callback";
    argument "name";
  }

  extension package-name {
    description "Package name which uniquely identifies the files generated per project";
    argument "package-name";
  }

  extension telemetry-package-name {
    description "Package name to be used for telemetry.";
    argument "package-name";
  }
      
  extension mapdeviation { 
    description "Package name which uniquely identifies the files generated per project";
  }

extension deviate-operation {
    description "Package name which uniquely identifies the files generated per project";
    argument "operation";
  }

  extension deviate-onwhat {
    description "Package name which uniquely identifies the files generated per project";
    argument "yang-stat";
  }

  extension deviate-value {
    description "Package name which uniquely identifies the files generated per project";
    argument "yang-stat-arg";
  }

  extension duplicate {
    description "duplicate this node";
    argument "xpath";
  }

  extension path-attributes {
    description "Contains sub-statments defining the attributes of the target node";
  }

  extension node-key {
    description "Define whether the target node is a key node or not";
    argument "boolean";
  }

  extension telemetry-not-supported {
      description "The parent data node is not supported in telemetry. Use " +  
                "this extension to mark nodes that will not be supported in telemetry " +
                "for example oper nodes that map to config or other oper nodes that " +
                "should be not be considered. If this extension is present under " +
                "a container or list, the children will not be included in the output.";
  }

  extension edm-callback {
    description "Indicate node is served by edm-callback for telemetry purpose";
  }

  extension xr-component {
    description "component name of XR that owned this node mapping";
    argument "name";
  }

  extension pathformat {
    argument "format";
    description "Format string specifying format of naming
                 attributes of element's SysDB path section.";
  }
}
