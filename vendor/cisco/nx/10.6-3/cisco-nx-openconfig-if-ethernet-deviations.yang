module cisco-nx-openconfig-if-ethernet-deviations {

  namespace "http://openconfig.net/yang/interfaces/ethernet-deviations";

  prefix "oc-eth-devs";


  import iana-if-type { prefix ianaift; }
  import ietf-interfaces { prefix if; }
  import ietf-yang-types { prefix yang; }
  import openconfig-extensions { prefix oc-ext; }
  import openconfig-if-ethernet { prefix oc-eth; }
  import openconfig-interfaces { prefix oc-if; }
  import openconfig-platform-types { prefix oc-platform-types; }
  import openconfig-transport-types { prefix oc-opt-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-if-ethernet module 
     set for Cisco NXOS.
     Copyright (c) 2015-2026 by Cisco Systems, Inc.
     All rights reserved.";

  revision 2026-04-24 {
    description
      "Deviation applicable to NXOS";
  }


  deviation /oc-if:interfaces/oc-if:interface/oc-eth:ethernet/oc-eth:config/oc-eth:fec-mode {
    //! NOTE_FEATURE_EXIST TRUE
    //! NOTE_DME_DONE      TRUE
    //! NOTE_COMMENT       ""
    deviate not-supported;
  }

  deviation /oc-if:interfaces/oc-if:interface/oc-eth:ethernet/oc-eth:config/oc-eth:standalone-link-training {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-8021q-frames {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-block-errors {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-carrier-errors {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-interrupted-tx {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-late-collision {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-mac-errors-rx {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-single-collision {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-symbol-error {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:in-undersize-frames {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:out-8021q-frames {
    //! NOTE_FEATURE_EXIST TRUE
    //! NOTE_DME_DONE      TRUE
    //! NOTE_COMMENT       ""
    deviate not-supported;
  }

  deviation /oc-if:interfaces/oc-if:interface/oc-eth:ethernet/oc-eth:state/oc-eth:counters/oc-eth:out-mac-errors-tx {
    //! NOTE_FEATURE_EXIST TRUE
    //! NOTE_DME_DONE      TRUE
    //! NOTE_COMMENT       ""
    deviate not-supported;
  }

  deviation /oc-if:interfaces/oc-if:interface/oc-eth:ethernet/oc-eth:state/oc-eth:fec-mode {
    //! NOTE_FEATURE_EXIST TRUE
    //! NOTE_DME_DONE      TRUE
    //! NOTE_COMMENT       ""
    deviate not-supported;
  }

  deviation /oc-if:interfaces/oc-if:interface/oc-eth:ethernet/oc-eth:state/oc-eth:standalone-link-training {
    //! NOTE_FEATURE_EXIST TRUE
    //! NOTE_DME_DONE      TRUE
    //! NOTE_COMMENT       ""
    deviate not-supported;
  }


}
