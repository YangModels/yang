module cisco-nx-openconfig-lacp-deviations {

  namespace "http://openconfig.net/yang/lacp-deviations";

  prefix "oc-lacp-devs";


  import ietf-interfaces { prefix if; }
  import ietf-yang-types { prefix yang; }
  import openconfig-extensions { prefix oc-ext; }
  import openconfig-interfaces { prefix oc-if; }
  import openconfig-lacp { prefix oc-lacp; }
  import openconfig-platform-types { prefix oc-platform-types; }
  import openconfig-transport-types { prefix oc-opt-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-lacp module 
     set for Cisco NXOS.
     Copyright (c) 2015-2026 by Cisco Systems, Inc.
     All rights reserved.";

  revision 2026-04-24 {
    description
      "Deviation applicable to NXOS";
  }


  deviation /oc-lacp:lacp/oc-lacp:config/oc-lacp:system-priority {
    deviate add {
        default "32768";
        }
         deviate replace {
               type uint16 {
                    range "1 .. 65535";
               }
         }
  }

  deviation /oc-lacp:lacp/oc-lacp:interfaces/oc-lacp:interface/oc-lacp:config/oc-lacp:fallback {
    //! NOTE_FEATURE_EXIST TRUE
    //! NOTE_DME_DONE      TRUE
    //! NOTE_COMMENT       ""
    deviate not-supported;
  }

  deviation /oc-lacp:lacp/oc-lacp:interfaces/oc-lacp:interface/oc-lacp:config/oc-lacp:system-id-mac {
    //! NOTE_FEATURE_EXIST TRUE
    //! NOTE_DME_DONE      TRUE
    //! NOTE_COMMENT       ""
    deviate not-supported;
  }

  deviation /oc-lacp:lacp/oc-lacp:interfaces/oc-lacp:interface/oc-lacp:config/oc-lacp:system-priority {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:config/oc-lacp:interface {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:config/oc-lacp:port-priority {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:state/oc-lacp:counters/oc-lacp:lacp-timeout-transitions {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:state/oc-lacp:last-change {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:state/oc-lacp:partner-port-priority {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:state/oc-lacp:port-priority {
    //! NOTE_FEATURE_EXIST TRUE
    //! NOTE_DME_DONE      TRUE
    //! NOTE_COMMENT       ""
    deviate not-supported;
  }

  deviation /oc-lacp:lacp/oc-lacp:interfaces/oc-lacp:interface/oc-lacp:members/oc-lacp:member/oc-lacp:state/oc-lacp:system-id {
    //! NOTE_FEATURE_EXIST TRUE
    //! NOTE_DME_DONE      TRUE
    //! NOTE_COMMENT       ""
    deviate not-supported;
  }

  deviation /oc-lacp:lacp/oc-lacp:interfaces/oc-lacp:interface/oc-lacp:state/oc-lacp:fallback {
    //! NOTE_FEATURE_EXIST TRUE
    //! NOTE_DME_DONE      TRUE
    //! NOTE_COMMENT       ""
    deviate not-supported;
  }

  deviation /oc-lacp:lacp/oc-lacp:interfaces/oc-lacp:interface/oc-lacp:state/oc-lacp:system-id-mac {
    //! NOTE_FEATURE_EXIST TRUE
    //! NOTE_DME_DONE      TRUE
    //! NOTE_COMMENT       ""
    deviate not-supported;
  }

  deviation /oc-lacp:lacp/oc-lacp:interfaces/oc-lacp:interface/oc-lacp:state/oc-lacp:system-priority {
    //! NOTE_FEATURE_EXIST TRUE
    //! NOTE_DME_DONE      TRUE
    //! NOTE_COMMENT       ""
    deviate not-supported;
  }

  deviation /oc-lacp:lacp/oc-lacp:state/oc-lacp:system-priority {
    deviate add {
        default "32768";
        }
         deviate replace {
               type uint16 {
                    range "1 .. 65535";
               }
         }
  }


}
