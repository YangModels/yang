module cisco-nx-openconfig-network-instance-policy-deviations {

  namespace "http://openconfig.net/yang/network-instance/policy-deviations";

  prefix "oc-ni-pol-devs";


  import ietf-interfaces { prefix if; }
  import ietf-yang-types { prefix yang; }
  import openconfig-extensions { prefix oc-ext; }
  import openconfig-inet-types { prefix oc-inet; }
  import openconfig-interfaces { prefix oc-if; }
  import openconfig-network-instance-policy { prefix oc-ni-pol; }
  import openconfig-platform-types { prefix oc-platform-types; }
  import openconfig-policy-types { prefix oc-pol-types; }
  import openconfig-routing-policy { prefix oc-rpol; }
  import openconfig-transport-types { prefix oc-opt-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-network-instance-policy module 
     set for Cisco NXOS.
     Copyright (c) 2015-2026 by Cisco Systems, Inc.
     All rights reserved.";

  revision 2026-04-24 {
    description
      "Deviation applicable to NXOS";
  }


  deviation /oc-rpol:routing-policy/oc-rpol:policy-definitions/oc-rpol:policy-definition/oc-rpol:statements/oc-rpol:statement/oc-rpol:conditions/oc-ni-pol:match-protocol-instance/oc-ni-pol:config/oc-ni-pol:protocol-identifier {
    deviate add {
          must "../oc-ni-pol:protocol-identifier='oc-pol-types:BGP' or ../oc-ni-pol:protocol-identifier='oc-pol-types:ISIS' or ../oc-ni-pol:protocol-identifier='oc-pol-types:OSPF' or ../oc-ni-pol:protocol-identifier='oc-pol-types:OSPF3' or ../oc-ni-pol:protocol-identifier='oc-pol-types:STATIC' or ../oc-ni-pol:protocol-identifier='oc-pol-types:DIRECTLY_CONNECTED' or ../oc-ni-pol:protocol-identifier='oc-pol-types:LOCAL_AGGREGATE'" {
            error-message "Only supports BGP, ISIS, OSPF, OSPF3, STATIC, DIRECTLY_CONNECTED and LOCAL_AGGREGATE on device model";
          }
        }
  }


}
