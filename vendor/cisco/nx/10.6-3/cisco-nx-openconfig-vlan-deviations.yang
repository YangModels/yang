module cisco-nx-openconfig-vlan-deviations {

  namespace "http://openconfig.net/yang/vlan-deviations";

  prefix "oc-vlan-devs";


  import iana-if-type { prefix ianaift; }
  import ietf-interfaces { prefix if; }
  import ietf-yang-types { prefix yang; }
  import openconfig-extensions { prefix oc-ext; }
  import openconfig-if-aggregate { prefix oc-lag; }
  import openconfig-if-ethernet { prefix oc-eth; }
  import openconfig-interfaces { prefix oc-if; }
  import openconfig-platform-types { prefix oc-platform-types; }
  import openconfig-transport-types { prefix oc-opt-types; }
  import openconfig-types { prefix oc-types; }
  import openconfig-vlan-types { prefix oc-vlan-types; }
  import openconfig-vlan { prefix oc-vlan; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-vlan module 
     set for Cisco NXOS.
     Copyright (c) 2015-2026 by Cisco Systems, Inc.
     All rights reserved.";

  revision 2026-04-24 {
    description
      "Deviation applicable to NXOS";
  }


  deviation /oc-if:interfaces/oc-if:interface/oc-if:config/oc-vlan:tpid {
    deviate add {
          must "../oc-vlan:tpid='oc-vlan-types:TPID_0X8100' or ../oc-vlan:tpid='oc-vlan-types:TPID_0X9100'" {
      		error-message "Only supports TPID_0X8100, TPID_0X9100 on device model";
          }
        }
  }

  deviation /oc-if:interfaces/oc-if:interface/oc-if:subinterfaces/oc-if:subinterface/oc-vlan:vlan/oc-vlan:egress-mapping/oc-vlan:config/oc-vlan:tpid {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:egress-mapping/oc-vlan:config/oc-vlan:vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:egress-mapping/oc-vlan:config/oc-vlan:vlan-stack-action {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:egress-mapping/oc-vlan:state/oc-vlan:tpid {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:egress-mapping/oc-vlan:state/oc-vlan:vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:egress-mapping/oc-vlan:state/oc-vlan:vlan-stack-action {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:config/oc-vlan:tpid {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:config/oc-vlan:vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:config/oc-vlan:vlan-stack-action {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:state/oc-vlan:tpid {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:state/oc-vlan:vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:ingress-mapping/oc-vlan:state/oc-vlan:vlan-stack-action {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-list/oc-vlan:config/oc-vlan:inner-vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-list/oc-vlan:config/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-list/oc-vlan:state/oc-vlan:inner-vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-list/oc-vlan:state/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:config/oc-vlan:inner-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:config/oc-vlan:inner-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:config/oc-vlan:outer-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:config/oc-vlan:outer-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:state/oc-vlan:inner-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:state/oc-vlan:inner-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:state/oc-vlan:outer-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-outer-range/oc-vlan:state/oc-vlan:outer-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:config/oc-vlan:inner-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:config/oc-vlan:inner-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:config/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:state/oc-vlan:inner-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:state/oc-vlan:inner-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-inner-range/oc-vlan:state/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-list/oc-vlan:config/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-list/oc-vlan:config/oc-vlan:outer-vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-list/oc-vlan:state/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-list/oc-vlan:state/oc-vlan:outer-vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:config/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:config/oc-vlan:outer-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:config/oc-vlan:outer-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:state/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:state/oc-vlan:outer-high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged-outer-range/oc-vlan:state/oc-vlan:outer-low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged/oc-vlan:config/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged/oc-vlan:config/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged/oc-vlan:state/oc-vlan:inner-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:double-tagged/oc-vlan:state/oc-vlan:outer-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-list/oc-vlan:config/oc-vlan:vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-list/oc-vlan:state/oc-vlan:vlan-ids {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-range/oc-vlan:config/oc-vlan:high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-range/oc-vlan:config/oc-vlan:low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-range/oc-vlan:state/oc-vlan:high-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged-range/oc-vlan:state/oc-vlan:low-vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged/oc-vlan:config/oc-vlan:vlan-id {
    //! NOTE_FEATURE_EXIST TRUE
    //! NOTE_DME_DONE      TRUE
    //! NOTE_COMMENT       ""
    deviate not-supported;
  }

  deviation /oc-if:interfaces/oc-if:interface/oc-if:subinterfaces/oc-if:subinterface/oc-vlan:vlan/oc-vlan:match/oc-vlan:single-tagged/oc-vlan:state/oc-vlan:vlan-id {
    //! NOTE_FEATURE_EXIST TRUE
    //! NOTE_DME_DONE      TRUE
    //! NOTE_COMMENT       ""
    deviate not-supported;
  }


}
