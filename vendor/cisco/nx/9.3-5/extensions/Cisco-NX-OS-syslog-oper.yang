module Cisco-NX-OS-syslog-oper {

  namespace "http://cisco.com/ns/yang/cisco-nx-os-syslog-oper";

  prefix "syslog-oper";

  organization "Cisco Systems, Inc.";

  contact 
    "Cisco Systems, Inc.
    Customer Service

    Postal: 170 W Tasman Drive, 
    San Jose, CA 95134

    Tel: +1 800 553-NETS

    E-mail: cs-yang@cisco.com";

  description 
    "This module contains a collection of YANG definitions for Cisco NXOS 
     syslog package operational data.

     NOTE:
       - Supported only by gNMI and telemetry agents.
       - Supports only subscription on-change.
       - Returns an error if used otherwise.";

  revision "2019-08-15" {
    description
      "Schema added for syslog messages operational data";
  }

  typedef System-message-severity {
    type enumeration {
      enum message-severity-unknown {
        value -1;
        description "Unknown";
      }
      enum message-severity-emergency {
        value 0;
        description "Emergency";
      }
      enum message-severity-alert {
        value 1;
        description "Alert";
      }
      enum message-severity-critical {
        value 2;
        description "Critical";
      }
      enum message-severity-error {
        value 3;
        description "Error";
      }
      enum message-severity-warning {
        value 4;
        description "Warning";
      }
      enum message-severity-notice {
        value 5;
        description "Notice";
      }
      enum message-severity-informational {
        value 6;
        description "Informational";
      }
      enum message-severity-debug {
        value 7;
        description "Debug";
      }
    }
    description "System message severity";
  }

  grouping SYSTEM-MESSAGE {
    description "System message";
    leaf node-name {
      type string;
      description "Message source location";
    }
    leaf time-stamp {
      type uint64;
      units "millisecond";
      description
        "Time in milliseconds since 00:00:00 UTC, January
        11970 of when message was generated";
    }
    leaf time-of-day {
      type string;
      description
        "Time of day of event in DDD MMM DD  YYYY HH:MM
        :SS format, e.g Wed Apr 01 2009  15:50:26";
    }
    leaf time-zone {
      type string;
      description
        "Time Zone Abbreviations, e.g., PST, EST, UTC, etc.";
    }
    leaf category {
      type string;
      description "Message category";
    }
    leaf group {
      type string;
      description "Message group";
    }
    leaf message-name {
      type string;
      description "Message name";
    }
    leaf severity {
      type System-message-severity;
      description "Message severity";
    }
    leaf text {
      type string;
      description "Additional message text";
    }
  }

  container syslog {
    config false;
    description "syslog";
    container messages {
      description "Message table information";

      list message {
        key "message-id";
        description "A system message";
        leaf message-id {
          type int32;
          description "Message ID of the system message";
        }
        uses SYSTEM-MESSAGE;
      }
    }
  }
}
