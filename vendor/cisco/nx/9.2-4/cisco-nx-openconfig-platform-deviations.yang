module cisco-nx-openconfig-platform-deviations {

  namespace "http://openconfig.net/yang/platform-deviations";

  prefix "oc-platform-devs";

  import openconfig-platform { prefix oc-platform; }
  import openconfig-platform-types { prefix oc-platform-types; }
  import openconfig-types { prefix oc-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform module 
     set for Cisco NXOS.
     Copyright (c) 2015-2017 by Cisco Systems, Inc.
     All rights reserved.";

  revision "2018-05-10" {
    description
      "Initial revision applicable to NXOS";
  }

  deviation /oc-platform:components/oc-platform:component/oc-platform:config/oc-platform:name {
    deviate "not-supported"; 
  }
  deviation /oc-platform:components/oc-platform:component/oc-platform:state/oc-platform:firmware-version {
    deviate "not-supported"; 
  }
  deviation /oc-platform:components/oc-platform:component/oc-platform:state/oc-platform:temperature {
    deviate "not-supported"; 
  }
  deviation /oc-platform:components/oc-platform:component/oc-platform:state/oc-platform:cpu/oc-platform:utilization {
    deviate "not-supported"; 
  }
  deviation /oc-platform:components/oc-platform:component/oc-platform:state/oc-platform:memory/oc-platform:available {
    deviate "not-supported"; 
  }
  deviation /oc-platform:components/oc-platform:component/oc-platform:state/oc-platform:memory/oc-platform:utilized {
    deviate "not-supported"; 
  }
  deviation /oc-platform:components/oc-platform:component/oc-platform:state/oc-platform:allocated-power {
    deviate "not-supported"; 
  }
  deviation /oc-platform:components/oc-platform:component/oc-platform:state/oc-platform:used-power {
    deviate "not-supported"; 
  }
  deviation /oc-platform:components/oc-platform:component/oc-platform:properties/oc-platform:property {
    deviate "not-supported"; 
  }
  deviation /oc-platform:components/oc-platform:component/oc-platform:subcomponents/oc-platform:subcomponent {
    deviate "not-supported"; 
  }
  deviation /oc-platform:components/oc-platform:component/oc-platform:chassis {
    deviate "not-supported"; 
  }
  deviation /oc-platform:components/oc-platform:component/oc-platform:power-supply {
    deviate "not-supported"; 
  }
  deviation /oc-platform:components/oc-platform:component/oc-platform:fan {
    deviate "not-supported"; 
  }
  deviation /oc-platform:components/oc-platform:component/oc-platform:fabric {
    deviate "not-supported"; 
  }
  deviation /oc-platform:components/oc-platform:component/oc-platform:storage {
    deviate "not-supported"; 
  }
  deviation /oc-platform:components/oc-platform:component/oc-platform:cpu {
    deviate "not-supported"; 
  }
  deviation /oc-platform:components/oc-platform:component/oc-platform:integrated-circuit {
    deviate "not-supported"; 
  }
  deviation /oc-platform:components/oc-platform:component/oc-platform:backplane {
    deviate "not-supported"; 
  }

}
