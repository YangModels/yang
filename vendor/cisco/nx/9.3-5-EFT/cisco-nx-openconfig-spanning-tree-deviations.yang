module cisco-nx-openconfig-spanning-tree-deviations {

  namespace "http://openconfig.net/yang/spanning-tree-deviations";

  prefix "oc-stp-devs";

  import openconfig-spanning-tree { prefix oc-stp; }

  import openconfig-spanning-tree-types { prefix oc-stp-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-spanning-tree module 
     set for Cisco NXOS.
     Copyright (c) 2015-2017 by Cisco Systems, Inc.
     All rights reserved.";

  revision "2018-02-07" {
    description
      "Initial revision applicable to NXOS";
  }
  deviation /oc-stp:stp/oc-stp:global/oc-stp:config/oc-stp:enabled-protocol { 
    deviate add {
      max-elements 1;
      must "../oc-stp:enabled-protocol='oc-stp-types:MSTP' 
         or ../oc-stp:enabled-protocol='oc-stp-types:RAPID_PVST'" {
      error-message "Only supports MSTP or RAPID_PVST";
      }
    }
  }
  deviation /oc-stp:stp/oc-stp:global/oc-stp:config/oc-stp:etherchannel-misconfig-guard {
    deviate "not-supported"; 
  }
  deviation /oc-stp:stp/oc-stp:global/oc-stp:config/oc-stp:bpduguard-timeout-recovery {
    deviate "not-supported"; 
  }
  deviation /oc-stp:stp/oc-stp:global/oc-stp:state/oc-stp:etherchannel-misconfig-guard {
    deviate "not-supported"; 
  }
  deviation /oc-stp:stp/oc-stp:global/oc-stp:state/oc-stp:bpduguard-timeout-recovery {
    deviate "not-supported"; 
  }
  deviation /oc-stp:stp/oc-stp:rstp/oc-stp:config/oc-stp:hello-time {
    deviate "not-supported"; 
  }
  deviation /oc-stp:stp/oc-stp:rstp/oc-stp:config/oc-stp:max-age {
    deviate "not-supported"; 
  }
  deviation /oc-stp:stp/oc-stp:rstp/oc-stp:config/oc-stp:forwarding-delay {
    deviate "not-supported"; 
  }
  deviation /oc-stp:stp/oc-stp:rstp/oc-stp:config/oc-stp:hold-count {
    deviate "not-supported"; 
  }
  deviation /oc-stp:stp/oc-stp:rstp/oc-stp:config/oc-stp:bridge-priority {
    deviate "not-supported"; 
  }
  deviation /oc-stp:stp/oc-stp:rstp/oc-stp:state/oc-stp:hello-time {
    deviate "not-supported"; 
  }
  deviation /oc-stp:stp/oc-stp:rstp/oc-stp:state/oc-stp:max-age {
    deviate "not-supported"; 
  }
  deviation /oc-stp:stp/oc-stp:rstp/oc-stp:state/oc-stp:forwarding-delay {
    deviate "not-supported"; 
  }
  deviation /oc-stp:stp/oc-stp:rstp/oc-stp:state/oc-stp:hold-count {
    deviate "not-supported"; 
  }
  deviation /oc-stp:stp/oc-stp:rstp/oc-stp:state/oc-stp:bridge-priority {
    deviate "not-supported"; 
  }
  deviation /oc-stp:stp/oc-stp:rstp/oc-stp:state/oc-stp:bridge-address {
    deviate "not-supported"; 
  }
  deviation /oc-stp:stp/oc-stp:rstp/oc-stp:state/oc-stp:designated-root-priority {
    deviate "not-supported"; 
  }
  deviation /oc-stp:stp/oc-stp:rstp/oc-stp:state/oc-stp:designated-root-address {
    deviate "not-supported"; 
  }
  deviation /oc-stp:stp/oc-stp:rstp/oc-stp:state/oc-stp:root-port {
    deviate "not-supported"; 
  }
  deviation /oc-stp:stp/oc-stp:rstp/oc-stp:state/oc-stp:root-cost {
    deviate "not-supported"; 
  }
  deviation /oc-stp:stp/oc-stp:rstp/oc-stp:state/oc-stp:hold-time {
    deviate "not-supported"; 
  }
  deviation /oc-stp:stp/oc-stp:rstp/oc-stp:state/oc-stp:topology-changes {
    deviate "not-supported"; 
  }
  deviation /oc-stp:stp/oc-stp:rstp/oc-stp:state/oc-stp:last-topology-change {
    deviate "not-supported"; 
  }
  deviation /oc-stp:stp/oc-stp:rstp/oc-stp:interfaces/oc-stp:interface {
    deviate "not-supported"; 
  }
  deviation /oc-stp:stp/oc-stp:mstp/oc-stp:config/oc-stp:hold-count {
    deviate "not-supported"; 
  }
  deviation /oc-stp:stp/oc-stp:mstp/oc-stp:state/oc-stp:hold-count {
    deviate "not-supported"; 
  }
  deviation /oc-stp:stp/oc-stp:rapid-pvst/oc-stp:vlan/oc-stp:config/oc-stp:hold-count {
    deviate "not-supported"; 
  }
  deviation /oc-stp:stp/oc-stp:rapid-pvst/oc-stp:vlan/oc-stp:state/oc-stp:hold-count {
    deviate "not-supported"; 
  }
  deviation /oc-stp:stp/oc-stp:mstp/oc-stp:mst-instances/oc-stp:mst-instance/oc-stp:config/oc-stp:bridge-priority {
    deviate add {
      must "../oc-stp:bridge-priority='oc-stp-types:stp-bridge-priority-type:0' 
         or ../oc-stp:bridge-priority='oc-stp-types:stp-bridge-priority-type:4096'
         or ../oc-stp:bridge-priority='oc-stp-types:stp-bridge-priority-type:8192'
         or ../oc-stp:bridge-priority='oc-stp-types:stp-bridge-priority-type:12288'
         or ../oc-stp:bridge-priority='oc-stp-types:stp-bridge-priority-type:16384'
         or ../oc-stp:bridge-priority='oc-stp-types:stp-bridge-priority-type:20480'
         or ../oc-stp:bridge-priority='oc-stp-types:stp-bridge-priority-type:24576'
         or ../oc-stp:bridge-priority='oc-stp-types:stp-bridge-priority-type:28672'
         or ../oc-stp:bridge-priority='oc-stp-types:stp-bridge-priority-type:32768'
         or ../oc-stp:bridge-priority='oc-stp-types:stp-bridge-priority-type:36864'
         or ../oc-stp:bridge-priority='oc-stp-types:stp-bridge-priority-type:40960'
         or ../oc-stp:bridge-priority='oc-stp-types:stp-bridge-priority-type:45056'
         or ../oc-stp:bridge-priority='oc-stp-types:stp-bridge-priority-type:49152'
         or ../oc-stp:bridge-priority='oc-stp-types:stp-bridge-priority-type:53248'
         or ../oc-stp:bridge-priority='oc-stp-types:stp-bridge-priority-type:57344'
         or ../oc-stp:bridge-priority='oc-stp-types:stp-bridge-priority-type:61440'" {
  		error-message "Only supports 0 4096 8192 12288 16384 20480 24576 28672 32768 36864 40960 45056 49152 53248 57344 61440 on device model";
      }     
    }
  }
  deviation /oc-stp:stp/oc-stp:rapid-pvst/oc-stp:vlan/oc-stp:config/oc-stp:bridge-priority {
    deviate add {
      must "../oc-stp:bridge-priority='oc-stp-types:stp-bridge-priority-type:0' 
         or ../oc-stp:bridge-priority='oc-stp-types:stp-bridge-priority-type:4096'
         or ../oc-stp:bridge-priority='oc-stp-types:stp-bridge-priority-type:8192'
         or ../oc-stp:bridge-priority='oc-stp-types:stp-bridge-priority-type:12288'
         or ../oc-stp:bridge-priority='oc-stp-types:stp-bridge-priority-type:16384'
         or ../oc-stp:bridge-priority='oc-stp-types:stp-bridge-priority-type:20480'
         or ../oc-stp:bridge-priority='oc-stp-types:stp-bridge-priority-type:24576'
         or ../oc-stp:bridge-priority='oc-stp-types:stp-bridge-priority-type:28672'
         or ../oc-stp:bridge-priority='oc-stp-types:stp-bridge-priority-type:32768'
         or ../oc-stp:bridge-priority='oc-stp-types:stp-bridge-priority-type:36864'
         or ../oc-stp:bridge-priority='oc-stp-types:stp-bridge-priority-type:40960'
         or ../oc-stp:bridge-priority='oc-stp-types:stp-bridge-priority-type:45056'
         or ../oc-stp:bridge-priority='oc-stp-types:stp-bridge-priority-type:49152'
         or ../oc-stp:bridge-priority='oc-stp-types:stp-bridge-priority-type:53248'
         or ../oc-stp:bridge-priority='oc-stp-types:stp-bridge-priority-type:57344'
         or ../oc-stp:bridge-priority='oc-stp-types:stp-bridge-priority-type:61440'" {
  		error-message "Only supports 0 4096 8192 12288 16384 20480 24576 28672 32768 36864 40960 45056 49152 53248 57344 61440 on device model";
      }     
    }
  }

}
