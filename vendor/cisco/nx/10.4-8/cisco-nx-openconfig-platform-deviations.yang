module cisco-nx-openconfig-platform-deviations {

  namespace "http://openconfig.net/yang/platform-deviations";

  prefix "oc-platform-devs";

  import openconfig-platform { prefix oc-platform; }
  import openconfig-alarm-types { prefix oc-alarm-types; }
  import openconfig-extensions { prefix oc-ext; }
  import openconfig-platform-types { prefix oc-platform-types; }
  import openconfig-yang-types { prefix oc-yang; }
  import openconfig-types { prefix oc-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform module 
     set for Cisco NXOS.
     Copyright (c) 2015-2017, 2019 by Cisco Systems, Inc.
     All rights reserved.";

  revision "2019-09-23" {
    description
      "Initial revision applicable to NXOS";
  }

  deviation /oc-platform:components/oc-platform:component/oc-platform:config/oc-platform:name {
    deviate "not-supported"; 
  }
  deviation /oc-platform:components/oc-platform:component/oc-platform:state/oc-platform:firmware-version {
    deviate "not-supported"; 
  }
  deviation /oc-platform:components/oc-platform:component/oc-platform:state/oc-platform:clei-code {
    deviate "not-supported";
  }
  deviation /oc-platform:components/oc-platform:component/oc-platform:state/oc-platform:parent {
    deviate "not-supported"; 
  }
  deviation /oc-platform:components/oc-platform:component/oc-platform:state/oc-platform:temperature/oc-platform:avg {
    deviate "not-supported"; 
  }
  deviation /oc-platform:components/oc-platform:component/oc-platform:state/oc-platform:temperature/oc-platform:min {
    deviate "not-supported"; 
  }
  deviation /oc-platform:components/oc-platform:component/oc-platform:state/oc-platform:temperature/oc-platform:max {
    deviate "not-supported"; 
  }
  deviation /oc-platform:components/oc-platform:component/oc-platform:state/oc-platform:temperature/oc-platform:interval {
    deviate "not-supported"; 
  }
  deviation /oc-platform:components/oc-platform:component/oc-platform:state/oc-platform:temperature/oc-platform:min-time {
    deviate "not-supported"; 
  }
  deviation /oc-platform:components/oc-platform:component/oc-platform:state/oc-platform:temperature/oc-platform:max-time {
    deviate "not-supported"; 
  }
  deviation /oc-platform:components/oc-platform:component/oc-platform:properties/oc-platform:property {
    deviate "not-supported"; 
  }
  deviation /oc-platform:components/oc-platform:component/oc-platform:subcomponents/oc-platform:subcomponent {
    deviate "not-supported"; 
  }

  deviation /oc-platform:components/oc-platform:component/oc-platform:state/oc-platform:redundant-role {
      deviate "not-supported";
  }
  deviation /oc-platform:components/oc-platform:component/oc-platform:state/oc-platform:last-switchover-reason{
      deviate "not-supported";
  }

  deviation /oc-platform:components/oc-platform:component/oc-platform:state/oc-platform:last-switchover-time {
      deviate "not-supported";
  }
  deviation /oc-platform:components/oc-platform:component/oc-platform:state/oc-platform:last-reboot-reason {
      deviate "not-supported";
  }
  deviation /oc-platform:components/oc-platform:component/oc-platform:state/oc-platform:last-reboot-time {
      deviate "not-supported";
  }
  deviation /oc-platform:components/oc-platform:component/oc-platform:state/oc-platform:switchover-ready{
      deviate "not-supported";
  }
  deviation /oc-platform:components/oc-platform:component/oc-platform:state/oc-platform:base-mac-address {
      deviate "not-supported";
  }
  deviation /oc-platform:components/oc-platform:component/oc-platform:state/oc-platform:pcie{
      deviate "not-supported";
  }
  deviation /oc-platform:components/oc-platform:component/oc-platform:chassis/oc-platform:utilization {
      deviate "not-supported";
  }
  deviation /oc-platform:components/oc-platform:component/oc-platform:integrated-circuit/oc-platform:utilization {
      deviate "not-supported";
  }
  deviation /oc-platform:components/oc-platform:component/oc-platform:controller-card {
      deviate "not-supported";
  }
  deviation /oc-platform:components/oc-platform:component/oc-platform:software-module {
      deviate "not-supported";
  }

}
