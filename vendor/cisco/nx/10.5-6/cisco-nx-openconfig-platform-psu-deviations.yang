module cisco-nx-openconfig-platform-psu-deviations {

  namespace "http://openconfig.net/yang/platform/psu-deviations";

  prefix "oc-platform-psu-devs";

  import openconfig-platform-psu { prefix oc-platform-psu; }
  import openconfig-extensions { prefix oc-ext; }
  import openconfig-platform { prefix oc-platform; }
  import openconfig-types { prefix oc-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform-psu module 
     set for Cisco NXOS.
     Copyright (c) 2015-2017, 2019 by Cisco Systems, Inc.
     All rights reserved.";

  revision "2019-09-23" {
    description
      "Initial revision applicable to NXOS";
  }

  deviation /oc-platform:components/oc-platform:component/oc-platform:power-supply/oc-platform:config/oc-platform-psu:enabled {
    deviate "not-supported"; 
  }

}
