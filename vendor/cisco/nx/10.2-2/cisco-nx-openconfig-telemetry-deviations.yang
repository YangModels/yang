module cisco-nx-openconfig-telemetry-deviations {

  namespace "http://openconfig.net/yang/telemetry-deviations";

  prefix "oc-telemetry-devs";

  import openconfig-telemetry { prefix oc-telemetry; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-telemetry module 
     set for Cisco NXOS.
     Copyright (c) 2015-2019, 2021 by Cisco Systems, Inc.
     All rights reserved.";

  revision "2018-12-14" {
    description
      "Initial revision applicable to NXOS";
  }

  deviation /oc-telemetry:telemetry-system/oc-telemetry:sensor-groups/oc-telemetry:sensor-group/oc-telemetry:config/oc-telemetry:sensor-group-id {
    deviate replace {
      type string {
        length "1..32";
      }
    }
  }

  deviation /oc-telemetry:telemetry-system/oc-telemetry:sensor-groups/oc-telemetry:sensor-group/oc-telemetry:sensor-paths/oc-telemetry:sensor-path/oc-telemetry:config/oc-telemetry:exclude-filter {
    //! NOTE_FEATURE_EXIST FALSE
    //! NOTE_DME_DONE      FALSE
    //! NOTE_COMMENT       ""
    deviate not-supported;
  }

  deviation /oc-telemetry:telemetry-system/oc-telemetry:sensor-groups/oc-telemetry:sensor-group/oc-telemetry:sensor-paths/oc-telemetry:sensor-path/oc-telemetry:state/oc-telemetry:exclude-filter {
    //! NOTE_FEATURE_EXIST FALSE
    //! NOTE_DME_DONE      FALSE
    //! NOTE_COMMENT       ""
    deviate not-supported;
  }

  deviation /oc-telemetry:telemetry-system/oc-telemetry:destination-groups/oc-telemetry:destination-group/oc-telemetry:config/oc-telemetry:group-id {
    deviate replace {
      type string {
        length "1..32";
      }
    }
  }
  deviation /oc-telemetry:telemetry-system/oc-telemetry:subscriptions/oc-telemetry:persistent-subscriptions/oc-telemetry:persistent-subscription/oc-telemetry:config/oc-telemetry:name {
    deviate replace {
      type string {
        pattern "[0-9]*";
      }
    }
  }

  deviation /oc-telemetry:telemetry-system/oc-telemetry:subscriptions/oc-telemetry:persistent-subscriptions/oc-telemetry:persistent-subscription/oc-telemetry:config/oc-telemetry:local-source-address {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:state/oc-telemetry:local-source-address {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:config/oc-telemetry:originated-qos-marking {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:state/oc-telemetry:originated-qos-marking {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:config/oc-telemetry:protocol {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:state/oc-telemetry:protocol {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:config/oc-telemetry:encoding {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:state/oc-telemetry:encoding {
    //! NOTE_FEATURE_EXIST FALSE
    //! NOTE_DME_DONE      FALSE
    //! NOTE_COMMENT       ""
    deviate not-supported;
  }

  deviation /oc-telemetry:telemetry-system/oc-telemetry:subscriptions/oc-telemetry:persistent-subscriptions/oc-telemetry:persistent-subscription/oc-telemetry:sensor-profiles/oc-telemetry:sensor-profile/oc-telemetry:config/oc-telemetry:sample-interval {
    deviate replace {
      type uint64 {
        range "0 | 1000..604800000";
      }
    }
    deviate add {
      mandatory true;
    }
    description
      "Operation remove or delete sample-interval sets sample-interval to 0.";
  }

  deviation /oc-telemetry:telemetry-system/oc-telemetry:subscriptions/oc-telemetry:persistent-subscriptions/oc-telemetry:persistent-subscription/oc-telemetry:sensor-profiles/oc-telemetry:sensor-profile/oc-telemetry:config/oc-telemetry:heartbeat-interval {
    //! NOTE_FEATURE_EXIST FALSE
    //! NOTE_DME_DONE      FALSE
    //! NOTE_COMMENT       "Feature plan to be added in K+, oc-mapping TBD"
    deviate not-supported;
  }

  deviation /oc-telemetry:telemetry-system/oc-telemetry:subscriptions/oc-telemetry:persistent-subscriptions/oc-telemetry:persistent-subscription/oc-telemetry:sensor-profiles/oc-telemetry:sensor-profile/oc-telemetry:state/oc-telemetry:heartbeat-interval {
    //! NOTE_FEATURE_EXIST FALSE
    //! NOTE_DME_DONE      FALSE
    //! NOTE_COMMENT       "Feature plan to be added in K+, oc-mapping TBD"
    deviate not-supported;
  }

  deviation /oc-telemetry:telemetry-system/oc-telemetry:subscriptions/oc-telemetry:persistent-subscriptions/oc-telemetry:persistent-subscription/oc-telemetry:sensor-profiles/oc-telemetry:sensor-profile/oc-telemetry:config/oc-telemetry:suppress-redundant {
    //! NOTE_FEATURE_EXIST FALSE
    //! NOTE_DME_DONE      FALSE
    //! NOTE_COMMENT       "Feature plan to be added in K+, oc-mapping TBD"
    deviate not-supported;
  }

  deviation /oc-telemetry:telemetry-system/oc-telemetry:subscriptions/oc-telemetry:persistent-subscriptions/oc-telemetry:persistent-subscription/oc-telemetry:sensor-profiles/oc-telemetry:sensor-profile/oc-telemetry:state/oc-telemetry:suppress-redundant {
    //! NOTE_FEATURE_EXIST FALSE
    //! NOTE_DME_DONE      FALSE
    //! NOTE_COMMENT       "Feature plan to be added in K+, oc-mapping TBD"
    deviate not-supported;
  }

  deviation /oc-telemetry:telemetry-system/oc-telemetry:subscriptions/oc-telemetry:dynamic-subscriptions {
    //! NOTE_FEATURE_EXIST FALSE
    //! NOTE_DME_DONE      FALSE
    //! NOTE_COMMENT       ""
    deviate not-supported;
  }

}
