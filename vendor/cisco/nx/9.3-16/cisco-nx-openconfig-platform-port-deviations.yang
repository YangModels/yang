module cisco-nx-openconfig-platform-port-deviations {

  namespace "http://openconfig.net/yang/platform/port-deviations";

  prefix "oc-port-devs";

  import openconfig-platform-port { prefix oc-port; }
  import openconfig-if-ethernet { prefix oc-eth; }
  import openconfig-extensions { prefix oc-ext; }
  import openconfig-interfaces { prefix oc-if; }
  import openconfig-platform { prefix oc-platform; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform-port module 
     set for Cisco NXOS.
     Copyright (c) 2015-2017, 2019 by Cisco Systems, Inc.
     All rights reserved.";

  revision "2019-09-23" {
    description
      "Initial revision applicable to NXOS";
  }

  deviation /oc-if:interfaces/oc-if:interface/oc-if:state/oc-port:hardware-port {
    deviate "not-supported"; 
  }

}
