module cisco-nx-openconfig-platform-linecard-deviations {

  namespace "http://openconfig.net/yang/platform/linecard-deviations";

  prefix "oc-linecard-devs";

  import openconfig-platform-linecard { prefix oc-linecard; }
  import openconfig-extensions { prefix oc-ext; }
  import openconfig-platform { prefix oc-platform; }
  import openconfig-platform-types { prefix oc-platform-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform-linecard module 
     set for Cisco NXOS.
     Copyright (c) 2015-2017, 2019 by Cisco Systems, Inc.
     All rights reserved.";

  revision "2019-09-23" {
    description
      "Initial revision applicable to NXOS";
  }

}
