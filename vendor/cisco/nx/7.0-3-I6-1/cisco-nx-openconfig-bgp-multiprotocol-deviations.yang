module cisco-nx-openconfig-bgp-multiprotocol-deviations {

  namespace "http://openconfig.net/yang/bgp-multiprotocol-deviations";

  prefix "oc-bgp-mp-devs";

  import openconfig_bgp_multiprotocol { prefix oc-bgp-mp; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-bgp-multiprotocol module 
     set for Cisco NXOS.
     Copyright (c) 2015-2016 by Cisco Systems, Inc.
     All rights reserved.";

  revision "2017-04-20" {
    description
      "Initial revision applicable to NXOS";
  }

}
