module openconfig-macsec-deviations {
  yang-version 1;
  namespace "http://openconfig.net/yang/macsec-deviations";
  prefix oc-macsec-devs;

import openconfig-macsec { prefix oc-macsec; }
  import openconfig-extensions {
    prefix oc-ext;
  }
  import openconfig-interfaces {
    prefix oc-if;
  }
  import openconfig-macsec-types {
    prefix macsec-types;
  }
  import openconfig-yang-types {
    prefix oc-yang;
  }
  import openconfig-keychain {
    prefix oc-keychain;
  }

  organization
    "OpenConfig working group";
  contact
    "Openconfig working group
     www.openconfig.net";
  description
    "This module defines configuration and state data for
     MACsec IEEE Std 802.1AE-2018.";
  oc-ext:openconfig-version "1.0.0";
  oc-ext:regexp-posix;
  oc-ext:catalog-organization "openconfig";
  oc-ext:origin "openconfig";

  revision 2023-05-25 {
    description
      "Add Deviation File";
    reference
      "1.0.0";
  }

  deviation /oc-macsec:macsec/oc-macsec:interfaces/oc-macsec:interface/oc-macsec:mka/oc-macsec:config/oc-macsec:mka-policy{
    deviate "not-supported";
  }

  deviation /oc-macsec:macsec/oc-macsec:interfaces/oc-macsec:interface/oc-macsec:mka/oc-macsec:config/oc-macsec:key-chain{
    deviate "not-supported";
  }

  deviation /oc-macsec:macsec/oc-macsec:interfaces/oc-macsec:interface/oc-macsec:mka/oc-macsec:state/oc-macsec:counters/oc-macsec:in-cak-mkpdu{
    deviate "not-supported";
  }

  deviation /oc-macsec:macsec/oc-macsec:interfaces/oc-macsec:interface/oc-macsec:mka/oc-macsec:state/oc-macsec:counters/oc-macsec:out-cak-mkpdu{
    deviate "not-supported";
  }

  deviation /oc-macsec:macsec/oc-macsec:interfaces/oc-macsec:interface/oc-macsec:config/oc-macsec:name{
    deviate "not-supported";
  }

  deviation /oc-macsec:macsec/oc-macsec:interfaces/oc-macsec:interface/oc-macsec:config/oc-macsec:enable{
    deviate "not-supported";
  }

  deviation /oc-macsec:macsec/oc-macsec:interfaces/oc-macsec:interface/oc-macsec:config/oc-macsec:replay-protection{
    deviate "not-supported";
  }

  deviation /oc-macsec:macsec/oc-macsec:interfaces/oc-macsec:interface/oc-macsec:scsa-tx/oc-macsec:scsa-tx/oc-macsec:state/oc-macsec:sci-tx{
    deviate "not-supported";
  }

  deviation /oc-macsec:macsec/oc-macsec:interfaces/oc-macsec:interface/oc-macsec:scsa-tx/oc-macsec:scsa-tx/oc-macsec:state/oc-macsec:counters/oc-macsec:sc-auth-only{
    deviate "not-supported";
  }

  deviation /oc-macsec:macsec/oc-macsec:interfaces/oc-macsec:interface/oc-macsec:scsa-tx/oc-macsec:scsa-tx/oc-macsec:state/oc-macsec:counters/oc-macsec:sc-encrypted{
    deviate "not-supported";
  }

  deviation /oc-macsec:macsec/oc-macsec:interfaces/oc-macsec:interface/oc-macsec:scsa-tx/oc-macsec:scsa-tx/oc-macsec:state/oc-macsec:counters/oc-macsec:sa-auth-only{
    deviate "not-supported";
  }

  deviation /oc-macsec:macsec/oc-macsec:interfaces/oc-macsec:interface/oc-macsec:scsa-tx/oc-macsec:scsa-tx/oc-macsec:state/oc-macsec:counters/oc-macsec:sa-encrypted{
    deviate "not-supported";
  }

  deviation /oc-macsec:macsec/oc-macsec:interfaces/oc-macsec:interface/oc-macsec:scsa-rx/oc-macsec:scsa-rx/oc-macsec:state/oc-macsec:sci-rx{
    deviate "not-supported";
  }

  deviation /oc-macsec:macsec/oc-macsec:interfaces/oc-macsec:interface/oc-macsec:scsa-rx/oc-macsec:scsa-rx/oc-macsec:state/oc-macsec:counters/oc-macsec:sc-invalid{
    deviate "not-supported";
  }

  deviation /oc-macsec:macsec/oc-macsec:interfaces/oc-macsec:interface/oc-macsec:scsa-rx/oc-macsec:scsa-rx/oc-macsec:state/oc-macsec:counters/oc-macsec:sc-valid{
    deviate "not-supported";
  }

  deviation /oc-macsec:macsec/oc-macsec:interfaces/oc-macsec:interface/oc-macsec:scsa-rx/oc-macsec:scsa-rx/oc-macsec:state/oc-macsec:counters/oc-macsec:sa-invalid{
    deviate "not-supported";
  }

  deviation /oc-macsec:macsec/oc-macsec:interfaces/oc-macsec:interface/oc-macsec:scsa-rx/oc-macsec:scsa-rx/oc-macsec:state/oc-macsec:counters/oc-macsec:sa-valid{
    deviate "not-supported";
  }

  deviation /oc-macsec:macsec/oc-macsec:mka/oc-macsec:policies/oc-macsec:policy/oc-macsec:config/oc-macsec:name{
    deviate "not-supported";
  }

  deviation /oc-macsec:macsec/oc-macsec:mka/oc-macsec:policies/oc-macsec:policy/oc-macsec:config/oc-macsec:key-server-priority{
    deviate "not-supported";
  }

  deviation /oc-macsec:macsec/oc-macsec:mka/oc-macsec:policies/oc-macsec:policy/oc-macsec:config/oc-macsec:macsec-cipher-suite{
    deviate "not-supported";
  }

  deviation /oc-macsec:macsec/oc-macsec:mka/oc-macsec:policies/oc-macsec:policy/oc-macsec:config/oc-macsec:confidentiality-offset{
    deviate "not-supported";
  }

  deviation /oc-macsec:macsec/oc-macsec:mka/oc-macsec:policies/oc-macsec:policy/oc-macsec:config/oc-macsec:delay-protection{
    deviate "not-supported";
  }

  deviation /oc-macsec:macsec/oc-macsec:mka/oc-macsec:policies/oc-macsec:policy/oc-macsec:config/oc-macsec:include-icv-indicator{
    deviate "not-supported";
  }

  deviation /oc-macsec:macsec/oc-macsec:mka/oc-macsec:policies/oc-macsec:policy/oc-macsec:config/oc-macsec:sak-rekey-interval{
    deviate "not-supported";
  }

  deviation /oc-macsec:macsec/oc-macsec:mka/oc-macsec:policies/oc-macsec:policy/oc-macsec:config/oc-macsec:sak-rekey-on-live-peer-loss{
    deviate "not-supported";
  }

  deviation /oc-macsec:macsec/oc-macsec:mka/oc-macsec:policies/oc-macsec:policy/oc-macsec:config/oc-macsec:use-updated-eth-header{
    deviate "not-supported";
  }

  deviation /oc-macsec:macsec/oc-macsec:mka/oc-macsec:state/oc-macsec:counters/oc-macsec:out-mkpdu-errors{
    deviate "not-supported";
  }

  deviation /oc-macsec:macsec/oc-macsec:mka/oc-macsec:state/oc-macsec:counters/oc-macsec:in-mkpdu-icv-verification-errors{
    deviate "not-supported";
  }

  deviation /oc-macsec:macsec/oc-macsec:mka/oc-macsec:state/oc-macsec:counters/oc-macsec:sak-cipher-mismatch-errors{
    deviate "not-supported";
  }

  deviation /oc-macsec:macsec/oc-macsec:interfaces/oc-macsec:interface/oc-macsec:mka/oc-macsec:state/oc-macsec:mka-policy{
    deviate "not-supported";
  }

  deviation /oc-macsec:macsec/oc-macsec:mka/oc-macsec:policies/oc-macsec:policy{
    deviate "not-supported";
  }

  deviation /oc-macsec:macsec/oc-macsec:mka/oc-macsec:policies{
    deviate "not-supported";
  }

  deviation /oc-macsec:macsec/oc-macsec:interfaces/oc-macsec:interface/oc-macsec:state/oc-macsec:name{
    deviate "not-supported";
  }

  deviation /oc-macsec:macsec/oc-macsec:interfaces/oc-macsec:interface/oc-macsec:state/oc-macsec:enable{
    deviate "not-supported";
  }

  deviation /oc-macsec:macsec/oc-macsec:interfaces/oc-macsec:interface/oc-macsec:state/oc-macsec:replay-protection{
    deviate "not-supported";
  }

  deviation /oc-macsec:macsec/oc-macsec:interfaces/oc-macsec:interface/oc-macsec:scsa-tx{
    deviate "not-supported";
  }

  deviation /oc-macsec:macsec/oc-macsec:interfaces/oc-macsec:interface/oc-macsec:scsa-rx{
    deviate "not-supported";
  }

  deviation /oc-macsec:macsec/oc-macsec:interfaces/oc-macsec:interface/oc-macsec:mka/oc-macsec:state/oc-macsec:key-chain{
    deviate "not-supported";
  }
}
