module openconfig-if-rates {

  yang-version "1";

  namespace "http://openconfig.net/yang/interfaces/rates";

  prefix "oc-if-rates";

  import openconfig-extensions { prefix oc-ext; }
  import openconfig-interfaces { prefix "oc-if"; }

  organization
    "OpenConfig working group";

  contact
    "www.openconfig.net";

  description
    "This module adds configuration and operational state for interface rates.";

  oc-ext:openconfig-version "0.1.0";

  revision 2024-04-02 {
    description
      "Augment of /interfaces/interface to include interface rates.";
    reference
      "0.1.0";
  }

  grouping interface-rates-config {
    description
      "Grouping of interface rates related configuration";

    leaf load-interval {
      type uint16 {
        range "1..600";
      }
      units "seconds";
      default 300;
      description
        "The interval of interface rates calculation in seconds";
    }
  }

  grouping interface-rates-state {
    description
      "Grouping of interface rates with different direction and units";

    leaf load-interval {
      type uint16;
      units "seconds";
      description
        "The interval of interface rates calculation in seconds";
    }

    leaf out-bits-rate {
      type uint64;
      units "bps";
      description
        "The calculated transmitted rate of the interface, measured in bits
        per second.";
    }

    leaf in-bits-rate {
      type uint64;
      units "bps";
      description
        "The calculated received rate of the interface, measured in bits
        per second.";
    }

    leaf out-pkts-rate {
      type uint64;
      units "pps";
      description
        "The calculated transmitted rate of the interface, measured in packets
        per second.";
    }

    leaf in-pkts-rate {
      type uint64;
      units "pps";
      description
        "The calculated received rate of the interface, measured in packets
        per second.";
    }
  }

  augment "/oc-if:interfaces/oc-if:interface" {
    description
      "Adds interface rates.";

    container rates {
      description
        "Enclosing container for interface rates.";

      container config {
        description
          "Enclosing container for interface rates related configuration";

        uses interface-rates-config;
      }

      container state {
        config false;
        description
          "Enclosing container for operational state representing
          interface rates.";

        uses interface-rates-state;
      }
    }
  }
}
