module cisco-nx-openconfig-spanning-tree-deviations {

  namespace "http://openconfig.net/yang/spanning-tree-deviations";

  prefix "oc-stp-devs";


  import ietf-interfaces { prefix if; }
  import ietf-yang-types { prefix yang; }
  import openconfig-extensions { prefix oc-ext; }
  import openconfig-interfaces { prefix oc-if; }
  import openconfig-platform-types { prefix oc-platform-types; }
  import openconfig-spanning-tree-types { prefix oc-stp-types; }
  import openconfig-spanning-tree { prefix oc-stp; }
  import openconfig-transport-types { prefix oc-opt-types; }
  import openconfig-types { prefix oc-types; }
  import openconfig-vlan-types { prefix oc-vlan-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-spanning-tree module 
     set for Cisco NXOS.
     Copyright (c) 2015-2026 by Cisco Systems, Inc.
     All rights reserved.";

  revision 2026-08-11 {
    description
      "Deviation applicable to NXOS";
  }


  deviation /oc-stp:stp/oc-stp:global/oc-stp:config/oc-stp:bpduguard-timeout-recovery {
    //! NOTE_FEATURE_EXIST TRUE
    //! NOTE_DME_DONE      TRUE
    //! NOTE_COMMENT       ""
    deviate not-supported;
  }

  deviation /oc-stp:stp/oc-stp:global/oc-stp:config/oc-stp:enabled-protocol {
    deviate add {
          max-elements 1;
          must "../oc-stp:enabled-protocol='oc-stp-types:MSTP'
             or ../oc-stp:enabled-protocol='oc-stp-types:RAPID_PVST'" {
          error-message "Only supports MSTP or RAPID_PVST";
          }
        }
  }

  deviation /oc-stp:stp/oc-stp:global/oc-stp:config/oc-stp:etherchannel-misconfig-guard {
    //! NOTE_FEATURE_EXIST TRUE
    //! NOTE_DME_DONE      TRUE
    //! NOTE_COMMENT       ""
    deviate not-supported;
  }

  deviation /oc-stp:stp/oc-stp:global/oc-stp:state/oc-stp:bpduguard-timeout-recovery {
    //! NOTE_FEATURE_EXIST TRUE
    //! NOTE_DME_DONE      TRUE
    //! NOTE_COMMENT       ""
    deviate not-supported;
  }

  deviation /oc-stp:stp/oc-stp:global/oc-stp:state/oc-stp:etherchannel-misconfig-guard {
    //! NOTE_FEATURE_EXIST TRUE
    //! NOTE_DME_DONE      TRUE
    //! NOTE_COMMENT       ""
    deviate not-supported;
  }

  deviation /oc-stp:stp/oc-stp:mstp/oc-stp:config/oc-stp:hold-count {
    //! NOTE_FEATURE_EXIST TRUE
    //! NOTE_DME_DONE      TRUE
    //! NOTE_COMMENT       ""
    deviate not-supported;
  }

  deviation /oc-stp:stp/oc-stp:mstp/oc-stp:config/oc-stp:revision {
    deviate replace {
            type uint32 {
                range "0..65535";
            }
        }
  }

  deviation /oc-stp:stp/oc-stp:mstp/oc-stp:mst-instances/oc-stp:mst-instance/oc-stp:config/oc-stp:bridge-priority {
    deviate replace {
            type uint32 {
                range "1..61440";
            }
        }
        deviate add {
          must "../oc-stp:bridge-priority='oc-stp-types:stp-bridge-priority-type:4096'
             or ../oc-stp:bridge-priority='oc-stp-types:stp-bridge-priority-type:8192'
             or ../oc-stp:bridge-priority='oc-stp-types:stp-bridge-priority-type:12288'
             or ../oc-stp:bridge-priority='oc-stp-types:stp-bridge-priority-type:16384'
             or ../oc-stp:bridge-priority='oc-stp-types:stp-bridge-priority-type:20480'
             or ../oc-stp:bridge-priority='oc-stp-types:stp-bridge-priority-type:24576'
             or ../oc-stp:bridge-priority='oc-stp-types:stp-bridge-priority-type:28672'
             or ../oc-stp:bridge-priority='oc-stp-types:stp-bridge-priority-type:32768'
             or ../oc-stp:bridge-priority='oc-stp-types:stp-bridge-priority-type:36864'
             or ../oc-stp:bridge-priority='oc-stp-types:stp-bridge-priority-type:40960'
             or ../oc-stp:bridge-priority='oc-stp-types:stp-bridge-priority-type:45056'
             or ../oc-stp:bridge-priority='oc-stp-types:stp-bridge-priority-type:49152'
             or ../oc-stp:bridge-priority='oc-stp-types:stp-bridge-priority-type:53248'
             or ../oc-stp:bridge-priority='oc-stp-types:stp-bridge-priority-type:57344'
             or ../oc-stp:bridge-priority='oc-stp-types:stp-bridge-priority-type:61440'" {
      		error-message "Only supports 4096 8192 12288 16384 20480 24576 28672 32768 36864 40960 45056 49152 53248 57344 61440 on device model";
          }
        }
  }

  deviation /oc-stp:stp/oc-stp:mstp/oc-stp:mst-instances/oc-stp:mst-instance/oc-stp:interfaces/oc-stp:interface/oc-stp:config/oc-stp:port-priority {
    deviate replace {
            type uint32 {
                range "1..224";
            }
        }
        deviate add {
          must "../oc-stp:port-priority='oc-stp-types:stp-port-priority-type:32'
             or ../oc-stp:port-priority='oc-stp-types:stp-port-priority-type:64'
             or ../oc-stp:port-priority='oc-stp-types:stp-port-priority-type:96'
             or ../oc-stp:port-priority='oc-stp-types:stp-port-priority-type:128'
             or ../oc-stp:port-priority='oc-stp-types:stp-port-priority-type:160'
             or ../oc-stp:port-priority='oc-stp-types:stp-port-priority-type:192'
             or ../oc-stp:port-priority='oc-stp-types:stp-port-priority-type:224'" {
      		error-message "Only supports 32   64   96   128   160   192   224 on device model";
          }
        }
  }

  deviation /oc-stp:stp/oc-stp:mstp/oc-stp:state/oc-stp:hold-count {
    //! NOTE_FEATURE_EXIST TRUE
    //! NOTE_DME_DONE      TRUE
    //! NOTE_COMMENT       ""
    deviate not-supported;
  }

  deviation /oc-stp:stp/oc-stp:rapid-pvst/oc-stp:vlan/oc-stp:config/oc-stp:bridge-priority {
    deviate replace {
            type uint32 {
                range "1..61440";
            }
        }
        deviate add {
          must "../oc-stp:bridge-priority='oc-stp-types:stp-bridge-priority-type:4096'
             or ../oc-stp:bridge-priority='oc-stp-types:stp-bridge-priority-type:8192'
             or ../oc-stp:bridge-priority='oc-stp-types:stp-bridge-priority-type:12288'
             or ../oc-stp:bridge-priority='oc-stp-types:stp-bridge-priority-type:16384'
             or ../oc-stp:bridge-priority='oc-stp-types:stp-bridge-priority-type:20480'
             or ../oc-stp:bridge-priority='oc-stp-types:stp-bridge-priority-type:24576'
             or ../oc-stp:bridge-priority='oc-stp-types:stp-bridge-priority-type:28672'
             or ../oc-stp:bridge-priority='oc-stp-types:stp-bridge-priority-type:32768'
             or ../oc-stp:bridge-priority='oc-stp-types:stp-bridge-priority-type:36864'
             or ../oc-stp:bridge-priority='oc-stp-types:stp-bridge-priority-type:40960'
             or ../oc-stp:bridge-priority='oc-stp-types:stp-bridge-priority-type:45056'
             or ../oc-stp:bridge-priority='oc-stp-types:stp-bridge-priority-type:49152'
             or ../oc-stp:bridge-priority='oc-stp-types:stp-bridge-priority-type:53248'
             or ../oc-stp:bridge-priority='oc-stp-types:stp-bridge-priority-type:57344'
             or ../oc-stp:bridge-priority='oc-stp-types:stp-bridge-priority-type:61440'" {
      		error-message "Only supports 4096 8192 12288 16384 20480 24576 28672 32768 36864 40960 45056 49152 53248 57344 61440 on device model";
          }
        }
  }

  deviation /oc-stp:stp/oc-stp:rapid-pvst/oc-stp:vlan/oc-stp:config/oc-stp:hold-count {
    //! NOTE_FEATURE_EXIST TRUE
    //! NOTE_DME_DONE      TRUE
    //! NOTE_COMMENT       ""
    deviate not-supported;
  }

  deviation /oc-stp:stp/oc-stp:rapid-pvst/oc-stp:vlan/oc-stp:interfaces/oc-stp:interface/oc-stp:config/oc-stp:port-priority {
    deviate replace {
            type uint32 {
                range "1..224";
            }
        }
        deviate add {
          must "../oc-stp:port-priority='oc-stp-types:stp-port-priority-type:32'
             or ../oc-stp:port-priority='oc-stp-types:stp-port-priority-type:64'
             or ../oc-stp:port-priority='oc-stp-types:stp-port-priority-type:96'
             or ../oc-stp:port-priority='oc-stp-types:stp-port-priority-type:128'
             or ../oc-stp:port-priority='oc-stp-types:stp-port-priority-type:160'
             or ../oc-stp:port-priority='oc-stp-types:stp-port-priority-type:192'
             or ../oc-stp:port-priority='oc-stp-types:stp-port-priority-type:224'" {
      		error-message "Only supports 32   64   96   128   160   192   224 on device model";
          }
        }
  }

  deviation /oc-stp:stp/oc-stp:rapid-pvst/oc-stp:vlan/oc-stp:state/oc-stp:hold-count {
    //! NOTE_FEATURE_EXIST TRUE
    //! NOTE_DME_DONE      TRUE
    //! NOTE_COMMENT       ""
    deviate not-supported;
  }

  deviation /oc-stp:stp/oc-stp:rstp/oc-stp:config/oc-stp:bridge-priority {
    //! NOTE_FEATURE_EXIST TRUE
    //! NOTE_DME_DONE      TRUE
    //! NOTE_COMMENT       ""
    deviate not-supported;
  }

  deviation /oc-stp:stp/oc-stp:rstp/oc-stp:config/oc-stp:forwarding-delay {
    //! NOTE_FEATURE_EXIST TRUE
    //! NOTE_DME_DONE      TRUE
    //! NOTE_COMMENT       ""
    deviate not-supported;
  }

  deviation /oc-stp:stp/oc-stp:rstp/oc-stp:config/oc-stp:hello-time {
    //! NOTE_FEATURE_EXIST TRUE
    //! NOTE_DME_DONE      TRUE
    //! NOTE_COMMENT       ""
    deviate not-supported;
  }

  deviation /oc-stp:stp/oc-stp:rstp/oc-stp:config/oc-stp:hold-count {
    //! NOTE_FEATURE_EXIST TRUE
    //! NOTE_DME_DONE      TRUE
    //! NOTE_COMMENT       ""
    deviate not-supported;
  }

  deviation /oc-stp:stp/oc-stp:rstp/oc-stp:config/oc-stp:max-age {
    //! NOTE_FEATURE_EXIST TRUE
    //! NOTE_DME_DONE      TRUE
    //! NOTE_COMMENT       ""
    deviate not-supported;
  }

  deviation /oc-stp:stp/oc-stp:rstp/oc-stp:interfaces/oc-stp:interface {
    //! NOTE_FEATURE_EXIST TRUE
    //! NOTE_DME_DONE      TRUE
    //! NOTE_COMMENT       ""
    deviate not-supported;
  }

  deviation /oc-stp:stp/oc-stp:rstp/oc-stp:state/oc-stp:bridge-address {
    //! NOTE_FEATURE_EXIST TRUE
    //! NOTE_DME_DONE      TRUE
    //! NOTE_COMMENT       ""
    deviate not-supported;
  }

  deviation /oc-stp:stp/oc-stp:rstp/oc-stp:state/oc-stp:bridge-priority {
    //! NOTE_FEATURE_EXIST TRUE
    //! NOTE_DME_DONE      TRUE
    //! NOTE_COMMENT       ""
    deviate not-supported;
  }

  deviation /oc-stp:stp/oc-stp:rstp/oc-stp:state/oc-stp:designated-root-address {
    //! NOTE_FEATURE_EXIST TRUE
    //! NOTE_DME_DONE      TRUE
    //! NOTE_COMMENT       ""
    deviate not-supported;
  }

  deviation /oc-stp:stp/oc-stp:rstp/oc-stp:state/oc-stp:designated-root-priority {
    //! NOTE_FEATURE_EXIST TRUE
    //! NOTE_DME_DONE      TRUE
    //! NOTE_COMMENT       ""
    deviate not-supported;
  }

  deviation /oc-stp:stp/oc-stp:rstp/oc-stp:state/oc-stp:forwarding-delay {
    //! NOTE_FEATURE_EXIST TRUE
    //! NOTE_DME_DONE      TRUE
    //! NOTE_COMMENT       ""
    deviate not-supported;
  }

  deviation /oc-stp:stp/oc-stp:rstp/oc-stp:state/oc-stp:hello-time {
    //! NOTE_FEATURE_EXIST TRUE
    //! NOTE_DME_DONE      TRUE
    //! NOTE_COMMENT       ""
    deviate not-supported;
  }

  deviation /oc-stp:stp/oc-stp:rstp/oc-stp:state/oc-stp:hold-count {
    //! NOTE_FEATURE_EXIST TRUE
    //! NOTE_DME_DONE      TRUE
    //! NOTE_COMMENT       ""
    deviate not-supported;
  }

  deviation /oc-stp:stp/oc-stp:rstp/oc-stp:state/oc-stp:hold-time {
    //! NOTE_FEATURE_EXIST TRUE
    //! NOTE_DME_DONE      TRUE
    //! NOTE_COMMENT       ""
    deviate not-supported;
  }

  deviation /oc-stp:stp/oc-stp:rstp/oc-stp:state/oc-stp:last-topology-change {
    //! NOTE_FEATURE_EXIST TRUE
    //! NOTE_DME_DONE      TRUE
    //! NOTE_COMMENT       ""
    deviate not-supported;
  }

  deviation /oc-stp:stp/oc-stp:rstp/oc-stp:state/oc-stp:max-age {
    //! NOTE_FEATURE_EXIST TRUE
    //! NOTE_DME_DONE      TRUE
    //! NOTE_COMMENT       ""
    deviate not-supported;
  }

  deviation /oc-stp:stp/oc-stp:rstp/oc-stp:state/oc-stp:root-cost {
    //! NOTE_FEATURE_EXIST TRUE
    //! NOTE_DME_DONE      TRUE
    //! NOTE_COMMENT       ""
    deviate not-supported;
  }

  deviation /oc-stp:stp/oc-stp:rstp/oc-stp:state/oc-stp:root-port {
    //! NOTE_FEATURE_EXIST TRUE
    //! NOTE_DME_DONE      TRUE
    //! NOTE_COMMENT       ""
    deviate not-supported;
  }

  deviation /oc-stp:stp/oc-stp:rstp/oc-stp:state/oc-stp:topology-changes {
    //! NOTE_FEATURE_EXIST TRUE
    //! NOTE_DME_DONE      TRUE
    //! NOTE_COMMENT       ""
    deviate not-supported;
  }


}
