module cisco-nx-openconfig-platform-port-deviations {

  namespace "http://openconfig.net/yang/platform/port-deviations";

  prefix "oc-port-devs";


  import iana-if-type { prefix ianaift; }
  import ietf-interfaces { prefix if; }
  import ietf-yang-types { prefix yang; }
  import openconfig-alarm-types { prefix oc-alarm-types; }
  import openconfig-extensions { prefix oc-ext; }
  import openconfig-if-ethernet { prefix oc-eth; }
  import openconfig-interfaces { prefix oc-if; }
  import openconfig-platform-port { prefix oc-port; }
  import openconfig-platform-types { prefix oc-platform-types; }
  import openconfig-platform { prefix oc-platform; }
  import openconfig-transport-types { prefix oc-opt-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform-port module 
     set for Cisco NXOS.
     Copyright (c) 2015-2026 by Cisco Systems, Inc.
     All rights reserved.";

  revision 2026-08-11 {
    description
      "Deviation applicable to NXOS";
  }


  deviation /oc-if:interfaces/oc-if:interface/oc-if:state/oc-port:hardware-port {
    //! NOTE_FEATURE_EXIST TRUE
    //! NOTE_DME_DONE      TRUE
    //! NOTE_COMMENT       ""
    deviate not-supported;
  }

  deviation /oc-platform:components/oc-platform:component/oc-platform:port/oc-port:breakout-mode/oc-port:groups/oc-port:group/oc-port:config/oc-port:num-physical-channels {
    //! NOTE_FEATURE_EXIST TRUE
    //! NOTE_DME_DONE      TRUE
    //! NOTE_COMMENT       ""
    deviate not-supported;
  }

  deviation /oc-platform:components/oc-platform:component/oc-platform:port/oc-port:breakout-mode/oc-port:groups/oc-port:group/oc-port:state/oc-port:num-physical-channels {
    //! NOTE_FEATURE_EXIST TRUE
    //! NOTE_DME_DONE      TRUE
    //! NOTE_COMMENT       ""
    deviate not-supported;
  }


}
