module cisco-nx-openconfig-lldp-deviations {

  namespace "http://openconfig.net/yang/lldp-deviations";

  prefix "oc-lldp-devs";


  import ietf-interfaces { prefix if; }
  import ietf-yang-types { prefix yang; }
  import openconfig-extensions { prefix oc-ext; }
  import openconfig-interfaces { prefix oc-if; }
  import openconfig-lldp-types { prefix oc-lldp-types; }
  import openconfig-lldp { prefix oc-lldp; }
  import openconfig-platform-types { prefix oc-platform-types; }
  import openconfig-transport-types { prefix oc-opt-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-lldp module 
     set for Cisco NXOS.
     Copyright (c) 2015-2026 by Cisco Systems, Inc.
     All rights reserved.";

  revision 2026-08-11 {
    description
      "Deviation applicable to NXOS";
  }


  deviation /oc-lldp:lldp/oc-lldp:config/oc-lldp:chassis-id {
    //! NOTE_FEATURE_EXIST TRUE
    //! NOTE_DME_DONE      TRUE
    //! NOTE_COMMENT       ""
    deviate not-supported;
  }

  deviation /oc-lldp:lldp/oc-lldp:config/oc-lldp:chassis-id-type {
    //! NOTE_FEATURE_EXIST TRUE
    //! NOTE_DME_DONE      TRUE
    //! NOTE_COMMENT       ""
    deviate not-supported;
  }

  deviation /oc-lldp:lldp/oc-lldp:config/oc-lldp:enabled {
    deviate replace {
        default "false";
        }
  }

  deviation /oc-lldp:lldp/oc-lldp:config/oc-lldp:hello-timer {
    deviate add {
        default "30";
        }
         deviate replace {
               type uint64 {
                    range "1 .. 254";
               }
         }
  }

  deviation /oc-lldp:lldp/oc-lldp:config/oc-lldp:suppress-tlv-advertisement {
    deviate add {
        must "../oc-lldp:suppress-tlv-advertisement='oc-lldp-types:SYSTEM_NAME' or ../oc-lldp:suppress-tlv-advertisement='oc-lldp-types:SYSTEM_DESCRIPTION' or ../oc-lldp:suppress-tlv-advertisement='oc-lldp-types:SYSTEM_CAPABILITIES' or ../oc-lldp:suppress-tlv-advertisement='oc-lldp-types:PORT_DESCRIPTION' or ../oc-lldp:suppress-tlv-advertisement='oc-lldp-types:MANAGEMENT_ADDRESS'" {
            error-message "Only supports SYSTEM_NAME, SYSTEM_DESCRIPTION, SYSTEM_CAPABILITIES, PORT_DESCRIPTION, MANAGEMENT_ADDRESS on device model";
        }
    
        }
  }

  deviation /oc-lldp:lldp/oc-lldp:config/oc-lldp:system-description {
    //! NOTE_FEATURE_EXIST TRUE
    //! NOTE_DME_DONE      TRUE
    //! NOTE_COMMENT       ""
    deviate not-supported;
  }

  deviation /oc-lldp:lldp/oc-lldp:config/oc-lldp:system-name {
    //! NOTE_FEATURE_EXIST TRUE
    //! NOTE_DME_DONE      TRUE
    //! NOTE_COMMENT       ""
    deviate not-supported;
  }

  deviation /oc-lldp:lldp/oc-lldp:interfaces/oc-lldp:interface/oc-lldp:neighbors/oc-lldp:neighbor/oc-lldp:capabilities/oc-lldp:capability/oc-lldp:name {
    deviate add {
        must "../oc-lldp:name='oc-lldp-types:OTHER' or ../oc-lldp:name='oc-lldp-types:REPEATER' or ../oc-lldp:name='oc-lldp-types:MAC_BRIDGE' or ../oc-lldp:name='oc-lldp-types:WLAN_ACCESS_POINT' or ../oc-lldp:name='oc-lldp-types:ROUTER' or ../oc-lldp:name='oc-lldp-types:TELEPHONE' or ../oc-lldp:name='oc-lldp-types:DOCSIS_CABLE_DEVICE' or ../oc-lldp:name='oc-lldp-types:STATION_ONLY'" {
            error-message "Only supports OTHER,REPEATER,MAC_BRIDGE,WLAN_ACCESS_POINT,ROUTER,TELEPHONE,DOCSIS_CABLE_DEVICE,STATION_ONLY on device model";
        }
        }
  }

  deviation /oc-lldp:lldp/oc-lldp:interfaces/oc-lldp:interface/oc-lldp:neighbors/oc-lldp:neighbor/oc-lldp:capabilities/oc-lldp:capability/oc-lldp:state/oc-lldp:name {
    deviate add {
        must "../oc-lldp:name='oc-lldp-types:OTHER' or ../oc-lldp:name='oc-lldp-types:REPEATER' or ../oc-lldp:name='oc-lldp-types:MAC_BRIDGE' or ../oc-lldp:name='oc-lldp-types:WLAN_ACCESS_POINT' or ../oc-lldp:name='oc-lldp-types:ROUTER' or ../oc-lldp:name='oc-lldp-types:TELEPHONE' or ../oc-lldp:name='oc-lldp-types:DOCSIS_CABLE_DEVICE' or ../oc-lldp:name='oc-lldp-types:STATION_ONLY'" {
            error-message "Only supports OTHER,REPEATER,MAC_BRIDGE,WLAN_ACCESS_POINT,ROUTER,TELEPHONE,DOCSIS_CABLE_DEVICE,STATION_ONLY on device model";
        }
        }
  }

  deviation /oc-lldp:lldp/oc-lldp:interfaces/oc-lldp:interface/oc-lldp:neighbors/oc-lldp:neighbor/oc-lldp:custom-tlvs/oc-lldp:tlv {
    //! NOTE_FEATURE_EXIST TRUE
    //! NOTE_DME_DONE      TRUE
    //! NOTE_COMMENT       ""
    deviate not-supported;
  }

  deviation /oc-lldp:lldp/oc-lldp:interfaces/oc-lldp:interface/oc-lldp:neighbors/oc-lldp:neighbor/oc-lldp:state/oc-lldp:age {
    //! NOTE_FEATURE_EXIST TRUE
    //! NOTE_DME_DONE      TRUE
    //! NOTE_COMMENT       ""
    deviate not-supported;
  }

  deviation /oc-lldp:lldp/oc-lldp:interfaces/oc-lldp:interface/oc-lldp:neighbors/oc-lldp:neighbor/oc-lldp:state/oc-lldp:last-update {
    //! NOTE_FEATURE_EXIST TRUE
    //! NOTE_DME_DONE      TRUE
    //! NOTE_COMMENT       ""
    deviate not-supported;
  }

  deviation /oc-lldp:lldp/oc-lldp:interfaces/oc-lldp:interface/oc-lldp:neighbors/oc-lldp:neighbor/oc-lldp:state/oc-lldp:management-address-type {
    //! NOTE_FEATURE_EXIST TRUE
    //! NOTE_DME_DONE      TRUE
    //! NOTE_COMMENT       ""
    deviate not-supported;
  }

  deviation /oc-lldp:lldp/oc-lldp:interfaces/oc-lldp:interface/oc-lldp:neighbors/oc-lldp:neighbor/oc-lldp:state/oc-lldp:ttl {
    //! NOTE_FEATURE_EXIST TRUE
    //! NOTE_DME_DONE      TRUE
    //! NOTE_COMMENT       ""
    deviate not-supported;
  }

  deviation /oc-lldp:lldp/oc-lldp:interfaces/oc-lldp:interface/oc-lldp:state/oc-lldp:counters/oc-lldp:frame-error-out {
    //! NOTE_FEATURE_EXIST TRUE
    //! NOTE_DME_DONE      TRUE
    //! NOTE_COMMENT       ""
    deviate not-supported;
  }

  deviation /oc-lldp:lldp/oc-lldp:interfaces/oc-lldp:interface/oc-lldp:state/oc-lldp:counters/oc-lldp:last-clear {
    //! NOTE_FEATURE_EXIST TRUE
    //! NOTE_DME_DONE      TRUE
    //! NOTE_COMMENT       ""
    deviate not-supported;
  }

  deviation /oc-lldp:lldp/oc-lldp:interfaces/oc-lldp:interface/oc-lldp:state/oc-lldp:counters/oc-lldp:tlv-discard {
    //! NOTE_FEATURE_EXIST TRUE
    //! NOTE_DME_DONE      TRUE
    //! NOTE_COMMENT       ""
    deviate not-supported;
  }

  deviation /oc-lldp:lldp/oc-lldp:state/oc-lldp:chassis-id {
    //! NOTE_FEATURE_EXIST TRUE
    //! NOTE_DME_DONE      TRUE
    //! NOTE_COMMENT       ""
    deviate not-supported;
  }

  deviation /oc-lldp:lldp/oc-lldp:state/oc-lldp:chassis-id-type {
    //! NOTE_FEATURE_EXIST TRUE
    //! NOTE_DME_DONE      TRUE
    //! NOTE_COMMENT       ""
    deviate not-supported;
  }

  deviation /oc-lldp:lldp/oc-lldp:state/oc-lldp:counters/oc-lldp:last-clear {
    //! NOTE_FEATURE_EXIST TRUE
    //! NOTE_DME_DONE      TRUE
    //! NOTE_COMMENT       ""
    deviate not-supported;
  }

  deviation /oc-lldp:lldp/oc-lldp:state/oc-lldp:counters/oc-lldp:tlv-accepted {
    //! NOTE_FEATURE_EXIST TRUE
    //! NOTE_DME_DONE      TRUE
    //! NOTE_COMMENT       ""
    deviate not-supported;
  }

  deviation /oc-lldp:lldp/oc-lldp:state/oc-lldp:counters/oc-lldp:tlv-discard {
    //! NOTE_FEATURE_EXIST TRUE
    //! NOTE_DME_DONE      TRUE
    //! NOTE_COMMENT       ""
    deviate not-supported;
  }

  deviation /oc-lldp:lldp/oc-lldp:state/oc-lldp:enabled {
    deviate replace {
        default "false";
        }
  }

  deviation /oc-lldp:lldp/oc-lldp:state/oc-lldp:hello-timer {
    deviate add {
        default "30";
        }
         deviate replace {
               type uint64 {
                    range "1 .. 254";
               }
         }
  }

  deviation /oc-lldp:lldp/oc-lldp:state/oc-lldp:suppress-tlv-advertisement {
    deviate add {
        must "../oc-lldp:suppress-tlv-advertisement='oc-lldp-types:SYSTEM_NAME' or ../oc-lldp:suppress-tlv-advertisement='oc-lldp-types:SYSTEM_DESCRIPTION' or ../oc-lldp:suppress-tlv-advertisement='oc-lldp-types:SYSTEM_CAPABILITIES' or ../oc-lldp:suppress-tlv-advertisement='oc-lldp-types:PORT_DESCRIPTION' or ../oc-lldp:suppress-tlv-advertisement='oc-lldp-types:MANAGEMENT_ADDRESS'" {
            error-message "Only supports SYSTEM_NAME, SYSTEM_DESCRIPTION, SYSTEM_CAPABILITIES, PORT_DESCRIPTION, MANAGEMENT_ADDRESS on device model";
        }
    
        }
  }

  deviation /oc-lldp:lldp/oc-lldp:state/oc-lldp:system-description {
    //! NOTE_FEATURE_EXIST TRUE
    //! NOTE_DME_DONE      TRUE
    //! NOTE_COMMENT       ""
    deviate not-supported;
  }

  deviation /oc-lldp:lldp/oc-lldp:state/oc-lldp:system-name {
    //! NOTE_FEATURE_EXIST TRUE
    //! NOTE_DME_DONE      TRUE
    //! NOTE_COMMENT       ""
    deviate not-supported;
  }


}
