module Cisco-NX-OS-device {
    yang-version 1;
    namespace "http://cisco.com/ns/yang/cisco-nx-os-device";
    prefix top;
    organization "Cisco Systems, Inc.";
    contact " Cisco Systems, Inc., Customer Service, Postal: 170 W Tasman Drive, San Jose, CA 95134, Tel: +1 1800 553-NETS, e-mail: nxos-dev-yang@cisco.com";
    description "NXOS Device YANG Model";
    reference "81548cbb93cb96be99a20a161689d98ece41489b";
    revision 2017-10-17 {
        description
                "Initial Revision
                Generated by mtx 1.0.1 Built on Wed Aug 30 15:23:11 PDT 2017 by kyyun";
    }

    typedef address_Ipv4 {
        type string {
        }
    }

    typedef address_Ipv6 {
        type string {
        }
    }

    typedef address_Ip {
        type union {
            type address_Ipv4;
            type address_Ipv6;
        }
    }

    typedef address_Mac {
        type string {
        }
    }

    typedef mtx_array_ifindex {
        type string {
        }
    }

    typedef mtx_array_uint8 {
        type string {
        }
    }

    typedef mtx_array_uint16 {
        type string {
        }
    }

    typedef mtx_array_uint32 {
        type string {
        }
    }

    typedef mtx_array_uint64 {
        type string {
        }
    }

    typedef mtx_array_bit {
        type string {
        }
    }

    typedef mtx_array_community {
        type string {
        }
    }

    typedef aaa_AccountStatus {
        type enumeration {

            // Active
            enum active {
                value 0;
            }

            // Inactive
            enum inactive {
                value 1;
            }
        }
        default "active";
    }

    typedef aaa_BannerMsg {
        type string;
    }

    typedef aaa_Boolean {
        type enumeration {

            // No
            enum no {
                value 0;
            }

            // Yes
            enum yes {
                value 1;
            }
        }
        default "yes";
    }

    typedef aaa_Clear {
        type enumeration {

            // No
            enum no {
                value 0;
            }

            // Yes
            enum yes {
                value 1;
            }
        }
        default "no";
    }

    typedef aaa_CmdType {
        type enumeration {

            // Config
            enum config {
                value 0;
            }

            // Exec
            enum exec {
                value 1;
            }
        }
        default "config";
    }

    typedef aaa_Date {
        type uint64;
    }

    typedef aaa_Delimiter {
        type string;
    }

    typedef aaa_Email {
        type address_Email {
        }
    }

    typedef aaa_EncKey {
        type string {
            length "0..240";
        }
    }

    typedef aaa_EncryptedArray {
        type mtx_array_uint8;
    }

    typedef aaa_ExternalUnixUID {
        type uint16 {
            range "16000..23999";
        }
    }

    typedef aaa_HistoryDepth {
        type uint8 {
            range "0..15";
        }
        default "5";
    }

    typedef aaa_IdleTimer {
        type uint16 {
            range "0..1440";
        }
    }

    typedef aaa_KeyEnc {
        type enumeration {

            // Clear Text
            enum 0 {
                value 0;
            }

            // Type-6 Encrypted
            enum 6 {
                value 6;
            }

            // Encrypted
            enum 7 {
                value 7;
            }
        }
        default "0";
    }

    typedef aaa_KeyEncUserPass {
        type enumeration {

            // Unspecified
            enum unspecified {
                value 255;
            }

            // Clear Text
            enum clear {
                value 0;
            }

            // Encrypted
            enum Encrypt {
                value 5;
            }
        }
    }

    typedef aaa_LdapAttribute {
        type string {
            length "0..63";
        }
    }

    // NXOS supports maximum limits in the type definitions
    typedef aaa_LdapDn {
        type string {
            length "0..127";
        }
    }

    typedef aaa_LdapFilter {
        type string {
            length "0..63";
        }
    }

    typedef aaa_LdapSSLStrictnessLevel {
        type enumeration {

            // Strict
            enum strict {
                value 0;
            }

            // Permissive
            enum permissive {
                value 1;
            }
        }
        default "strict";
    }

    typedef aaa_LoggingLevel {
        type enumeration {

            // Emergency
            enum Emergency {
                value 0;
            }

            // Alert
            enum Alert {
                value 1;
            }

            // Critical
            enum Critical {
                value 2;
            }

            // Error
            enum Error {
                value 3;
            }

            // Warning
            enum Warning {
                value 4;
            }

            // Notifications
            enum Notif {
                value 5;
            }

            // Informational
            enum Inform {
                value 6;
            }

            // Debug
            enum Debug {
                value 7;
            }
        }
        default "Error";
    }

    typedef aaa_MonitorServerType {
        type enumeration {

            // Disabled
            enum disabled {
                value 0;
            }

            // Enabled
            enum enabled {
                value 1;
            }
        }
        default "disabled";
    }

    typedef aaa_MonitoringPasswordType {
        type string;
    }

    typedef aaa_MonitoringUserType {
        type string {
        }
        default "test";
    }

    typedef aaa_NoRolePolicy {
        type enumeration {

            // No Login
            enum no-login {
                value 0;
            }

            // Assign Default Role
            enum assign-default-role {
                value 1;
            }
        }
    }

    typedef aaa_Order {
        type uint16 {
            range "0..16";
        }
    }

    typedef aaa_Passwd {
        type string {
            length "1..127";
        }
    }

    typedef aaa_Phone {
        type address_Phone;
    }

    typedef aaa_Port {
        type uint32 {
            range "1..65535";
        }
    }

    typedef aaa_ProviderGroupDeadtime {
        type uint32 {
            range "0..1440";
        }
        default "0";
    }

    // Limited by NXOS maximum size for server group
    typedef aaa_ProviderGroupName {
        type string {
            length "0..127";
        }
    }

    typedef aaa_ProviderGroupProtocol {
        type enumeration {

            // TACACS
            enum tacacs {
                value 0;
            }

            // RADIUS
            enum radius {
                value 1;
            }

            // LDAP
            enum ldap {
                value 2;
            }
        }
    }

    typedef aaa_ProviderGroupSnmpIndex {
        type uint32;
    }

    typedef aaa_ProviderSnmpIndex {
        type uint32;
    }

    typedef aaa_ProviderState {
        type enumeration {

            // Unknown
            enum unknown {
                value 0;
            }

            // Operable
            enum operable {
                value 1;
            }

            // Inoperable
            enum inoperable {
                value 2;
            }
        }
        default "unknown";
    }

    typedef aaa_PwdChangeCount {
        type uint8 {
            range "0..10";
        }
    }

    typedef aaa_PwdChangeInterval {
        type uint16 {
            range "1..745";
        }
    }

    typedef aaa_PwdExpWarnTime {
        type uint8 {
            range "0..30";
        }
    }

    typedef aaa_PwdHistory {
        type string;
    }

    typedef aaa_PwdLen {
        type uint32;
    }

    typedef aaa_PwdLifeTime {
        type uint16 {
            range "0..3650";
        }
    }

    typedef aaa_PwdPolicy {
        type enumeration {

            // Enable
            enum enable {
                value 0;
            }

            // Disable
            enum disable {
                value 1;
            }
        }
        default "enable";
    }

    typedef aaa_RadPort {
        type uint32 {
            range "0..65535";
        }
    }

    typedef aaa_RadSrvUseType {
        type enumeration {

            // Authentication
            enum Auth {
                value 0;
            }

            // Authorization
            enum Author {
                value 1;
            }

            // Accounting
            enum Acc {
                value 2;
            }

            // All
            enum All {
                value 3;
            }
        }
        default "All";
    }

    typedef aaa_Realm {
        type enumeration {

            // Local
            enum local {
                value 0;
            }

            // RADIUS
            enum radius {
                value 1;
            }

            // TACACS+
            enum tacacs {
                value 2;
            }

            // LDAP
            enum ldap {
                value 3;
            }
        }
        default "local";
    }

    typedef aaa_Retries {
        type uint32 {
            range "0..5";
        }
        default "1";
    }

    typedef aaa_RuleAccessType {
        type enumeration {

            // none
            enum none {
                value 0;
            }

            // Read
            enum read {
                value 1;
            }

            // Read Write
            enum read-write {
                value 2;
            }

            // Command
            enum command {
                value 3;
            }
        }
    }

    typedef aaa_RuleCmdStrType {
        type string {
            length "0..128";
        }
    }

    typedef aaa_RuleEntityType {
        type string {
            length "0..512";
        }
    }

    typedef aaa_RuleNumberType {
        type uint32 {
            range "1..256";
        }
    }

    typedef aaa_RulePermissionType {
        type enumeration {

            // none
            enum none {
                value 0;
            }

            // Permit
            enum permit {
                value 1;
            }

            // Deny
            enum deny {
                value 2;
            }
        }
    }

    typedef aaa_RuleScopeType {
        type enumeration {

            // none
            enum none {
                value 0;
            }

            // Feature
            enum feature {
                value 2;
            }

            // Feature Group
            enum feature-group {
                value 3;
            }

            // OID
            enum oid {
                value 21;
            }
        }
    }

    typedef aaa_SshData {
        type string {
            length "0..16384";
        }
    }

    typedef aaa_TimeMin {
        type uint32 {
            range "0..1440";
        }
        default "0";
    }

    typedef aaa_TimeSec {
        type uint32 {
            range "1..60";
        }
        default "5";
    }

    typedef aaa_UnixUID {
        type uint16 {
            range "99..15999";
        }
    }

    typedef aaa_UserCertDataType {
        type string;
    }

    typedef aaa_UserRolePrivType {
        type enumeration {

            // No Privilege
            enum noDataPriv {
                value 0;
            }

            // Read Privilege
            enum readPriv {
                value 1;
            }

            // Write Privilege
            enum writePriv {
                value 2;
            }
        }
        default "noDataPriv";
    }

    typedef aaa_authenticationProtocol {
        type enumeration {

            // PAP
            enum pap {
                value 0;
            }

            // CHAP
            enum chap {
                value 1;
            }

            // MS-CHAP
            enum mschap {
                value 2;
            }

            // MS-CHAPv2
            enum mschapv2 {
                value 3;
            }

            // ASCII
            enum ascii {
                value 4;
            }
        }
    }

    // Bank type
    typedef ac_BankT {
        type enumeration {

            // Even
            enum even {
                value 1;
            }

            // Odd
            enum Odd {
                value 2;
            }
        }
        default "even";
    }

    // Control
    typedef ac_Control {

        // bits- Using string
        type string;
    }

    // ECN
    typedef ac_Ecn {
        type uint8 {
            range "0..2";
        }
        default "0";
    }

    // Ether type
    typedef ac_EtherT {
        type uint16;
    }

    // Ip flags
    typedef ac_IpFlags {
        type l3_IpFlags;
    }

    // Ip options
    typedef ac_IpOpt {

        // bits- Using string
        type string;
    }

    // MAC
    typedef ac_Mac {
        type address_Mac;
    }

    // Order
    typedef ac_Order {
        type uint16 {
            range "1..1024";
        }
    }

    // Payload size
    typedef ac_PayloadSz {
        type uint8;
    }

    // Port id
    typedef ac_PortId {
        type nw_IfId;
    }

    // Operational state of HW rules
    typedef ac_RuleOperSt {
        type enumeration {

            // Pending
            enum pending {
                value 1;
            }

            // Installed
            enum installed {
                value 2;
            }

            // Failed
            enum failed {
                value 3;
            }
        }
        default "pending";
    }

    typedef acl_ACEStats {
        type uint8;
        default "0";
    }

    // ACE action type
    typedef acl_ActionType {
        type enumeration {

            // Invalid
            enum invalid {
                value 0;
            }

            // Permit
            enum permit {
                value 1;
            }

            // Deny
            enum deny {
                value 2;
            }

            // Copy
            enum copy {
                value 3;
            }

            // Divert
            enum divert {
                value 4;
            }

            // Redirect
            enum redirect {
                value 5;
            }
        }
        default "invalid";
    }

    // Capture Session
    typedef acl_CaptureSes {
        type uint16 {
            range "0..48";
        }
    }

    // config State
    typedef acl_ConfigState {
        type uint8;
        default "0";
    }

    // http option (http-method) value enum
    typedef acl_HttpOptionType {
        type enumeration {

            // get
            enum get {
                value 1;
            }

            // put
            enum put {
                value 2;
            }

            // head
            enum head {
                value 3;
            }

            // post
            enum post {
                value 4;
            }

            // delete
            enum delete {
                value 5;
            }

            // trace
            enum trace {
                value 6;
            }

            // connect
            enum connect {
                value 7;
            }

            // invalid
            enum invalid {
                value 0;
            }
        }
    }

    // Name of interface, e.g. "Eth1/2"
    typedef acl_IfName {
        type nw_IfId;
    }

    // MAC Protocol
    typedef acl_MACProtocol {

        // MAX Converted to int from 0x10000
        type uint32 {
            range "0..65536";
        }
        default "65536";
    }

    // ACL name
    typedef acl_Name {
        type string {
            length "1..64";
        }
    }

    // L4 port relationship operator
    typedef acl_Operator {
        type uint8;
        default "0";
    }

    // Packet Length
    typedef acl_PktLen {
        type uint16 {
            range "19..9210";
        }
    }

    // L4 port number
    typedef acl_PortNumber {
        type uint16;
        default "0";
    }

    // ACL name
    typedef acl_RemarkStr {
        type string {
            length "1..100";
        }
    }

    // ACE sequence number
    typedef acl_SequenceNumber {
        type uint32 {
            range "0..4294967295";
        }
    }

    // TCP Flags Mask
    typedef acl_TcpFlagsMask {
        type uint8 {
            range "0..64";
        }
    }

    // TCP option length
    typedef acl_TcpOptionLengthType {
        type uint32 {
            range "0..40";
        }
    }

    // time-range name
    typedef acl_TimeRangeName {
        type string {
            length "0..64";
        }
    }

    // UDF mask
    typedef acl_UdfMask {
        type uint16 {
            range "0..65535";
        }
    }

    // UDF name
    typedef acl_UdfName {
        type string {
            length "1..16";
        }
    }

    // UDF value
    typedef acl_UdfVal {
        type uint16 {
            range "0..65535";
        }
    }

    // VLAN Acl action type
    typedef acl_VAclActionType {
        type enumeration {

            // invalid
            enum invalid {
                value 0;
            }

            // forward
            enum forward {
                value 1;
            }

            // drop
            enum drop {
                value 2;
            }

            // redirect
            enum redirect {
                value 3;
            }
        }
        default "invalid";
    }

    // VLAN Acl action log enable/disable
    typedef acl_VAclLog {
        type uint8;
        default "0";
    }

    // VLAN Acl match acl type
    // Refer to CLI_ACL_IP/CLI_ACL_IPV6/CLI_ACL_MAC for values
    typedef acl_VAclMatchType {
        type uint16;
        default "0";
    }

    // Vlan List String for VLAN Acl Policy
    typedef acl_VlanListStr {
        type string {
            length "0..512";
        }
    }

    // VLAN
    // Default Value "4294967295" Removed - out of range 0..4095
    typedef acl_VlanType {
        type uint32 {
            range "0..4095";
        }
    }

    // nve vni ID
    typedef acl_VniType {
        type uint32 {
            range "0..16777215";
        }
    }

    // cos type
    typedef acl_cosType {
        type uint8 {
            range "0..8";
        }
        default "8";
    }

    // erspan DSCP
    typedef acl_erspanDscpType {
        type uint8 {
            range "0..64";
        }
        default "64";
    }

    // erspan gre protocol
    typedef acl_erspanGreType {
        type uint32 {
            range "0..65536";
        }
        default "65536";
    }

    // VLAN Acl policy operation apply/remove
    typedef acl_operation {
        type uint8;
        default "1";
    }

    typedef action_AdminSt {
        type enumeration {

            // Unknown
            enum unknown {
                value 0;
            }

            // Start
            enum start {
                value 1;
            }

            // Stop
            enum stop {
                value 2;
            }

            // Suspend
            enum suspend {
                value 3;
            }
        }
        default "unknown";
    }

    typedef action_Descr {
        type string;
    }

    // Frequency of the task
    typedef action_Freq {
        type uint64;
    }

    typedef action_OperSt {
        type enumeration {

            // Scheduled
            enum scheduled {
                value 0;
            }

            // Processing
            enum processing {
                value 1;
            }

            // Completed
            enum completed {
                value 2;
            }

            // Cancelled
            enum cancelled {
                value 3;
            }

            // Failed
            enum failed {
                value 4;
            }

            // Indeterminate
            enum indeterminate {
                value 5;
            }

            // Suspended
            enum suspended {
                value 6;
            }

            // Crash-Suspect
            enum crashsuspect {
                value 7;
            }
        }
        default "scheduled";
    }

    // Task status qualifier
    typedef action_Qual {
        type string;
    }

    // Result history retention size: how many records
    // to keep per rule
    typedef action_RetentionSize {
        type uint16 {
            range "1..1024";
        }
        default "100";
    }

    // Resuilt history retention time: how long records are
    // to be kept per rule
    typedef action_RetentionTime {
        type uint64;
    }

    // Type of the task
    typedef action_Type {
        type enumeration {

            // Clear
            enum clear {
                value 1;
            }

            // Reset
            enum reset {
                value 2;
            }

            // Reload
            enum reload {
                value 3;
            }

            // Locate
            enum locate {
                value 4;
            }

            // Install
            enum install {
                value 5;
            }

            // Test
            enum test {
                value 6;
            }

            // Collect
            enum collect {
                value 7;
            }

            // Set Interface In-Service
            enum interface-in-service {
                value 8;
            }
        }
        default "clear";
    }

    // Global access controls
    typedef actrl_AccControl {

        // bits- Using string
        type string;
    }

    // Action
    typedef actrl_Action {
        type vz_Action;
    }

    // Rule direction
    typedef actrl_Direction {
        type enumeration {

            // Uni-directional
            enum uni-dir {
                value 1;
            }

            // Bi-directional
            enum bi-dir {
                value 2;
            }
        }
        default "uni-dir";
    }

    // Entry priority, this is the priority for entry
    // Default Value "7" Removed - out of range 1..6
    typedef actrl_EntryPrio {
        type uint8 {
            range "1..6";
        }
    }

    // Filter id
    // @@@ Keep this in sync with vzFltId.
    // @@@ Only way to moving FltId from 16 to 32 bits without dropping traffic
    // @@@ during upgrade, was to introduce vzFiltId (16 bits)
    typedef actrl_FltId {

        // MAX Converted to int from 0xffffffff
        type uint32 {
            range "1..4294967295";
        }
    }

    // Log clear interval
    typedef actrl_LogClrIntvl {
        type uint16 {
            range "1000..2800";
        }
        default "2800";
    }

    // Operational state of Rule
    typedef actrl_OperSt {
        type enumeration {

            // enabled
            enum enabled {
                value 1;
            }

            // disabled
            enum disabled {
                value 2;
            }
        }
        default "disabled";
    }

    // Reasons for rule being disabled.
    typedef actrl_OperStQual {

        // bits- Using string
        type string;
    }

    // Policy control tag
    typedef actrl_PcTag {
        type vz_GPCTag;
    }

    // PPF Node id
    typedef actrl_PpfNodeId {

        // MAX Converted to int from 0xffffffff
        type uint32 {
            range "1..4294967295";
        }
    }

    // Array PPF Node id
    typedef actrl_PpfNodeIdArray {
        type mtx_array_uint32;
    }

    // Rule id
    typedef actrl_RuleId {

        // MAX Converted to int from 0xffffffff
        type uint32 {
            range "1..4294967295";
        }
    }

    // Filter to Rule ID mapping array
    typedef actrl_RuleIdArray {
        type mtx_array_uint32;
    }

    // Rule ID array index
    typedef actrl_RuleIndex {
        type uint16 {
            range "1..1024";
        }
    }

    // Rule priority, this is the priority for a set of rules
    typedef actrl_RulePrio {
        type uint8 {
            range "1..11";
        }
    }

    // Rule type
    typedef actrl_RuleT {
        type enumeration {

            // Tenant
            enum tenant {
                value 1;
            }

            // Management
            enum mgmt {
                value 2;
            }

            // SNMP
            enum snmp {
                value 3;
            }

            // Flood
            enum bd_flood {
                value 4;
            }

            // Vrf
            enum vrf_default {
                value 5;
            }

            // Infra
            enum infra {
                value 6;
            }
        }
        default "tenant";
    }

    // Scope id (24-bit)
    typedef actrl_ScopeId {

        // MAX Converted to int from 0xffffff
        type uint32 {
            range "1..16777215";
        }
        default "1";
    }

    // Security Label (12-bit)
    typedef actrl_SecLbl {

        // MAX Converted to int from 0xfff
        type uint16 {
            range "1..4095";
        }
    }

    // Subject represents the entitiy to which the capability constraint gets applied
    typedef actrlcap_Subj {
        type enumeration {

            // Unknown
            enum unknown {
                value 0;
            }

            // Actrl Rules
            enum rule-namespace {
                value 1;
            }

            // Actrl Scopes
            enum scope-namespace {
                value 2;
            }
        }
        default "unknown";
    }

    typedef address_Email {
        type string;
    }

    typedef address_HostNameOrDottedQuad {
        type string {
            length "256..4096";
        }
    }

    typedef address_Phone {
        type string;
    }

    // Adjacency Flags
    typedef adjacency_AdjFlags {

        // bits- Using string
        type string;
    }

    // Adjacency operational state
    typedef adjacency_AdjOperSt {
        type enumeration {

            // Unknown
            enum unspecified {
                value 0;
            }

            // Incomplete
            enum incomplete {
                value 1;
            }

            // Resolved
            enum normal {
                value 2;
            }
        }
    }

    // Database type
    typedef adjacency_DbT {
        type enumeration {

            // IP database
            enum ip {
                value 1;
            }

            // IPv6 database
            enum ipv6 {
                value 2;
            }
        }
        default "ip";
    }

    typedef aggregate_AdminState {
        type enumeration {

            // Unknown
            enum unknown {
                value 0;
            }

            // Up
            enum up {
                value 1;
            }

            // Down
            enum down {
                value 2;
            }
        }
        default "down";
    }

    // Address Family Type
    typedef aggregate_AfT {
        type enumeration {

            // Ipv4 unicast address family
            enum ipv4-ucast {
                value 0;
            }

            // Vpnv4 unicast address family
            enum vpnv4-ucast {
                value 1;
            }

            // Ipv6 unicast address family
            enum ipv6-ucast {
                value 2;
            }

            // Vpnv6 unicast address family
            enum vpnv6-ucast {
                value 3;
            }

            // L2-Evpn unicast address family
            enum l2-evpn {
                value 4;
            }
        }
        default "l2-evpn";
    }

    typedef aggregate_BfdStatus {
        type enumeration {

            // Unknown
            enum unknown {
                value 0;
            }

            // Admin Down
            enum admin_down {
                value 1;
            }

            // Oper Down
            enum down {
                value 2;
            }

            // Intialization
            enum init {
                value 3;
            }

            // Up
            enum up {
                value 4;
            }
        }
        default "admin_down";
    }

    typedef aggregate_BooleanFlag {
        type enumeration {

            // No
            enum no {
                value 0;
            }

            // Yes
            enum yes {
                value 1;
            }
        }
        default "no";
    }

    // <type name="VxLanMCFlag"
    // base="scalar:Enum8"
    // >
    // <const name="unknown" value="0" label="Unknown"/>
    // <const name="yes" value="1" label="Yes"/>
    // <const name="no" value="2" label="No"/>
    // <default value="no"/>
    // </type>
    // <type name="IpVnidBindingFlag"
    // base="scalar:Enum8"
    // >
    // <const name="unknown" value="0" label="Unknown"/>
    // <const name="yes" value="1" label="Yes"/>
    // <const name="no" value="2" label="No"/>
    // <default value="no"/>
    // </type>
    // Bandwidth metric of the SVI in kilobits per second.
    typedef aggregate_Bw {
        type uint32 {
            range "1..400000000";
        }
        default "10000000";
    }

    typedef aggregate_ConfigMgmtStatus {
        type enumeration {

            // Unknown
            enum unknown {
                value 0;
            }

            // ConfigMgmtReady
            enum configMgmtReady {
                value 1;
            }

            // ConfigMgmtNotReady
            enum configMgmtNotReady {
                value 2;
            }

            // ConfigMgmtPurgeStart
            enum configMgmtPurgeStart {
                value 4;
            }
        }
        default "configMgmtNotReady";
    }

    typedef aggregate_ConfigSourceType {
        type enumeration {

            // Unknown
            enum unknown {
                value 0;
            }

            // Cli
            enum cli {
                value 1;
            }

            // Controller
            enum controller {
                value 2;
            }
        }
        default "cli";
    }

    typedef aggregate_ConfigStatus {
        type enumeration {

            // Unknown
            enum unknown {
                value 0;
            }

            // ConfigReady
            enum configReady {
                value 1;
            }

            // ConfigNotReady
            enum configNotReady {
                value 2;
            }

            // ConfigPurgeInProgress
            enum configPurgeInProgress {
                value 4;
            }
        }
        default "configNotReady";
    }

    typedef aggregate_ControllerID {
        type uint32 {
            range "0..16";
        }
        default "0";
    }

    typedef aggregate_ControllerIdBitmap {
        type mtx_array_bit;
    }

    typedef aggregate_CpuType {
        type string;
    }

    typedef aggregate_CtrlrType {
        type enumeration {

            // Unknown
            enum unknown {
                value 0;
            }

            // L2Vxlan
            enum l2-vxlan {
                value 1;
            }

            // Vxlan
            enum vxlan {
                value 2;
            }
        }
        default "l2-vxlan";
    }

    // Default Value computed from unicast
    typedef aggregate_EpType {

        // bits- Using string
        type string;
        default "unicast";
    }

    typedef aggregate_GroupAddr {
        type string;
    }

    typedef aggregate_HostReachabilityMode {
        type enumeration {

            // Unknown
            enum unknown {
                value 0;
            }

            // FloodAndLearn
            enum floodAndLearn {
                value 1;
            }

            // Controller
            enum controller {
                value 2;
            }

            // Bgp
            enum bgp {
                value 3;
            }
        }
        default "floodAndLearn";
    }

    typedef aggregate_IngressRepProtocolType {
        type enumeration {

            // Unknown
            enum unknown {
                value 0;
            }

            // Static
            enum static {
                value 1;
            }

            // Bgp
            enum bgp {
                value 2;
            }
        }
        default "unknown";
    }

    typedef aggregate_IntfAssignMode {
        type enumeration {

            // Dedicated
            enum dedicated {
                value 0;
            }

            // Shared
            enum shared {
                value 1;
            }
        }
    }

    typedef aggregate_IntfTrunkVlans {
        type l2_VlanBitmap;
        default "1-4092";
    }

    typedef aggregate_IntfType {
        type enumeration {

            // Unknown
            enum unknown {
                value 0;
            }

            // Port
            enum port {
                value 1;
            }

            // Port Channel
            enum port-channel {
                value 2;
            }

            // Tunnel
            enum tunnel {
                value 3;
            }

            // Loopback
            enum loopback {
                value 4;
            }

            // SVI
            enum svi {
                value 5;
            }
        }
    }

    typedef aggregate_MTU {
        type uint32 {
            range "1..9216";
        }
        default "9216";
    }

    // Mac type
    typedef aggregate_MacType {
        type enumeration {

            // Unknown
            enum unknown {
                value 0;
            }

            // Unicast
            enum unicast {
                value 1;
            }

            // Multicast
            enum multicast {
                value 2;
            }
        }
        default "unicast";
    }

    // Minimum rx interval (in ms)
    typedef aggregate_MinRxIntvl {
        type uint16 {
            range "0..999";
        }
        default "50";
    }

    // Minimum tx interval (in ms)
    typedef aggregate_MinTxIntvl {
        type uint16 {
            range "0..999";
        }
        default "50";
    }

    typedef aggregate_ModuleType {
        type string;
    }

    typedef aggregate_OperState {
        type enumeration {

            // Unknown
            enum unknown {
                value 0;
            }

            // Up
            enum up {
                value 1;
            }

            // Down
            enum down {
                value 2;
            }
        }
        default "down";
    }

    typedef aggregate_ReplicationModeType {
        type enumeration {

            // Unknown
            enum unknown {
                value 0;
            }

            // ReplicationServer
            enum replicationServer {
                value 1;
            }

            // IngressReplication
            enum ingressReplication {
                value 2;
            }

            // IpMulticast
            enum ipMulticast {
                value 3;
            }
        }
        default "unknown";
    }

    typedef aggregate_ResourceStatus {
        type enumeration {

            // Unknown
            enum unknown {
                value 0;
            }

            // VlanCreated
            enum vlanCreated {
                value 1;
            }

            // VlanFailed
            enum vlanFailed {
                value 2;
            }

            // VnidCreated
            enum vnidCreated {
                value 3;
            }

            // VnidFailed
            enum vnidFailed {
                value 4;
            }

            // VlansCarved
            enum vlansCarved {
                value 5;
            }

            // VlansNotCarved
            enum vlansNotCarved {
                value 6;
            }

            // VnidCreationReceived
            enum vnidCreationReceived {
                value 7;
            }

            // MyTEPIPPublished
            enum myTEPIPPublished {
                value 101;
            }

            // ControllerIntfNotCarved
            enum controllerIntfNotCarved {
                value 201;
            }

            // ControllerIntfCarved
            enum controllerIntfCarved {
                value 202;
            }
        }
        default "unknown";
    }

    // Route target policy type
    typedef aggregate_RttPType {
        type enumeration {

            // Import
            enum import {
                value 1;
            }

            // Export
            enum export {
                value 2;
            }
        }
        default "import";
    }

    typedef aggregate_TunnelType {
        type enumeration {

            // Unknown
            enum unknown {
                value 0;
            }

            // VxLanOverIPV4
            enum vxlanipv4 {
                value 1;
            }

            // VxLanOverIPV6
            enum vxlanipv6 {
                value 2;
            }

            // NVGRE
            enum nvgre {
                value 3;
            }
        }
    }

    typedef aggregate_VpcKeepaliveStatus {
        type enumeration {

            // VpcOobUnknown
            enum VpcOobUnknown {
                value 0;
            }

            // VpcOobDisabled
            enum VpcOobDisabled {
                value 1;
            }

            // VpcOobPeerAlive
            enum VpcOobPeerAlive {
                value 2;
            }

            // VpcOobPeerNotAlive
            enum VpcOobPeerNotAlive {
                value 3;
            }

            // VpcOobPeerAliveDomainMismatch
            enum VpcOobPeerAliveDomainMismatch {
                value 4;
            }

            // VpcOobSuspended
            enum VpcOobSuspended {
                value 5;
            }

            // VpcOobNotOperational
            enum VpcOobNotOperational {
                value 6;
            }

            // VpcOobSuspendedVrf
            enum VpcOobSuspendedVrf {
                value 7;
            }

            // VpcOobMisconfig
            enum VpcOobMisconfig {
                value 8;
            }
        }
        default "VpcOobUnknown";
    }

    typedef aggregate_VpcOperStatus {
        type enumeration {

            // down
            enum down {
                value 0;
            }

            // up
            enum up {
                value 1;
            }
        }
        default "down";
    }

    typedef aggregate_VpcPeerLinkStatus {
        type enumeration {

            // VpcPeerNolink
            enum VpcPeerNolink {
                value 0;
            }

            // VpcPeerLinkDown
            enum VpcPeerLinkDown {
                value 1;
            }

            // VpcPeerOk
            enum VpcPeerOk {
                value 2;
            }

            // VpcPeerNotfound
            enum VpcPeerNotfound {
                value 3;
            }
        }
        default "VpcPeerNolink";
    }

    // Fabric Forwarding Mode
    typedef aggregate_fabFwdMode {
        type enumeration {

            // Standard
            enum standard {
                value 0;
            }

            // Anycast Gateway
            enum anycastgw {
                value 1;
            }

            // ProxyGw
            enum proxygw {
                value 2;
            }
        }
        default "standard";
    }

    // Database type
    typedef aib_DbT {
        type enumeration {

            // Adjacency Database
            enum adj {
                value 1;
            }
        }
        default "adj";
    }

    // Owner type
    typedef aib_Owner {
        type string;
    }

    // Preference type
    typedef aib_Pref {

        // MAX Converted to int from 0xffff
        type uint16 {
            range "1..65535";
        }
        default "1";
    }

    // Update time stamp type
    typedef aib_UpdateTs {
        type uint64;
    }

    // Burst interval shift
    typedef analytics_BurstIntvlShift {
        type uint8 {
            range "0..255";
        }
        default "0";
    }

    // Mode
    typedef analytics_CModeT {
        type enumeration {

            // ACI mode
            enum aci {
                value 0;
            }

            // Standalone mode
            enum standalone {
                value 1;
            }
        }
        default "aci";
    }

    // Collector buket identifier
    typedef analytics_CollBucketId {
        type uint8 {
            range "1..255";
        }
    }

    // Collect Interval
    typedef analytics_CollIntvl {
        type uint32 {
            range "100..64000";
        }
        default "100";
    }

    // Collector version
    typedef analytics_CollVersion {
        type enumeration {

            // Version 5
            enum v5 {
                value 1;
            }

            // Version 9
            enum v9 {
                value 2;
            }

            // Cisco proprietary version 1
            enum cisco-v1 {
                value 3;
            }
        }
        default "cisco-v1";
    }

    // Collect params
    // Default Value computed from src-intf
    typedef analytics_CollectParams {

        // bits- Using string
        type string;
        default "src-intf";
    }

    // Collector identifier
    typedef analytics_CollectorId {
        type uint32 {
            range "0..65535";
        }
    }

    // Default filtering policy type
    typedef analytics_DefPolicyT {
        type enumeration {

            // Permit
            enum permit {
                value 0;
            }

            // Deny
            enum deny {
                value 1;
            }
        }
        default "permit";
    }

    // Direction type
    typedef analytics_DirectionT {
        type enumeration {

            // Ingress
            enum in {
                value 1;
            }

            // Egress
            enum out {
                value 2;
            }

            // Both
            enum both {
                value 3;
            }
        }
        default "in";
    }

    // IP filter type
    typedef analytics_FltType {
        type enumeration {

            // Ipv4 type
            enum ipv4 {
                value 1;
            }

            // Ipv6 type
            enum ipv6 {
                value 2;
            }

            // CE type
            enum ce {
                value 3;
            }
        }
        default "ipv4";
    }

    // Forwarding instance target identifier
    typedef analytics_FwdInstTargetId {
        type uint32 {
            range "0..16777215";
        }
    }

    // Hash value
    typedef analytics_HashT {
        type uint32 {
            range "0..4294967295";
        }
        default "0";
    }

    // Hash width type
    typedef analytics_HashWidthT {
        type uint16 {
            range "1..255";
        }
        default "12";
    }

    // IP packet identifier shift
    typedef analytics_IpPktIdShift {
        type uint8 {
            range "0..255";
        }
        default "0";
    }

    // Layer4 port
    typedef analytics_L4Port {
        type uint32 {
            range "1..65535";
        }
    }

    // Match params
    // Default Value computed from src-ipv4
    typedef analytics_MatchParams {

        // bits- Using string
        type string;
        default "src-ipv4";
    }

    // Mode
    typedef analytics_ModeT {
        type enumeration {

            // Analytics mode
            enum analytics {
                value 0;
            }

            // Netflow mode
            enum netflow {
                value 1;
            }
        }
        default "netflow";
    }

    // MTU
    typedef analytics_Mtu {
        type uint16 {
            range "576..9216";
        }
        default "1500";
    }

    // Operational state of Rule
    typedef analytics_OperSt {
        type enumeration {

            // enabled
            enum enabled {
                value 1;
            }

            // disabled
            enum disabled {
                value 2;
            }
        }
        default "disabled";
    }

    // Reasons for rule being disabled.
    typedef analytics_OperStQual {

        // bits- Using string
        type string;
    }

    // Payload length identifier
    typedef analytics_PayloadLenIdT {
        type uint8 {
            range "0..10";
        }
    }

    // Payload length
    typedef analytics_PayloadLenT {

        // MAX Converted to int from 0x3fff
        type uint32 {
            range "0..16383";
        }
        default "0";
    }

    // Receive window size identifier
    typedef analytics_RcvWindowSzIdT {
        type uint8 {
            range "0..4";
        }
    }

    // Receive window size
    typedef analytics_RcvWindowSzT {
        type uint32 {
            range "0..65535";
        }
        default "0";
    }

    // Sample size
    typedef analytics_SampleSzT {
        type uint32 {
            range "1..65535";
        }
        default "1";
    }

    // Sampler mode
    typedef analytics_SamplerMode {
        type enumeration {

            // M out of N flows
            enum flow {
                value 1;
            }

            // M out of N pkts
            enum pkts {
                value 2;
            }
        }
        default "flow";
    }

    // TCP options header length identifier
    typedef analytics_TCPOptHdrLenIdT {
        type uint8 {
            range "0..6";
        }
    }

    // TCP options header length
    typedef analytics_TCPOptHdrLenT {
        type uint32 {
            range "0..15";
        }
        default "0";
    }

    // Sequence number guess threshold
    typedef analytics_ThresholdT {
        type uint32 {
            range "0..4294967295";
        }
        default "0";
    }

    // Create Count
    typedef analytics_createCount {
        type uint32 {
            range "0..16777215";
        }
        default "0";
    }

    // Hit Count
    typedef analytics_hitCount {
        type uint32 {
            range "0..16777215";
        }
        default "0";
    }

    // Num tcam entries type
    typedef analytics_numTcamEntT {
        type uint32 {
            range "1..65535";
        }
        default "1024";
    }

    // Num tcam entries per V4 type
    typedef analytics_numTcamEntV4T {
        type uint16 {
            range "1..256";
        }
        default "1";
    }

    // Num tcam entries per V6 type
    typedef analytics_numTcamEntV6T {
        type uint16 {
            range "1..256";
        }
        default "4";
    }

    // Adjacency Flags
    typedef arp_AdjFlags {

        // bits- Using string
        type string;
    }

    // Adjacency operational state
    typedef arp_AdjOperSt {
        type enumeration {

            // Unknown
            enum unspecified {
                value 0;
            }

            // Incomplete
            enum incomplete {
                value 1;
            }

            // Resolved
            enum normal {
                value 2;
            }
        }
    }

    typedef arp_AdjRouteDist {
        type uint32 {
            range "2..250";
        }
        default "250";
    }

    // ARP Cache Limit
    typedef arp_ArpCacheLimit {
        type uint32 {
            range "1..614400";
        }
        default "174080";
    }

    // ARP Cache Syslog Rate
    typedef arp_ArpCacheSyslogRate {
        type uint32 {
            range "1..1000";
        }
        default "1";
    }

    // Config Error
    typedef arp_ConfigErr {

        // bits- Using string
        type string;
    }

    // Config Error Inst MO
    typedef arp_ConfigErrInst {

        // bits- Using string
        type string;
    }

    // Database type
    typedef arp_DbT {
        type enumeration {

            // IP database
            enum ip {
                value 1;
            }

            // SupCache database
            enum supcache {
                value 2;
            }
        }
        default "ip";
    }

    // Event History Size
    typedef arp_EventLogSize {
        type enumeration {

            // Disable
            enum disabled {
                value 0;
            }

            // Small
            enum small {
                value 1;
            }

            // Medium
            enum medium {
                value 2;
            }

            // Large
            enum large {
                value 3;
            }
        }
        default "small";
    }

    // Event Log Type
    typedef arp_EventType {
        type enumeration {

            // CLI Events
            enum cli {
                value 0;
            }

            // Client Events
            enum client-events {
                value 1;
            }

            // Client Errors
            enum client-errors {
                value 2;
            }

            // Control Events
            enum control-events {
                value 3;
            }

            // Internal Events
            enum internal-events {
                value 4;
            }

            // Internal Errors
            enum internal-errors {
                value 5;
            }

            // High Availability Events
            enum high-availability {
                value 6;
            }

            // IP Sync Events
            enum ip-sync {
                value 7;
            }

            // ARP Local Cache Events
            enum local-cache-events {
                value 8;
            }

            // ARP Local Cache Errors
            enum local-cache-errors {
                value 9;
            }

            // Packet Messages Logs
            enum pkt-messages {
                value 10;
            }

            // SNMP Events
            enum snmp {
                value 11;
            }

            // ARP Suppression Events
            enum suppress-events {
                value 12;
            }

            // ARP Suppression Errors
            enum suppress-errors {
                value 13;
            }

            // Sync Event Logs
            enum sync {
                value 14;
            }

            // Controller MAC-IP route error logs
            enum arp-controller-errors {
                value 15;
            }

            // DME debug event
            enum arp-dme-event {
                value 16;
            }

            // Adjacency Control Logs
            enum adjacency-control {
                value 101;
            }

            // Adjacency Error Logs
            enum adjacency-errors {
                value 102;
            }

            // Adjacency IPC Logs
            enum adjacency-ipc-events {
                value 103;
            }

            // Adjacency Stats Logs
            enum adjacency-stats {
                value 104;
            }

            // Adjacency High Availability Logs
            enum adjacency-high-availability {
                value 105;
            }

            // Adjacency CLI Logs
            enum adjacency-cli {
                value 106;
            }

            // Adjacency SDB Logs
            enum adjacency-sdb {
                value 107;
            }

            // Adjacency SNMP Logs
            enum adjacency-snmp {
                value 108;
            }

            // Adjacency Net Broker Logs
            enum adjacency-netbroker {
                value 109;
            }

            // Adjacency DME event debugs
            enum am-dme-event {
                value 110;
            }

            // Adjacency event debugs
            enum am-event {
                value 111;
            }
        }
    }

    // Logging Level
    typedef arp_LoggingLevel {
        type enumeration {

            // Emergency
            enum emergency {
                value 0;
            }

            // Alert
            enum alert {
                value 1;
            }

            // Critical
            enum critical {
                value 2;
            }

            // Error
            enum error {
                value 3;
            }

            // Warning
            enum warning {
                value 4;
            }

            // Notification
            enum notification {
                value 5;
            }

            // Informational
            enum informational {
                value 6;
            }

            // Debug
            enum debug {
                value 7;
            }
        }
        default "error";
    }

    // Max packet count
    typedef arp_MaxPacket {
        type uint32 {
            range "0..32767";
        }
        default "1000";
    }

    // ARP off list timeout
    typedef arp_OffListTimeout {
        type uint16 {
            range "180..1800";
        }
        default "180";
    }

    // Opcode
    typedef arp_Opcode {
        type enumeration {

            // Unspecified
            enum unspecified {
                value 0;
            }

            // ARP request
            enum req {
                value 1;
            }

            // ARP reply
            enum reply {
                value 2;
            }
        }
        default "unspecified";
    }

    // RARP Fabric Forwarding Rate Limit
    typedef arp_RarpForwadingRate {
        type uint16 {
            range "200..400";
        }
        default "200";
    }

    // Static Adjacency operational state
    typedef arp_StAdjOperSt {
        type enumeration {

            // Down
            enum down {
                value 0;
            }

            // Incomplete
            enum up {
                value 1;
            }

            // Unspecified
            enum unspecified {
                value 10;
            }
        }
        default "unspecified";
    }

    // Static Adjacency operational state qualifier
    typedef arp_StAdjOperStQual {
        type enumeration {

            // Unspecified
            enum unspecified {
                value 0;
            }

            // Subnet mismatch
            enum subnet-mismatch {
                value 1;
            }

            // Invalid MAC
            enum invalid-mac {
                value 2;
            }

            // Invalid IP
            enum invalid-ip {
                value 3;
            }

            // Invalid VRF
            enum invalid-vrf {
                value 4;
            }

            // Own MAC
            enum own-mac {
                value 5;
            }

            // Interface down
            enum if-down {
                value 6;
            }

            // Up
            enum up {
                value 7;
            }

            // Invalid Interface
            enum invalid-if {
                value 8;
            }

            // Invalid CLI Data
            enum invalid-clidata {
                value 9;
            }

            // No Memory
            enum no-memory {
                value 10;
            }
        }
        default "unspecified";
    }

    // Suppression Cache flag
    typedef arp_SupCacheFlag {

        // bits- Using string
        type string;
    }

    // Suppression ARP Mode
    typedef arp_SuppressArpMode {
        type enumeration {

            // Disabled
            enum disabled {
                value 0;
            }

            // L2SuppressARP
            enum l2suppressarp {
                value 1;
            }

            // L2L3SuppressARP
            enum l2l3suppressarp {
                value 2;
            }

            // Invalid
            enum invalid {
                value 3;
            }
        }
    }

    // ARP suppress timeout
    typedef arp_SuppressionTimeout {
        type uint16 {
            range "0..28800";
        }
        default "0";
    }

    // Syslog threshold
    typedef arp_SyslogCnt {
        type uint32 {
            range "0..65535";
        }
        default "10000";
    }

    // throttle timeout
    typedef arp_ThrottleTimeout {
        type uint16 {
            range "300..1800";
        }
        default "300";
    }

    // ARP timeout
    typedef arp_Timeout {
        type uint16 {
            range "60..28800";
        }
        default "1500";
    }

    // Default SVI autoState
    typedef bd_DefaultSVIAutoState {
        type enumeration {
            enum disable {
                value 0;
            }
            enum enable {
                value 1;
            }
        }
        default "enable";
    }

    // Address family type
    typedef bfd_AfT {
        type enumeration {

            // IPv4 address family
            enum ipv4 {
                value 1;
            }

            // IPv6 address family
            enum ipv6 {
                value 2;
            }
        }
        default "ipv4";
    }

    // Application private data
    typedef bfd_AppData {
        type mtx_array_uint8;
    }

    // Application session flags
    typedef bfd_AppFlags {

        // bits- Using string
        type string;
    }

    // Application ID
    typedef bfd_AppId {
        type uint32;
    }

    // Authentication hex key
    typedef bfd_AuthHexKey {
        type mtx_array_uint8;
    }

    // Authentication hex key size
    typedef bfd_AuthHexKeySize {
        type uint8 {
            range "0..40";
        }
    }

    // Authentication key
    typedef bfd_AuthKey {
        type string {
            length "min..20";
        }
    }

    // Authentication key id
    typedef bfd_AuthKeyId {
        type uint8 {
            range "1..255";
        }
    }

    // Authentication Sequence Number
    typedef bfd_AuthSeqno {
        type uint32;
    }

    // Authentication type
    typedef bfd_AuthT {
        type enumeration {

            // No authentication
            enum none {
                value 0;
            }

            // Keyed SHA1
            enum sha1 {
                value 4;
            }

            // Met Keyed SHA1
            enum met-sha1 {
                value 5;
            }
        }
        default "none";
    }

    // Current session index
    typedef bfd_CurSessIndex {
        type uint32;
    }

    // Detection multiplier
    typedef bfd_DetectMult {
        type uint8 {
            range "1..50";
        }
        default "3";
    }

    // Diag Code
    typedef bfd_DiagCode {
        type enumeration {

            // No Diagnostic
            enum none {
                value 0;
            }

            // Control Detection Time Expired
            enum detect-timeout {
                value 1;
            }

            // Echo Function Failed
            enum echo-fail {
                value 2;
            }

            // Neighbor Signaled Session Down
            enum nbr-signal-down {
                value 3;
            }

            // Forwarding Plane Reset
            enum fwd-plane-reset {
                value 4;
            }

            // Path Down
            enum path-down {
                value 5;
            }

            // Concatenated Path Down
            enum concat-path-down {
                value 6;
            }

            // Administratively Down
            enum admin-down {
                value 7;
            }

            // Reverse Concatenated Path Down
            enum rev-concat-path-down {
                value 8;
            }
        }
    }

    // Session discriminator
    typedef bfd_Discr {
        type uint32;
    }

    // echo rx interval (in ms)
    typedef bfd_EchoRxIntvl {
        type uint16 {
            range "0..999";
        }
        default "0";
    }

    typedef bfd_IfControl {

        // bits- Using string
        type string;
    }

    // Global flags
    typedef bfd_InstFlags {

        // bits- Using string
        type string;
    }

    // Minimum rx interval (in ms)
    typedef bfd_MinRxIntvl {
        type uint16 {
            range "50..999";
        }
        default "50";
    }

    // Minimum tx interval (in ms)
    typedef bfd_MinTxIntvl {
        type uint16 {
            range "50..999";
        }
        default "50";
    }

    // Oper State
    typedef bfd_OperSt {
        type enumeration {

            // AdminDown
            enum admin-down {
                value 0;
            }

            // Down
            enum down {
                value 1;
            }

            // Init
            enum init {
                value 2;
            }

            // Up
            enum up {
                value 3;
            }
        }
    }

    // Packet flags
    typedef bfd_PktFlags {

        // bits- Using string
        type string;
    }

    // Packet Interval (in ms)
    typedef bfd_PktInterval {
        type uint32;
    }

    // Application sap ID
    typedef bfd_SapId {
        type uint32;
    }

    // Slow interval (in ms)
    typedef bfd_SlowIntvl {
        type uint16 {
            range "1000..30000";
        }
        default "2000";
    }

    // BFD Start timeout
    // Default Value "0" Removed - out of range 60..3600
    typedef bfd_StTm {
        type uint32 {
            range "60..3600";
        }
    }

    // Startup interval (in second)
    typedef bfd_StartupIntvl {
        type uint16 {
            range "0..30";
        }
        default "5";
    }

    // BFD Cfg State
    typedef bfd_TrkMbrLnk {
        type enumeration {

            // Enabled
            enum enable {
                value 1;
            }

            // Disabled
            enum disable {
                value 0;
            }
        }
        default "disable";
    }

    // Additional Paths capability in DomAf
    typedef bgp_AddlPathCapT {

        // bits- Using string
        type string;
    }

    // Administrative state
    typedef bgp_AdminSt {
        type enumeration {

            // Enabled
            enum enabled {
                value 1;
            }

            // Disabled
            enum disabled {
                value 2;
            }
        }
        default "disabled";
    }

    // Advertisement Interval
    // Default Value "0" Removed - out of range 1..600
    typedef bgp_AdvInterval {
        type uint16 {
            range "1..600";
        }
    }

    // Advertise l2vpn evpn
    typedef bgp_AdvertL2vpnEvpn {
        type enumeration {

            // Enabled
            enum enabled {
                value 1;
            }

            // Disabled
            enum disabled {
                value 0;
            }
        }
        default "disabled";
    }

    typedef bgp_AdvtMapCondition {
        type enumeration {

            // no options
            enum none {
                value 0;
            }

            // Exist Route Map
            enum exist {
                value 1;
            }

            // Non-Exist Route Map
            enum non-exist {
                value 2;
            }
        }
        default "none";
    }

    // Address family type
    typedef bgp_AfT {
        type enumeration {

            // IPv4 unicast address family
            enum ipv4-ucast {
                value 1;
            }

            // IPv4 multicast address family
            enum ipv4-mcast {
                value 2;
            }

            // Vpnv4 unicast address family
            enum vpnv4-ucast {
                value 3;
            }

            // IPv6 unicast address family
            enum ipv6-ucast {
                value 5;
            }

            // IPv6 multicast address family
            enum ipv6-mcast {
                value 6;
            }

            // Vpnv6 unicast address family
            enum vpnv6-ucast {
                value 7;
            }

            // L2Vpn EVpn address family
            enum l2vpn-evpn {
                value 9;
            }

            // IPv4 labeled unicast  address family
            enum ipv4-lucast {
                value 10;
            }

            // IPv6 labeled unicast  address family
            enum ipv6-lucast {
                value 11;
            }

            // Link state address family
            enum lnkstate {
                value 12;
            }

            // IPv4 mvpn address family
            enum ipv4-mvpn {
                value 13;
            }

            // IPv6 mvpn address family
            enum ipv6-mvpn {
                value 14;
            }

            // L2Vpn vpls address family
            enum l2vpn-vpls {
                value 15;
            }

            // IPv4 mdt address family
            enum ipv4-mdt {
                value 16;
            }
        }
        default "ipv4-ucast";
    }

    // Activate the affinity group
    // Default Value "0" Removed - out of range 1..65535
    typedef bgp_AffGrpActv {
        type uint16 {
            range "1..65535";
        }
    }

    // AS path database size
    typedef bgp_AsPathDbSz {
        type uint32;
    }

    // AS segment type
    typedef bgp_AsSegT {
        type enumeration {

            // Sequence
            enum sequence {
                value 1;
            }

            // Set
            enum set {
                value 2;
            }
        }
        default "set";
    }

    // AS Set
    typedef bgp_AsSet {
        type enumeration {

            // Enabled
            enum enabled {
                value 1;
            }

            // Disabled
            enum disabled {
                value 0;
            }
        }
        default "disabled";
    }

    // Asn number
    typedef bgp_AsnNum {
        type string;
    }

    // Customizes AS_PATH attribute for routes received from eBGP neighbor
    typedef bgp_AsnPropagation {
        type enumeration {

            // no options
            enum none {
                value 0;
            }

            // no-prepend
            enum no-prepend {
                value 1;
            }

            // no-prepend+replace-as
            enum replace-as {
                value 2;
            }

            // noPrepend+replace-as+dual-as
            enum dual-as {
                value 3;
            }
        }
        default "none";
    }

    // Attribute database size
    typedef bgp_AttribDbSz {
        type uint32;
    }

    // BestPath Timeout Limit
    typedef bgp_BestPathIntvl {
        type uint16 {
            range "1..3600";
        }
        default "300";
    }

    // Additional Paths capability in Neighbor Af
    typedef bgp_CapAddlPathCapT {

        // bits- Using string
        type string;
    }

    // Capability type
    typedef bgp_CapT {

        // bits- Using string
        type string;
    }

    // Cluster ID
    typedef bgp_ClusterId {
        type string;
    }

    // Connection Attempts
    typedef bgp_ConnAttempts {
        type uint32;
        default "0";
    }

    // Connection info
    typedef bgp_ConnMode {

        // bits- Using string
        type string;
    }

    // BGP Distance
    typedef bgp_Distance {
        type uint16 {
            range "1..255";
        }
    }

    // VRF Id
    typedef bgp_DomId {
        type uint32;
    }

    // Domain operational state
    typedef bgp_DomOperSt {
        type enumeration {

            // Unknown
            enum unknown {
                value 0;
            }

            // Up
            enum up {
                value 1;
            }

            // Down
            enum down {
                value 2;
            }
        }
        default "unknown";
    }

    // Egress Peer Engineering EPE for neighbor status
    typedef bgp_EgressPeerEng {
        type enumeration {

            // Disabled
            enum none {
                value 0;
            }

            // Egress Peer Engineering Enabled
            enum enabled {
                value 1;
            }

            // Advertise Adjacency-SIDs for multi-hop neighbor paths
            enum enabled-adj-sid {
                value 2;
            }
        }
        default "none";
    }

    // Event History Buffer Type
    typedef bgp_EhType {
        type enumeration {
            enum none {
                value 0;
            }

            // Cli buffer
            enum cli {
                value 1;
            }

            // Events buffer
            enum events {
                value 2;
            }

            // Periodic buffer
            enum periodic {
                value 3;
            }

            // Detailed buffer
            enum detail {
                value 4;
            }

            // Errors buffer
            enum errors {
                value 5;
            }

            // Objstore buffer
            enum objstore {
                value 6;
            }
        }
        default "none";
    }

    // EVPN route-type
    typedef bgp_EvpnRtType {
        type enumeration {

            // Unspecified
            enum none {
                value 0;
            }

            // Ethernet Auto-Discovery route
            enum a-d {
                value 1;
            }

            // MAC/IP Advertisement route
            enum mac-ip {
                value 2;
            }

            // Inclusive Multicast Ethernet Tag route
            enum imet {
                value 3;
            }

            // Ethernet Segment route
            enum eth-seg {
                value 4;
            }

            // IP Prefix route
            enum ip-pfx {
                value 5;
            }
        }
        default "none";
    }

    // Graceful restart controls
    // Default Value computed from complete
    typedef bgp_GrCtrl {

        // bits- Using string
        type string;
        default "complete";
    }

    // Graceful restart interval
    typedef bgp_GrIntvl {
        type uint16 {
            range "1..3600";
        }
        default "120";
    }

    // Graceful stale interval
    typedef bgp_GrStaleIntvl {
        type uint16 {
            range "1..3600";
        }
        default "300";
    }

    // Hold Interval
    typedef bgp_HoldIntvl {
        type uint16 {
            range "3..3600";
        }
        default "180";
    }

    // IGP Preference
    typedef bgp_IgpPref {
        type uint8;
    }

    // IGP Route Type
    typedef bgp_IgpRtType {
        type uint8;
    }

    // Inherit template peer control bits. This contains common    fields of peer and peer-session templates (please refer to
    // MOs PeerCont and SessionCont).
    typedef bgp_InheritContPeerCtrlType {

        // bits- Using string
        type string;
    }

    // Inherit template peer-policy control bits. (Please refer
    // to MO PolicyCont).
    typedef bgp_InheritContPeerPolicyCtrlType {

        // bits- Using string
        type string;
    }

    // Keepalive Interval
    typedef bgp_KaIntvl {
        type uint16 {
            range "0..3600";
        }
        default "60";
    }

    // Last error len
    typedef bgp_LastErrLen {
        type uint8;
    }

    // Last error value
    typedef bgp_LastErrVal {
        type uint32;
    }

    // NH iLast Resolved Timestamp
    typedef bgp_LastResolvTs {
        type uint64;
        default "0";
    }

    // Label
    typedef bgp_Lbl {
        type uint32;
        default "0";
    }

    // Link Attribute TLV flags for Link-state
    // Default Value computed from none
    typedef bgp_LnkLsAttrFlags {

        // bits- Using string
        type string;
        default "none";
    }

    // Log Neighbor changes
    typedef bgp_LogNbrSt {
        type enumeration {

            // none
            enum none {
                value 0;
            }

            // Enable
            enum enable {
                value 1;
            }

            // Disable
            enum disable {
                value 2;
            }
        }
        default "none";
    }

    // Link-State status
    typedef bgp_LsAdminSt {
        type enumeration {

            // Inactive
            enum inactive {
                value 0;
            }

            // Active
            enum active {
                value 1;
            }
        }
        default "inactive";
    }

    // Link-State attribute entry type
    typedef bgp_LsAttrEntryType {
        type enumeration {

            // Unspecified
            enum none {
                value 0;
            }

            // Peer Node Segment Identifier
            enum peer-node-sid {
                value 1101;
            }

            // Peer Adjacency Segment Identifier
            enum peer-adj-sid {
                value 1102;
            }

            // Peer Set Segment Identifier
            enum peer-set-sid {
                value 1103;
            }
        }
        default "none";
    }

    // Link-State NLRI Type
    typedef bgp_LsNlriType {
        type enumeration {

            // Unspecified
            enum none {
                value 0;
            }

            // Node NLRI
            enum node {
                value 1;
            }

            // Link NLRI
            enum link {
                value 2;
            }

            // IPv4 Topology Prefix NLRI
            enum ipv4-topo {
                value 3;
            }

            // IPv6 Topology Prefix NLRI
            enum ipv6-topo {
                value 4;
            }
        }
        default "none";
    }

    // Link-State Protocol Identifier
    typedef bgp_LsProtoId {
        type enumeration {

            // Unspecified
            enum none {
                value 0;
            }

            // IS-IS Level 1
            enum isis-l1 {
                value 1;
            }

            // IS-IS Level 2
            enum isis-l2 {
                value 2;
            }

            // OSPFv2
            enum ospf-v2 {
                value 3;
            }

            // Direct
            enum direct {
                value 4;
            }

            // Static configuration
            enum static {
                value 5;
            }

            // OSPFv3
            enum ospf-v3 {
                value 6;
            }

            // Egress Peer Engineering
            enum epe {
                value 7;
            }
        }
        default "none";
    }

    // Major notify error
    typedef bgp_MajNotifErr {
        type enumeration {

            // None
            enum none {
                value 0;
            }

            // Header Error
            enum hdr-err {
                value 1;
            }

            // Open Message Error
            enum open-msg-err {
                value 2;
            }

            // Update Message Error
            enum upd-msg-err {
                value 3;
            }

            // Holdtimer Expired
            enum hold-timer-exp {
                value 4;
            }

            // FSM Error
            enum fsm-err {
                value 5;
            }

            // Cease Error
            enum cease-err {
                value 6;
            }

            // Capability Message Error
            enum cap-msg-err {
                value 7;
            }

            // Process Restart Error
            enum process-restart-err {
                value 101;
            }

            // FD Read Error
            enum fd-read-err {
                value 102;
            }

            // FD Ioctl Error
            enum fd-ioctl-err {
                value 103;
            }

            // Peer Closed Session Error
            enum peer-close-sess-err {
                value 104;
            }

            // Peer Received Notification Error
            enum rcvd-notif-err {
                value 105;
            }

            // Received Duplicate Connection Request
            enum rcvd-dup-conn-req {
                value 106;
            }

            // Dynamic Capability no Buffer
            enum dyn-cap-no-buf {
                value 107;
            }
        }
    }

    // Maximum AS Limit
    // Default Value "0" Removed - out of range 1..512
    typedef bgp_MaxAsLimit {
        type uint16 {
            range "1..512";
        }
    }

    // Maximum Ecmp
    typedef bgp_MaxEcmp {
        type uint8 {
            range "1..64";
        }
        default "1";
    }

    // Maximum Peers
    typedef bgp_MaxPeerCnt {
        type uint32 {
            range "0..1000";
        }
    }

    // Maximum Prefix
    typedef bgp_MaxPfx {
        type uint32;
    }

    // Action when the prefixes crosses the maximum limit
    typedef bgp_MaxPfxAct {
        type enumeration {

            // Log
            enum log {
                value 1;
            }

            // Shutdown
            enum shut {
                value 2;
            }

            // Restart
            enum restart {
                value 3;
            }
        }
        default "shut";
    }

    // Duration before we restart the peer when the maximum
    // prefix limit is reached
    typedef bgp_MaxPfxDuration {

        // MAX Converted to int from 0xffff
        type uint16 {
            range "0..65535";
        }
    }

    // Threshold at which warning is issued when number of prefixes
    // crosses the threshold, units in percentage
    typedef bgp_MaxPfxThresh {
        type uint8 {
            range "0..100";
        }
    }

    // MED dampening interval
    // Default Value "0" Removed - out of range 60..4294967295
    typedef bgp_MedIntvl {
        type uint32 {
            range "60..4294967295";
        }
    }

    // Memory consumed (in bytes)
    typedef bgp_MemConsumed {
        type uint32;
    }

    // Metric
    typedef bgp_Metric {
        type uint32;
    }

    // Minor notify error
    typedef bgp_MinNotifErr {
        type enumeration {

            // None
            enum none {
                value 0;
            }

            // Unspecified Msg Header Error
            enum unspecified-msg-hdr-err {
                value 1;
            }

            // Connection not Synchronized
            enum conn-not-synced {
                value 2;
            }

            // Bad Message Length
            enum bad-msg-len {
                value 3;
            }

            // Bad Message Type
            enum bad-msg-type {
                value 4;
            }

            // Unknown Message Header Error
            enum unknown-msg-hdr-err {
                value 5;
            }

            // Unspecified Open Error
            enum unspecified-open-err {
                value 6;
            }

            // Unsupported Version
            enum unsupp-version {
                value 7;
            }

            // Bad Peer AS
            enum bad-peer-as {
                value 8;
            }

            // Bad Peer Router ID
            enum bad-peer-rtrid {
                value 9;
            }

            // Unsupported Optional Parameter
            enum unsupp-opt-param {
                value 10;
            }

            // Authentication Error
            enum auth-err {
                value 11;
            }

            // Unacceptable Holdtime
            enum bad-holdtime {
                value 12;
            }

            // Unsupported Capability
            enum unsupp-cap {
                value 13;
            }

            // Unknown Open Header Error
            enum unknown-open-hdr-err {
                value 14;
            }

            // Unspecified Update Error
            enum unspecified-update-err {
                value 15;
            }

            // Malformed Attribute List
            enum malformed-attr-list {
                value 16;
            }

            // Unrecognized Wellknown Attr
            enum unrecognized-wellknown-attr {
                value 17;
            }

            // Missing Well-known Attribute
            enum missing-wellknown-attr {
                value 18;
            }

            // Attribute Flags Error
            enum attr-flags-err {
                value 19;
            }

            // Attribute Length Error
            enum attr-len-err {
                value 20;
            }

            // Invalid Origin Attribute
            enum invalid-origin-attr {
                value 21;
            }

            // Bgp AS Routing Loop Error
            enum as-loop-err {
                value 22;
            }

            // Invalid Next-hop Attribute
            enum invalid-nh-attr {
                value 23;
            }

            // Optional Attribute Error
            enum opt-attr-err {
                value 24;
            }

            // Invalid Network Field
            enum invalid-nw-field {
                value 25;
            }

            // Malformed AS Path
            enum bad-as-path {
                value 26;
            }

            // Unknown Update Header Error
            enum unknown-update-hdr-err {
                value 27;
            }

            // Unspecified Cease Error
            enum unspecified-cease-err {
                value 28;
            }

            // Maximum Prefix Count
            enum max-pfx-count-err {
                value 29;
            }

            // Administratively Shutdown
            enum admin-shut {
                value 30;
            }

            // Peer Deconfigured
            enum peer-decfg {
                value 31;
            }

            // Session Cleared
            enum session-cleared {
                value 32;
            }

            // Connection Rejected
            enum conn-rej {
                value 33;
            }

            // Other Configuration Change Error
            enum other-cfg-chg {
                value 34;
            }

            // Connection Collision Resolution
            enum conn-coll-resolution {
                value 35;
            }

            // Out of Resource
            enum out-of-rsrc {
                value 36;
            }

            // Dynamic Capability Configuration Change
            enum dyn-cap-cfg-chg {
                value 37;
            }

            // TTL Configuration Change
            enum ttl-cfg-chg {
                value 38;
            }

            // TTL Security Configuration Change
            enum ttl-security-cfg-chg {
                value 39;
            }

            // Passive Neighbor Configuration Change
            enum passive-neighbor-cfg-chg {
                value 40;
            }

            // Address-family Configuration Change
            enum af-cfg-chg {
                value 41;
            }

            // Route-reflector Configuration Change
            enum rr-cfg-chg {
                value 42;
            }

            // Router-id Configuration Change
            enum rtrid-cfg-chg {
                value 43;
            }

            // Confederation Id Change
            enum confed-id-chg {
                value 44;
            }

            // Confederation Membership Change
            enum confed-membership-change {
                value 45;
            }

            // Graceful-restart Configuration Change
            enum gr-cfg-chg {
                value 46;
            }

            // Soft-reconfiguration Change
            enum soft-recfg-chg {
                value 47;
            }

            // Update-source Interface Change
            enum updatesrc-if-chg {
                value 48;
            }

            // Local-as Change
            enum localas-chg {
                value 49;
            }

            // Unknown Cease Error
            enum unknown-cease-err {
                value 50;
            }

            // Unspecified Cappability Message Error
            enum unspecified-cap-msg-err {
                value 51;
            }

            // Unknown Sequence Number
            enum unknown-seq-num {
                value 52;
            }

            // Invalid Capability Length
            enum invalid-cap-len {
                value 53;
            }

            // Malformed Capability Value
            enum bad-cap-val {
                value 54;
            }

            // Unsupported Capability Code
            enum unsupp-cap-code {
                value 55;
            }

            // Unknown Capability Error
            enum unknown-cap-err {
                value 56;
            }
        }
    }

    // Mode
    typedef bgp_Mode {
        type enumeration {

            // Fabric
            enum fabric {
                value 1;
            }

            // External
            enum external {
                value 2;
            }
        }
        default "fabric";
    }

    // NH Next Advertised Timestamp
    typedef bgp_NextAdvTs {
        type uint64;
        default "0";
    }

    // Nexthop flags
    typedef bgp_NhFlags {

        // bits- Using string
        type string;
    }

    // Link Attribute TLV flags for Link-state
    // Default Value computed from none
    typedef bgp_NodeLsAttrFlags {

        // bits- Using string
        type string;
        default "none";
    }

    // Number of paths
    typedef bgp_NumPaths {
        type uint32;
    }

    // Number of Peers
    typedef bgp_NumPeers {
        type uint32;
    }

    // Order (for AS path segments and AS path items)
    typedef bgp_Order {
        type uint16;
    }

    // Origin
    typedef bgp_Origin {
        type enumeration {

            // Learned Via IGP
            enum igp {
                value 1;
            }

            // Learned Via EGP
            enum egp {
                value 2;
            }

            // Learned by some other Means
            enum incomplete {
                value 3;
            }
        }
        default "igp";
    }

    // Authentication status
    typedef bgp_PasswdSet {
        type enumeration {

            // Enabled
            enum enabled {
                value 1;
            }
            enum disabled {
                value 0;
            }
        }
        default "disabled";
    }

    // Path flags
    typedef bgp_PathFlags {

        // bits- Using string
        type string;
    }

    // Path id
    typedef bgp_PathId {
        type uint32;
    }

    // Path status
    typedef bgp_PathSt {
        type enumeration {

            // Deleted
            enum deleted {
                value 0;
            }

            // Staled
            enum staled {
                value 1;
            }

            // Valid
            enum valid {
                value 2;
            }

            // InValid
            enum invalid {
                value 3;
            }

            // history
            enum history {
                value 4;
            }

            // suppressed
            enum suppressed {
                value 5;
            }

            // dampened
            enum dampened {
                value 6;
            }
        }
    }

    // Path type
    typedef bgp_PathT {
        type enumeration {

            // Internal
            enum internal {
                value 1;
            }

            // External
            enum external {
                value 2;
            }

            // Confederation
            enum confederation {
                value 3;
            }

            // Local
            enum local {
                value 4;
            }

            // Aggregate
            enum aggregate {
                value 5;
            }

            // Redistribute
            enum redistribute {
                value 6;
            }

            // Injected
            enum injected {
                value 7;
            }
        }
        default "internal";
    }

    // Peer Address Family Control
    typedef bgp_PeerAfControl {

        // bits- Using string
        type string;
    }

    // Peer AF flags
    typedef bgp_PeerAfFlags {

        // bits- Using string
        type string;
    }

    // Peer Control
    typedef bgp_PeerControl {

        // bits- Using string
        type string;
    }

    // TODO: Change this to nw:Cnt64     Count of BGP Messages
    typedef bgp_PeerCount {
        type uint64;
    }

    // Peer Fabric Type
    typedef bgp_PeerFabType {
        type enumeration {

            // Fabric internal
            enum fabric-internal {
                value 0;
            }

            // Fabric external
            enum fabric-external {
                value 1;
            }

            // Fabric Border Leaf
            enum fabric-border-leaf {
                value 2;
            }
        }
        default "fabric-internal";
    }

    // Peer flags
    typedef bgp_PeerFlags {

        // bits- Using string
        type string;
    }

    // Peer graceful restart state
    typedef bgp_PeerGrSt {
        type enumeration {

            // Not applicable
            enum na {
                value 1;
            }

            // Reset
            enum reset {
                value 2;
            }

            // Up
            enum up {
                value 3;
            }
        }
        default "na";
    }

    // Peer Index
    typedef bgp_PeerIdx {
        type uint16;
    }

    // Peer operational state
    typedef bgp_PeerOperSt {
        type enumeration {

            // Unspecified
            enum unspecified {
                value 0;
            }

            // Illegal
            enum illegal {
                value 1;
            }

            // Shut
            enum shut {
                value 2;
            }

            // Idle
            enum idle {
                value 3;
            }

            // Connect
            enum connect {
                value 4;
            }

            // Active
            enum active {
                value 5;
            }

            // Open sent
            enum open-sent {
                value 6;
            }

            // Open confirm
            enum open-confirm {
                value 7;
            }

            // Established
            enum established {
                value 8;
            }

            // Closing
            enum closing {
                value 9;
            }

            // Error
            enum error {
                value 10;
            }

            // Unknown
            enum unknown {
                value 11;
            }
        }
        default "unspecified";
    }

    // Peer Type
    typedef bgp_PeerType {
        type enumeration {

            // ibgp
            enum ibgp {
                value 1;
            }

            // ebgp
            enum ebgp {
                value 2;
            }
        }
        default "ibgp";
    }

    // Pfx Flushed
    typedef bgp_PfxFlushed {
        type uint64;
    }

    // Prefix Attributes TLV flags for Link-state
    // Default Value computed from none
    typedef bgp_PfxLsAttrFlags {

        // bits- Using string
        type string;
        default "none";
    }

    // TODO: Change this to nw:Cnt64    Counts for Prefix Peers
    typedef bgp_PfxPeerCounts {
        type uint64;
    }

    // Prefix Peer Timeout
    typedef bgp_PfxPeerTimeout {
        type uint16 {
            range "0..1200";
        }
    }

    // Prefix Peer Wait
    typedef bgp_PfxPeerWaitTime {
        type uint16 {
            range "0..1200";
        }
    }

    // TODO: Change this to nw:Cnt64    Pfx Saved
    typedef bgp_PfxSaved {
        type uint64;
    }

    // Pfx Sent
    typedef bgp_PfxSent {
        type uint64;
    }

    // Prefix-Sid attribute entry type
    typedef bgp_PfxSidAttrEntryType {
        type enumeration {

            // Unspecified
            enum none {
                value 0;
            }

            // Label Index
            enum label-index {
                value 1;
            }

            // IPv6-SID
            enum ipv6-sid {
                value 2;
            }

            // Originator SRGB
            enum origin-srgb {
                value 3;
            }
        }
        default "none";
    }

    // PMSI Tunnel Type
    typedef bgp_PmsiTunType {
        type enumeration {

            // Unspecified
            enum none {
                value 0;
            }

            // Ingress Replication
            enum ingress-repl {
                value 1;
            }
        }
        default "none";
    }

    // private-as Control
    typedef bgp_PrivateASControl {
        type enumeration {
            enum none {
                value 0;
            }

            // Remove private AS
            enum remove-exclusive {
                value 1;
            }

            // Remove all private AS
            enum remove-all {
                value 2;
            }

            // Replace private AS with local AS
            enum replace-as {
                value 3;
            }
        }
        default "none";
    }

    // Reconnect Interval Value
    typedef bgp_ReConnectIntvl {
        type uint16 {
            range "1..60";
        }
        default "60";
    }

    // RNH Epoch
    typedef bgp_RnhEpoch {
        type uint8;
    }

    // Route control direction
    typedef bgp_RtCtrlDir {
        type enumeration {

            // Incoming
            enum in {
                value 1;
            }

            // Outgoing
            enum out {
                value 2;
            }
        }
        default "in";
    }

    // Route control operational state
    typedef bgp_RtCtrlOperSt {
        type enumeration {

            // Unresolved
            enum unresolved {
                value 1;
            }

            // Resolved
            enum resolved {
                value 2;
            }
        }
        default "unresolved";
    }

    // Route flags
    typedef bgp_RtFlags {

        // bits- Using string
        type string;
    }

    // Labeled address-family route flags
    typedef bgp_RtLblAfFlags {

        // bits- Using string
        type string;
    }

    // Route version
    typedef bgp_RtVer {
        type uint32;
    }

    // Route target policy type
    typedef bgp_RttPType {
        type enumeration {

            // Import
            enum import {
                value 1;
            }

            // Export
            enum export {
                value 2;
            }
        }
        default "import";
    }

    // Segment Routing Global Block
    // Default Value "0" Removed - out of range 16..471804
    typedef bgp_SRGBRange {
        type uint32 {
            range "16..471804";
        }
    }

    // Peer shut state qualifier
    typedef bgp_ShutStQual {
        type enumeration {

            // Unspecified
            enum unspecified {
                value 0;
            }

            // Administratively down
            enum admin {
                value 1;
            }

            // No memory
            enum no-mem {
                value 2;
            }

            // Exceeded prefix limit
            enum exceeded-pfxlimit {
                value 3;
            }

            // Administratively up
            enum admin-up {
                value 4;
            }

            // No Affinity
            enum no-affinity {
                value 5;
            }
        }
        default "unspecified";
    }

    // Event History Buffer Size
    typedef bgp_Size {
        type uint32 {
            range "0..4 | 8192..1048576";
        }
        default "0";
    }

    // FD to connect to the peer
    typedef bgp_SockFD {
        type uint32;
    }

    // Soft Reconfiguration
    typedef bgp_SoftReconfigBackup {
        type enumeration {
            enum none {
                value 0;
            }

            // Inbound Only
            enum inbound {
                value 1;
            }

            // Inbound Always
            enum inbound-always {
                value 2;
            }
        }
    }

    // Peer Idle State Reason
    typedef bgp_StReason {
        type enumeration {
            enum none {
                value 0;
            }

            // NoMem
            enum no-mem {
                value 1;
            }
        }
        default "none";
    }

    // Aggregate Address Summary-Only
    typedef bgp_SummaryOnly {
        type enumeration {

            // Enabled
            enum enabled {
                value 1;
            }

            // Disabled
            enum disabled {
                value 0;
            }
        }
        default "disabled";
    }

    // Table state
    typedef bgp_TblSt {
        type enumeration {

            // Unknown
            enum unknown {
                value 0;
            }

            // Up
            enum up {
                value 1;
            }

            // Down
            enum down {
                value 2;
            }
        }
    }

    // Table version
    typedef bgp_TblVer {
        type uint32;
    }

    // eBGP Multihop TTL value
    // Default Value "0" Removed - out of range 2..255
    typedef bgp_TtlVal {
        type uint16 {
            range "2..255";
        }
    }

    // Unknown Attribute Length
    typedef bgp_UnknownAttrLen {

        // MAX Converted to int from 0xffffffff
        type uint32 {
            range "0..4294967295";
        }
    }

    // Version
    typedef bgp_Ver {
        type enumeration {

            // BGP Version 4
            enum v4 {
                value 4;
            }
        }
        default "v4";
    }

    // VNID
    // Default Value "0" Removed - out of range 4096..16777215
    typedef bgp_Vnid {

        // MAX Converted to int from 0xffffff
        type uint32 {
            range "4096..16777215";
        }
    }

    // Dampen Igp Metric
    typedef bgp_igpMetric {
        type uint16 {
            range "0..3600";
        }
        default "600";
    }

    typedef cap_Constraint {
        type uint32;
    }

    typedef cap_Counter {
        type uint32;
    }

    typedef cap_Model {
        type string;
    }

    // Quantitative
    typedef cap_Quant {

        // MAX Converted to int from 0xFFFF
        type uint16 {
            range "0..65535";
        }
        default "0";
    }

    typedef cap_RaiseFaultState {
        type enumeration {
            enum nominal {
                value 0;
            }
            enum ruleHasLess {
                value 1;
            }
            enum ruleHasMore {
                value 2;
            }
        }
        default "nominal";
    }

    typedef cap_RuleT {
        type enumeration {
            enum limit {
                value 1;
            }
        }
        default "limit";
    }

    typedef cap_Scope {
        type enumeration {
            enum node {
                value 0;
            }
            enum policy-domain {
                value 1;
            }
            enum fabric {
                value 2;
            }
        }
        default "node";
    }

    typedef cap_StorageHint {
        type uint8;
    }

    typedef cap_Vendor {
        type string;
    }

    typedef cap_Version {
        type string;
    }

    // Adjacency state qualifier
    typedef cdp_AdjStQual {

        // bits- Using string
        type string;
    }

    // Capability type
    typedef cdp_CapT {

        // bits- Using string
        type string;
    }

    // Neighbor device id
    typedef cdp_DevId {
        type string;
    }

    // Device identifier type
    typedef cdp_DevIdT {
        type enumeration {

            // MAC address
            enum mac {
                value 1;
            }

            // Serial number
            enum serialNum {
                value 2;
            }

            // System name
            enum sysName {
                value 3;
            }

            // System name and serial number
            enum sysNameAndSerialNum {
                value 4;
            }
        }
        default "sysNameAndSerialNum";
    }

    // Neighbor device index
    typedef cdp_DevIndex {
        type uint32;
    }

    // Duplex
    typedef cdp_Duplex {
        type enumeration {

            // Unknown
            enum unknown {
                value 0;
            }

            // Half duplex
            enum half {
                value 1;
            }

            // Full duplex
            enum full {
                value 2;
            }
        }
    }

    // Hold interval
    // No Enums - transformed from scalar:Enum8 to scalar:UByte, YANG integer equivalent uint8
    typedef cdp_HoldIntvl {
        type uint8 {
            range "10..255";
        }
        default "180";
    }

    // MTU
    typedef cdp_MTU {
        type uint32;
    }

    // Neighbor version
    typedef cdp_NbrVer {
        type string;
    }

    // Operational state
    typedef cdp_OperSt {
        type enumeration {

            // Up
            enum up {
                value 1;
            }

            // Down
            enum down {
                value 2;
            }
        }
        default "down";
    }

    // Operational state qualifier
    typedef cdp_OperStQual {
        type enumeration {

            // Up
            enum up {
                value 1;
            }

            // Administratively down
            enum admin-down {
                value 2;
            }

            // Interface down
            enum if-down {
                value 3;
            }

            // Unsupported
            enum unsupported {
                value 4;
            }
        }
        default "unsupported";
    }

    // Neighbor platform id
    typedef cdp_PlatId {
        type string;
    }

    // Neighbor port id
    typedef cdp_PortId {
        type string;
    }

    // System Location
    typedef cdp_SysLoc {
        type string;
    }

    // System name
    typedef cdp_SysName {
        type string;
    }

    // System OID Length
    typedef cdp_SysObjIdL {
        type uint8;
    }

    // System OID Value
    typedef cdp_SysObjIdV {
        type mtx_array_uint32;
    }

    // Transmission frequency
    // No Enums - transformed from scalar:Enum8 to scalar:UByte, YANG integer equivalent uint8
    typedef cdp_TxFreq {
        type uint8 {
            range "5..254";
        }
        default "60";
    }

    // Version
    typedef cdp_Ver {
        type enumeration {

            // Version 1
            enum v1 {
                value 1;
            }

            // Version 2
            enum v2 {
                value 2;
            }
        }
        default "v2";
    }

    // Vlan id
    typedef cdp_VlanId {
        type uint16;
        default "0";
    }

    typedef comm_Port {
        type uint32 {
            range "1024..65000";
        }
    }

    typedef comp_DelimitedString {
        type string;
    }

    typedef comp_HostState {
        type enumeration {

            // Maintenance Mode
            enum maintenance {
                value 0;
            }

            // Connected
            enum connected {
                value 1;
            }

            // Not Responding
            enum noresponse {
                value 2;
            }

            // Disconnected
            enum disconnected {
                value 3;
            }

            // Powered On
            enum poweredOn {
                value 4;
            }

            // Powered Off
            enum poweredOff {
                value 5;
            }

            // StandBy
            enum standBy {
                value 6;
            }

            // Suspended
            enum suspended {
                value 7;
            }

            // Unknown
            enum unknown {
                value 8;
            }
        }
        default "disconnected";
    }

    typedef comp_InstType {
        type enumeration {

            // Unknown
            enum unknown {
                value 0;
            }

            // Baremetal Host
            enum phys {
                value 1;
            }

            // Virtual Machine
            enum virt {
                value 2;
            }

            // Hypervisor Host
            enum hv {
                value 3;
            }
        }
        default "unknown";
    }

    typedef comp_NicInstType {
        type comp_InstType;
    }

    typedef comp_NicState {
        type enumeration {

            // Down
            enum down {
                value 0;
            }

            // Up
            enum up {
                value 1;
            }
        }
        default "down";
    }

    typedef comp_Vendor {
        type enumeration {
            enum VMware {
                value 1;
            }
            enum Microsoft {
                value 2;
            }
        }
        default "VMware";
    }

    // Result of filter check
    typedef compat_FilterStatus {
        type enumeration {

            // failed
            enum failed {
                value 0;
            }

            // passed
            enum passed {
                value 1;
            }
        }
        default "failed";
    }

    // Adj addr
    typedef coop_AdjAddr {
        type address_Ipv4;
    }

    // Adjacency flags
    typedef coop_AdjFlags {

        // bits- Using string
        type string;
    }

    // Adjacency operational state
    typedef coop_AdjOperSt {
        type enumeration {

            // Down
            enum down {
                value 1;
            }

            // Up
            enum up {
                value 2;
            }
        }
        default "down";
    }

    // Adjacency operational state qualifier
    typedef coop_AdjOperStQual {
        type enumeration {

            // Unspecified
            enum unspecified {
                value 0;
            }

            // Route not reachable
            enum route-unreachable {
                value 1;
            }

            // TCP Connection Down
            enum tcp-down {
                value 2;
            }

            // Peer inactive
            enum peer-inactive {
                value 3;
            }

            // Peer congested
            enum peer-congested {
                value 4;
            }

            // Up
            enum up {
                value 5;
            }
        }
        default "unspecified";
    }

    // Collisions load factor
    typedef coop_CollLdFactor {

        // MAX Converted to int from 0xffff
        type uint16 {
            range "1..65535";
        }
        default "1";
    }

    // Ctx flags
    typedef coop_CtxFlags {

        // bits- Using string
        type string;
    }

    // Dampen action
    typedef coop_DampAction {
        type enumeration {

            // Freeze
            enum freeze {
                value 1;
            }

            // Withdraw
            enum withdraw {
                value 2;
            }
        }
        default "freeze";
    }

    // Half life
    typedef coop_DampHalfLife {

        // MAX Converted to int from 0xffff
        type uint16 {
            range "1..65535";
        }
        default "10";
    }

    // Dampen Penalty
    typedef coop_DampPenalty {

        // MAX Converted to int from 0xffff
        type uint16 {
            range "100..65535";
        }
        default "1000";
    }

    // Dampen reuse threshold
    typedef coop_DampReuseThresh {

        // MAX Converted to int from 0xffff
        type uint16 {
            range "100..65535";
        }
        default "2500";
    }

    // Dampen saturation threshold
    typedef coop_DampSatThresh {

        // MAX Converted to int from 0xffff
        type uint16 {
            range "100..65535";
        }
        default "10000";
    }

    // Dampen threshold
    typedef coop_DampThresh {

        // MAX Converted to int from 0xffff
        type uint16 {
            range "100..65535";
        }
        default "4000";
    }

    // Domain operational state
    typedef coop_DomOperSt {
        type enumeration {

            // Down
            enum down {
                value 0;
            }

            // Initializing
            enum init {
                value 1;
            }

            // Up
            enum up {
                value 2;
            }
        }
        default "down";
    }

    // Domain operational state qualifier
    typedef coop_DomOperStQual {
        type enumeration {

            // Unspecified
            enum unspecified {
                value 0;
            }

            // Configuration not resolved
            enum config-unresolved {
                value 1;
            }

            // Time not synced
            enum time-not-synced {
                value 2;
            }

            // Infra domain down
            enum infra-dom-down {
                value 3;
            }

            // Council pending
            enum council-pending {
                value 4;
            }

            // Inconsistent configuration
            enum inconsistent-config {
                value 5;
            }

            // Admin down
            enum admin-down {
                value 6;
            }

            // Up
            enum up {
                value 7;
            }
        }
        default "unspecified";
    }

    // Ep controls
    // Default Value computed from notify-citizen
    typedef coop_EpControl {

        // bits- Using string
        type string;
        default "notify-citizen";
    }

    // Ep flags
    typedef coop_EpFlags {

        // bits- Using string
        type string;
    }

    // Graceful restart time (in seconds)
    typedef coop_GRTime {

        // MAX Converted to int from 0xffff
        type uint32 {
            range "1..65535";
        }
        default "600";
    }

    // Hello Interval (in seconds)
    typedef coop_HelloIntvl {

        // MAX Converted to int from 0xffff
        type uint16 {
            range "1..65535";
        }
        default "60";
    }

    // IGMP version
    typedef coop_IGMPVersion {
        type uint8 {
            range "1..3";
        }
        default "2";
    }

    // McastGrp flags
    typedef coop_McGrpFlags {

        // bits- Using string
        type string;
    }

    // Mrtr flags
    typedef coop_MrtrFlags {

        // bits- Using string
        type string;
    }

    // Peer controls
    typedef coop_PeerControl {

        // bits- Using string
        type string;
    }

    // Port id
    typedef coop_PortId {

        // MAX Converted to int from 0xffffffff
        type uint32 {
            range "0..4294967295";
        }
        default "0";
    }

    // Publisher id
    typedef coop_PubId {
        type address_Ipv4;
    }

    // Refresh interval (in seconds)
    typedef coop_RefreshIntvl {

        // MAX Converted to int from 0x2aaaaaaa
        type uint32 {
            range "1..715827882";
        }
        default "3600";
    }

    // Repository size
    typedef coop_RepSz {

        // MAX Converted to int from 0xffffffff
        type uint32 {
            range "1..4294967295";
        }
        default "1000000";
    }

    // Repository type
    typedef coop_RepT {
        type enumeration {

            // Endpoint reachability repository
            enum ep {
                value 1;
            }

            // Oracle repository
            enum oracle {
                value 2;
            }

            // Leaf repository
            enum leaf {
                value 3;
            }

            // Multicast group membership repository
            enum mgrpmbr {
                value 4;
            }

            // Multicast router repository
            enum mrouter {
                value 5;
            }

            // Service node repository
            enum svcnode {
                value 6;
            }

            // Anycast repository
            enum anycast {
                value 7;
            }

            // External router repository
            enum extrtr {
                value 8;
            }

            // VPC repository
            enum vpc {
                value 9;
            }

            // VTEP repository
            enum vtep {
                value 10;
            }

            // Context repository
            enum ctx {
                value 11;
            }
        }
        default "ep";
    }

    // Role
    typedef coop_Role {
        type enumeration {

            // Citizen
            enum citizen {
                value 1;
            }

            // Oracle
            enum oracle {
                value 2;
            }
        }
        default "citizen";
    }

    // Shard Interval
    typedef coop_ShardIntvl {

        // MAX Converted to int from 0xffffffff
        type uint32 {
            range "1..4294967295";
        }
    }

    // Switch id
    typedef coop_SwId {
        type address_Ipv4;
    }

    // Synthetic flags
    typedef coop_SynthFlags {

        // bits- Using string
        type string;
    }

    // Synthetic Generator algorithm
    typedef coop_SynthGen {
        type enumeration {
            enum xxx {
                value 1;
            }
        }
        default "xxx";
    }

    // Synthetic ip
    typedef coop_SynthIp {
        type address_Ipv4;
    }

    // Synthetic vrf
    typedef coop_SynthVrf {
        type uint32;
    }

    // Timestamp (NTP raw format)
    typedef coop_Timestamp {
        type uint64;
    }

    // VNID
    typedef coop_Vnid {

        // MAX Converted to int from 0xffffff
        type uint32 {
            range "1..16777215";
        }
        default "1";
    }

    // Vpc flags
    typedef coop_VpcFlags {

        // bits- Using string
        type string;
    }

    // Affix type
    typedef copp_Affix {
        type enumeration {

            // Unknown
            enum unknown {
                value 0;
            }

            // Prefix
            enum prefix {
                value 1;
            }

            // Suffix
            enum suffix {
                value 2;
            }
        }
        default "unknown";
    }

    // Burst unit
    typedef copp_BurstUnit {
        type enumeration {

            // Unknown
            enum Unknown {
                value 0;
            }

            // Bytes
            enum bytes {
                value 1;
            }

            // KiloBytes
            enum kbytes {
                value 2;
            }

            // MegaBytes
            enum mbytes {
                value 3;
            }

            // Packets
            enum packets {
                value 4;
            }

            // Micro sec
            enum us {
                value 5;
            }

            // Milli sec
            enum ms {
                value 6;
            }
        }
        default "Unknown";
    }

    // Burst value
    typedef copp_BurstVal {
        type uint32;
    }

    // Confrom Action
    typedef copp_ConformAction {
        type enumeration {

            // Undefined
            enum Undefined {
                value 0;
            }

            // Transmit
            enum transmit {
                value 1;
            }

            // Drop
            enum drop {
                value 2;
            }
        }
        default "Undefined";
    }

    // Cos value
    typedef copp_CosVal {
        type uint16;
    }

    // Dscp value
    typedef copp_DscpVal {
        type uint16 {
            range "0..63";
        }
        default "0";
    }

    // Exceed action
    typedef copp_ExceedAction {
        type enumeration {

            // Undefined
            enum Undefined {
                value 0;
            }

            // Transmit
            enum transmit {
                value 1;
            }

            // Drop
            enum drop {
                value 2;
            }
        }
        default "Undefined";
    }

    // Exception options
    typedef copp_Excep {
        type enumeration {

            // Undefined
            enum Undefined {
                value 0;
            }

            // Glean
            enum glean {
                value 1;
            }

            // Mtu-failure
            enum mtu-failure {
                value 2;
            }

            // TTL-failure
            enum ttl-failure {
                value 3;
            }

            // Nat-flow
            enum nat-flow {
                value 4;
            }
        }
        default "Undefined";
    }

    // MPLs exp value
    typedef copp_ExpVal {
        type uint32 {
            range "0..7";
        }
    }

    typedef copp_Fcoe {
        type boolean;
    }

    // Icmp options
    typedef copp_Icmp {
        type enumeration {

            // Undefined
            enum Undefined {
                value 0;
            }

            // icmp redirect
            enum redirect {
                value 1;
            }

            // icmp unreachable
            enum unreachable {
                value 2;
            }
        }
        default "Undefined";
    }

    // Information Rate unit
    typedef copp_IrUnit {
        type enumeration {

            // Unknown
            enum Unknown {
                value 0;
            }

            // Bits/sec
            enum bps {
                value 1;
            }

            // Packets/sec
            enum pps {
                value 2;
            }

            // Kilo Bits/sec
            enum kbps {
                value 3;
            }

            // Mega Bits/sec
            enum mbps {
                value 4;
            }

            // Giga Bits/sec
            enum gbps {
                value 5;
            }
        }
        default "Unknown";
    }

    // Information rate value
    typedef copp_IrVal {
        type uint64;
    }

    // Level
    typedef copp_LevelRange {
        type uint16 {
            range "1..7";
        }
        default "1";
    }

    // Match Option
    typedef copp_MatchOption {
        type enumeration {

            // Unknown
            enum Unknown {
                value 0;
            }

            // Match Any
            enum MatchAny {
                value 1;
            }

            // Match All
            enum MatchAll {
                value 2;
            }
        }
        default "Unknown";
    }

    // Match criteria
    typedef copp_MatchT {
        type enumeration {

            // Undefined
            enum Undefined {
                value 0;
            }

            // match access-group
            enum access-group {
                value 1;
            }

            // match redirect
            enum redirect {
                value 2;
            }

            // match exception
            enum exception {
                value 3;
            }

            // match protocol
            enum protocol {
                value 4;
            }
        }
        default "Undefined";
    }

    // Multicast options
    typedef copp_Mcast {
        type enumeration {

            // Undefined
            enum Undefined {
                value 0;
            }

            // multicast dest-miss
            enum dest-miss {
                value 1;
            }

            // multicast rpf-failure
            enum rpf-failure {
                value 2;
            }

            // multicast sg-rpf-failure
            enum sg-rpf-failure {
                value 3;
            }

            // multicast ipv6-dest-miss
            enum ipv6-dest-miss {
                value 4;
            }

            // multicast ipv6-rpf-failure
            enum ipv6-rpf-failure {
                value 5;
            }

            // multicast ipv6-sg-rpf-failure
            enum ipv6-sg-rpf-failure {
                value 6;
            }
        }
        default "Undefined";
    }

    // CoPP Profile Type
    typedef copp_ProfT {
        type enumeration {

            // Unknown
            enum unknown {
                value 0;
            }

            // Strict
            enum strict {
                value 1;
            }

            // Moderate
            enum moderate {
                value 2;
            }

            // Dense
            enum dense {
                value 4;
            }

            // Lenient
            enum lenient {
                value 3;
            }
        }
        default "unknown";
    }

    // Protocol
    typedef copp_Proto {

        // bits- Using string
        type string;
    }

    typedef copp_Ralert {
        type boolean;
    }

    // Redirect options
    typedef copp_Rdrct {
        type enumeration {

            // Undefined
            enum Undefined {
                value 0;
            }

            // redirect arp-inspect
            enum arp-inspect {
                value 1;
            }

            // rediret dhcp-snoop
            enum dhcp-snoop {
                value 2;
            }
        }
        default "Undefined";
    }

    // Violate action
    typedef copp_ViolateAction {
        type enumeration {

            // Undefined
            enum Undefined {
                value 0;
            }

            // Transmit
            enum transmit {
                value 1;
            }

            // Drop
            enum drop {
                value 2;
            }
        }
        default "Undefined";
    }

    typedef datetime_AdminState {
        type enumeration {
            enum enabled {
                value 1;
            }
            enum disabled {
                value 2;
            }
        }
        default "disabled";
    }

    typedef datetime_AuthKeyId {

        // MAX Converted to int from 0xffff
        type uint16 {
            range "1..65535";
        }
        default "1";
    }

    typedef datetime_ClockFormat {
        type enumeration {

            // 24 Hours
            enum 24hours {
                value 0;
            }

            // 12 Hours
            enum 12hours {
                value 1;
            }
        }
        default "24hours";
    }

    typedef datetime_ClockProtocol {
        type enumeration {

            // Unspecified
            enum unspecified {
                value 0;
            }

            // Ptp
            enum ptp {
                value 1;
            }

            // Ntp
            enum ntp {
                value 2;
            }

            // None
            enum none {
                value 3;
            }
        }
        default "ntp";
    }

    typedef datetime_Date {
        type uint16 {
            range "1..31";
        }
    }

    // IsEncrpt type
    typedef datetime_Encrypt {
        type boolean;
        default "false";
    }

    typedef datetime_Gauge32 {
        type uint32;
    }

    typedef datetime_HourOffset {
        type int16 {
            range "-12..14";
        }
    }

    typedef datetime_InetAddressType {
        type enumeration {

            // Unknown
            enum unknown {
                value 0;
            }

            // IPv4
            enum ipv4 {
                value 1;
            }

            // IPv6
            enum ipv6 {
                value 2;
            }

            // IPv4z
            enum ipv4z {
                value 3;
            }

            // IPv6z
            enum ipv6z {
                value 4;
            }

            // DNS
            enum dns {
                value 16;
            }
        }
    }

    typedef datetime_Key {
        type string;
    }

    typedef datetime_KeyId {
        type uint16;
    }

    // Logging Level
    typedef datetime_LoggingLevel {
        type enumeration {

            // Emergency
            enum emergency {
                value 0;
            }

            // Alert
            enum alert {
                value 1;
            }

            // Critical
            enum critical {
                value 2;
            }

            // Error
            enum error {
                value 3;
            }

            // Warning
            enum warning {
                value 4;
            }

            // Notifications
            enum notif {
                value 5;
            }

            // Informational
            enum inform {
                value 6;
            }

            // Debug
            enum debug {
                value 7;
            }
        }
        default "critical";
    }

    typedef datetime_MinuteOffsetSt {
        type uint16 {
            range "1..1440";
        }
    }

    typedef datetime_MinuteOffsetTz {
        type uint16 {
            range "0..59";
        }
    }

    typedef datetime_Month {
        type enumeration {

            // January
            enum january {
                value 0;
            }

            // February
            enum february {
                value 1;
            }

            // March
            enum march {
                value 2;
            }

            // April
            enum april {
                value 3;
            }

            // May
            enum may {
                value 4;
            }

            // June
            enum june {
                value 5;
            }

            // July
            enum july {
                value 6;
            }

            // August
            enum august {
                value 7;
            }

            // September
            enum september {
                value 8;
            }

            // October
            enum october {
                value 9;
            }

            // November
            enum november {
                value 10;
            }

            // December
            enum december {
                value 11;
            }
        }
    }

    typedef datetime_NTPAssocIdentifier {
        type uint32 {
            range "0..2147483647";
        }
    }

    typedef datetime_NTPLeapIndicator {
        type uint8;
    }

    // NTP Peer Mode
    typedef datetime_NTPPeerMode {
        type enumeration {

            // Unspecified
            enum unspecified {
                value 0;
            }

            // Symmetric Active
            enum symmetricActive {
                value 1;
            }

            // Symmetric Passive
            enum symmetricPassive {
                value 2;
            }

            // Client
            enum client {
                value 3;
            }

            // Server
            enum server {
                value 4;
            }

            // Broadcast
            enum broadcast {
                value 5;
            }

            // Reserved Control
            enum reservedControl {
                value 6;
            }

            // Reserved Private
            enum reservedPrivate {
                value 7;
            }
        }
    }

    typedef datetime_NTPPollInterval {
        type int32 {
            range "-20..20";
        }
    }

    typedef datetime_NTPRefId {
        type address_Ipv4;
    }

    typedef datetime_NTPSignedTimeValue {
        type int32;
    }

    typedef datetime_NTPStratum {
        type uint8;
    }

    typedef datetime_NTPUnsignedTimeValue {
        type uint32;
    }

    // NTP Server Status
    typedef datetime_NtpSrvStatus {
        type enumeration {

            // Unknown
            enum unknown {
                value 1;
            }

            // Not Running
            enum not_running {
                value 2;
            }

            // Not Synchronized
            enum not_synchronized {
                value 3;
            }

            // Synced to Local Clock
            enum synced_local_clock {
                value 4;
            }

            // Synced to Local RefClock
            enum synced_local_hw_refclk {
                value 5;
            }

            // Synced to Remote NTP Server
            enum synced_remote_server {
                value 6;
            }
        }
        default "unknown";
    }

    // NTP Peer Status flags
    typedef datetime_PeerStatusFlags {

        // bits- Using string
        type string;
    }

    typedef datetime_Poll {
        type uint8 {
            range "4..16";
        }
    }

    typedef datetime_ProvT {
        type enumeration {

            // NTP peer
            enum peer {
                value 0;
            }

            // NTP server
            enum server {
                value 1;
            }

            // invalid
            enum invalid {
                value 2;
            }
        }
        default "invalid";
    }

    typedef datetime_Stratum {
        type uint8 {
            range "1..15";
        }
        default "8";
    }

    // System Status flags
    typedef datetime_SysStatusFlags {

        // bits- Using string
        type string;
    }

    typedef datetime_VdcId {
        type uint16 {
            range "1";
        }
        default "1";
    }

    typedef datetime_WeekNum {
        type uint16 {
            range "1..5";
        }
    }

    typedef datetime_Year {
        type uint16 {
            range "2000..2030";
        }
    }

    // Client interface operational state
    typedef dhcp_ClIfOperSt {
        type enumeration {

            // Unspecified
            enum unspecified {
                value 0;
            }

            // Initializing
            enum init {
                value 1;
            }

            // Discover
            enum discover {
                value 2;
            }

            // Requesting
            enum requesting {
                value 3;
            }

            // Address received
            enum addr-rcvd {
                value 4;
            }

            // Failed
            enum failed {
                value 5;
            }

            // Request timedout
            enum request-timedout {
                value 6;
            }

            // Operationally down
            enum down {
                value 7;
            }
        }
    }

    // DHCP Client identifier
    typedef dhcp_ClientId {
        type string;
    }

    // DAI Logging options
    typedef dhcp_DAILogType {
        type enumeration {

            // Logging for denied DHCP bindings
            enum deny {
                value 1;
            }

            // Log for Permitted DHCP Bindings
            enum permit {
                value 2;
            }

            // Log for All DHCP bindings
            enum all {
                value 3;
            }

            // No Logging for any DHCP bindings
            enum inone {
                value 5;
            }
        }
        default "deny";
    }

    // The file given by the server to the client
    typedef dhcp_File {
        type string;
    }

    // Host name
    typedef dhcp_HostName {
        type string;
    }

    // Lease time given the server
    typedef dhcp_LeaseTime {
        type uint16;
    }

    // Client mode, whether we are getting a dhcp address using my own
    // interface or through other pseudo interfaces
    typedef dhcp_Mode {
        type enumeration {

            // Normal
            enum normal {
                value 1;
            }

            // Pseudo
            enum pseudo {
                value 2;
            }
        }
        default "normal";
    }

    // DHCP message type
    typedef dhcp_MsgT {
        type enumeration {

            // Discover
            enum discover {
                value 1;
            }

            // Offer
            enum offer {
                value 2;
            }

            // Request
            enum request {
                value 3;
            }

            // Decline
            enum decline {
                value 4;
            }

            // Ack
            enum ack {
                value 5;
            }

            // Nak
            enum nak {
                value 6;
            }

            // Release
            enum release {
                value 7;
            }

            // Inform
            enum inform {
                value 8;
            }

            // Invalid
            enum invalid {
                value 255;
            }
        }
        default "discover";
    }

    // Status of client node Notification
    typedef dhcp_NotifStatus {
        type enumeration {

            // Active
            enum active {
                value 1;
            }

            // Processed
            enum processed {
                value 2;
            }
        }
        default "active";
    }

    typedef dhcp_NumLogBuffers {
        type uint16 {
            range "1..1024";
        }
        default "32";
    }

    typedef dhcp_OptionId {
        type uint8;
    }

    // DHCP options
    // Default Value computed from none
    typedef dhcp_Options {

        // bits- Using string
        type string;
        default "none";
    }

    // Represents the mode to be used for doing DHCP relay
    typedef dhcp_RelayVisibility {
        type enumeration {
            enum visible {
                value 0;
            }
            enum not-visible {
                value 1;
            }
        }
        default "not-visible";
    }

    // Vendor id
    typedef dhcp_VendorId {
        type string;
    }

    // Active interval
    typedef eigrp_ActIntvl {
        type uint16 {
            range "1..65535";
        }
        default "3";
    }

    // Adjacency operational state
    typedef eigrp_AdjOperSt {

        // bits- Using string
        type string;
    }

    // Adj Stub Route Advertise Flags    This is the PEER_INFORMATION_TYPE tlv received from the peer.
    // These flags are informational signals to the neighbors as to
    // which types of routes will be advertised
    typedef eigrp_AdjStubRtAdvFlags {

        // bits- Using string
        type string;
    }

    // Address family type
    typedef eigrp_AfT {
        type enumeration {

            // IPv4 unicast address family
            enum ipv4-ucast {
                value 1;
            }

            // IPv6 unicast address family
            enum ipv6-ucast {
                value 2;
            }
        }
        default "ipv4-ucast";
    }

    // Bandwidth
    typedef eigrp_Bw {
        type uint64;
    }

    // Database type
    typedef eigrp_DbT {
        type enumeration {

            // Route Database
            enum rt {
                value 1;
            }
        }
        default "rt";
    }

    // Delay
    typedef eigrp_Delay {
        type uint64;
    }

    // Administrative Distance (internal/external)
    typedef eigrp_Dist {
        type uint8 {
            range "1..255";
        }
    }

    // Eigrp major version
    typedef eigrp_EigrpMajVer {
        type uint8;
    }

    // Eigrp minor version
    typedef eigrp_EigrpMinVer {
        type uint8;
    }

    // External Protocol Nexthop flags
    typedef eigrp_ExtNhFlags {

        // bits- Using string
        type string;
    }

    // External Protocol Nexthop Originator
    typedef eigrp_ExtProtNhOrigin {
        type enumeration {

            // IGRP v1
            enum igrp-v1 {
                value 1;
            }

            // IGRP v2
            enum igrp-v2 {
                value 2;
            }

            // Static
            enum static {
                value 3;
            }

            // RIP
            enum rip {
                value 4;
            }

            // Hello Protocol
            enum hellop {
                value 5;
            }

            // OSPF
            enum ospf {
                value 6;
            }

            // ISIS
            enum isis {
                value 7;
            }

            // EGP
            enum egp {
                value 8;
            }

            // BGP
            enum bgp {
                value 9;
            }

            // IDRP
            enum idrp {
                value 10;
            }

            // Connected
            enum connected {
                value 11;
            }
        }
        default "bgp";
    }

    // Feasible Distance
    typedef eigrp_FDist {
        type uint64;
    }

    // Hello interval
    typedef eigrp_HelloIntvl {
        type uint16 {
            range "1..65535";
        }
        default "5";
    }

    // Hold interval
    typedef eigrp_HoldIntvl {
        type uint16 {
            range "1..65535";
        }
        default "15";
    }

    // Hops
    typedef eigrp_Hops {
        type uint16;
    }

    // Interface address family controls
    // Default Value computed from split-horizon,nh-self
    typedef eigrp_IfAfControl {

        // bits- Using string
        type string;
        default "split-horizon,nh-self";
    }

    // Load as a fraction of 255
    typedef eigrp_Load {
        type uint8;
    }

    // MTU
    typedef eigrp_MTU {
        type uint32;
    }

    // Maximum ECMP Paths
    typedef eigrp_MaxPaths {
        type uint8 {
            range "1..32";
        }
        default "8";
    }

    // Metric
    typedef eigrp_Metric {
        type uint32;
    }

    // Neighbor ID
    typedef eigrp_NbrId {
        type uint32;
    }

    // Nexthop Flags
    typedef eigrp_NhFlags {

        // bits- Using string
        type string;
    }

    // Nexthop Originator
    typedef eigrp_NhOrigin {
        type enumeration {

            // Connected
            enum connected {
                value 0;
            }

            // Static
            enum static {
                value 1;
            }

            // Connected via leak
            enum redist-connected {
                value 2;
            }

            // External protocol
            enum external {
                value 3;
            }

            // BGP VPNv4
            enum bgp-vpnv4 {
                value 4;
            }

            // Summary
            enum summary {
                value 5;
            }

            // EIGRP
            enum eigrp {
                value 7;
            }
        }
        default "eigrp";
    }

    // NSF operational state
    typedef eigrp_NsfOperSt {

        // bits- Using string
        type string;
    }

    // Reliability as a fraction of 255
    typedef eigrp_Reliability {
        type uint8;
    }

    // Reported Distance
    typedef eigrp_RepDist {
        type uint64;
    }

    // Route Flags
    typedef eigrp_RtFlags {

        // bits- Using string
        type string;
    }

    // Route operational state
    typedef eigrp_RtOperSt {
        type enumeration {

            // Passive
            enum passive {
                value 0;
            }

            // Active
            enum active {
                value 1;
            }
        }
        default "passive";
    }

    // Sequence Number
    typedef eigrp_SeqNo {
        type uint32;
    }

    // Serial Number
    typedef eigrp_SerNo {
        type uint64;
    }

    // Stub Route Advertise Controls    @@@ If none of the bits are set, no prefixes are advertised,
    // @@@ which is the equivalent of recv-only option
    // Default Value computed from connected,summary
    typedef eigrp_StubRtAdvControl {

        // bits- Using string
        type string;
        default "connected,summary";
    }

    // Software major version
    typedef eigrp_SwMajVer {
        type uint8;
    }

    // Software minor version
    typedef eigrp_SwMinVer {
        type uint8;
    }

    // Tag
    typedef eigrp_Tag {
        type uint32;
    }

    // URIB state for the nexthop
    // Default Value computed from in-rib
    typedef eigrp_UribSt {

        // bits- Using string
        type string;
        default "in-rib";
    }

    // BD operational state
    typedef epm_BdOperSt {

        // bits- Using string
        type string;
    }

    // Database type
    typedef epm_DbT {
        type enumeration {

            // Endpoint database
            enum ep {
                value 1;
            }
        }
        default "ep";
    }

    // Ep flags
    typedef epm_EpFlags {

        // bits- Using string
        type string;
    }

    // Ep operational state
    typedef epm_EpOperSt {
        type enumeration {

            // Down
            enum down {
                value 0;
            }

            // Up
            enum up {
                value 1;
            }
        }
    }

    // Ep operational state qualifier
    typedef epm_EpOperStQual {
        type enumeration {

            // Unspecified
            enum unspecified {
                value 0;
            }

            // Port Down
            enum port-down {
                value 1;
            }

            // Encapsulation Down
            enum encap-down {
                value 2;
            }

            // Internal Error
            enum internal-err {
                value 3;
            }

            // Up
            enum up {
                value 4;
            }
        }
    }

    // Operational State Qualifier
    typedef eptrk_OperStQual {
        type enumeration {

            // Success
            enum ok {
                value 1;
            }

            // Control Plane failure
            enum cp-fail {
                value 2;
            }

            // Data Plane failure
            enum dp-fail {
                value 3;
            }

            // LC out of Sync
            enum lc-out-of-sync {
                value 4;
            }

            // Policy not present
            enum pol-absent {
                value 5;
            }
        }
        default "ok";
    }

    // Memory access
    typedef eqpt_Acc {
        type enumeration {

            // Read only
            enum read-only {
                value 0;
            }

            // Write only
            enum read-write {
                value 1;
            }
        }
    }

    // Administrative state of equipment related mo
    typedef eqpt_AdSt {
        type enumeration {

            // Unknown
            enum unknown {
                value 0;
            }

            // Enabled
            enum enabled {
                value 1;
            }

            // Disabled
            enum disabled {
                value 2;
            }
        }
        default "enabled";
    }

    // air flow direction
    typedef eqpt_AirDir {
        type enumeration {

            // Unknown
            enum unknown {
                value 0;
            }

            // front2back
            enum front2back {
                value 1;
            }

            // back2front
            enum back2front {
                value 2;
            }
        }
        default "unknown";
    }

    // Amps
    typedef eqpt_Amps {
        type decimal64 {
            fraction-digits 2;
        }
    }

    // Capability type
    typedef eqpt_AsicCapability {

        // bits- Using string
        type string;
    }

    typedef eqpt_AsicNumSlices {
        type uint8 {
            range "0..6";
        }
        default "0";
    }

    // Type of the asic
    typedef eqpt_AsicT {
        type enumeration {

            // Northstar
            enum northstar {
                value 1;
            }

            // Alpine
            enum alpine {
                value 2;
            }

            // Broadcom
            enum bcm {
                value 3;
            }

            // Davos
            enum davos {
                value 4;
            }

            // Sugarbowl
            enum sugarbowl {
                value 5;
            }

            // Homewood
            enum homewood {
                value 6;
            }
        }
        default "northstar";
    }

    // baud rate type
    typedef eqpt_BaudRate {
        type enumeration {

            // 300 Baud Rate
            enum 300 {
                value 1;
            }

            // 1200 Baud Rate
            enum 1200 {
                value 2;
            }

            // 2400 Baud Rate
            enum 2400 {
                value 3;
            }

            // 4800 Baud Rate
            enum 4800 {
                value 4;
            }

            // 9600 Baud Rate
            enum 9600 {
                value 5;
            }

            // 38400 Baud Rate
            enum 38400 {
                value 6;
            }

            // 57600 Baud Rate
            enum 57600 {
                value 7;
            }

            // 115200 Baud Rate
            enum 115200 {
                value 8;
            }
        }
        default "115200";
    }

    // Operational status of the card
    typedef eqpt_COpSt {
        type enumeration {

            // Unknown
            enum unknown {
                value 0;
            }

            // Inserted
            enum inserted {
                value 1;
            }

            // Absent
            enum absent {
                value 2;
            }

            // Mismatch
            enum mismatch {
                value 3;
            }

            // Failed
            enum fail {
                value 4;
            }

            // Present
            enum present {
                value 5;
            }

            // Removed
            enum removed {
                value 6;
            }

            // Online
            enum online {
                value 7;
            }

            // Offline
            enum offline {
                value 8;
            }

            // Powered up
            enum pwr-up {
                value 9;
            }

            // Powered down
            enum pwr-down {
                value 10;
            }

            // Errored powered down
            enum err-pwr-down {
                value 11;
            }

            // Testing
            enum testing {
                value 12;
            }

            // Initializing
            enum init {
                value 13;
            }

            // Registration failed
            enum reg-failure {
                value 14;
            }

            // Downloading
            enum dnld {
                value 15;
            }

            // Upgrading
            enum upg {
                value 16;
            }

            // SRG failed
            enum srg-fail {
                value 17;
            }

            // HA Sequence number failed
            enum ha-seq-fail {
                value 18;
            }
        }
        default "unknown";
    }

    // Memory capacity
    typedef eqpt_Capacity {
        type uint32;
        default "0";
    }

    typedef eqpt_CardId {
        type uint32;
    }

    typedef eqpt_CardNumPorts {
        type uint16 {
            range "0..256";
        }
        default "0";
    }

    // Type of the card
    typedef eqpt_CardT {
        type enumeration {

            // Unknown
            enum unknown {
                value 0;
            }

            // Supervisor
            enum supervisor {
                value 1;
            }

            // Line card
            enum linecard {
                value 2;
            }

            // Fabric card
            enum fabriccard {
                value 3;
            }

            // System control card
            enum sysctrlcard {
                value 4;
            }

            // Extension chassis card
            enum extchcard {
                value 5;
            }

            // fan tray
            enum fan-tray {
                value 6;
            }

            // power supply
            enum power-supply {
                value 7;
            }
        }
        default "unknown";
    }

    // Chassis operational state
    typedef eqpt_ChOperSt {
        type enumeration {

            // Not Operational
            enum not-operational {
                value 0;
            }

            // Failed
            enum failed {
                value 1;
            }

            // Online
            enum online {
                value 2;
            }
        }
        default "not-operational";
    }

    // Led color
    typedef eqpt_Color {
        type enumeration {

            // No color
            enum no-color {
                value 0;
            }

            // Green
            enum green {
                value 1;
            }

            // Yellow
            enum yellow {
                value 2;
            }

            // Amber
            enum amber {
                value 3;
            }

            // Red
            enum red {
                value 4;
            }

            // Blue
            enum blue {
                value 5;
            }
        }
        default "no-color";
    }

    // Number of cores
    typedef eqpt_Cores {
        type uint16;
    }

    typedef eqpt_DataBits {
        type uint16 {
            range "5..8";
        }
        default "8";
    }

    // Ejector status for the card
    typedef eqpt_EjSt {
        type enumeration {

            // Open
            enum open {
                value 0;
            }

            // Closed
            enum closed {
                value 1;
            }
        }
        default "closed";
    }

    // Extended chassis Id
    typedef eqpt_ExtChId {
        type uint16 {
            range "100..200";
        }
    }

    typedef eqpt_ExtChNumMacs {
        type uint16 {
            range "1..128";
        }
        default "64";
    }

    typedef eqpt_ExtChNumUplinkP {
        type uint16 {
            range "4..32";
        }
        default "4";
    }

    // Extended chassis (fex) state
    typedef eqpt_ExtChSt {
        type enumeration {

            // Unknown
            enum unknown {
                value 0;
            }

            // Initializing
            enum initializing {
                value 1;
            }

            // Discovered
            enum discovered {
                value 2;
            }

            // Connected
            enum connected {
                value 3;
            }

            // Registering
            enum reg {
                value 4;
            }

            // Registered
            enum regDone {
                value 5;
            }

            // Ready
            enum ready {
                value 6;
            }

            // Online sequence
            enum onlSeq {
                value 7;
            }

            // Online
            enum online {
                value 8;
            }

            // Offline Request
            enum offReq {
                value 9;
            }

            // Offline Sequence
            enum offSeq {
                value 10;
            }

            // Offline
            enum offline {
                value 11;
            }

            // Image download
            enum imgDld {
                value 12;
            }

            // Failed
            enum failed {
                value 13;
            }

            // Removed
            enum removed {
                value 14;
            }

            // Hitless upgrade sequence
            enum hlUpgSeq {
                value 15;
            }

            // Check upgrade sequence
            enum chkUpgSeq {
                value 16;
            }

            // Save states
            enum svStates {
                value 17;
            }

            // Hitless upgrade idle
            enum hlUpgIdle {
                value 18;
            }

            // Check insert sequence
            enum chkInsSeq {
                value 19;
            }

            // Hitless upgrade failed
            enum hlUpgFail {
                value 20;
            }

            // Active active upgrade ready
            enum aaUpgRdy {
                value 21;
            }

            // Active active upgrade idle
            enum aaUpgIdle {
                value 22;
            }

            // Active active upgrade done
            enum aaUpgOver {
                value 23;
            }

            // Active active upgrade fail
            enum aaUpgFail {
                value 24;
            }

            // Active active version mismatch
            enum aaVersMismatch {
                value 25;
            }

            // Extended chassis type mismatch
            enum ExtChTypeMismatch {
                value 26;
            }
        }
        default "unknown";
    }

    // Type of the fpga
    typedef eqpt_FpgaT {
        type enumeration {

            // IO FPGA
            enum io {
                value 1;
            }

            // MI FPGA
            enum mi {
                value 2;
            }
        }
        default "io";
    }

    // Generic item identifier
    typedef eqpt_Id {
        type uint32;
    }

    typedef eqpt_InactiveIntvl {
        type uint32 {
            range "0..525600";
        }
        default "0";
    }

    // Led operational state
    typedef eqpt_LedOpSt {
        type enumeration {

            // Unknown
            enum unknown {
                value 0;
            }

            // Off
            enum off {
                value 1;
            }

            // On
            enum on {
                value 2;
            }

            // Blinking
            enum blinking {
                value 3;
            }

            // Fail
            enum fail {
                value 4;
            }
        }
        default "unknown";
    }

    // indicator led type, should match snmp led types
    typedef eqpt_LedType {
        type enumeration {

            // Unknown
            enum unknown {
                value 0;
            }

            // status
            enum status {
                value 1;
            }

            // system
            enum system {
                value 2;
            }

            // active
            enum active {
                value 3;
            }

            // power
            enum power {
                value 4;
            }

            // battery
            enum battery {
                value 5;
            }

            // LC status
            enum lc-status {
                value 6;
            }

            // SUP status
            enum sup-status {
                value 7;
            }

            // Fabric status
            enum fc-status {
                value 8;
            }

            // Fan status
            enum fan-status {
                value 9;
            }

            // power status
            enum pwr-status {
                value 10;
            }
        }
        default "unknown";
    }

    // Default Value computed from unk
    typedef eqpt_LogType {

        // bits- Using string
        type string;
        default "unk";
    }

    typedef eqpt_MacAddr {
        type string;
    }

    typedef eqpt_MacAddrLen {
        type uint16;
    }

    // Memory type
    typedef eqpt_MemT {
        type enumeration {

            // Unknown
            enum unk {
                value 0;
            }

            // Dimm
            enum dimm {
                value 1;
            }

            // Flash
            enum flash {
                value 2;
            }

            // sprom
            enum sprom {
                value 3;
            }
        }
    }

    // Model
    typedef eqpt_Model {
        type string;
    }

    // Non redundancy reason
    typedef eqpt_NRdnRsn {
        type enumeration {

            // Not applicable
            enum na {
                value 1;
            }

            // Unknown
            enum unknown {
                value 2;
            }

            // Single power supply
            enum single {
                value 3;
            }

            // Mis matched power supply
            enum mismatch {
                value 4;
            }

            // Power supply error
            enum error {
                value 5;
            }
        }
        default "na";
    }

    // Operational state of equipment related mo
    typedef eqpt_OpSt {
        type enumeration {

            // Unknown
            enum unknown {
                value 0;
            }

            // OK
            enum ok {
                value 1;
            }

            // Fail
            enum fail {
                value 2;
            }

            // Absent
            enum absent {
                value 3;
            }

            // Shut
            enum shut {
                value 4;
            }

            // mismatch
            enum mismatch {
                value 5;
            }
        }
        default "unknown";
    }

    // Operational state qualifier
    typedef eqpt_OperStQual {
        type string;
    }

    // parity type
    typedef eqpt_Parity {
        type enumeration {

            // No parity
            enum none {
                value 0;
            }

            // Even parity
            enum even {
                value 1;
            }

            // Odd parity
            enum odd {
                value 2;
            }
        }
        default "none";
    }

    typedef eqpt_PartNum {
        type string;
    }

    // Type of the port
    typedef eqpt_PortT {
        type enumeration {

            // Unknown
            enum unknown {
                value 0;
            }

            // EOBC
            enum eobc {
                value 1;
            }

            // Management Port
            enum mgmt {
                value 2;
            }

            // Fabric Port
            enum fab {
                value 3;
            }

            // Access Port
            enum leaf {
                value 4;
            }

            // Extended Chassis Host Port
            enum extchhp {
                value 5;
            }

            // Extended Chassis Fabric Port
            enum extchfp {
                value 6;
            }
        }
        default "unknown";
    }

    // Power supply redundancy mode
    typedef eqpt_PsRdnM {
        type enumeration {

            // unknown
            enum unknown {
                value 0;
            }

            // Not supported
            enum not-supp {
                value 1;
            }

            // Redundant
            enum rdn {
                value 2;
            }

            // Combined
            enum comb {
                value 3;
            }

            // Non redundant
            enum n-rdn {
                value 4;
            }

            // Power output redundancy
            enum ps-rdn {
                value 5;
            }

            // Input source redundancy
            enum insrc-rdn {
                value 6;
            }

            // Single input redundancy
            enum sinin-rdn {
                value 7;
            }
        }
        default "comb";
    }

    // power state of a card
    typedef eqpt_PwrState {
        type enumeration {

            // Unknown
            enum unknown {
                value 0;
            }

            // Off
            enum off {
                value 1;
            }

            // On
            enum on {
                value 2;
            }

            // Deny
            enum deny {
                value 3;
            }

            // Multiple boot failure
            enum multi-boot-fail {
                value 4;
            }
        }
        default "unknown";
    }

    // Redundancy state
    typedef eqpt_RdSt {
        type enumeration {

            // Unknown
            enum unknown {
                value 0;
            }

            // Active
            enum active {
                value 1;
            }

            // Standby
            enum standby {
                value 2;
            }
        }
        default "unknown";
    }

    // Revision
    typedef eqpt_Revision {
        type string;
        default "0";
    }

    // Operational state of sensor mo
    typedef eqpt_SensorOpSt {
        type enumeration {

            // Fail
            enum fail {
                value 0;
            }

            // Normal
            enum normal {
                value 1;
            }

            // Minor Alarm
            enum minor {
                value 2;
            }

            // Major Alarm
            enum major {
                value 3;
            }

            // Absent
            enum absent {
                value 4;
            }

            // Bad Asic
            enum bad-asic {
                value 5;
            }
        }
        default "absent";
    }

    // Sensor type
    typedef eqpt_SensorT {
        type enumeration {

            // CPU sensor
            enum cpu {
                value 1;
            }

            // Inlet sensor
            enum inlet {
                value 2;
            }

            // Outlet sensor
            enum outlet {
                value 3;
            }

            // Hotswap sensor
            enum hotswap {
                value 4;
            }

            // Dimm sensor
            enum dimm {
                value 5;
            }

            // Phy sensor
            enum phy {
                value 6;
            }

            // SFP sensor
            enum sfp {
                value 7;
            }

            // QSFP sensor
            enum qsfp {
                value 8;
            }

            // Asic sensor
            enum asic {
                value 9;
            }

            // PCH
            enum pch {
                value 10;
            }

            // cpu VRM
            enum cpu-crm {
                value 11;
            }

            // Asic VRM
            enum asic-vrm {
                value 12;
            }

            // x86 cpu
            enum x86 {
                value 18;
            }

            // arm cpu
            enum arm {
                value 19;
            }
        }
        default "asic";
    }

    // Serial number
    typedef eqpt_Serial {
        type string;
    }

    // Status of the card from slot perspective
    typedef eqpt_SlotCardOpSt {
        type enumeration {

            // Unknown
            enum unknown {
                value 0;
            }

            // Mis matched
            enum mismatch {
                value 1;
            }

            // Unrecoverable Error
            enum unrecoverable {
                value 2;
            }
        }
        default "unknown";
    }

    // Slot controls
    typedef eqpt_SlotControl {

        // bits- Using string
        type string;
    }

    // Location of the slot
    typedef eqpt_SlotLoc {
        type enumeration {

            // Unknown
            enum unknown {
                value 0;
            }

            // Front
            enum front {
                value 1;
            }

            // Rear
            enum rear {
                value 2;
            }
        }
        default "unknown";
    }

    // Status of the slot
    typedef eqpt_SlotOpSt {
        type enumeration {

            // empty
            enum empty {
                value 0;
            }

            // Inserted
            enum inserted {
                value 1;
            }
        }
        default "empty";
    }

    // Type of the slot
    typedef eqpt_SlotT {
        type enumeration {

            // Unknown
            enum unknown {
                value 0;
            }

            // Supervisor slot
            enum supslot {
                value 1;
            }

            // Line card slot
            enum lcslot {
                value 2;
            }

            // Fabric card slot
            enum fcslot {
                value 3;
            }

            // System control card slot
            enum scslot {
                value 4;
            }

            // Extension chassis slot
            enum extchslot {
                value 5;
            }

            // Power supply slot
            enum psuslot {
                value 6;
            }

            // Fan tray
            enum fantray {
                value 7;
            }

            // Board Slot
            enum bslot {
                value 8;
            }

            // Nic Slot
            enum nslot {
                value 9;
            }
        }
        default "unknown";
    }

    // Socket
    typedef eqpt_Sock {
        type enumeration {

            // socket
            enum unspecified {
                value 0;
            }
        }
    }

    // Error reason for sprom failure
    typedef eqpt_SpErrRsn {
        type enumeration {

            // Unknown
            enum unknown {
                value 0;
            }

            // Checksum failure
            enum cksumfail {
                value 1;
            }

            // Access failure
            enum accessfail {
                value 2;
            }

            // none
            enum none {
                value 3;
            }
        }
        default "unknown";
    }

    // Speed
    typedef eqpt_Speed {
        type decimal64 {
            fraction-digits 2;
        }
    }

    typedef eqpt_StopBits {
        type uint16 {
            range "1..2";
        }
        default "1";
    }

    // Temperature threshold
    typedef eqpt_TempThresh {
        type int16;
    }

    // Voltage source
    typedef eqpt_VSrc {
        type enumeration {

            // Unknown
            enum unknown {
                value 0;
            }

            // 110v
            enum 110v {
                value 1;
            }

            // 220v
            enum 220v {
                value 2;
            }
        }
        default "unknown";
    }

    // Vendor
    typedef eqpt_Vendor {
        type string;
    }

    // Volts
    typedef eqpt_Volts {
        type decimal64 {
            fraction-digits 2;
        }
    }

    // Watts
    typedef eqpt_Watts {
        type uint32;
    }

    // Connector type
    typedef eqptcap_ConnT {
        type enumeration {

            // Unspecified
            enum unspecified {
                value 0;
            }

            // SC
            enum sc {
                value 1;
            }

            // FC1-COPPER
            enum fc1-copper {
                value 2;
            }

            // FC2-COPPER
            enum fc2-copper {
                value 3;
            }

            // BNC-TNC
            enum bnc-tnc {
                value 4;
            }

            // FC-COAX
            enum fc-coax {
                value 5;
            }

            // FIBER-JACK
            enum fiber-jack {
                value 6;
            }

            // LC
            enum lc {
                value 7;
            }

            // MT-RJ
            enum mt-rj {
                value 8;
            }

            // MU
            enum mu {
                value 9;
            }

            // SG
            enum sg {
                value 10;
            }

            // OPTICAL-PIGTAIL
            enum optical-pigtail {
                value 11;
            }

            // MPO
            enum mpo {
                value 12;
            }

            // HSSDC-2
            enum hssdc-2 {
                value 32;
            }

            // COPPER-PIGTAIL
            enum copper-pigtail {
                value 33;
            }

            // RJ45
            enum rj45 {
                value 34;
            }
        }
        default "unspecified";
    }

    // Internal vendor ID
    typedef eqptcap_IntVendorId {
        type uint8 {
            range "0..64";
        }
        default "64";
    }

    // Sfp Vendor Magic Key
    typedef eqptcap_SfpVendorMagicKey {
        type mtx_array_uint8;
    }

    typedef eqptcap_Size {
        type decimal64 {
            fraction-digits 2;
        }
        default "0.0";
    }

    // Weight units (pounds).
    typedef eqptcap_Weight {
        type decimal64 {
            fraction-digits 2;
        }
        default "0.0";
    }

    // Xcvr type
    typedef eqptcap_XcvrT {
        type enumeration {

            // Unspecified
            enum unspecified {
                value 0;
            }

            // GBIC
            enum gbic {
                value 1;
            }

            // SOLDER
            enum solder {
                value 2;
            }

            // SFP
            enum sfp {
                value 3;
            }

            // XBI
            enum xbi {
                value 4;
            }

            // XENPAK
            enum xenpak {
                value 5;
            }

            // XFP
            enum xfp {
                value 6;
            }

            // XFF
            enum xff {
                value 7;
            }

            // XFP-E
            enum xfp-e {
                value 8;
            }

            // XPAK
            enum xpak {
                value 9;
            }

            // X2
            enum x2 {
                value 10;
            }

            // DWDM-SFP
            enum dwdm-sfp {
                value 11;
            }

            // QSFP
            enum qsfp {
                value 12;
            }
        }
        default "unspecified";
    }

    // All Diag Test Groups
    typedef eqptdiag_AllGrpsT {
        type enumeration {

            // None
            enum none {
                value 0;
            }

            // System Memory
            enum sys-mem {
                value 1;
            }

            // CPU
            enum cpu {
                value 2;
            }

            // Peripherals
            enum peripherals {
                value 3;
            }

            // Internal Connectivity
            enum internal-conn {
                value 4;
            }

            // ASIC
            enum asic {
                value 5;
            }

            // Port
            enum port {
                value 6;
            }
        }
        default "none";
    }

    // Type of all the test rules
    typedef eqptdiag_Type {
        type uint16;
        default "0";
    }

    // Bitmap Type of All the test rules
    // Default Value computed from unspecified
    typedef eqptdiag_TypeBm {

        // bits- Using string
        type string;
        default "unspecified";
    }

    // Access pacer credits
    typedef ethpm_AccessCredits {
        type uint32 {
            range "1..16";
        }
        default "1";
    }

    // Active PC Members    Size based off of PCM_MAX_PORTS_PER_CHANNEL
    typedef ethpm_ActiveMembersList {
        type mtx_array_ifindex;
    }

    // EEE 10G wake times    Size based off of MAX_EEE_WAKE_TIMES
    typedef ethpm_EeeWakeTimesList {
        type mtx_array_uint16;
    }

    // Error disable event type
    typedef ethpm_ErrDisEvent {
        type enumeration {

            // Link State Flapping
            enum event-link-flap {
                value 0;
            }

            // UDLD
            enum event-udld {
                value 1;
            }

            // BPDU Guard
            enum event-bpduguard {
                value 2;
            }

            // Loopback detected by UDLD
            enum event-loopback {
                value 3;
            }

            // Storm Control
            enum event-storm-ctrl {
                value 4;
            }
            enum event-dhcp-rate-lim {
                value 5;
            }
            enum event-arp-inspection {
                value 6;
            }

            // 802.1x Violation
            enum event-sec-violation {
                value 7;
            }

            // Psecure Violation
            enum event-psec-violation {
                value 8;
            }

            // STP Inconsistent VPC Peer-link state
            enum event-stp-inconsist-vpc-peerlink {
                value 9;
            }

            // STP set port state failure
            enum event-set-port-state-failed {
                value 10;
            }
            enum event-debug-1 {
                value 11;
            }
            enum event-debug-2 {
                value 12;
            }
            enum event-debug-3 {
                value 13;
            }
            enum event-debug-4 {
                value 14;
            }
            enum event-debug-5 {
                value 15;
            }
            enum event-ip-addr-conflict {
                value 16;
            }
            enum event-ipqos-mgr-error {
                value 17;
            }
            enum event-ethpm {
                value 18;
            }
            enum event-ipqos-dcbxp-compat-failure {
                value 19;
            }
            enum event-syserr-based {
                value 20;
            }
            enum unknown {
                value 21;
            }

            // Loop indication by MCP
            enum event-mcp-loop {
                value 22;
            }

            // Frequent EP move
            enum event-ep-move {
                value 23;
            }
        }
    }

    typedef ethpm_ErrDisRecovIntvl {
        type uint32 {
            range "30..65535";
        }
        default "300";
    }

    // Error Vlan Status    Size based off of ETHPM_MAX_VLAN_COUNT    TODO: This is too large as an array of 4k status
    // We need to rethink the design of this at some point
    // when this is needed
    typedef ethpm_ErrorVlanStatusList {
        type uint32;
    }

    // Fabric port pacer credits
    typedef ethpm_FabricPortCredits {
        type uint32 {
            range "0..48";
        }
        default "0";
    }

    // Fcot flags
    typedef ethpm_FcotFlags {
        type enumeration {
            enum unknown {
                value 0;
            }
            enum access-failed {
                value 1;
            }
            enum checksum-failed {
                value 2;
            }
            enum vendor-crc-failed {
                value 3;
            }
            enum sfp-speed-mismatch {
                value 4;
            }
            enum eth-compalint-failed {
                value 5;
            }
            enum unknown-xcvr-type {
                value 6;
            }
            enum emphasis-checksum-failed {
                value 7;
            }
            enum init-failed {
                value 8;
            }
            enum ok-auth-success-no-md5 {
                value 9;
            }
            enum auth-failed {
                value 10;
            }
            enum ok-delayed-auth-success {
                value 11;
            }
            enum delayed-auth-failed {
                value 12;
            }
            enum ok-no-md5 {
                value 13;
            }
            enum ok {
                value 14;
            }
        }
        default "unknown";
    }

    // Fcot state
    typedef ethpm_FcotState {
        type enumeration {
            enum unknown {
                value 0;
            }
            enum inserted {
                value 1;
            }
            enum removed {
                value 2;
            }
            enum hw-failure {
                value 3;
            }
            enum inserted-initializing {
                value 4;
            }
        }
        default "unknown";
    }

    // Fcot type
    typedef ethpm_FcotType {
        type enumeration {
            enum unknown {
                value 0;
            }
            enum xfp {
                value 1;
            }
            enum x2 {
                value 2;
            }
            enum dummy {
                value 3;
            }
            enum sfp {
                value 4;
            }
            enum qsfp {
                value 5;
            }
            enum cfp-40g {
                value 6;
            }
            enum cfp-100g {
                value 7;
            }
            enum cfp {
                value 8;
            }
        }
        default "unknown";
    }

    // Bundle List    Size based off of MAX_BUNDLES
    typedef ethpm_IfBundleList1024 {
        type mtx_array_ifindex;
    }

    // Last Errors    Size based off of ETHPM_MAX_LAST_ERRORS
    typedef ethpm_LastErrorsList {
        type mtx_array_uint32;
    }

    // LB Bitmap
    typedef ethpm_LbBitmap {
        type mtx_array_bit;
    }

    // Model List
    typedef ethpm_ModelList {
        type mtx_array_uint8;
    }

    // Not connected timer
    typedef ethpm_NotConnectedTimer {
        type uint32 {
            range "1000..60000";
        }
        default "30000";
    }

    // Not up timer
    typedef ethpm_NotUpTimer {
        type uint32 {
            range "3000..60000";
        }
        default "60000";
    }

    // Per sub-interface pacer credits
    typedef ethpm_PerSiCredits {
        type uint32 {
            range "0..8";
        }
        default "0";
    }

    // Per vlan pacer credits
    typedef ethpm_PerVlanCredits {
        type uint32 {
            range "0..8";
        }
        default "0";
    }

    // Port Bitmap
    typedef ethpm_PortBitmap {
        type mtx_array_bit;
    }

    // Port Group Bitmap
    typedef ethpm_PortGroupBitmap {
        type mtx_array_bit;
    }

    // Port Oper Bitset    Size based off of ETHPM_PORT_OPER_BITSET_SZ
    typedef ethpm_PortOperBitmap {
        type mtx_array_bit;
    }

    // Routed port pacer credits
    typedef ethpm_RouetdPortCredits {
        type uint32 {
            range "1..16";
        }
        default "2";
    }

    // Sfp Date Code    Size based off of SFP_MSA_SID_DATE_CODE_SZ
    typedef ethpm_SfpDateCodeBytes {
        type mtx_array_uint8;
    }

    // Sfp Description    Size based off of SFP_MSA_SID_CISCO_PID_SZ+1
    typedef ethpm_SfpDescriptionBytes {
        type mtx_array_uint8;
    }

    // Sfp Extended Option    Size based off of SFP_MSA_SID_OPT_SZ
    typedef ethpm_SfpExtendedOptionBytes {
        type mtx_array_uint8;
    }

    // Sfp Part Number    Size based off of SFP_MSA_SID_CISCO_PN_SZ+1
    typedef ethpm_SfpPartNumberBytes {
        type mtx_array_uint8;
    }

    // SFP Reserved4    Size based off of SFP_MSA_SID_RESERVED4_SZ
    typedef ethpm_SfpReserved4Array {
        type mtx_array_uint8;
    }

    // Sfp Vendor Id    Size based off of SFP_MSA_SID_VENDOR_OUI_SZ
    typedef ethpm_SfpVendorIdBytes {
        type mtx_array_uint8;
    }

    // Sfp Vendor Name    Size based off of SFP_MSA_SID_VENDOR_NAME_SZ
    typedef ethpm_SfpVendorNameBytes {
        type mtx_array_uint8;
    }

    // Sfp Vendor Revision Number    Size based off of SFP_MSA_SID_VENDOR_REV_SZ
    typedef ethpm_SfpVendorRevisionNumberBytes {
        type mtx_array_uint8;
    }

    // Sfp Vendor Serial Number    Size based off of SFP_MSA_SID_VENDOR_SN_SZ
    typedef ethpm_SfpVendorSerialNumberBytes {
        type mtx_array_uint8;
    }

    // Sfp Version Id    Size based off of SFP_MSA_SID_CISCO_VID_SZ+1
    typedef ethpm_SfpVersionIdBytes {
        type mtx_array_uint8;
    }

    // Sfp Xcvr Code    Size based off of SFP_MSA_SID_TRANS_SZ
    typedef ethpm_SfpXcvrCodeBytes {
        type mtx_array_uint8;
    }

    // Si List    Size based off of ETHPM_MAX_VLAN_COUNT
    typedef ethpm_SiBitmap {
        type mtx_array_bit;
    }

    // Syslog Info
    typedef ethpm_SyslogInfo {
        type enumeration {
            enum default {
                value 0;
            }
            enum info-1 {
                value 1;
            }
        }
        default "default";
    }

    // Syslog level
    typedef ethpm_SyslogLevel {
        type uint32 {
            range "1..7";
        }
        default "5";
    }

    // Total pacer credits
    typedef ethpm_TotalCredits {
        type uint32 {
            range "1..256";
        }
        default "32";
    }

    // Trunk pacer credits
    typedef ethpm_TrunkCredits {
        type uint32 {
            range "1..16";
        }
        default "4";
    }

    // Type List
    typedef ethpm_TypeList {
        type mtx_array_uint8;
    }

    // Sfp Vendor Part Number    Size based off of SFP_MSA_SID_VENDOR_PN_SZ
    typedef ethpm_VendorPartNumberBytes {
        type mtx_array_uint8;
    }

    // X2 Bit Rate    Size based off of SFP_XMSA_BIT_RATE_SZ
    typedef ethpm_X2BitRateBytes {
        type mtx_array_uint8;
    }

    // X2 Cisco Part Number    Size based off of SFP_XMSA_CISCO_PN_SZ
    typedef ethpm_X2CiscoPartNumberBytes {
        type mtx_array_uint8;
    }

    // X2 Cisco Pid    Size based off of SFP_XMSA_CISCO_PID_SZ
    typedef ethpm_X2CiscoPidBytes {
        type mtx_array_uint8;
    }

    // X2 Cisco Revision Number    Size based off of SFP_XMSA_CISCO_REV_SZ
    typedef ethpm_X2CiscoRevisionNumberBytes {
        type mtx_array_uint8;
    }

    // X2 Cisco Serial Number    Size based off of SFP_XMSA_CISCO_SN_SZ
    typedef ethpm_X2CiscoSerialNumberBytes {
        type mtx_array_uint8;
    }

    // X2 Cisco Vendor Id    Size based off of SFP_XMSA_CISCO_VID_SZ
    typedef ethpm_X2CiscoVendorIdBytes {
        type mtx_array_uint8;
    }

    // X2 Date Code    Size based off of SFP_XMSA_DATE_CODE_SZ
    typedef ethpm_X2DateCodeBytes {
        type mtx_array_uint8;
    }

    // X2 Extended Vendor Specific Info    Size based off of SFP_XMSA_EXNTD_VENDOR_SPEC_SZ
    typedef ethpm_X2ExtendedVendorSpecificInfoBytes {
        type mtx_array_uint8;
    }

    // X2 Fibre Type    Size based off of SFP_XMSA_FIBRE_TYPE_SZ
    typedef ethpm_X2FibreTypeBytes {
        type mtx_array_uint8;
    }

    // X2 Lot Code    Size based off of SFP_XMSA_LOT_CODE_SZ
    typedef ethpm_X2LotCodeBytes {
        type mtx_array_uint8;
    }

    // X2 Package Oui    Size based off of SFP_XMSA_PACKAGE_OUI_SZ
    typedef ethpm_X2PackageOuiBytes {
        type mtx_array_uint8;
    }

    // X2 Range    Size based off of SFP_XMSA_RANGE_SZ
    typedef ethpm_X2RangeBytes {
        type mtx_array_uint8;
    }

    // X2 Sonet Sdh Code    Size based off of SFP_XMSA_SONET_SDH_CODE_SZ
    typedef ethpm_X2SonetSdhCodeBytes {
        type mtx_array_uint8;
    }

    // Vendor Data    Size based off of SFP_VENDOR_SPECIFIC_DATA_SZ
    typedef ethpm_X2VendorDataBytes {
        type mtx_array_uint8;
    }

    // X2 Vendor Name    Size based off of SFP_XMSA_SID_VENDOR_NAME_SZ
    typedef ethpm_X2VendorNameBytes {
        type mtx_array_uint8;
    }

    // X2 Vendor Oui    Size based off of SFP_XMSA_VENDOR_OUI_SZ
    typedef ethpm_X2VendorOuiBytes {
        type mtx_array_uint8;
    }

    // X2 Vendor Part Number    Size based off of SFP_XMSA_SID_VENDOR_PN_SZ
    typedef ethpm_X2VendorPartNumberBytes {
        type mtx_array_uint8;
    }

    // X2 Vendor Revision    Size based off of SFP_XMSA_VENDOR_REV_SZ
    typedef ethpm_X2VendorRevisionBytes {
        type mtx_array_uint8;
    }

    // X2 Vendor Serial Number    Size based off of SFP_XMSA_VENDOR_SERIAL_NO_SZ
    typedef ethpm_X2VendorSerialNumberBytes {
        type mtx_array_uint8;
    }

    // X2 Wavelength Channel    Size based off of SFP_XMSA_WAVE_LEN_SZ
    typedef ethpm_X2WavelengthChannelBytes {
        type mtx_array_uint8;
    }

    // X2 Xg Fc Code    Size based off of SFP_XMSA_XGFC_CODE_SZ
    typedef ethpm_X2XbFcCodeBytes {
        type mtx_array_uint8;
    }

    // X2 Xg Eth Code    Size based off of SFP_XMSA_XG_ETH_CODE_SZ
    typedef ethpm_X2XgEthCodeBytes {
        type mtx_array_uint8;
    }

    // Port duplex capabilities
    typedef ethpm_capDuplex {

        // bits- Using string
        type string;
    }

    // Port speed capabilities
    typedef ethpm_capSpeed {

        // bits- Using string
        type string;
    }

    // description
    typedef ethpm_operDescr {
        type string {
            length "0..254";
        }
    }

    // Loose Node Id Type
    // @@@ This could be String form MgmtIP or ChassisID
    // @@@ reported in LLDP
    typedef fabric_LooseNodeId {
        type string;
    }

    typedef fabric_NodeId {
        type uint16 {
            range "1..16000";
        }
        default "1";
    }

    // Primary Key Type
    typedef fabric_PrimKey {
        type string;
    }

    typedef fabric_TickCount {
        type uint32;
        default "0";
    }

    // Firmware name
    typedef firmware_Name {
        type reference_URI;
    }

    // Firmware running mode
    typedef firmware_RunningMode {
        type enumeration {

            // Normal
            enum normal {
                value 0;
            }

            // Reovery
            enum recovery {
                value 1;
            }
        }
        default "normal";
    }

    // Running operational state
    typedef firmware_RunningOperSt {
        type enumeration {

            // Version Match
            enum ok {
                value 0;
            }

            // Version Mismatch
            enum ver-mismatch {
                value 1;
            }
        }
    }

    // Firmware type
    typedef firmware_Type {
        type enumeration {

            // Controller
            enum controller {
                value 0;
            }

            // Switch
            enum switch {
                value 1;
            }

            // Catalog
            enum catalog {
                value 2;
            }
        }
        default "switch";
    }

    typedef flow_CollectParams {

        // bits- Using string
        type string;
    }

    typedef flow_Direction {
        type enumeration {

            // Unspecified
            enum unspecified {
                value 0;
            }

            // Input
            enum in {
                value 1;
            }

            // Output
            enum out {
                value 2;
            }

            // Both
            enum both {
                value 3;
            }
        }
        default "in";
    }

    typedef flow_ExportVersion {
        type enumeration {

            // Unspecified
            enum unspecified {
                value 0;
            }

            // Version 5
            enum v5 {
                value 1;
            }

            // Version 9
            enum v9 {
                value 2;
            }

            // Cisco proprietary version 1
            enum cisco1 {
                value 3;
            }
        }
        default "cisco1";
    }

    typedef flow_L4Port {
        type uint32 {
            range "1..65535";
        }
    }

    typedef flow_MatchParams {

        // bits- Using string
        type string;
    }

    typedef flow_Mtu {
        type uint16 {
            range "576..9216";
        }
        default "1500";
    }

    typedef flow_PayloadLen {

        // MAX Converted to int from 0x3fff
        type uint32 {
            range "0..16383";
        }
    }

    typedef flow_ReceiveWindowSize {
        type uint32 {
            range "0..65535";
        }
    }

    typedef flow_SamplerMode {
        type enumeration {

            // Unspecified
            enum unspecified {
                value 0;
            }

            // M out of N flows
            enum flow {
                value 1;
            }

            // M out of N pkts
            enum pkts {
                value 2;
            }
        }
        default "flow";
    }

    typedef flow_TCPOptHdrLen {
        type uint32 {
            range "0..15";
        }
    }

    // Admin status of feature
    typedef fm_AdminState {
        type enumeration {

            // Feature enabled
            enum enabled {
                value 1;
            }

            // Feature disabled
            enum disabled {
                value 2;
            }
        }
        default "disabled";
    }

    // Operational status of instance
    typedef fm_InstOperState {
        type enumeration {

            // Feature enabled for instance
            enum enabled {
                value 1;
            }

            // Feature disabled for instance
            enum disabled {
                value 2;
            }

            // Feature enabled and not running for the instance
            enum enabled-not-running {
                value 3;
            }
        }
        default "disabled";
    }

    // Number of instances
    typedef fm_Instance {
        type uint32;
        default "1";
    }

    // Operational status of feature
    typedef fm_OperState {
        type enumeration {

            // Feature enabled
            enum enabled {
                value 1;
            }

            // Feature disabled
            enum disabled {
                value 2;
            }
        }
        default "disabled";
    }

    // Diameter
    typedef fmcast_Diameter {
        type uint16;
    }

    typedef fmcast_DiameterAlert {
        type enumeration {

            // Normal
            enum inactive {
                value 1;
            }

            // Excessive Diameter Alert
            enum active {
                value 2;
            }
        }
        default "inactive";
    }

    // Id
    // Default Value "0" Removed - out of range 1..12
    typedef fmcast_Id {
        type uint8 {
            range "1..12";
        }
    }

    // OIF List Large
    typedef fmcast_OIFList128 {
        type mtx_array_ifindex;
    }

    // OIF List Small
    typedef fmcast_OIFList16 {
        type mtx_array_ifindex;
    }

    // Operational state
    typedef fmcast_OperSt {
        type enumeration {

            // Active
            enum active {
                value 1;
            }

            // Inactive
            enum inactive {
                value 2;
            }
        }
        default "inactive";
    }

    // Origin
    typedef fmcast_Origin {
        type enumeration {

            // Static
            enum static {
                value 1;
            }

            // Learned through isis
            enum isis {
                value 2;
            }
        }
        default "static";
    }

    // Admin status of feature
    typedef fset_AdminState {
        type enumeration {

            // featureSet none
            enum none {
                value 0;
            }

            // featureSet enabled
            enum enabled {
                value 1;
            }

            // featureSet disabled
            enum disabled {
                value 2;
            }

            // featureSet installed
            enum installed {
                value 3;
            }

            // featureSet uninstalled
            enum uninstalled {
                value 4;
            }
        }
        default "none";
    }

    // Operational status of feature
    typedef fset_OperState {
        type enumeration {

            // featureSet none
            enum none {
                value 0;
            }

            // featureSet enabled
            enum enabled {
                value 1;
            }

            // featureSet disabled
            enum disabled {
                value 2;
            }

            // featureSet installed
            enum installed {
                value 3;
            }

            // featureSet uninstalled
            enum uninstalled {
                value 4;
            }
        }
        default "none";
    }

    typedef fv_EpCount {
        type uint32;
        default "0";
    }

    // Represents the deployment immediacy preference of the EpG
    typedef fv_Immediacy {
        type enumeration {

            // Immediate
            enum immediate {
                value 1;
            }

            // On Demand
            enum lazy {
                value 2;
            }
        }
        default "lazy";
    }

    // Instrumentation Immediacy Specification for when policies are instrumented in HW
    // immediate: instrument policy in hardware as soon as policy is resolved at the node
    // lazy: instrument policy in hardware only when EP shows up
    // This immediacy constraint is specified at EPG-level, and is copied into EPP, and is enforced per EPP.
    typedef fv_InstrImedcy {
        type fv_Immediacy;
    }

    // Life Cycle Control specifies how this entity (EP)'s Lifecycle is controlled:
    // created, deleted, modified
    typedef fv_LcC {

        // bits- Using string
        type string;
    }

    // Policy Control Enforcement Preference
    typedef fv_PcEnfPref {
        type enumeration {

            // Enforced
            enum enforced {
                value 1;
            }

            // Unenforced
            enum unenforced {
                value 2;
            }
        }
        default "enforced";
    }

    // EPg DN
    typedef fv_PrimKey {
        type string;
    }

    // Resolution Immediacy Specification for CompMM/VMM binding:
    // immediate: push to corresponding nodes ASAP as soon as policy is at CompMM/VMM
    // lazy: push policies when VM/Comp is attached
    // This immediacy constraint is specified at VMM/Comp Binding, and is copied into EPP, and is enforced per EPP.
    typedef fv_ResImedcy {
        type fv_Immediacy;
    }

    // Gateway ip
    typedef glean_GwIp {
        type address_Ip;
    }

    // Gateway mac
    typedef glean_GwMac {
        type address_Mac;
    }

    typedef hmm_Boolean {
        type enumeration {

            // No
            enum no {
                value 0;
            }

            // Yes
            enum yes {
                value 1;
            }
        }
        default "no";
    }

    // Fabric Forwarding mode
    typedef hmm_FwdMode {
        type enumeration {

            // Standard
            enum standard {
                value 0;
            }

            // Anycast Gateway mode
            enum anycastGW {
                value 1;
            }

            // Proxy Gateway mode
            enum proxyGW {
                value 2;
            }
        }
        default "standard";
    }

    // Use-Bia Scope
    typedef hsrp_BiaScopeType {
        type enumeration {

            // scope is interface and its sub-interfaces
            enum global {
                value 1;
            }

            // scope is interface
            enum local {
                value 2;
            }
        }
        default "global";
    }

    // Address family type
    typedef hsrp_GroupAf {
        type enumeration {

            // IPv4 address family
            enum ipv4 {
                value 1;
            }

            // IPv6 address family
            enum ipv6 {
                value 2;
            }
        }
        default "ipv4";
    }

    // Group Id for HSRP version 1 and 2
    typedef hsrp_GroupId {
        type uint16 {
            range "0..4095";
        }
        default "0";
    }

    // Control bits of HSRP Group
    typedef hsrp_GrpControl {

        // bits- Using string
        type string;
    }

    // IP obtain mode
    typedef hsrp_GrpIpObtainMode {
        type enumeration {

            // Address is configured
            enum admin {
                value 0;
            }

            // Auto configure ipv6 address
            enum auto {
                value 1;
            }

            // learn IP from HSRP peer
            enum learn {
                value 2;
            }
        }
        default "admin";
    }

    // Group Priority
    typedef hsrp_GrpPrio {
        type uint16 {
            range "0..255";
        }
        default "100";
    }

    // Hello Interval in msecs
    typedef hsrp_HelloIntvl {
        type uint32 {
            range "250..254000";
        }
        default "3000";
    }

    // Hold Interval in msecs
    typedef hsrp_HoldIntvl {
        type uint32 {
            range "750..255000";
        }
        default "10000";
    }

    // Hsrp Version
    typedef hsrp_HsrpVersion {
        type enumeration {

            // Hsrp version 1
            enum v1 {
                value 1;
            }

            // Hsrp version 2
            enum v2 {
                value 2;
            }
        }
        default "v1";
    }

    // Control bits at the Interface
    typedef hsrp_IfControl {

        // bits- Using string
        type string;
    }

    // Delay before preempting a lower priority Active
    typedef hsrp_PreemptDelay {
        type uint16 {
            range "0..3600";
        }
        default "0";
    }

    // ICMP code
    typedef icmp_Code {
        type uint16 {
            range "0..255";
        }
        default "0";
    }

    // ICMP flags
    typedef icmp_Flags {
        type uint8 {
            range "0..255";
        }
        default "0";
    }

    // ICMP type
    typedef icmp_Type {
        type uint8 {
            range "0..255";
        }
        default "0";
    }

    // Type
    typedef icmpv4_Type {
        type uint8;
        default "255";
    }

    // Adjacency Stale Timer
    typedef icmpv6_AdjStaleTimer {
        type uint16 {
            range "300..65535";
        }
        default "1380";
    }

    // Event History Size
    typedef icmpv6_EventLogSize {
        type enumeration {

            // Disable
            enum disabled {
                value 0;
            }

            // Small
            enum small {
                value 1;
            }

            // Medium
            enum medium {
                value 2;
            }

            // Large
            enum large {
                value 3;
            }
        }
        default "small";
    }

    // Event Log Type
    typedef icmpv6_EventType {
        type enumeration {

            // ICMPV6 CLI related event
            enum cli {
                value 0;
            }

            // Error log ICMPv6
            enum errors {
                value 1;
            }

            // ICMPv6 related High Availability event
            enum highAvailability {
                value 2;
            }

            // Internal debug events of ICMPV6
            enum icmpv6-internal {
                value 3;
            }

            // ICMPV6 debugs for CFS and MCECM related events for l3
            enum ipv6SyncEvent {
                value 4;
            }

            // ICMPV6 MLD debug messages
            enum mldDebug {
                value 5;
            }

            // ICMPV6 MLD non-periodic events
            enum mldEvent {
                value 6;
            }

            // ICMPV6 ND debug
            enum nd {
                value 7;
            }

            // ICMPV6 debugs for CFS and MCECM related events
            enum sync-event {
                value 8;
            }

            // ICMPV6 VRF related events
            enum vrf {
                value 9;
            }
        }
    }

    // Interface controls
    // Default Value computed from redirect
    typedef icmpv6_IfControl {

        // bits- Using string
        type string;
        default "redirect";
    }

    // Logging Level
    typedef icmpv6_LoggingLevel {
        type enumeration {

            // Emergencies
            enum Emergency {
                value 0;
            }

            // Alert
            enum Alert {
                value 1;
            }

            // Critical
            enum Critical {
                value 2;
            }

            // Error
            enum Error {
                value 3;
            }

            // Warning
            enum Warning {
                value 4;
            }

            // Notice
            enum Notice {
                value 5;
            }

            // Informational
            enum Informational {
                value 6;
            }

            // Debug
            enum Debug {
                value 7;
            }
        }
        default "Error";
    }

    // Operational state
    typedef icmpv6_OperSt {
        type enumeration {

            // Down
            enum down {
                value 0;
            }

            // Up
            enum up {
                value 1;
            }

            // Failed
            enum failed {
                value 2;
            }
        }
        default "up";
    }

    // Type
    typedef icmpv6_Type {
        type uint8;
        default "0";
    }

    typedef ident_ShardId {
        type uint8;
    }

    // Database type
    typedef igmp_DbT {
        type enumeration {

            // IGMP Route database
            enum route {
                value 1;
            }
        }
        default "route";
    }

    // State limit status
    typedef igmp_LimitSt {
        type enumeration {

            // Below threshold of 80%
            enum below-thresh {
                value 0;
            }

            // Above 80% threshold
            enum above-thresh {
                value 1;
            }

            // No entries available
            enum exhausted {
                value 2;
            }
        }
        default "below-thresh";
    }

    typedef im_BreakoutMapT {
        type enumeration {

            // 10g-4x
            enum 10g-4x {
                value 5;
            }

            // 10g-2x
            enum 10g-2x {
                value 9;
            }

            // 25g-4x
            enum 25g-4x {
                value 8;
            }

            // 50g-2x
            enum 50g-2x {
                value 7;
            }
        }
        default "10g-4x";
    }

    typedef im_Mode100M {
        type enumeration {
            enum disabled {
                value 0;
            }
            enum enabled {
                value 1;
            }
        }
        default "disabled";
    }

    typedef im_ModeHwProfile {
        type enumeration {
            enum 4C {
                value 0;
            }
            enum 2C+4Q {
                value 1;
            }
        }
        default "2C+4Q";
    }

    // Stage
    typedef imginstall_Stage {
        type enumeration {

            // Copying images
            enum copy-image {
                value 0;
            }

            // Initializing
            enum initializing {
                value 1;
            }

            // Extracting
            enum extracting {
                value 2;
            }

            // Verification of images
            enum verifying {
                value 3;
            }

            // SRG collection
            enum srg-collect {
                value 4;
            }

            // SRG processing
            enum srg-processing {
                value 5;
            }

            // Performing runtime checks
            enum runtime-check {
                value 6;
            }

            // Syncing images
            enum sync-image {
                value 7;
            }

            // Upgrading linecard
            enum upg-lc-image {
                value 8;
            }

            // Upgrading fex
            enum upg-fex {
                value 9;
            }
        }
    }

    // Address controls
    typedef ip_AddrControl {

        // bits- Using string
        type string;
    }

    // Address Operational state qualifier
    typedef ip_AddrOperStQual {
        type enumeration {

            // Unspecified
            enum unspecified {
                value 0;
            }

            // Up
            enum up {
                value 1;
            }

            // Subnet overlap
            enum subnet-overlap {
                value 2;
            }

            // No primary address
            enum no-primary {
                value 3;
            }

            // Interface down
            enum if-down {
                value 4;
            }

            // Address already exists
            enum addr-exists {
                value 5;
            }

            // Context invalid
            enum invalid-vrf {
                value 6;
            }

            // Configured as static-rt nh
            enum static-rt-nh {
                value 7;
            }

            // Loopback address
            enum lb-addr {
                value 8;
            }

            // Invalid use of link local
            enum invalid-ll-use {
                value 9;
            }

            // No global address
            enum no-glbl-addr {
                value 10;
            }

            // No link local address
            enum no-ll-addr {
                value 11;
            }

            // DAD in progress
            enum dad-in-progress {
                value 12;
            }

            // DAD failed
            enum dad-failed {
                value 13;
            }

            // Invalid maks length
            enum invalid-mask-len {
                value 14;
            }

            // IP cfg not allowed on L2 intf
            enum l2-intf-err {
                value 15;
            }

            // IP cfg not allowed on superintf
            enum super-intf-err {
                value 16;
            }

            // Invalid link local address
            enum invalid-ll {
                value 17;
            }

            // IF init error
            enum if-init-err {
                value 18;
            }

            // Failed to get ifindex
            enum ifindex-err {
                value 19;
            }

            // Invalid EUI64 format
            enum invalid-eui64 {
                value 20;
            }

            // Failed to create Link Local Addr.
            enum lladdr-create-fail {
                value 21;
            }

            // DAD failed, state=tentative.
            enum DAD-tentative {
                value 22;
            }

            // DAD failed, state=local duplicate.
            enum DAD-lcl-duplicate {
                value 23;
            }

            // DAD failed, state=duplicate.
            enum DAD-duplicate {
                value 24;
            }

            // DAD failed, state=preferred.
            enum DAD-preferred {
                value 25;
            }

            // DAD failed, state=deprecated.
            enum DAD-deprecated {
                value 26;
            }

            // DAD failed, state=invalid.
            enum DAD-invalid {
                value 27;
            }

            // multiple lladdr cfg not allowed.
            enum multiple-lladdr {
                value 28;
            }

            // IPv6 Address Enablement is not supported on this tunnel type
            enum invalid-tunnel {
                value 29;
            }

            // IPv6 Link Local Address Enablement is not supported on this tunnel type
            enum lladdr-invalid-tunnel {
                value 30;
            }
        }
        default "unspecified";
    }

    // Address type
    typedef ip_AddrT {
        type enumeration {

            // Primary
            enum primary {
                value 1;
            }

            // Secondary
            enum secondary {
                value 2;
            }
        }
        default "primary";
    }

    // If controls
    // Default Value computed from unspecified
    typedef ip_IfControl {

        // bits- Using string
        type string;
        default "unspecified";
    }

    // If mode
    // Default Value computed from unspecified
    typedef ip_IfMode {

        // bits- Using string
        type string;
        default "unspecified";
    }

    // load share mode for 'ip load-sharing' cli, there are four modes
    // - 1. {address destination port destination}
    // cli: ip load-sharing address source-destination gre
    // concatenation rotate 1 universal-id 2
    // - 2. {address source-destination}
    // cli: ip load-sharing address source-destination gre-outer
    // concatenation rotate 1 universal-id 2
    // - 3. {address source-destination gre-key}
    // cli: ip load-sharing address destination port destination
    // rotate 1 universal-id 2
    // - 4. {address source-destination port source-destination}
    // cli: ip load-sharing address source-destination port
    // source-destination concatenation
    typedef ip_LoadShareFormat {
        type enumeration {

            // Disabled
            enum disabled {
                value 1;
            }

            // Destnation Port
            enum destPort {
                value 2;
            }

            // Source-Destination
            enum srcDest {
                value 3;
            }

            // Source-Destination GRE
            enum srcDestGre {
                value 4;
            }

            // Source-Destination Port
            enum srcDestPort {
                value 5;
            }

            // Source
            enum source {
                value 6;
            }
        }
        default "disabled";
    }

    // Nexthop Flags
    // Default Value computed from unspecified
    typedef ip_NhFlags {

        // bits- Using string
        type string;
        default "unspecified";
    }

    // Nexthop Operational state qualifier
    typedef ip_NhOperStQual {
        type enumeration {

            // Unspecified
            enum unspecified {
                value 0;
            }

            // Up
            enum up {
                value 1;
            }

            // Route unreachable
            enum rt-unreachable {
                value 2;
            }

            // Interface down
            enum if-down {
                value 3;
            }

            // Link local prefix
            enum link-local-pfx {
                value 4;
            }

            // Invalid prefix mask
            enum invalid-pfx-mask {
                value 5;
            }

            // Invalid prefix
            enum invalid-pfx {
                value 6;
            }

            // Invalid pin interface VRF
            enum invalid-pin-if-vrf {
                value 7;
            }

            // Invalid nexthop
            enum invalid-nh {
                value 8;
            }

            // Invalid nexthop Mask
            enum invalid-nh-mask {
                value 9;
            }

            // No Interface
            enum invalid-if {
                value 10;
            }

            // Local Nexthop
            enum local-nh {
                value 11;
            }

            // Multicast Nexthop
            enum mcast-nh {
                value 12;
            }

            // Loopback Address
            enum lo-addr {
                value 13;
            }

            // Max NH count exceeded
            enum max-nh-exceeded {
                value 14;
            }

            // Invalid route-vrf
            enum invalid-route-vrf {
                value 15;
            }

            // Nexthop not specified
            enum no-nexthop {
                value 16;
            }

            // Route exists with no or different pin number
            enum route-exists {
                value 17;
            }

            // Recursive nexthop not resolved
            enum rnh-not-resolved {
                value 18;
            }

            // Internal config error
            enum internal-cfg-err {
                value 19;
            }

            // Nexthop configured as local address
            enum local-addr {
                value 20;
            }

            // VRF down
            enum vrf-down {
                value 21;
            }
        }
        default "unspecified";
    }

    // Operational state
    typedef ip_OperSt {
        type enumeration {

            // Unspecified
            enum unspecified {
                value 0;
            }

            // Down
            enum down {
                value 1;
            }

            // Up
            enum up {
                value 2;
            }

            // Failed
            enum failed {
                value 3;
            }
        }
        default "up";
    }

    // Rt control
    typedef ip_RtControl {

        // bits- Using string
        type string;
    }

    // Router ID
    typedef ip_RtrId {
        type address_Ipv4;
    }

    // SwitchPacket Target form for "ipv6 switch-packets [lla]'.
    // - 1. {switchPacket:- Switch ND packets received on core ports}
    // cli: ipv6 switch-packets
    // - 2. {lla:- Switch ND packets targeted to Link local address on core ports}
    // cli: ipv6 switch-packets lla
    typedef ip_SwitchPktTarget {
        type enumeration {

            // Disabled
            enum disabled {
                value 0;
            }

            // Switch Packets all
            enum all {
                value 1;
            }

            // Switch Packets with lla
            enum lla {
                value 2;
            }
        }
        default "disabled";
    }

    // Bootup Delay
    typedef ipmc_BootupDelay {
        type uint16 {
            range "0..65535";
        }
        default "0";
    }

    // Group Timeout
    typedef ipmc_GrpTimeout {
        type uint16 {
            range "3..65535";
        }
        default "260";
    }

    // Interface level Controls
    typedef ipmc_IfCtrl {

        // bits- Using string
        type string;
    }

    // If flags
    typedef ipmc_IfFlags {

        // bits- Using string
        type string;
    }

    // Inst level Controls
    typedef ipmc_InstCtrl {

        // bits- Using string
        type string;
    }

    // Join Type
    typedef ipmc_JoinType {
        type enumeration {

            // Static Group
            enum 0 {
                value 0;
            }

            // Join Group
            enum 1 {
                value 1;
            }
        }
    }

    typedef ipmc_RouteFlags {

        // bits- Using string
        type string;
    }

    // Version
    typedef ipmc_Ver {
        type enumeration {

            // Unspecified
            enum unspecified {
                value 0;
            }

            // IGMP v2
            enum 2 {
                value 2;
            }

            // IGMP v3
            enum 3 {
                value 3;
            }
        }
    }

    // Database type
    typedef ipmcsnoop_DbT {
        type enumeration {

            // Multicast Local Group Database
            enum local-mcgrp {
                value 1;
            }

            // Multicast Fabric Group Database
            enum fabric-mcgrp {
                value 2;
            }
        }
        default "local-mcgrp";
    }

    // Domain level controls
    // Default Value computed from opt-flood
    typedef ipmcsnoop_DomControl {

        // bits- Using string
        type string;
        default "opt-flood";
    }

    // Domain flags
    typedef ipmcsnoop_DomFlags {

        // bits- Using string
        type string;
    }

    // IPMC snooping forwarding mode
    typedef ipmcsnoop_FwdMode {
        type enumeration {

            // IP based forwarding
            enum ip {
                value 1;
            }

            // Mac based forwarding
            enum mac {
                value 2;
            }
        }
        default "ip";
    }

    // Number of multicast groups
    typedef ipmcsnoop_InstFlags {

        // bits- Using string
        type string;
    }

    // Life Cycle Control specifies how the router-if
    // is controlled
    typedef ipmcsnoop_LcC {

        // bits- Using string
        type string;
    }

    // Multicast traffic source address
    typedef ipmcsnoop_McastSrc {
        type address_Ip;
        default "0";
    }

    // Querier flags
    typedef ipmcsnoop_QuerierFlags {

        // bits- Using string
        type string;
    }

    // Report flags
    typedef ipmcsnoop_RepFlags {

        // bits- Using string
        type string;
    }

    // Reporter address
    typedef ipmcsnoop_Reporter {
        type address_Ip;
    }

    // Default Value "0" Removed - out of range 5000..12582912
    typedef ipqos_BuffSize {
        type uint64 {
            range "5000..12582912";
        }
    }

    typedef ipqos_BurstRate {
        type uint64 {
            range "0..536870912";
        }
    }

    typedef ipqos_BurstRateUnit {
        type enumeration {

            // invalid
            enum unspecified {
                value 0;
            }

            // bytes
            enum bytes {
                value 1;
            }

            // kilobytes
            enum kbytes {
                value 2;
            }

            // megabytes
            enum mbytes {
                value 3;
            }

            // milli-seconds
            enum ms {
                value 4;
            }

            // micro-seconds
            enum us {
                value 5;
            }

            // packets
            enum packets {
                value 6;
            }
        }
        default "unspecified";
    }

    typedef ipqos_CMapName {
        type string {
            length "1..40";
        }
    }

    // Cos unit
    typedef ipqos_Cos {
        type uint8 {
            range "0..7";
        }
    }

    typedef ipqos_DescStr {
        type string {
            length "0..200";
        }
    }

    typedef ipqos_DropAvailRange {
        type uint8 {
            range "0..100";
        }
    }

    typedef ipqos_Dscp {
        type uint8 {
            range "0..63";
        }
        default "0";
    }

    typedef ipqos_IfName {
        type nw_IfId;
    }

    typedef ipqos_MPLSExperimental {
        type uint8 {
            range "0..7";
        }
    }

    typedef ipqos_MTU {
        type uint16 {
            range "576..9216";
        }
        default "1500";
    }

    typedef ipqos_MatchCMapName {
        type string {
            length "0..40";
        }
    }

    typedef ipqos_PMapName {
        type string {
            length "1..40";
        }
    }

    typedef ipqos_Percent {
        type uint8 {
            range "0..100";
        }
    }

    typedef ipqos_PoliceAction {
        type enumeration {

            // unspecified
            enum unspecified {
                value 0;
            }

            // transmit
            enum transmit {
                value 1;
            }

            // drop
            enum drop {
                value 2;
            }

            // set-cos-transmit
            enum set-cos-transmit {
                value 3;
            }

            // set-dscp-transmit
            enum set-dscp-transmit {
                value 4;
            }

            // set-prec-transmit
            enum set-prec-transmit {
                value 5;
            }

            // set-qos-transmit
            enum set-qos-transmit {
                value 6;
            }
        }
    }

    typedef ipqos_PoliceRate {
        type uint64 {
            range "0..100000000000";
        }
    }

    typedef ipqos_Prec {
        type enumeration {

            // routine
            enum routine {
                value 0;
            }

            // priority
            enum priority {
                value 1;
            }

            // immediate
            enum immediate {
                value 2;
            }

            // flash
            enum flash {
                value 3;
            }

            // flash-override
            enum flash-override {
                value 4;
            }

            // critical
            enum critical {
                value 5;
            }

            // internet
            enum internet {
                value 6;
            }

            // network
            enum network {
                value 7;
            }
        }
    }

    typedef ipqos_PriorFlowCtrlMode {
        type uint8;
        default "0";
    }

    typedef ipqos_PriorityLevel {
        type uint8 {
            range "1..8";
        }
        default "1";
    }

    typedef ipqos_Protocol {
        type enumeration {

            // unspecified
            enum unspecified {
                value 0;
            }

            // IP ARP
            enum arp {
                value 1;
            }

            // Bridging
            enum bridging {
                value 2;
            }

            // Cisco Discovery Protocol
            enum cdp {
                value 3;
            }

            // Dynamic Host Configuration
            enum dhcp {
                value 7;
            }

            // Intermediate System Intermediate System Protocol
            enum isis {
                value 8;
            }

            // Fcoe
            enum fcoe {
                value 14;
            }
        }
    }

    typedef ipqos_QoSGrpId {
        type uint16 {
            range "0..7";
        }
    }

    // match all, any or first
    typedef ipqos_QoSMatchType {
        type enumeration {
            enum match-any {
                value 0;
            }
            enum match-all {
                value 1;
            }
            enum match-first {
                value 2;
            }
        }
        default "match-all";
    }

    // queue-limit
    typedef ipqos_QueueLimit {
        type uint64 {
            range "0..12582912";
        }
        default "0";
    }

    typedef ipqos_QueueLimitDynamic {
        type uint8 {
            range "0..10";
        }
    }

    typedef ipqos_QueueLimitUnit {
        type enumeration {

            // none
            enum none {
                value 0;
            }

            // packets
            enum packets {
                value 1;
            }

            // bytes
            enum bytes {
                value 2;
            }

            // kbytes
            enum kbytes {
                value 3;
            }

            // mbytes
            enum mbytes {
                value 4;
            }

            // gbytes
            enum gbytes {
                value 5;
            }

            // ms
            enum ms {
                value 6;
            }

            // us
            enum us {
                value 7;
            }

            // perc
            enum perc {
                value 8;
            }
        }
        default "none";
    }

    typedef ipqos_RandOptType {
        type uint8;
        default "0";
    }

    typedef ipqos_RateUnit {
        type enumeration {

            // unspecified
            enum unspecified {
                value 0;
            }

            // bps
            enum bps {
                value 1;
            }

            // kbps
            enum kbps {
                value 2;
            }

            // mbps
            enum mbps {
                value 3;
            }

            // gbps
            enum gbps {
                value 4;
            }

            // pps
            enum pps {
                value 5;
            }

            // percentage
            enum pct {
                value 6;
            }
        }
        default "unspecified";
    }

    typedef ipqos_ShapeRate {
        type uint64 {
            range "0..100000000000";
        }
    }

    typedef ipqos_StatsType {
        type enumeration {

            // none
            enum none {
                value 0;
            }

            // Match under the class-map
            enum matchCMap {
                value 1;
            }

            // MTU
            enum MTU {
                value 2;
            }

            // Set Action
            enum setAction {
                value 3;
            }

            // Pause
            enum pause {
                value 4;
            }

            // Bandwidth
            enum bw {
                value 5;
            }

            // Bandwith remaining
            enum bwRem {
                value 6;
            }

            // Shape
            enum shape {
                value 7;
            }

            // Priority
            enum prio {
                value 8;
            }

            // Random Detect
            enum randomDetect {
                value 9;
            }

            // Queuing
            enum queuing {
                value 10;
            }

            // Policing
            enum police {
                value 11;
            }

            // Queue Limit
            enum qlimit {
                value 12;
            }
        }
    }

    typedef ipqos_ThreshUnit {
        type enumeration {

            // none
            enum none {
                value 0;
            }

            // packets
            enum packets {
                value 1;
            }

            // bytes
            enum bytes {
                value 2;
            }

            // kbytes
            enum kbytes {
                value 3;
            }

            // mbytes
            enum mbytes {
                value 4;
            }
        }
        default "none";
    }

    typedef ipqos_ThreshVal {
        type uint32 {
            range "0..52428800";
        }
        default "0";
    }

    typedef ipqos_Weight {
        type uint8 {
            range "0..15";
        }
    }

    typedef ipqos_XoffBytes {
        type uint64 {
            range "0..12582912";
        }
    }

    typedef ipqos_XonBytes {
        type uint64 {
            range "0..12582912";
        }
    }

    // 253/512/64
    typedef ipqos_ethernetList {
        type string {
        }
        default "0";
    }

    typedef ipqos_policyDirection {
        type enumeration {

            // none
            enum none {
                value 0;
            }

            // ingress
            enum ingress {
                value 1;
            }

            // egress
            enum egress {
                value 2;
            }

            // both
            enum both {
                value 3;
            }
        }
    }

    typedef ipqos_policyType {
        type enumeration {

            // none
            enum none {
                value 0;
            }

            // qos
            enum qos {
                value 1;
            }

            // queuing
            enum queuing {
                value 2;
            }
        }
    }

    // <1-4096>  List of port-channle ids
    typedef ipqos_portChanList {
        type string {
        }
        default "0";
    }

    typedef ipqos_statsState {
        type enumeration {

            // enabled
            enum enabled {
                value 0;
            }

            // disabled
            enum disabled {
                value 1;
            }
        }
        default "enabled";
    }

    // <1-4094>  List of vlan ids
    typedef ipqos_vlanList {
        type string {
        }
        default "0";
    }

    typedef ipv4_ClientFlagType {
        type uint8;
    }

    typedef ipv4_ClientMtsSapType {
        type int16;
    }

    // ICMP Code
    typedef ipv4acl_ICMPCode {
        type uint16 {
            range "0..256";
        }
        default "256";
    }

    // ICMP Enum
    typedef ipv4acl_ICMPEnum {
        type uint16;
        default "256";
    }

    // ICMP Type
    typedef ipv4acl_ICMPType {
        type uint16 {
            range "0..256";
        }
        default "256";
    }

    // IPv4 prefix
    typedef ipv4acl_IPv4Prefix {
        type address_Ipv4;
    }

    // IPv4 prefix length
    typedef ipv4acl_IPv4PrefixLen {
        type uint8 {
            range "0..32";
        }
        default "0";
    }

    // Prefix wildcard mask
    typedef ipv4acl_IPv4PrefixMask {
        type address_Ipv4;
    }

    // IP precedence
    typedef ipv4acl_Precedence {
        type uint8 {
            range "0..8";
        }
        default "8";
    }

    // ACE protocol
    typedef ipv4acl_Protocol {
        type uint8;
        default "255";
    }

    // Tos
    typedef ipv4acl_Tos {
        type uint8 {
            range "0..15";
        }
        default "0";
    }

    // Config Error
    typedef ipv6_ConfigErr {
        type enumeration {

            // Unknown
            enum noerror {
                value 0;
            }

            // Config failed for IPv6 neighbor address
            enum nghbrAddress {
                value 1;
            }

            // Config failed for IPv6 use link local only
            enum useLinkLocalOnly {
                value 2;
            }

            // Config failed for IPv6 forward
            enum forward {
                value 3;
            }
        }
    }

    // Event History Size
    typedef ipv6_IPv6EventLogSize {
        type enumeration {

            // Disable
            enum disabled {
                value 0;
            }

            // Small
            enum small {
                value 1;
            }

            // Medium
            enum medium {
                value 2;
            }

            // Large
            enum large {
                value 3;
            }
        }
        default "small";
    }

    // Event Log Type
    typedef ipv6_IPv6EventType {
        type enumeration {

            // IPv6 Error Log
            enum ipv6Event {
                value 0;
            }

            // Bfd Debug Message for IPv6
            enum bfdEvent {
                value 1;
            }

            // Syslog Message for IPv6
            enum syslog {
                value 2;
            }

            // Ipc Debug Message
            enum ipc {
                value 3;
            }

            // SNMP Events
            enum snmp {
                value 4;
            }

            // High Availability Event
            enum highAvailability {
                value 5;
            }

            // Sdb Message of IPv6
            enum sdb {
                value 6;
            }
        }
    }

    // Router ID
    typedef ipv6_RtrId {
        type address_Ip;
    }

    // Flow Label
    typedef ipv6acl_FlowLabel {
        type uint32 {
            range "0..1048576";
        }
    }

    // ICMPv6 Code
    typedef ipv6acl_ICMPCode {
        type uint16 {
            range "0..256";
        }
        default "256";
    }

    // ICMPv6 Enum
    typedef ipv6acl_ICMPEnum {
        type uint16;
        default "256";
    }

    // ICMPv6 Type
    typedef ipv6acl_ICMPType {
        type uint16 {
            range "0..256";
        }
        default "256";
    }

    // IPv6 prefix
    typedef ipv6acl_IPv6Prefix {
        type address_Ipv6;
    }

    // IPv6 prefix length
    typedef ipv6acl_IPv6PrefixLen {
        type uint8 {
            range "0..128";
        }
        default "0";
    }

    // IPv6 prefix mask
    typedef ipv6acl_IPv6PrefixMask {
        type address_Ipv6;
    }

    // ACE protocol
    typedef ipv6acl_Protocol {
        type uint8;
        default "255";
    }

    // Adj operational state
    typedef isis_AdjOperSt {
        type enumeration {

            // Initializing
            enum init {
                value 1;
            }

            // Up
            enum up {
                value 2;
            }

            // Down
            enum down {
                value 3;
            }

            // Graceful restart initializing
            enum gr-init {
                value 4;
            }
        }
        default "init";
    }

    // Address family type
    typedef isis_AfT {
        type enumeration {

            // IPv4 address family
            enum v4 {
                value 1;
            }

            // IPv6 address family
            enum v6 {
                value 2;
            }
        }
        default "v4";
    }

    // Area id
    typedef isis_AreaId {
        type uint8 {
            range "0..255";
        }
        default "0";
    }

    // Attached
    typedef isis_Attached {
        type boolean;
    }

    // Bandwidth reference
    typedef isis_BwRef {
        type uint32 {
            range "1..4000000";
        }
        default "40000";
    }

    // Checksum
    typedef isis_Cksum {
        type uint16;
    }

    typedef isis_CktId {
        type uint8;
    }

    // CktPrio
    typedef isis_CktPrio {
        type uint8 {
            range "0..127";
        }
        default "64";
    }

    // Circuit type
    typedef isis_CktT {
        type enumeration {

            // Point to point
            enum p2p {
                value 1;
            }

            // Broadcast
            enum bcast {
                value 2;
            }
        }
        default "p2p";
    }

    // Csnp interval
    typedef isis_CsnpIntvl {
        type uint16 {
            range "1..65535";
        }
        default "90";
    }

    // Database type
    typedef isis_DbT {
        type enumeration {

            // Link State Dtabase
            enum ls {
                value 1;
            }

            // Route Database
            enum rt {
                value 2;
            }

            // Nexthop Database
            enum nh {
                value 3;
            }

            // Multicast Group Database
            enum mcgrp {
                value 4;
            }

            // Fabric Node Database
            enum fn {
                value 5;
            }

            // Dynamic Tunnel Endpoint Database
            enum dtep {
                value 6;
            }
        }
        default "ls";
    }

    // Distance
    typedef isis_Dist {
        type uint8 {
            range "1..255";
        }
        default "115";
    }

    // Per address family controls
    typedef isis_DomAfControl {

        // bits- Using string
        type string;
    }

    // Per level controls
    typedef isis_DomLvlControl {

        // bits- Using string
        type string;
    }

    // ECMP max paths
    typedef isis_Ecmp {
        type uint8 {
            range "1..16";
        }
        default "12";
    }

    // Fragment number
    typedef isis_FragNum {
        type uint8;
    }

    // Graceful restart T3 interval
    typedef isis_GrT3Intvl {
        type uint16 {
            range "30..65535";
        }
        default "60";
    }

    // Hello interval
    typedef isis_HelloIntvl {
        type uint16 {
            range "1..65535";
        }
        default "10";
    }

    // Hello multiplier
    typedef isis_HelloMult {
        type uint16 {
            range "3..1000";
        }
        default "3";
    }

    // Interface controls
    typedef isis_IfControl {

        // bits- Using string
        type string;
    }

    // IS type
    typedef isis_IsT {
        type enumeration {

            // L1 IS type
            enum l1 {
                value 1;
            }

            // L2 IS type
            enum l2 {
                value 2;
            }

            // L1-2 IS type
            enum l12 {
                value 3;
            }
        }
        default "l1";
    }

    // Lan id
    typedef isis_LanId {
        type uint8;
    }

    // Lifetime
    typedef isis_LifeTime {
        type uint16;
    }

    // Lsp generation initial wait interval
    typedef isis_LspGenInitIntvl {
        type uint32 {
            range "50..120000";
        }
        default "50";
    }

    // Lsp generation maximum wait interval
    typedef isis_LspGenMaxIntvl {
        type uint32 {
            range "50..120000";
        }
        default "8000";
    }

    // Lsp generation second wait interval
    typedef isis_LspGenSecIntvl {
        type uint32 {
            range "50..120000";
        }
        default "50";
    }

    // LSP refresh interval
    typedef isis_LspRefreshIntvl {
        type uint32 {
            range "10..65535";
        }
        default "33";
    }

    // Level type
    typedef isis_LvlT {
        type enumeration {

            // Level1
            enum l1 {
                value 1;
            }

            // Level2
            enum l2 {
                value 2;
            }
        }
        default "l1";
    }

    // Mesh group controls
    typedef isis_MeshGrpControl {

        // bits- Using string
        type string;
    }

    // Mesh group id
    typedef isis_MeshGrpId {

        // MAX Converted to int from 0xffffffff
        type uint32 {
            range "1..4294967295";
        }
    }

    // Metric
    typedef isis_Metric {
        type uint32 {
            range "1..63";
        }
        default "1";
    }

    // Metric style
    typedef isis_MetricStyle {
        type enumeration {

            // Narrow
            enum narrow {
                value 1;
            }

            // Wide
            enum wide {
                value 2;
            }
        }
        default "narrow";
    }

    // Mode
    typedef isis_Mode {
        type enumeration {

            // Fabric
            enum fabric {
                value 1;
            }

            // External
            enum external {
                value 2;
            }
        }
        default "fabric";
    }

    // LSP MTU
    typedef isis_Mtu {
        type uint16 {
            range "256..4352";
        }
        default "1492";
    }

    // Network selector
    typedef isis_NSEL {
        type enumeration {

            // IP
            enum ip {
                value 0;
            }
        }
        default "ip";
    }

    // Operational state
    typedef isis_OperSt {
        type enumeration {

            // Unknown
            enum unknown {
                value 0;
            }

            // Initializing
            enum initializing {
                value 1;
            }

            // Running smoothly
            enum ok {
                value 2;
            }

            // Failed
            enum failed {
                value 3;
            }
        }
    }

    // Overload
    typedef isis_Overload {
        type boolean;
    }

    // Overload administrative state
    typedef isis_OverloadAdminSt {
        type enumeration {

            // Off
            enum off {
                value 0;
            }

            // Always on
            enum always-on {
                value 1;
            }

            // On at bootup
            enum bootup {
                value 2;
            }

            // Set till bgp convergence
            enum bgp-converge {
                value 3;
            }
        }
        default "bootup";
    }

    // Partition
    typedef isis_Partition {
        type boolean;
    }

    // Peer graceful restart flags
    typedef isis_PeerGrFlags {

        // bits- Using string
        type string;
    }

    // Sequence number
    typedef isis_SeqNum {
        type uint32;
    }

    // Spf computation initial wait interval
    typedef isis_SpfCompInitIntvl {
        type uint32 {
            range "50..120000";
        }
        default "50";
    }

    // Spf computation maximum wait interval
    typedef isis_SpfCompMaxIntvl {
        type uint32 {
            range "50..120000";
        }
        default "8000";
    }

    // Spf computation second wait interval
    typedef isis_SpfCompSecIntvl {
        type uint32 {
            range "50..120000";
        }
        default "50";
    }

    // System id
    typedef isis_SysId {
        type address_Mac;
    }

    // TimerType
    typedef isis_TimerType {
        type enumeration {

            // Invalid Timer
            enum invalid {
                value 1;
            }

            // Refresh Timer
            enum refresh {
                value 2;
            }

            // Hold Timer
            enum hold {
                value 3;
            }

            // Zero-Age Timer
            enum zeroAge {
                value 4;
            }

            // Delete Timer
            enum delete {
                value 5;
            }

            // Sequence Wrap Wait Timer
            enum seqWrap {
                value 6;
            }
        }
        default "invalid";
    }

    // TLV length
    typedef isis_TlvLen {
        type uint16;
    }

    // TLV type
    typedef isis_TlvType {
        type uint8;
    }

    // TLV value
    typedef isis_TlvVal {
        type string;
    }

    // Ud bit
    typedef isis_UdBit {
        type boolean;
    }

    // Interface administrative state
    typedef l1_AdminSt {
        type enumeration {
            enum down {
                value 1;
            }
            enum up {
                value 2;
            }
        }
        default "up";
    }

    // Auto negotiate
    typedef l1_AutoNeg {
        type enumeration {
            enum on {
                value 1;
            }
            enum off {
                value 2;
            }
        }
        default "on";
    }

    // Beacon Mode
    typedef l1_Beacon {
        type enumeration {
            enum on {
                value 1;
            }
            enum off {
                value 2;
            }
        }
        default "off";
    }

    typedef l1_BufferBoost {
        type enumeration {
            enum disable {
                value 0;
            }
            enum enable {
                value 1;
            }
        }
        default "enable";
    }

    // Port bandwidth
    typedef l1_Bw {
        type uint32 {
            range "0..100000000";
        }
        default "0";
    }

    // Dce mode
    typedef l1_DceMode {
        type enumeration {
            enum core {
                value 1;
            }
            enum edge {
                value 2;
            }
            enum auto {
                value 3;
            }
            enum off {
                value 4;
            }
        }
        default "off";
    }

    // Interface throughput delay
    typedef l1_Delay {
        type uint32 {
            range "1..16777215";
        }
        default "1";
    }

    // diags type
    typedef l1_DiagsT {
        type enumeration {
            enum none {
                value 1;
            }
            enum dom {
                value 2;
            }
            enum ddm {
                value 3;
            }
        }
        default "none";
    }

    // Dot 1Q Ethertype
    typedef l1_Dot1qEtherType {
        type enumeration {
            enum 0x8100 {
                value 1;
            }
            enum 0x88A8 {
                value 2;
            }
            enum 0x9100 {
                value 3;
            }
            enum any {
                value 4;
            }
        }
        default "0x8100";
    }

    // Duplex
    typedef l1_Duplex {
        type enumeration {
            enum auto {
                value 1;
            }
            enum full {
                value 2;
            }
            enum half {
                value 3;
            }
        }
        default "auto";
    }

    // EEE latency
    typedef l1_EEELatency {
        type enumeration {
            enum variable {
                value 1;
            }
            enum constant {
                value 2;
            }
        }
        default "variable";
    }

    // EEE Lpi threshold
    typedef l1_EEELpi {
        type enumeration {
            enum aggressive {
                value 1;
            }
            enum normal {
                value 2;
            }
        }
        default "aggressive";
    }

    // Energy Efficient Ethernet (EEE) state
    typedef l1_EEEState {
        type enumeration {
            enum enable {
                value 1;
            }
            enum disable {
                value 2;
            }
            enum disagreed {
                value 3;
            }
            enum not-applicable {
                value 4;
            }
        }
        default "not-applicable";
    }

    typedef l1_FlowControl {

        // bits- Using string
        type string;
    }

    // Inherit Bandwidth
    // Default Value "4294967295" Removed - out of range 1..100000000
    typedef l1_InheritBw {
        type uint32 {
            range "1..100000000";
        }
    }

    // ethpm Interface type
    typedef l1_IntfT {
        type enumeration {
            enum phy {
                value 1;
            }
            enum phy-shared {
                value 2;
            }
        }
        default "phy";
    }

    // Port Layer
    typedef l1_Layer {
        type enumeration {

            // switched
            enum Layer2 {
                value 1;
            }

            // routed
            enum Layer3 {
                value 2;
            }
        }
        default "Layer2";
    }

    // Link debounce interval
    typedef l1_LinkDebounce {
        type uint16 {
            range "0..5000";
        }
        default "100";
    }

    // Link logging
    typedef l1_LinkLog {
        type enumeration {
            enum default {
                value 1;
            }
            enum enable {
                value 2;
            }
            enum disable {
                value 3;
            }
        }
        default "default";
    }

    // Load Interval
    typedef l1_LoadIntvl {
        type uint16 {
            range "5..300";
        }
        default "30";
    }

    typedef l1_LogEventBitmap {

        // bits- Using string
        type string;
    }

    // Mdix mode
    typedef l1_Mdix {
        type enumeration {
            enum auto {
                value 1;
            }
            enum mdi {
                value 2;
            }
            enum mdi-x {
                value 3;
            }
        }
        default "auto";
    }

    // Medium
    typedef l1_Medium {
        type enumeration {
            enum broadcast {
                value 1;
            }
            enum p2p {
                value 2;
            }
        }
        default "broadcast";
    }

    // Port mode
    typedef l1_Mode {
        type enumeration {
            enum access {
                value 1;
            }
            enum trunk {
                value 2;
            }
            enum fex-fabric {
                value 3;
            }
            enum dot1q-tunnel {
                value 4;
            }
            enum promiscuous {
                value 5;
            }
            enum host {
                value 6;
            }
            enum trunk_secondary {
                value 7;
            }
            enum trunk_promiscuous {
                value 8;
            }
        }
        default "access";
    }

    // Module Type
    typedef l1_Module {
        type enumeration {
            enum lc {
                value 0;
            }
            enum sup {
                value 1;
            }
        }
        default "lc";
    }

    // MTU
    typedef l1_Mtu {
        type uint32 {
            range "576..9216";
        }
        default "1500";
    }

    // Oper error disable reason
    typedef l1_OperErrDisQual {
        type l1_OperStQual;
    }

    // Oper Status
    typedef l1_OperSt {
        type enumeration {

            // unknown
            enum unknown {
                value 0;
            }

            // down
            enum down {
                value 1;
            }

            // up
            enum up {
                value 2;
            }

            // link-up
            enum link-up {
                value 3;
            }
        }
        default "down";
    }

    // Oper State Reason    Labels here are based off status values: infra/if_manager/if_manager_cmd.h    Some labels have spaces due to limitations of python restapi which assumes
    // uniqueness between labels
    typedef l1_OperStQual {
        type enumeration {

            // down
            enum unknown {
                value 0;
            }
            enum up {
                value 1;
            }

            // disabled
            enum admin-down {
                value 2;
            }

            // parentEthDown
            enum link-down {
                value 3;
            }
            enum fail {
                value 4;
            }

            // portLicNtAvl
            enum no-license {
                value 5;
            }

            // link-up-connected
            enum link-up {
                value 6;
            }

            // faulty
            enum hw-fail {
                value 7;
            }

            // faulty
            enum sw-fail {
                value 8;
            }

            // err-disabled
            enum err-disabled {
                value 9;
            }

            // sfpAbsent
            enum sfp-missing {
                value 10;
            }

            // faulty
            enum loopback-diag-failure {
                value 11;
            }

            // udldUnidir
            enum udld-unidir-detected {
                value 12;
            }

            // udldLoop
            enum udld-tx-rx-loop {
                value 13;
            }

            // udldMismatch
            enum udld-neighbor-mismatch {
                value 14;
            }

            // udldEmpEcho
            enum udld-empty-echo {
                value 15;
            }

            // udldAggr
            enum udld-aggressive-mode-link-failed {
                value 16;
            }

            // linkFlapErr
            enum link-flap-err {
                value 17;
            }

            // conflctErrDis
            enum err-disabled-ip-conflict {
                value 18;
            }

            // ipQosDcbxpCompatFailure
            enum ipqos-dcbxp-compat-failure {
                value 19;
            }

            // notconnect
            enum link-failure {
                value 20;
            }

            // offline
            enum offline {
                value 21;
            }

            // init
            enum initializing {
                value 22;
            }

            // inactive
            enum inactive {
                value 23;
            }

            // channelDown
            enum channel-admin-down {
                value 24;
            }

            // Channel error-disabled-err-disabled
            enum channel-err-disabled {
                value 25;
            }

            // suspnd
            enum suspended {
                value 26;
            }

            // portSuspnd
            enum proto-port-suspend {
                value 27;
            }

            // channelUpdate
            enum channel-membership-update-in-progress {
                value 28;
            }

            // parentDown
            enum parent-down {
                value 29;
            }

            // adminDown-parentDown
            enum parent-admin-down {
                value 30;
            }

            // ifRemoved
            enum interface-removed {
                value 31;
            }

            // fcotAbsent
            enum fcot-no-present {
                value 32;
            }

            // SFP vendor not supported-err-disabled
            enum fcot-vendor-not-supported {
                value 33;
            }

            // errDisabledIncompatPortMode-err-disabled
            enum incompatible-admin-mode {
                value 34;
            }

            // errDisabledIncompatPortSpeed-err-disabled
            enum incompatible-admin-speed {
                value 35;
            }

            // suspended
            enum suspended-by-mode {
                value 36;
            }

            // suspended
            enum suspended-by-speed {
                value 37;
            }

            // isolated
            enum domain-max-retransmission-failure {
                value 38;
            }

            // isolated
            enum loopback-isolation {
                value 39;
            }

            // modUpgrade
            enum upgrade-in-progress {
                value 40;
            }

            // noOperMembers
            enum port-channel-members-down {
                value 41;
            }

            // parentEthDown
            enum ethernet-link-down {
                value 42;
            }

            // interface-parentEthDown
            enum ethernet-interface-down {
                value 43;
            }

            // adminCfgChng
            enum admin-config-change {
                value 44;
            }

            // modRemoved
            enum module-removed {
                value 45;
            }

            // vrfUnusable
            enum vrf-unusable {
                value 46;
            }

            // connected
            enum none {
                value 47;
            }

            // sfpInit
            enum xcvr-initializing {
                value 48;
            }

            // capAbsent
            enum cap-absent {
                value 49;
            }

            // xcvrEthComplianceErr
            enum sfp-eth-compliant-err {
                value 50;
            }

            // SDP timeout/SFP Mismatch
            enum sdp-timeout {
                value 51;
            }

            // FEX identity mismatch
            enum sat-incompat-topo {
                value 52;
            }

            // FEX not configured
            enum sat-not-configured {
                value 53;
            }

            // xcvrAuthFailed
            enum auth-fail {
                value 54;
            }

            // authPending
            enum auth-pending {
                value 55;
            }

            // suspendedMinLinks
            enum suspended-due-to-minlinks {
                value 56;
            }

            // suspended(no LACP PDUs)
            enum suspended-due-to-no-lacp-pdus {
                value 57;
            }

            // fabrcIfDown
            enum sat-fabric-if-down {
                value 58;
            }

            // invalidFbIf
            enum invalid-sat-fabric-if {
                value 59;
            }

            // FEX-fabric sfp invalid
            enum fex-sfp-invalid {
                value 60;
            }

            // mtuFailure
            enum suspend-by-mtu {
                value 61;
            }

            // suspndByVpc
            enum suspend-by-vpc {
                value 62;
            }

            // routrmacFail
            enum router-mac-failure {
                value 63;
            }

            // xcvrAuthFailed
            enum xcvr-auth-failed {
                value 64;
            }

            // ServDisab
            enum non-sticky-externally-disabled {
                value 65;
            }

            // xcvrSpeedMismatch
            enum sfp-speed-mismatch {
                value 66;
            }

            // SFP checksum error
            enum fcot-chksum-err {
                value 67;
            }

            // Transceiver validation failed
            enum xcvr-invalid {
                value 68;
            }

            // vpcPeerLinkDown
            enum vpc-peer-link-down {
                value 69;
            }

            // vpcConfigInProgress
            enum vpc-cfg-in-progress {
                value 70;
            }

            // noRespFrmVpc
            enum vpc-no-response-from-peer {
                value 71;
            }

            // BPDUGuard errDisable
            enum bpdu-guard-err-disable {
                value 72;
            }

            // htStdbyInBndl
            enum hot-standby-in-bundle {
                value 73;
            }

            // intFailErrDis
            enum handshake-fail-errdisable {
                value 74;
            }
        }
        default "admin-down";
    }

    // Oper state reason code
    typedef l1_OperStQualCode {
        type uint32;
    }

    // Phy layer/Port type
    typedef l1_PhyLayer {
        type enumeration {
            enum ethernet {
                value 2;
            }
            enum sup-inband {
                value 4;
            }
            enum eobc {
                value 5;
            }
            enum mgmt {
                value 6;
            }
            enum max {
                value 8;
            }
        }
        default "ethernet";
    }

    // Storm Control Policer Packet Type
    typedef l1_PktT {
        type enumeration {
            enum bcast {
                value 1;
            }
            enum unk-ucast {
                value 2;
            }
            enum mcast {
                value 3;
            }
            enum all {
                value 4;
            }
        }
        default "all";
    }

    // Port usage
    // Default Value computed from discovery
    typedef l1_PortUsage {

        // bits- Using string
        type string;
        default "discovery";
    }

    typedef l1_RouterMacIpv6Extract {
        type enumeration {
            enum disable {
                value 0;
            }
            enum enable {
                value 1;
            }
        }
        default "disable";
    }

    // Snmp trap state
    typedef l1_SnmpTrapSt {
        type enumeration {
            enum enable {
                value 1;
            }
            enum disable {
                value 2;
            }
        }
        default "enable";
    }

    // Span mode
    typedef l1_SpanMode {
        type enumeration {
            enum not-a-span-dest {
                value 1;
            }
            enum span-dest {
                value 2;
            }
            enum span-dest-fwd {
                value 3;
            }
            enum span-dest-fwd-learn {
                value 4;
            }
        }
        default "not-a-span-dest";
    }

    // Speed
    typedef l1_Speed {
        type enumeration {

            // Unspecified
            enum unknown {
                value 0;
            }

            // 100 Mbps
            enum 100M {
                value 2;
            }

            // 1 Gbps
            enum 1G {
                value 3;
            }

            // 10 Gbps
            enum 10G {
                value 4;
            }

            // 40 Gbps
            enum 40G {
                value 5;
            }

            // auto
            enum auto {
                value 6;
            }

            // auto 100 Mbps
            enum auto_100M {
                value 7;
            }

            // auto 100 Mbps/1Gbps
            enum auto_100M_1G {
                value 8;
            }

            // 100 Gbps
            enum 100G {
                value 9;
            }

            // 25G Gbps
            enum 25G {
                value 10;
            }
        }
        default "auto";
    }

    // Speed Group
    typedef l1_SpeedGroup {
        type enumeration {

            // Unspecified
            enum unknown {
                value 0;
            }

            // 10 Gbps
            enum 10000 {
                value 4;
            }

            // 40 Gbps
            enum 40000 {
                value 5;
            }

            // auto
            enum auto {
                value 6;
            }
        }
        default "auto";
    }

    // Default Value computed from none
    typedef l1_StormCtrlAct {

        // bits- Using string
        type string;
        default "none";
    }

    // Storm Control Policer Packet Rate PPS   Max range is arrived at by using pkt size of 256 bytes
    // for 1   G link = ((1/8)/256))*(10^9)  = 488281
    // for 10  G link = ((10/8)/256)*(10^9)  = 4882812
    // for 40  G link = ((40/8)/256)*(10^9)  = 19531250
    // for 100 G link = ((100/8)/256)*(10^9) = 48828125
    // Default Value "4294967295" Removed - out of range 0..4882812
    typedef l1_StormCtrlPps {
        type uint32 {
            range "0..4882812";
        }
    }

    // Storm Control Policer Packet Rate
    typedef l1_StormCtrlRate {
        type decimal64 {
            fraction-digits 2;
            range "0..100";
        }
        default "100";
    }

    // switching state
    typedef l1_SwitchingSt {
        type enumeration {
            enum disabled {
                value 0;
            }
            enum enabled {
                value 1;
            }
        }
        default "disabled";
    }

    typedef l1_SwitchportBlock {

        // bits- Using string
        type string;
    }

    // Trunk logging
    typedef l1_TrunkLog {
        type enumeration {
            enum default {
                value 1;
            }
            enum enable {
                value 2;
            }
            enum disable {
                value 3;
            }
        }
        default "default";
    }

    // Port Tx Type
    typedef l1_TxT {
        type enumeration {
            enum unknown {
                value 1;
            }
            enum LL {
                value 2;
            }
            enum SN {
                value 3;
            }
            enum LC {
                value 4;
            }
            enum EL {
                value 5;
            }
            enum 10GBASE-SR {
                value 6;
            }
            enum 10GBASE-LR {
                value 7;
            }
            enum 10GBASE-ER {
                value 8;
            }
            enum 10GBASE-LX4 {
                value 9;
            }
            enum 10GBASE-SW {
                value 10;
            }
            enum 10GBASE-LW {
                value 11;
            }
            enum 10GBASE-EW {
                value 12;
            }
        }
        default "unknown";
    }

    // VDC state
    typedef l1_VdcSt {
        type enumeration {
            enum not-created {
                value 0;
            }
            enum created {
                value 1;
            }
            enum cleanup {
                value 2;
            }
        }
        default "not-created";
    }

    typedef l1_l1IfAccessVlan {
        type string;
        default "vlan-1";
    }

    typedef l1_l1IfNativeVlan {
        type string;
        default "vlan-1";
    }

    typedef l1_l1IfTrunkVlans {
        type l2_VlanBitmap;
        default "1-4094";
    }

    typedef l1_translatevlanid {
        type string;
        default "vlan-1";
    }

    // User Configured Flags
    // Default Value computed from none
    typedef l1_userCfgdFlags {

        // bits- Using string
        type string;
        default "none";
    }

    // Subject represents the entitiy to which the capability constraint gets applied
    typedef l1cap_Subj {
        type enumeration {

            // Unknown
            enum unknown {
                value 0;
            }

            // Port Channel
            enum pc-namespace {
                value 1;
            }

            // Physical Ethernet Ports
            enum ethport {
                value 2;
            }
        }
        default "unknown";
    }

    typedef l2_BdMedia {
        type enumeration {

            // Not Set
            enum not_set {
                value 0;
            }

            // Ethernet
            enum enet {
                value 1;
            }
        }
        default "enet";
    }

    // Bounce Ep age interval
    typedef l2_BounceEpAgeIntvl {

        // MAX Converted to int from 0xffff
        type uint16 {
            range "0 | 150..65535";
        }
        default "630";
    }

    // Bounce trigger
    // Default Value computed from protocol
    typedef l2_BounceTrig {

        // bits- Using string
        type string;
        default "protocol";
    }

    // BD bridging mode
    typedef l2_BridgeMode {
        type enumeration {

            // Bridge with IP
            enum ip {
                value 1;
            }

            // Bridge with MAC
            enum mac {
                value 2;
            }
        }
        default "mac";
    }

    // CreateState
    typedef l2_CreateState {
        type enumeration {
            enum created {
                value 1;
            }
            enum removed {
                value 2;
            }
            enum deleted-and-stale {
                value 3;
            }
        }
        default "removed";
    }

    // admin state of domain
    typedef l2_DomAdminSt {
        type enumeration {
            enum suspend {
                value 1;
            }
            enum active {
                value 2;
            }
        }
        default "active";
    }

    // Domain controls
    // Default Value computed from none
    typedef l2_DomCtrl {

        // bits- Using string
        type string;
        default "none";
    }

    // domain id
    typedef l2_DomId {
        type uint32 {
            range "1..4096";
        }
    }

    // domain mode
    typedef l2_DomMode {
        type enumeration {
            enum CE {
                value 1;
            }
            enum FabricPath {
                value 2;
            }
        }
        default "CE";
    }

    // oper state of domain
    typedef l2_DomOperSt {
        type enumeration {
            enum up {
                value 1;
            }
            enum down {
                value 2;
            }
            enum unknown {
                value 3;
            }
        }
        default "down";
    }

    // domain type
    typedef l2_DomType {
        type enumeration {

            // BD regular
            enum bd-regular {
                value 1;
            }

            // BD reserved
            enum bd-reserved {
                value 2;
            }

            // BD control
            enum bd-control {
                value 3;
            }

            // BD external
            enum bd-external {
                value 4;
            }

            // Vlan circuit
            enum ckt-vlan {
                value 5;
            }

            // Vxlan circuit
            enum ckt-vxlan {
                value 6;
            }
        }
        default "bd-regular";
    }

    // Enforcement preference
    typedef l2_EnfPref {
        type enumeration {

            // Software
            enum sw {
                value 1;
            }

            // Hardware
            enum hw {
                value 2;
            }
        }
        default "hw";
    }

    typedef l2_EtherType {
        type enumeration {

            // Unspecified
            enum unspecified {
                value 0;
            }

            // ARP
            enum arp {
                value 2054;
            }

            // Trill
            enum trill {
                value 8947;
            }

            // MPLS Unicast
            enum mpls_ucast {
                value 34887;
            }

            // MAC Security
            enum mac_security {
                value 35045;
            }

            // FCOE
            enum fcoe {
                value 35078;
            }

            // IP
            enum ip {
                value 43981;
            }
        }
        default "unspecified";
    }

    // Fex chassis Id
    typedef l2_ExtChasId {
        type uint16 {
            range "100..200";
        }
    }

    // BD forwarding controls
    // Default Value computed from mdst-flood
    typedef l2_FwdCtrl {

        // bits- Using string
        type string;
        default "mdst-flood";
    }

    // BD forwarding mode
    // Default Value computed from route,bridge
    typedef l2_FwdMode {

        // bits- Using string
        type string;
        default "route,bridge";
    }

    // Endpoint move hold interval
    typedef l2_HoldIntvl {

        // MAX Converted to int from 0xffff
        type uint16 {
            range "5..65535";
        }
        default "300";
    }

    // Local Ep age interval
    typedef l2_LocalEpAgeIntvl {

        // MAX Converted to int from 0xffff
        type uint16 {
            range "0 | 120..65535";
        }
        default "900";
    }

    // Endpoint move frequency
    typedef l2_MoveFreq {

        // MAX Converted to int from 0xffff
        type uint16 {
            range "0..65535";
        }
        default "256";
    }

    // Remote Ep age interval
    typedef l2_RemoteEpAgeIntvl {

        // MAX Converted to int from 0xffff
        type uint16 {
            range "0 | 120..65535";
        }
        default "300";
    }

    // MAC unknown unicast destination action; The options are
    // valid only with classical bridging case (Bridge with MAC);
    // In all other scenerios, it is always proxy
    typedef l2_UnkMacUcastAct {
        type enumeration {

            // Flood
            enum flood {
                value 0;
            }

            // Hardware Proxy
            enum proxy {
                value 1;
            }
        }
        default "proxy";
    }

    // Unknown multicast destination action    @@@ Due to the ASIC multicast transit bug, the default
    // @@@ behavior for unknown multicast traffic is flood.
    // @@@ The expected behavior of unknown multicast traffic
    // @@@ when igmp snooping is enabled is to send to only
    // @@@ router ports. To achieve the expected behavior, set
    // @@@ this to optimized flood. But this may have scaling
    // @@@ limitations and users are expected to set opt-flood
    // @@@ only for BDs where the multicast traffic is running
    // @@@ and this behavior is absolutely needed.
    typedef l2_UnkMcastAct {
        type enumeration {

            // Flood
            enum flood {
                value 0;
            }

            // Optimized Flood
            enum opt-flood {
                value 1;
            }
        }
        default "flood";
    }

    // vdc id
    typedef l2_VdcId {
        type uint16 {
            range "1..4096";
        }
    }

    typedef l2_VlanBitmap {
        type mtx_array_bit;
    }

    // Subject represents the entitiy to which the capability constraint gets applied
    typedef l2cap_Subj {
        type enumeration {

            // Unknown
            enum unknown {
                value 0;
            }

            // VXLAN
            enum vxlan-namespace {
                value 1;
            }

            // NVGRE
            enum nvgre-namespace {
                value 2;
            }

            // L2 Domain (Bridge Domain, Circuit, VLAN)
            enum domain-namespace {
                value 3;
            }

            // Tunnel Interface
            enum tunnel-namespace {
                value 4;
            }
        }
        default "unknown";
    }

    // BGP RD    Size based off of BGP_RD_LEN
    typedef l3_BgpRdBytes {
        type mtx_array_uint8;
    }

    // Context type
    typedef l3_CtxT {
        type enumeration {

            // Out of band management
            enum oob-mgmt {
                value 1;
            }

            // Inband management
            enum inb-mgmt {
                value 2;
            }

            // Tenant
            enum tenant {
                value 3;
            }
        }
        default "tenant";
    }

    // Ip header flags
    // Default Value computed from unspecified
    typedef l3_IpFlags {

        // bits- Using string
        type string;
        default "unspecified";
    }

    // Ip prefix length
    typedef l3_IpPfxLen {
        type uint16 {
            range "0..128";
        }
        default "0";
    }

    // Ip protocol
    typedef l3_IpProt {
        type uint8 {
            range "0..255";
        }
        default "0";
    }

    // ttl
    // Default Value "0" Removed - out of range 1..255
    typedef l3_Ttl {
        type uint8 {
            range "1..255";
        }
    }

    // admin state of vrf
    typedef l3_VrfAdminState {
        type enumeration {
            enum shutdown {
                value 1;
            }
            enum admin-up {
                value 2;
            }
        }
        default "admin-up";
    }

    // vrf gsdb context type
    typedef l3_VrfGsdbCtxType {
        type enumeration {
            enum vrf {
                value 1;
            }
            enum if {
                value 2;
            }
            enum table {
                value 3;
            }
            enum if-table {
                value 4;
            }
            enum if-list {
                value 5;
            }
            enum purge {
                value 6;
            }
            enum vpnid {
                value 7;
            }
            enum source-of-origin {
                value 8;
            }
            enum route-limits {
                value 9;
            }
        }
        default "if";
    }

    // VRF id
    typedef l3_VrfId {
        type uint16 {
            range "1..65535";
        }
    }

    // VRF name
    typedef l3_VrfName {
        type string;
    }

    // oper state of vrf
    typedef l3_VrfOperState {
        type enumeration {
            enum up {
                value 1;
            }
            enum down {
                value 2;
            }
        }
        default "down";
    }

    // oper state reason of vrf
    typedef l3_VrfOperStateQual {
        type enumeration {
            enum admin-down {
                value 1;
            }
            enum admin-down-pending {
                value 2;
            }
            enum delete-holddown {
                value 3;
            }
            enum delete-pending {
                value 4;
            }
            enum invalid {
                value 5;
            }
            enum create-pending {
                value 6;
            }
        }
        default "admin-down";
    }

    // Subject represents the entitiy to which the capability constraint gets applied
    typedef l3cap_Subj {
        type enumeration {

            // Unknown
            enum unknown {
                value 0;
            }

            // VRF
            enum vrf-namespace {
                value 1;
            }

            // LOOPBACK
            enum lb-namespace {
                value 2;
            }

            // NN
            enum rdnn-namespace {
                value 3;
            }
        }
        default "unknown";
    }

    // Port
    typedef l4_Port {

        // MAX Converted to int from 0xffff
        type uint16 {
            range "0..65535";
        }
        default "0";
    }

    // TCP flags
    // Default Value computed from unspecified
    typedef l4_TcpFlags {

        // bits- Using string
        type string;
        default "unspecified";
    }

    // Activity flags
    typedef lacp_ActivityFlags {

        // bits- Using string
        type string;
    }

    // Operational key
    typedef lacp_Key {
        type uint16 {
            range "1..65535";
        }
    }

    typedef lacp_LACPInstCtrl {

        // bits- Using string
        type string;
    }

    // Port num
    typedef lacp_PortNum {
        type uint16 {
            range "0..65535";
        }
    }

    // Port priority
    typedef lacp_PortPrio {
        type uint16 {
            range "1..65535";
        }
        default "32768";
    }

    // System mac
    typedef lacp_SysMac {
        type address_Mac;
    }

    // System priority
    typedef lacp_SysPrio {
        type uint16 {
            range "1..65535";
        }
        default "32768";
    }

    // Transmit rate
    typedef lacp_TxRate {
        type enumeration {

            // Normal
            enum normal {
                value 1;
            }

            // Fast
            enum fast {
                value 2;
            }
        }
        default "normal";
    }

    // Adjacency Id
    typedef lldp_AdjId {
        type uint16 {
            range "1..10";
        }
    }

    // Adjacency state qualifier
    typedef lldp_AdjStQual {

        // bits- Using string
        type string;
    }

    // Administrative state
    typedef lldp_AdminSt {
        type enumeration {

            // Enabled
            enum enabled {
                value 1;
            }

            // Disabled
            enum disabled {
                value 2;
            }
        }
        default "enabled";
    }

    // Capability
    typedef lldp_Capability {

        // bits- Using string
        type string;
    }

    // Chassis ID type
    typedef lldp_ChassisIdT {
        type uint8;
    }

    // Chassis id value; FIXME IFC to give ByteArray type
    typedef lldp_ChassisIdV {
        type string;
    }

    // Hold time
    typedef lldp_HoldTime {
        type uint16 {
            range "10..255";
        }
        default "120";
    }

    // Infra vlan
    typedef lldp_InfraVlan {
        type uint16;
        default "0";
    }

    // Init delay time
    typedef lldp_InitDelayTime {
        type uint16 {
            range "1..10";
        }
        default "2";
    }

    // Management ip
    typedef lldp_MgmtIp {
        type address_Ip;
        default "0";
    }

    // Management port mac
    typedef lldp_MgmtPortMac {
        type address_Mac;
        default "0";
    }

    // Neighbor System Description
    typedef lldp_NbrSysDesc {
        type string;
    }

    // Operational state
    typedef lldp_OperSt {
        type enumeration {

            // Disabled
            enum disabled {
                value 1;
            }

            // Enabled
            enum enabled {
                value 2;
            }
        }
        default "disabled";
    }

    // Optional TLV Selectors
    // Default Value computed from port-desc,sys-name,sys-desc,sys-cap,mgmt-addr,port-vlan
    typedef lldp_OptTlvSel {

        // bits- Using string
        type string;
        default "port-desc,sys-name,sys-desc,sys-cap,mgmt-addr,port-vlan";
    }

    // Port id type
    typedef lldp_PortIdT {
        type uint8;
    }

    // Port id value; FIXME IFC to give ByteArray type
    typedef lldp_PortIdV {
        type string;
    }

    // Port vlan
    typedef lldp_PortVlan {
        type uint16;
        default "0";
    }

    // System name
    typedef lldp_SysName {
        type string;
    }

    // TTL
    typedef lldp_TTL {
        type uint16;
    }

    // Transmission frequency
    typedef lldp_TxFreq {
        type uint16 {
            range "5..254";
        }
        default "30";
    }

    // Wiring Issues - used to raise fault for wiring errors
    // Default Value computed from none
    typedef lldp_WiringIssues {

        // bits- Using string
        type string;
        default "none";
    }

    // PortRole TLV values
    typedef lldptlv_PortRole {
        type enumeration {

            // Reserved
            enum unknown {
                value 0;
            }

            // Active
            enum active {
                value 1;
            }

            // Backup
            enum backup {
                value 2;
            }
        }
    }

    // Cipher Suite
    typedef macsec_CipherSuite {
        type enumeration {

            // gcm-aes-128
            enum gcm-aes-128 {
                value 1;
            }

            // gcm-aes-256
            enum gcm-aes-256 {
                value 2;
            }

            // gcm-aes-xpn-128
            enum gcm-aes-xpn-128 {
                value 3;
            }

            // gcm-aes-xpn-256
            enum gcm-aes-xpn-256 {
                value 4;
            }
        }
        default "gcm-aes-xpn-256";
    }

    // Server Priority
    // <type name="ServerPriority"
    // base="scalar:UByte"
    // >
    // <range min="0" max="255"/>
    // <default value="16"/>
    // </type>    Confidentiality Offset
    typedef macsec_ConfOffset {
        type enumeration {

            // Skip 0 bytes
            enum offset-0 {
                value 1;
            }

            // Skip 30 bytes
            enum offset-30 {
                value 2;
            }

            // Skip 50 bytes
            enum offset-50 {
                value 3;
            }

            // Skip 1 vlan tag
            enum vlan-tag-1 {
                value 4;
            }

            // Skip 2 vlan tags
            enum vlan-tag-2 {
                value 5;
            }
        }
        default "offset-0";
    }

    // Key Name
    typedef macsec_KeyName {
        type string {
            length "0..64";
        }
    }

    // Operational state
    typedef macsec_OperSt {
        type enumeration {

            // Up
            enum up {
                value 1;
            }

            // Down
            enum down {
                value 2;
            }
        }
        default "down";
    }

    // Operational state qualifier
    typedef macsec_OperStQual {
        type enumeration {

            // Up
            enum up {
                value 1;
            }

            // Administratively down
            enum admin-down {
                value 2;
            }

            // Interface down
            enum if-down {
                value 3;
            }

            // Unsupported
            enum unsupported {
                value 4;
            }
        }
        default "unsupported";
    }

    // PreShared Key
    typedef macsec_PreSharedKey {
        type string {
            length "0..32";
        }
    }

    // Secure Mode
    typedef macsec_SecureMode {
        type enumeration {

            // Must secure mode
            enum must-secure {
                value 1;
            }

            // Should secure mode
            enum should-secure {
                value 2;
            }

            // Must not secure mode
            enum must-not-secure {
                value 3;
            }
        }
        default "should-secure";
    }

    // Window Size
    typedef macsec_WindowSize {
        type uint32 {
            range "0..1024";
        }
        default "0";
    }

    // Maintenance status of a node.
    typedef maint_CatUpgradeStatus {
        type enumeration {

            // Scheduled
            enum scheduled {
                value 0;
            }

            // Completed Successfully
            enum completeok {
                value 4;
            }

            // Failed
            enum completenok {
                value 5;
            }

            // No Maintenance Scheduled
            enum notscheduled {
                value 6;
            }
        }
        default "scheduled";
    }

    // Firmware Installation progress in percent
    typedef maint_InstallProgPercent {
        type uint16 {
            range "0..100";
        }
        default "0";
    }

    // Installation stage of a Controller/Switch with upgrade in progress
    typedef maint_InstallStage {
        type enumeration {

            // Controller Image Verification
            enum ctrlrImageVerification {
                value 1;
            }

            // Controller Partition Verification
            enum ctrlrPartitionVerification {
                value 2;
            }

            // Controller Image Extraction
            enum ctrlrImageExtraction {
                value 3;
            }

            // Updating Grub/efiboot Boot Manager
            enum ctrlrUpdatingBootorder {
                value 4;
            }

            // Copying Images
            enum switchCopyImage {
                value 5;
            }

            // Initializing
            enum switchInitializing {
                value 6;
            }

            // Extracting
            enum switchExtracting {
                value 7;
            }

            // Verification of Images
            enum switchVerifying {
                value 8;
            }

            // SRG Collection
            enum switchSrgCollect {
                value 9;
            }

            // SRG Processing
            enum switchSrgProcessing {
                value 10;
            }

            // Performing Runtime Checks
            enum switchRuntimeCheck {
                value 11;
            }

            // Syncing Images
            enum switchSyncImage {
                value 12;
            }

            // Upgrading Linecard
            enum switchUpgLcImage {
                value 13;
            }

            // Upgrading Fex
            enum switchUpgFex {
                value 14;
            }
            enum InstallNotStarted {
                value 0;
            }
        }
        default "InstallNotStarted";
    }

    // Maintenance status of a node.
    typedef maint_NodeUpgradeStatus {
        type enumeration {

            // Scheduled
            enum scheduled {
                value 0;
            }

            // In Queue
            enum inqueue {
                value 1;
            }

            // In Progress
            enum inprogress {
                value 2;
            }

            // Completed Successfully
            enum completeok {
                value 4;
            }

            // Failed
            enum completenok {
                value 5;
            }

            // No Maintenance Scheduled
            enum notscheduled {
                value 6;
            }

            // Failed Due to Incompatible Desired Version
            enum incompatible {
                value 7;
            }

            // Queued for Retry
            enum inretryqueue {
                value 8;
            }
        }
        default "scheduled";
    }

    // Filter mode, valid only with v3
    typedef mcast_FiltMode {
        type enumeration {

            // Include
            enum include {
                value 1;
            }

            // Exclude
            enum exclude {
                value 2;
            }
        }
        default "include";
    }

    // Multicast group ip address
    typedef mcast_GrpIp {
        type address_Ip;
    }

    // Last member query count
    typedef mcast_LastMbrQueryCnt {
        type uint16 {
            range "1..5";
        }
        default "2";
    }

    // Last member query interval
    typedef mcast_LastMbrQueryIntvl {
        type uint16 {
            range "1..25";
        }
        default "1";
    }

    // Last member response time
    typedef mcast_LastMbrRespTime {
        type uint16 {
            range "1..25";
        }
        default "1";
    }

    // Number of (*,G) or (S,G) entries
    typedef mcast_NumEntries {
        type uint32 {
            range "0..4294967295";
        }
        default "0";
    }

    // Querier Ip address
    typedef mcast_QuerierIp {
        type address_Ip;
    }

    // Querier timeout
    typedef mcast_QuerierTimeout {

        // MAX Converted to int from 0xffff
        type uint16 {
            range "1..65535";
        }
        default "255";
    }

    // Query count
    typedef mcast_QueryCnt {
        type uint8 {
            range "1..10";
        }
        default "2";
    }

    // Query interval
    typedef mcast_QueryIntvl {
        type uint16 {
            range "1..18000";
        }
        default "125";
    }

    // Query response interval
    typedef mcast_QueryRspIntvl {
        type uint16 {
            range "1..25";
        }
        default "10";
    }

    // Robust factor
    typedef mcast_RobustFactor {
        type uint8 {
            range "1..7";
        }
        default "2";
    }

    // Multicast root node, identified by the ip address
    typedef mcast_Root {
        type address_Ip;
    }

    // Startup Query interval
    typedef mcast_StartQueryIntvl {
        type uint16 {
            range "1..18000";
        }
        default "31";
    }

    // Version
    typedef mcast_Ver {
        type enumeration {

            // Unspecified
            enum unspecified {
                value 0;
            }
        }
    }

    // Loop detection multiplier
    typedef mcp_LoopDetectMult {
        type uint8 {
            range "1..32";
        }
        default "3";
    }

    // Operational state
    typedef mcp_OperSt {
        type enumeration {

            // Initializing
            enum init {
                value 0;
            }

            // Forwarding
            enum up {
                value 1;
            }

            // Down
            enum down {
                value 3;
            }
        }
        default "init";
    }

    // Operational state blocked qualifier
    typedef mcp_OperStQual {
        type enumeration {

            // Up
            enum up {
                value 0;
            }

            // Interface down
            enum if-down {
                value 1;
            }

            // Loop detected
            enum loop {
                value 2;
            }
        }
        default "up";
    }

    // Transmission frequency
    typedef mcp_TxFreq {
        type uint16 {
            range "2..300";
        }
        default "2";
    }

    typedef mit_LockStatus {
        type enumeration {

            // MIT_UNLOCKED
            enum mit_unlocked {
                value 0;
            }

            // MIT_LOCKED
            enum mit_locked {
                value 1;
            }
        }
    }

    typedef mit_OperType {
        type enumeration {

            // COMMIT_VERIFY
            enum commit_verify {
                value 0;
            }

            // COMMIT_NORMAL
            enum commit_normal {
                value 1;
            }

            // COMMIT_CONFIRM_START
            enum commit_confirm_start {
                value 2;
            }

            // COMMIT_CONFRIM_END
            enum commit_confirm_end {
                value 4;
            }

            // COMMIT_RESET_TIMEOUT
            enum commit_reset_timeout {
                value 8;
            }

            // COMMIT_CONFRIM_CANCEL
            enum commit_confirm_cancel {
                value 16;
            }
        }
        default "commit_normal";
    }

    // Enum type
    typedef mit_TreeType {
        type enumeration {

            // MIT_RUNNING
            enum mit_running {
                value 0;
            }

            // MIT_CANDIDATE
            enum mit_candidate {
                value 1;
            }
        }
    }

    typedef mo_TStamp {
        type uint64;
        default "0";
    }

    // Duration in units of moc timer tick
    typedef mock_Duration {

        // MAX Converted to int from 0xFFFFFFFF
        type uint32 {
            range "1..4294967295";
        }
        default "1";
    }

    // Represents the mode a Mock session
    typedef mock_Mode {
        type enumeration {
            enum Repeated {
                value 0;
            }
            enum Once {
                value 1;
            }
        }
        default "Repeated";
    }

    // Observable
    typedef mock_Observable {
        type string;
    }

    // Counter Value
    typedef mock_Value {
        type uint64;
        default "0";
    }

    typedef mon_AdminState {
        type enumeration {
            enum enabled {
                value 1;
            }
            enum disabled {
                value 2;
            }
        }
        default "enabled";
    }

    // Database type
    typedef monitor_DbT {
        type enumeration {

            // IP endpoint resolution database
            enum ipep-resolve {
                value 1;
            }
        }
        default "ipep-resolve";
    }

    // Destination encapsulation
    typedef monitor_DestEncapT {
        type enumeration {

            // Gre encapsulated
            enum gre {
                value 1;
            }
        }
        default "gre";
    }

    // Direction, to figure out the direction in which the traffic
    // is monitored on the span source
    typedef monitor_Direction {
        type enumeration {

            // Incoming
            enum in {
                value 1;
            }

            // Outgoing
            enum out {
                value 2;
            }

            // Both
            enum both {
                value 3;
            }

            // None
            enum none {
                value 4;
            }
        }
        default "none";
    }

    // ErSpan Version
    typedef monitor_ErSpanVer {
        type enumeration {

            // Version 2
            enum ver2 {
                value 2;
            }

            // Version 3
            enum ver3 {
                value 3;
            }
        }
        default "ver3";
    }

    // Flow id
    typedef monitor_FlowId {
        type uint16 {
            range "1..1023";
        }
        default "1";
    }

    // Mode
    typedef monitor_Mode {
        type enumeration {

            // Access
            enum access {
                value 1;
            }

            // Fabric
            enum fabric {
                value 2;
            }
        }
        default "access";
    }

    // Mtu
    typedef monitor_Mtu {
        type uint16 {
            range "64..1518";
        }
        default "1518";
    }

    // Operational state
    typedef monitor_OperSt {
        type enumeration {

            // Up
            enum up {
                value 1;
            }

            // Down
            enum down {
                value 2;
            }

            // Failed
            enum failed {
                value 3;
            }
        }
        default "down";
    }

    // Operational state qualifier
    typedef monitor_OperStQual {
        type string;
    }

    // Session id
    typedef monitor_SessionId {
        type uint8 {
            range "1..48";
        }
    }

    // Source id
    typedef monitor_SrcId {

        // MAX Converted to int from 0xffff
        type uint16 {
            range "1..65535";
        }
    }

    // Source type
    typedef monitor_SrcT {
        type enumeration {

            // Port
            enum port {
                value 1;
            }

            // Encap
            enum encap {
                value 2;
            }

            // Port and encap
            enum port-encap {
                value 3;
            }
        }
        default "port";
    }

    typedef mpls_OperSt {
        type enumeration {

            // Down
            enum down {
                value 0;
            }

            // Up
            enum up {
                value 1;
            }
        }
        default "up";
    }

    // Address family type
    typedef mplsstatic_AfT {
        type enumeration {

            // IPv4 unicast address family
            enum ipv4-ucast {
                value 1;
            }

            // IPv6 unicast address family
            enum ipv6-ucast {
                value 2;
            }
        }
        default "ipv4-ucast";
    }

    typedef mplsstatic_InLabelVal {
        type uint32 {
            range "16..471804";
        }
        default "16";
    }

    // Default Value "1048577" Removed - out of range 16..1048575
    typedef mplsstatic_OutLabelVal {
        type uint32 {
            range "16..1048575";
        }
    }

    // Authentication key
    typedef msdp_AuthKey {
        type string;
    }

    // Authentication type
    typedef msdp_AuthT {
        type enumeration {

            // No authentication
            enum none {
                value 0;
            }

            // MD5 authentication
            enum md5 {
                value 1;
            }
        }
        default "none";
    }

    // Database type
    typedef msdp_DbT {
        type enumeration {

            // Route database
            enum route {
                value 0;
            }

            // Source database
            enum source {
                value 1;
            }
        }
    }

    // Domain Control
    typedef msdp_DomCtrl {

        // bits- Using string
        type string;
    }

    // Keepalive Interval
    typedef msdp_KaIntvl {
        type uint16 {
            range "1..60";
        }
        default "60";
    }

    // Keepalive Timeout
    typedef msdp_KaTimeout {
        type uint16 {
            range "1..90";
        }
        default "90";
    }

    // Max Group Limit
    typedef msdp_MaxGrpLimit {
        type uint32 {
            range "0..4294967295";
        }
        default "4294967295";
    }

    // Operational state
    typedef msdp_OperSt {
        type enumeration {

            // Inactive
            enum inactive {
                value 0;
            }

            // Down
            enum down {
                value 1;
            }

            // Admin-Down
            enum admin-down {
                value 2;
            }

            // Connecting
            enum connecting {
                value 3;
            }

            // Listening
            enum listening {
                value 4;
            }

            // Established
            enum established {
                value 5;
            }
        }
        default "inactive";
    }

    // Reconnect Interval
    typedef msdp_ReConnIntvl {
        type uint16 {
            range "1..60";
        }
        default "10";
    }

    // Source Announcement interval
    typedef msdp_SrcActiveMsgIntvl {
        type uint16 {
            range "60..65535";
        }
        default "60";
    }

    // Source Announcement Limit
    typedef msdp_SrcActiveMsgLimit {
        type uint32 {
            range "0..4294967295";
        }
        default "4294967295";
    }

    typedef naming_Descr {
        type string {
            length "0..128";
        }
    }

    typedef naming_Id {
        type uint64;
    }

    typedef naming_LongDescr {
        type string;
    }

    typedef naming_Name {
        type string {
            length "0..16";
        }
    }

    typedef naming_PrimKey {
        type string;
    }

    typedef naming_Regex {
        type string {
            length "0..256";
        }
    }

    // Config Error Inst MO
    typedef nat_ConfigErrNat {

        // bits- Using string
        type string;
    }

    typedef nat_NatMaxTranslation {
        type uint32 {
            range "1..1023";
        }
        default "80";
    }

    // Default Value "0" Removed - out of range 1..1023
    typedef nat_NatMaxTranslationAllHost {
        type uint32 {
            range "1..1023";
        }
    }

    typedef nat_NatPoolname {
        type string {
            length "1..64";
        }
    }

    // Default Value "0" Removed - out of range 1..32
    typedef nat_NatPrefixType {
        type uint32 {
            range "1..32";
        }
    }

    typedef nat_NatTimeout {
        type uint32 {
            range "60..172800";
        }
        default "3600";
    }

    typedef nat_booltype {
        type boolean;
        default "false";
    }

    typedef nbm_nbmBwUnitEn {
        type enumeration {

            // Invalid Value
            enum UNSPECIFIED {
                value 0;
            }

            // KiloBits Per Second
            enum KBPS {
                value 1;
            }

            // MegaBits Per Second
            enum MBPS {
                value 2;
            }

            // GigaBits Per Second
            enum GBPS {
                value 3;
            }
        }
        default "GBPS";
    }

    // DSCP
    typedef nbm_nbmDscp {
        type uint8 {
            range "0..50";
        }
        default "8";
    }

    typedef nbm_nbmFlowOperEn {
        type enumeration {

            // No Operation
            enum NOOP {
                value 0;
            }

            // Add a new Route
            enum ROUTE_ADD {
                value 1;
            }

            // Delete Existing Route
            enum ROUTE_DEL {
                value 2;
            }

            // Add a new OIF to existing Route
            enum UPD_ADD_OIF {
                value 3;
            }

            // Remove an OIF from an existing Route
            enum UPD_DEL_OIF {
                value 4;
            }

            // Update Local OIF ADD
            enum LOC_ADD_OIF {
                value 5;
            }

            // Update Local OIF DEL
            enum LOC_DEL_OIF {
                value 6;
            }

            // Update IIF
            enum UPD_IIF {
                value 7;
            }

            // Applied Deny Policy
            enum DENY_POLICY {
                value 8;
            }

            // Dummy case 9
            enum DUMMY_9 {
                value 9;
            }

            // Dummy case A
            enum DUMMY_A {
                value 10;
            }
        }
        default "NOOP";
    }

    // Name of interface, e.g. "Eth1/2"    base="nw:IfId">
    typedef nbm_nbmIf {
        type uint32;
    }

    typedef nbm_nbmIpAddr {
        type address_Ip;
    }

    // L4 Port
    typedef nbm_nbmL4Port {
        type uint16 {
            range "1..65535";
        }
    }

    // Address Type
    // Default Value computed from none
    typedef nd_AddrType {

        // bits- Using string
        type string;
        default "none";
    }

    // Adjacency MAC
    typedef nd_AdjMac {
        type address_Mac;
        default "0";
    }

    // Adjacency operational state
    typedef nd_AdjOperSt {
        type enumeration {

            // Unknown
            enum unspecified {
                value 0;
            }

            // Incomplete
            enum incomplete {
                value 1;
            }

            // Resolved
            enum normal {
                value 2;
            }
        }
    }

    // Aging interval for cached entries
    typedef nd_AgingInterval {
        type uint16 {
            range "300..65535";
        }
        default "1380";
    }

    // Config Error
    typedef nd_ConfigErr {
        type enumeration {

            // Unknown
            enum noerror {
                value 0;
            }

            // Config of ipv6 nd managed-config-flag failed
            enum managedConfigFlag {
                value 1;
            }

            // Config of ipv6 nd other-config-flag failed
            enum otherConfigFlag {
                value 2;
            }

            // Config of ipv6 nd ra-interval failed
            enum raIntvl {
                value 3;
            }

            // Config of ipv6 nd ra-lifetime failed
            enum raLifetime {
                value 4;
            }

            // Config of ipv6 nd suppress-ra failed
            enum suppressRa {
                value 5;
            }

            // Config of ipv6 nd mac-extract failed
            enum macExtract {
                value 6;
            }
        }
    }

    // Config Error Inst MO
    typedef nd_ConfigErrInst {

        // bits- Using string
        type string;
    }

    // DNSSeqNum
    typedef nd_DNSSeqNum {

        // MAX Converted to int from 0xffffffff
        type uint32 {
            range "0..4294967295";
        }
    }

    // DadAttempts
    typedef nd_DadAttempts {
        type uint16 {
            range "0..15";
        }
        default "1";
    }

    // Dadns-Interval
    typedef nd_DadnsInverval {
        type uint16 {
            range "1000..6000";
        }
        default "5000";
    }

    // Database type
    typedef nd_DbT {
        type enumeration {

            // Adjacency Database
            enum adj {
                value 1;
            }
        }
        default "adj";
    }

    // Hop limit
    typedef nd_HopLimit {
        type uint8 {
            range "0..255";
        }
        default "64";
    }

    // Interface Controls
    // Default Value computed from redirects
    typedef nd_IfControl {

        // bits- Using string
        type string;
        default "redirects";
    }

    // Lifetime    @@@ 0xffffffff == infinite
    typedef nd_Lifetime {

        // MAX Converted to int from 0xffffffff
        type uint32 {
            range "0..4294967295";
        }
        default "2592000";
    }

    // Solicit Accept Value
    typedef nd_MacExtract {
        type enumeration {

            // Default
            enum none {
                value 0;
            }

            // Nud-phase
            enum nud-phase {
                value 1;
            }

            // Exclude-nud-phase
            enum exclude-nud-phase {
                value 2;
            }
        }
        default "none";
    }

    // Max pack cnt
    typedef nd_MaxPacket {
        type uint32 {
            range "0..32767";
        }
        default "1000";
    }

    // Neighbor solitication transmission Retry Count
    // <type name="NsRetries"
    // base="scalar:UByte"
    // >
    // <range min="1" max="100"/>
    // <default value="3"/>
    // </type>
    // MTU
    typedef nd_Mtu {
        type uint16 {
            range "1280..65535";
        }
        default "1500";
    }

    // ND Cache Limit
    typedef nd_NdCacheLimit {
        type uint32 {
            range "1..614400";
        }
        default "174080";
    }

    // ND Cache Syslog Rate
    typedef nd_NdCacheSyslogRate {
        type uint32 {
            range "1..1000";
        }
        default "1";
    }

    // NDRouteLifeTime    @@@ 0xffffffff == infinite
    typedef nd_NdRtLifeTime {

        // MAX Converted to int from 0xffffffff
        type uint32 {
            range "0..4294967295";
        }
    }

    // Neighbor solitication transmission interval
    typedef nd_NsIntvl {
        type uint32 {
            range "1000..3600000";
        }
        default "1000";
    }

    // OffListTimeout
    typedef nd_OffListTimeout {
        type uint16 {
            range "180..1800";
        }
        default "180";
    }

    // OperNDRouteLifeTime    @@@ 0xffffffff == infinite
    typedef nd_OperNdRtLifeTime {

        // MAX Converted to int from 0xffffffff
        type uint32 {
            range "0..4294967295";
        }
    }

    // Prefix Controls
    // Default Value computed from auto-cfg,on-link,advertise,router-address
    typedef nd_PfxControl {

        // bits- Using string
        type string;
        default "auto-cfg,on-link,advertise,router-address";
    }

    // Lifetime    @@@ 0xffffffff == infinite
    typedef nd_PrefLifetime {

        // MAX Converted to int from 0xffffffff
        type uint32 {
            range "0..4294967295";
        }
        default "604800";
    }

    // Interval between RA transmissions
    typedef nd_RaIntvl {
        type uint16 {
            range "4..1800";
        }
        default "600";
    }

    // Interval between RA transmissions minimum
    typedef nd_RaIntvlMin {
        type uint16 {
            range "3..1350";
        }
        default "200";
    }

    // RA lifetime
    typedef nd_RaLifetime {
        type uint16 {
            range "0..9000";
        }
        default "1800";
    }

    // Reachable time
    typedef nd_ReachableTime {
        type uint32 {
            range "0..3600000";
        }
        default "0";
    }

    // Retransmit timer
    typedef nd_RetransTimer {

        // MAX Converted to int from 0xffffffff
        type uint32 {
            range "0..4294967295";
        }
        default "0";
    }

    // Router Preference
    typedef nd_RouterPreference {
        type enumeration {

            // ICMPv6 nd router preference medium
            enum Medium {
                value 0;
            }

            // ICMPv6 nd router preference high
            enum High {
                value 1;
            }

            // ICMPv6 nd router preference reserved
            enum Reserved {
                value 2;
            }

            // ICMPv6 nd router preference low
            enum Low {
                value 3;
            }
        }
    }

    // Router Preference for command
    typedef nd_RtPrefForCmd {
        type enumeration {

            // ICMPv6 nd router preference (if not specified)
            enum unspecified {
                value 0;
            }

            // ICMPv6 nd router preference low
            enum low {
                value 1;
            }

            // ICMPv6 nd router preference medium
            enum medium {
                value 2;
            }

            // ICMPv6 nd router preference high
            enum high {
                value 3;
            }
        }
    }

    // Route Preference for ND Route specific
    typedef nd_RtPrefForNdRt {
        type enumeration {

            // ICMPv6 nd router preference low
            enum low {
                value 0;
            }

            // ICMPv6 nd router preference medium
            enum medium {
                value 1;
            }

            // ICMPv6 nd router preference high
            enum high {
                value 2;
            }
        }
    }

    // Solicit Accept Value
    typedef nd_SolicitAcceptValue {
        type enumeration {

            // Default
            enum none {
                value 0;
            }

            // Accept
            enum accept {
                value 1;
            }

            // No-accept
            enum no-accept {
                value 2;
            }
        }
        default "none";
    }

    // SolicitProbeValue    Range for probe interval is from 1 to 20.
    // Special value zero (0) indicates no-probe.
    typedef nd_SolicitProbeValue {
        type uint16 {
            range "0..20";
        }
        default "5";
    }

    // Static Adjacency operational state
    typedef nd_StAdjOperSt {
        type enumeration {

            // Down
            enum down {
                value 0;
            }

            // Incomplete
            enum up {
                value 1;
            }
        }
        default "down";
    }

    // Static Adjacency operational state qualifier
    typedef nd_StAdjOperStQual {
        type enumeration {

            // Subnet mismatch
            enum subnet-mismatch {
                value 1;
            }

            // Invalid MAC
            enum invalid-mac {
                value 2;
            }

            // Invalid IP
            enum invalid-ip {
                value 3;
            }

            // Invalid VRF
            enum invalid-vrf {
                value 4;
            }

            // Own MAC
            enum own-mac {
                value 5;
            }

            // Interface down
            enum if-down {
                value 6;
            }

            // Up
            enum up {
                value 7;
            }
        }
        default "up";
    }

    // Syslog threshold
    typedef nd_SyslogCnt {
        type uint32 {
            range "0..65535";
        }
        default "10000";
    }

    // throttle timeout
    typedef nd_ThrTimeout {
        type uint16 {
            range "300..1800";
        }
        default "300";
    }

    // VADDR Client state
    typedef nd_VaddrClientState {
        type enumeration {

            // ICMPv6 client state inactive
            enum ICMPV6_CLIENT_STATE_INACTIVE {
                value 0;
            }

            // ICMPv6 client state active
            enum ICMPV6_CLIENT_STATE_ACTIVE {
                value 1;
            }

            // ICMPv6 client state anycast inactive
            enum ICMPV6_CLIENT_STATE_ANYCAST_INACTIVE {
                value 2;
            }
        }
    }

    typedef nd_adjRouteDist {
        type uint32 {
            range "2..250";
        }
        default "250";
    }

    typedef network_SwitchId {
        type enumeration {

            // NONE
            enum NONE {
                value 0;
            }

            // A
            enum A {
                value 1;
            }

            // B
            enum B {
                value 2;
            }
        }
        default "A";
    }

    // Authentication Key
    typedef ngoam_AuthKey {
        type string {
            length "0..63";
        }
    }

    // Counter
    typedef ngoam_Counter {
        type uint32;
    }

    // Description
    typedef ngoam_Desc {
        type string {
            length "0..64";
        }
    }

    // Num packets to send for a given ping task
    typedef ngoam_DestPort {

        // MAX Converted to int from 0xffff
        type uint16 {
            range "0..65535";
        }
        default "0";
    }

    // dot1q id
    typedef ngoam_Dot1q {
        type uint16 {
            range "0..4096";
        }
    }

    // dot1q id under flow forward
    typedef ngoam_Dot1qFlow {
        type uint16 {
            range "0..3967";
        }
    }

    // Hop count
    typedef ngoam_Hop {
        type uint8 {
            range "1..255";
        }
        default "100";
    }

    // Hop count
    typedef ngoam_Hops {
        type uint8 {
            range "1..255";
        }
        default "32";
    }

    // Interface range
    typedef ngoam_Interface {
        type string {
        }
        default "unspecified";
    }

    // Num packets to send for a given ping task
    typedef ngoam_NumPkt {

        // MAX Converted to int from 0xffff
        type uint16 {
            range "1..65535";
        }
        default "5";
    }

    // Type of the path
    typedef ngoam_OamChannel {
        type enumeration {

            // INVALID
            enum invalid {
                value 0;
            }

            // TISSA
            enum tissa {
                value 2;
            }
        }
        default "invalid";
    }

    // Order
    typedef ngoam_Order {
        type uint8;
    }

    // Path id
    typedef ngoam_PathId {
        type uint8;
    }

    // Payload pad value
    typedef ngoam_PayloadPad {

        // MAX Converted to int from 0xffff
        type uint16 {
            range "0..65535";
        }
        default "0";
    }

    // The packet size to be used for sending the ping packet
    typedef ngoam_PktSz {
        type uint16 {
            range "1..65486";
        }
        default "56";
    }

    // Profile id
    typedef ngoam_ProfId {
        type uint16 {
            range "1..1023";
        }
    }

    // Flow protocol number
    typedef ngoam_Protocol {
        type uint16 {
            range "0..255";
        }
    }

    // Round trip time
    typedef ngoam_Rtt {
        type uint32;
    }

    // The interval between every ping packet that is sent out
    typedef ngoam_SendIntvl {
        type uint8 {
            range "0..60";
        }
        default "0";
    }

    // SessionId
    typedef ngoam_SessionId {

        // MAX Converted to int from 0xffff
        type uint16 {
            range "0..65535";
        }
    }

    // Source port range
    typedef ngoam_Sport {
        type string {
        }
        default "0";
    }

    // Source port to be used in the packet
    typedef ngoam_SrcPort {

        // MAX Converted to int from 0xffff
        type uint16 {
            range "0..65535";
        }
        default "0";
    }

    // The interval between every ping packet that is sent out
    typedef ngoam_SweepSz {
        type uint16 {
            range "90..9600";
        }
        default "90";
    }

    // Hop count
    typedef ngoam_TTL {
        type uint8 {
            range "1..255";
        }
        default "5";
    }

    // The timeout before the ping task gives up with the reply
    typedef ngoam_Timeout {
        type uint8 {
            range "0..60";
        }
        default "2";
    }

    // Vni id
    typedef ngoam_Vnid {
        type uint32 {
            range "1..16777215";
        }
    }

    // The vrf the oam task is running
    typedef ngoam_Vrf {
        type l3_VrfName;
    }

    typedef nvo_CfgSrcT {
        type uint16 {
            range "0..2";
        }
    }

    typedef nvo_ETimeStamp {
        type uint64;
        default "0";
    }

    typedef nvo_EncapT {
        type uint16 {
            range "0..8";
        }
    }

    // Fault handling for EpMo. Each (non-oper) property
    // of EpMo has alternate config and unconfig bits to
    // indicate the cause of the fault.
    typedef nvo_EpFaultBitmapT {

        // bits- Using string
        type string;
    }

    typedef nvo_EpIdT {
        type uint32;
    }

    typedef nvo_HostLearnModeT {
        type uint16;
        default "1";
    }

    typedef nvo_HostReachT {
        type uint16 {
            range "0..4";
        }
    }

    typedef nvo_IngReplProtoT {
        type uint16 {
            range "0..2";
        }
    }

    // Fault handling for IngReplMo. Each (non-oper) property
    // of IngReplMo has alternate config and unconfig bit to
    // indicate the cause of the fault.
    typedef nvo_IrFaultBitmapT {

        // bits- Using string
        type string;
    }

    // Fault handling for NwMo. Each (non-oper) property
    // of NwMo has alternate config and unconfig bit to
    // indicate the cause of the fault.
    typedef nvo_NwFaultBitmapT {

        // bits- Using string
        type string;
    }

    typedef nvo_PeerStateT {
        type uint16;
        default "2";
    }

    // This type is used for the hidden property replMode in the IngRepl Mo.
    // The values in this enum are a subset of the values in the aggregate model
    // type ReplicationModeType (defined in file switch/aggregate/types.xml).
    // Const values defined in this enum should be the same as the corresponding
    // values in the aggregate model enum
    typedef nvo_ReplModeT {
        type enumeration {

            // Unknown
            enum unknown {
                value 0;
            }

            // ReplicationServer
            enum replicationServer {
                value 1;
            }

            // IngressReplication
            enum ingressReplication {
                value 2;
            }
        }
        default "ingressReplication";
    }

    // Fault handling for StIRPeerMo. Each (non-oper) property
    // of StIRPeerMo has alternate config and unconfig bit to
    // indicate the cause of the fault.
    typedef nvo_StIRFaultBitmapT {

        // bits- Using string
        type string;
    }

    // Fault handling for StPeerMo. Each (non-oper) property
    // of StPeerMo has alternate config and unconfig bit to
    // indicate the cause of the fault.
    typedef nvo_StPeerFaultBitmapT {

        // bits- Using string
        type string;
    }

    typedef nvo_VniStateT {
        type uint16;
        default "2";
    }

    typedef nvo_VniT {
        type uint32 {
            range "1..16777215";
        }
    }

    typedef nvo_VniTypeT {
        type uint16;
    }

    // Address family
    typedef nw_AddrF {
        type enumeration {

            // IPv4
            enum ipv4 {
                value 1;
            }

            // IPv6
            enum ipv6 {
                value 2;
            }

            // Mac
            enum mac {
                value 3;
            }
        }
        default "ipv4";
    }

    // Administrative state
    typedef nw_AdminSt {
        type enumeration {

            // Enabled
            enum enabled {
                value 1;
            }

            // Disabled
            enum disabled {
                value 2;
            }
        }
        default "enabled";
    }

    // 32 bit Counter
    typedef nw_Counter32 {
        type uint32;
    }

    // 64 bit Counter
    typedef nw_Counter64 {
        type uint64;
    }

    // Operational state of entity
    typedef nw_EntOperSt {
        type enumeration {
            enum unknown {
                value 0;
            }
            enum enabled {
                value 1;
            }
            enum disabled {
                value 2;
            }
            enum initializing {
                value 3;
            }
            enum failed {
                value 4;
            }
        }
        default "enabled";
    }

    // Administrative state of interface
    typedef nw_IfAdminSt {
        type nw_AdminSt;
    }

    // Interface identifier
    typedef nw_IfId {
        type string;
    }

    // Instance controls
    typedef nw_InstCtrl {

        // bits- Using string
        type string;
    }

    // Interface ordinal
    typedef nw_Iod {

        // MAX Converted to int from 0xffffffff
        type uint32 {
            range "1..4294967295";
        }
        default "1";
    }

    // Memory alert level
    typedef nw_MemAlertLevel {
        type enumeration {

            // Normal
            enum normal {
                value 0;
            }

            // Minor
            enum minor {
                value 1;
            }

            // Major
            enum major {
                value 2;
            }

            // Critical
            enum critical {
                value 3;
            }
        }
        default "normal";
    }

    // Operational state summary
    typedef nw_OSSum {
        type enumeration {

            // Failed
            enum failed {
                value 0;
            }

            // Initializing
            enum initializing {
                value 1;
            }

            // Resetting
            enum resetting {
                value 2;
            }

            // Degraded
            enum degraded {
                value 3;
            }

            // Ok
            enum ok {
                value 4;
            }
        }
        default "ok";
    }

    // Operational state summary qualifier
    typedef nw_OSSumQual {
        type string;
    }

    // Operational error qualifier
    typedef nw_OperErrQual {

        // bits- Using string
        type string;
    }

    // Endpoint type
    typedef oam_EpT {
        type enumeration {

            // EP
            enum ep {
                value 1;
            }

            // EP behind a vtep
            enum vtep-ep {
                value 2;
            }

            // Node
            enum node {
                value 3;
            }
        }
        default "node";
    }

    // Ip identifier
    typedef oam_IpId {
        type address_Ip;
    }

    // MAC identifier
    typedef oam_MacId {
        type address_Mac;
    }

    // Payload size
    typedef oam_PayloadSz {
        type uint16 {
            range "20..8904";
        }
        default "56";
    }

    // Profile name
    typedef oam_ProfName {
        type string;
    }

    // Tenant name
    typedef oam_TenantName {
        type string;
    }

    // The vrf the oam task is running
    typedef oam_Vrf {
        type l3_VrfName;
    }

    // Default Value computed from none
    typedef opflex_DevOperIssues {

        // bits- Using string
        type string;
        default "none";
    }

    typedef opflex_DevOperState {
        type enumeration {

            // Unknown
            enum unknown {
                value 0;
            }

            // Online
            enum online {
                value 1;
            }

            // Offline
            enum offline {
                value 2;
            }

            // Identified
            enum identified {
                value 3;
            }

            // Compatible
            enum compatible {
                value 4;
            }

            // Incompatible
            enum incompatible {
                value 5;
            }
        }
        default "identified";
    }

    // Type of opflex device
    typedef opflex_DeviceType {
        type enumeration {
            enum unknown {
                value 0;
            }
            enum n1kv {
                value 1;
            }
            enum hyperv {
                value 2;
            }
            enum ovs {
                value 3;
            }
        }
        default "n1kv";
    }

    typedef opflex_Direction {
        type enumeration {
            enum in {
                value 0;
            }
            enum out {
                value 1;
            }
        }
        default "in";
    }

    // Ep Transition Status
    typedef opflex_EpTransitionStatus {
        type enumeration {
            enum unknown {
                value 0;
            }
            enum attached {
                value 1;
            }
            enum detached {
                value 2;
            }
        }
        default "attached";
    }

    // epp download hint
    typedef opflex_EppDownloadHint {
        type enumeration {
            enum unknown {
                value 0;
            }
            enum always {
                value 1;
            }
            enum optimal {
                value 2;
            }
        }
        default "always";
    }

    // hb status
    typedef opflex_HbStatus {
        type enumeration {
            enum unknown {
                value 0;
            }
            enum invalid-dvs {
                value 1;
            }
            enum valid-dvs {
                value 2;
            }
        }
        default "valid-dvs";
    }

    typedef os_OsString {
        type string {
            length "0..256";
        }
    }

    // ASBR  Router Status
    typedef ospf_ASBdrRtr {
        type uint8 {
            range "0..1";
        }
        default "0";
    }

    // Adjacency change logging levels
    typedef ospf_AdjChangeLogLevel {
        type enumeration {

            // No logging
            enum none {
                value 0;
            }

            // Brief logging
            enum brief {
                value 1;
            }

            // Detailed logging
            enum detail {
                value 2;
            }
        }
        default "none";
    }

    // Adjacency flags
    // Default Value computed from unspecified
    typedef ospf_AdjFlags {

        // bits- Using string
        type string;
        default "unspecified";
    }

    // Adjacency router id
    typedef ospf_AdjId {
        type ip_RtrId;
    }

    // Adjacency interface id
    typedef ospf_AdjIfId {
        type uint32;
    }

    // Adjancency operational state
    typedef ospf_AdjOperSt {
        type enumeration {

            // Unknown
            enum unknown {
                value 0;
            }

            // Down
            enum down {
                value 1;
            }

            // Attempt
            enum attempt {
                value 2;
            }

            // Initializing
            enum initializing {
                value 3;
            }

            // Two-way
            enum two-way {
                value 4;
            }

            // Exstart
            enum exstart {
                value 5;
            }

            // Exchange
            enum exchange {
                value 6;
            }

            // Loading
            enum loading {
                value 7;
            }

            // Full
            enum full {
                value 8;
            }

            // Self
            enum self {
                value 9;
            }
        }
        default "down";
    }

    // Address family type
    typedef ospf_AfT {
        type enumeration {

            // IPv4 unicast address family
            enum ipv4-ucast {
                value 1;
            }

            // IPv6 unicast address family
            enum ipv6-ucast {
                value 2;
            }
        }
        default "ipv6-ucast";
    }

    // Always option for DefLeak
    typedef ospf_Always {
        type enumeration {

            // No
            enum no {
                value 0;
            }

            // Yes
            enum yes {
                value 1;
            }
        }
        default "no";
    }

    // Area Border Router Status
    typedef ospf_AreaBdrRtr {
        type uint8 {
            range "0..1";
        }
        default "0";
    }

    // Area controls
    // Default Value computed from unspecified
    typedef ospf_AreaControl {

        // bits- Using string
        type string;
        default "unspecified";
    }

    // Area default cost
    typedef ospf_AreaCost {
        type uint32 {
            range "0..16777215";
        }
        default "1";
    }

    // Area id
    typedef ospf_AreaId {
        type address_Ipv4;
    }

    // Area type
    typedef ospf_AreaT {
        type enumeration {

            // Regular area
            enum regular {
                value 1;
            }

            // Stub area
            enum stub {
                value 2;
            }

            // NSSA area
            enum nssa {
                value 3;
            }
        }
        default "regular";
    }

    // AS Border Router count
    typedef ospf_AsbrCnt {
        type uint32;
    }

    // Authentication key
    typedef ospf_AuthKey {
        type string;
    }

    // Authentication key id
    typedef ospf_AuthKeyId {
        type uint8 {
            range "0..255";
        }
    }

    // Authentication type
    typedef ospf_AuthT {
        type enumeration {

            // No authentication
            enum none {
                value 0;
            }

            // Simple authentication
            enum simple {
                value 1;
            }

            // MD5 authentication
            enum md5 {
                value 2;
            }

            // Unspecified
            enum unspecified {
                value 3;
            }
        }
        default "unspecified";
    }

    // Bidirectional Forwarding Detection Control
    typedef ospf_BfdControl {
        type enumeration {

            // Unconfigure interface BFD configuration
            enum unspecified {
                value 0;
            }

            // Configure interface to use BFD
            enum enabled {
                value 1;
            }

            // Configure interface not to use BFD
            enum disabled {
                value 2;
            }
        }
        default "unspecified";
    }

    // BFD state
    typedef ospf_BfdOperSt {
        type enumeration {

            // Down
            enum down {
                value 0;
            }

            // Up
            enum up {
                value 1;
            }
        }
    }

    // Border Router count
    typedef ospf_BrCnt {
        type uint32;
    }

    // Bandwidth reference value
    typedef ospf_BwRef {
        type uint32;
        default "40000";
    }

    // Bandwidth reference unit
    typedef ospf_BwRefUnit {
        type enumeration {

            // Mbps
            enum mbps {
                value 0;
            }

            // Gbps
            enum gbps {
                value 1;
            }
        }
        default "mbps";
    }

    // Counter
    typedef ospf_Counter32 {
        type uint32;
    }

    typedef ospf_CurrSleepCnt {
        type uint32 {
            range "0..4294967295";
        }
        default "0";
    }

    // Database type
    typedef ospf_DbT {
        type enumeration {

            // Link state database
            enum ls {
                value 1;
            }

            // Route database
            enum rt {
                value 2;
            }

            // Nexthop database
            enum nh {
                value 3;
            }
        }
        default "ls";
    }

    // Dead interval
    typedef ospf_DeadIntvl {
        type uint16 {
            range "0..65535";
        }
        default "0";
    }

    // Designated address
    typedef ospf_DesigAddr {
        type address_Ip;
    }

    // Designated priority
    typedef ospf_DesigPrio {
        type uint8 {
            range "0..255";
        }
        default "1";
    }

    // Discard Route
    // Default Value computed from int,ext
    typedef ospf_DiscardRoute {

        // bits- Using string
        type string;
        default "int,ext";
    }

    // Distance
    typedef ospf_Dist {
        type uint8 {
            range "1..255";
        }
        default "110";
    }

    // Dom controls
    // Default Value computed from unspecified
    typedef ospf_DomControl {

        // bits- Using string
        type string;
        default "unspecified";
    }

    // Dom name
    typedef ospf_DomName {
        type string;
    }

    // ECMP max paths
    typedef ospf_Ecmp {
        type uint8 {
            range "1..64";
        }
        default "8";
    }

    // Event history Buffer size
    typedef ospf_EventLogSize {
        type enumeration {

            // Event history logging disabled
            enum disabled {
                value 0;
            }

            // Small
            enum small {
                value 1;
            }

            // Medium
            enum medium {
                value 2;
            }

            // Large
            enum large {
                value 3;
            }
        }
        default "small";
    }

    // Event history Bufer size in Kbytes
    typedef ospf_EventLogSizeKBytes {
        type uint16 {
            range "0..65535";
        }
    }

    // Event Log Type
    typedef ospf_EventType {
        type enumeration {

            // Adjacency Events
            enum adj {
                value 0;
            }

            // Internal Events
            enum internal {
                value 1;
            }

            // Events
            enum ha {
                value 2;
            }

            // LSA flooding Events
            enum lsa-flood {
                value 3;
            }

            // LSA Events
            enum lsa {
                value 4;
            }

            // SPF Events
            enum spf {
                value 5;
            }

            // Redistribution Events
            enum redist {
                value 6;
            }

            // LDP Events
            enum ldp {
                value 7;
            }

            // MPLS TE Events
            enum mpls-te {
                value 8;
            }

            // Hellog logs
            enum hello {
                value 9;
            }

            // RIB Events
            enum rib {
                value 10;
            }

            // SPF Trigger Events
            enum spf-trigger {
                value 11;
            }

            // CLI Events
            enum cli {
                value 12;
            }
        }
    }

    // Failed state qualifier
    // Default Value computed from unspecified
    typedef ospf_FailStQual {

        // bits- Using string
        type string;
        default "unspecified";
    }

    // Graceful restart controls
    typedef ospf_GrCtrl {
        type enumeration {

            // Planned graceful restarts only
            enum planned-only {
                value 1;
            }

            // Complete graceful restart enabled
            enum complete {
                value 2;
            }

            // Graceful restart disabled
            enum disabled {
                value 3;
            }
        }
        default "complete";
    }

    // Graceful restart time period in seconds
    typedef ospf_GrPeriod {
        type uint32 {
            range "5..1800";
        }
        default "60";
    }

    // Hello interval
    typedef ospf_HelloIntvl {
        type uint16 {
            range "1..65535";
        }
        default "10";
    }

    // Peer Helper Age
    typedef ospf_HelperAge {
        type uint32;
    }

    // Neighbor restart helper reason
    typedef ospf_HelperExitQual {
        type enumeration {

            // Not Attempted
            enum none {
                value 1;
            }

            // Restart In Progress
            enum in-progress {
                value 2;
            }

            // Successfully Completed
            enum completed {
                value 3;
            }

            // Timed Out
            enum timed-out {
                value 4;
            }

            // Topology Changed
            enum topology-changed {
                value 5;
            }
        }
        default "none";
    }

    // Neighbor restart helper status
    typedef ospf_HelperSt {
        type enumeration {

            // Not Helping
            enum not-helping {
                value 1;
            }

            // Helping
            enum helping {
                value 2;
            }
        }
        default "not-helping";
    }

    // Interface controls
    // Default Value computed from unspecified
    typedef ospf_IfControl {

        // bits- Using string
        type string;
        default "unspecified";
    }

    // Interface cost
    typedef ospf_IfCost {
        type uint16 {
            range "0..65535";
        }
        default "0";
    }

    // Interface flags
    // Default Value computed from unspecified
    typedef ospf_IfFlags {

        // bits- Using string
        type string;
        default "unspecified";
    }

    // Interface operational state
    typedef ospf_IfOperSt {
        type enumeration {

            // Unknown
            enum unknown {
                value 0;
            }

            // Down
            enum down {
                value 1;
            }

            // Loopback
            enum loopback {
                value 2;
            }

            // Waiting
            enum waiting {
                value 3;
            }

            // p2p
            enum p2p {
                value 4;
            }

            // DR
            enum dr {
                value 5;
            }

            // BDR
            enum bdr {
                value 6;
            }

            // DR-other
            enum dr-other {
                value 7;
            }
        }
        default "down";
    }

    // Interface type
    typedef ospf_IfType {
        type enumeration {

            // Unspecified
            enum unspecified {
                value 0;
            }

            // Loopback
            enum loopback {
                value 1;
            }

            // P2P
            enum p2p {
                value 2;
            }

            // P2MP
            enum p2mp {
                value 3;
            }

            // NBMA
            enum nbma {
                value 4;
            }

            // Broadcast
            enum bcast {
                value 5;
            }
        }
        default "unspecified";
    }

    // Instance id
    typedef ospf_InstanceID {
        type uint8 {
            range "0..255";
        }
        default "0";
    }

    // Instance name
    typedef ospf_InstanceName {
        type string {
            length "0..20";
        }
    }

    // Lsa router id
    typedef ospf_LsaAdvRtr {
        type ip_RtrId;
    }

    // LSA Advertisement
    typedef ospf_LsaAdvert {
        type mtx_array_uint8;
    }

    // Lsa age
    typedef ospf_LsaAge {
        type uint32;
    }

    // Lsa arrival interval
    typedef ospf_LsaArrivalIntvl {
        type uint32 {
            range "10..600000";
        }
        default "1000";
    }

    // Lsa checksum
    typedef ospf_LsaCksum {
        type uint32;
    }

    // LSA checksum sum
    typedef ospf_LsaCksumSum {
        type uint32;
    }

    // Lsa group pacing interval
    typedef ospf_LsaGpPacingIntvl {
        type uint16 {
            range "1..1800";
        }
        default "10";
    }

    // Lsa id
    typedef ospf_LsaId {
        type address_Ipv4;
    }

    typedef ospf_LsaLeakOperSt {
        type enumeration {

            // InActive
            enum Inactive {
                value 0;
            }

            // Active
            enum active {
                value 1;
            }
        }
        default "Inactive";
    }

    // Lsa sequence number
    typedef ospf_LsaSeq {
        type uint32;
    }

    // Lsa type
    typedef ospf_LsaT {
        type enumeration {

            // Router LSA
            enum router {
                value 1;
            }

            // Network LSA
            enum nw {
                value 2;
            }

            // Summary LSA
            enum summary {
                value 3;
            }

            // ASBR LSA
            enum asbr {
                value 4;
            }

            // External LSA
            enum ext {
                value 5;
            }

            // NSSA LSA
            enum nssa {
                value 7;
            }

            // Link opaque LSA
            enum link-opq {
                value 9;
            }

            // Area opaque LSA
            enum area-opq {
                value 10;
            }

            // AS opaque LSA
            enum as-opq {
                value 11;
            }
        }
        default "router";
    }

    // Lsa throttle hold interval
    typedef ospf_LsaThHoldIntvl {
        type uint32 {
            range "50..30000";
        }
        default "5000";
    }

    // Lsa throttle maximum interval
    typedef ospf_LsaThMaxIntvl {
        type uint32 {
            range "50..30000";
        }
        default "5000";
    }

    // Lsa throttle start wait interval
    typedef ospf_LsaThStartIntvl {
        type uint32 {
            range "0..5000";
        }
        default "0";
    }

    // Maximum number of non self-generated LSAs
    typedef ospf_MaxLsa {
        type uint32 {
            range "1..4294967295";
        }
    }

    typedef ospf_MaxLsaAct {
        type enumeration {

            // Reject
            enum reject {
                value 0;
            }

            // Restart
            enum restart {
                value 1;
            }

            // Log
            enum log {
                value 2;
            }
        }
        default "reject";
    }

    typedef ospf_MaxLsaOperSt {
        type enumeration {

            // ok
            enum ok {
                value 0;
            }

            // Threshold Exceeded
            enum threshold-exceeded {
                value 1;
            }
        }
        default "ok";
    }

    typedef ospf_MaxLsaOperStQual {
        type enumeration {

            // ok
            enum ok {
                value 0;
            }

            // warning
            enum warning {
                value 1;
            }

            // Overload
            enum overload {
                value 2;
            }

            // Sleep
            enum sleep {
                value 3;
            }

            // Reset
            enum reset {
                value 4;
            }

            // Perm-Sleep
            enum perm-sleep {
                value 5;
            }
        }
        default "ok";
    }

    typedef ospf_MaxLsaThresh {
        type uint16 {
            range "1..100";
        }
        default "75";
    }

    // Max metric value to be used for advertising LSAs
    typedef ospf_MaxMetric {
        type uint32 {
            range "0..16777215";
        }
        default "0";
    }

    // Max metric controls - specifies when to send max
    // metric LSAs and for which LSAs/links
    typedef ospf_MaxMetricControl {

        // bits- Using string
        type string;
    }

    // Metric
    // Default Value "0" Removed - out of range 1..16777214
    typedef ospf_Metric {
        type uint32 {
            range "1..16777214";
        }
    }

    // Nexthop flags
    // Default Value computed from unspecified
    typedef ospf_NhFlags {

        // bits- Using string
        type string;
        default "unspecified";
    }

    typedef ospf_NonSelfLsaCnt {
        type uint32 {
            range "0..4294967295";
        }
        default "0";
    }

    // NSSA translator role
    typedef ospf_NssaTransRole {
        type enumeration {

            // Always
            enum always {
                value 1;
            }

            // Candidate
            enum candidate {
                value 2;
            }

            // Never
            enum never {
                value 3;
            }
        }
        default "candidate";
    }

    // NSSA translator state
    typedef ospf_NssaTransSt {
        type enumeration {

            // Enabled
            enum enabled {
                value 1;
            }

            // Elected
            enum elected {
                value 2;
            }

            // Disabled
            enum disabled {
                value 3;
            }
        }
        default "elected";
    }

    // NSSA translator interval
    typedef ospf_NssaTransStabIntvl {
        type uint32 {
            range "0..4294967295";
        }
        default "40";
    }

    // Network type
    typedef ospf_NwT {
        type enumeration {

            // Unspecified
            enum unspecified {
                value 0;
            }

            // Point-to-point
            enum p2p {
                value 1;
            }

            // Broadcast
            enum bcast {
                value 2;
            }
        }
        default "unspecified";
    }

    // L3vm Operational state
    typedef ospf_OperSt {
        type enumeration {

            // Invalid
            enum invalid {
                value 0;
            }

            // Down
            enum down {
                value 1;
            }

            // Up
            enum up {
                value 2;
            }
        }
        default "down";
    }

    // Neighbor options
    typedef ospf_Options {
        type uint32;
    }

    // Passive Control
    typedef ospf_PassiveControl {
        type enumeration {

            // Unconfigure interface passive configuration
            enum unspecified {
                value 0;
            }

            // Configure interface as passive
            enum enabled {
                value 1;
            }

            // Configure interface as non-passive
            enum disabled {
                value 2;
            }
        }
        default "unspecified";
    }

    // Path type
    typedef ospf_PathT {
        type enumeration {

            // Intra
            enum intra {
                value 1;
            }

            // Discard internal
            enum discard-int {
                value 2;
            }

            // Inter
            enum inter {
                value 3;
            }

            // Discard external
            enum discard-ext {
                value 4;
            }

            // External1
            enum ext1 {
                value 5;
            }

            // NSSA1
            enum nssa1 {
                value 6;
            }

            // External2
            enum ext2 {
                value 7;
            }

            // NSSA2
            enum nssa2 {
                value 8;
            }
        }
        default "intra";
    }

    typedef ospf_ResetIntvl {
        type uint32 {
            range "1..1440";
        }
        default "10";
    }

    // Graceful restart exit reason
    typedef ospf_RestartExitReason {
        type enumeration {

            // None
            enum none {
                value 0;
            }

            // In Progress
            enum in_progress {
                value 1;
            }

            // Completed
            enum completed {
                value 2;
            }

            // Timed Out
            enum timedout {
                value 3;
            }

            // Topology Changed
            enum topology_changed {
                value 4;
            }
        }
        default "none";
    }

    // Graceful restart status
    typedef ospf_RestartStatus {
        type enumeration {

            // Not Restarting
            enum not-restarting {
                value 0;
            }

            // Planned
            enum planned {
                value 1;
            }

            // Unplanned
            enum unplanned {
                value 2;
            }
        }
        default "not-restarting";
    }

    // Retransmit interval
    typedef ospf_RexmitIntvl {
        type uint16 {
            range "1..65535";
        }
        default "5";
    }

    // Route cost
    typedef ospf_RtCost {
        type uint16 {
            range "1..65535";
        }
        default "1";
    }

    // Route flags
    // Default Value computed from unspecified
    typedef ospf_RtFlags {

        // bits- Using string
        type string;
        default "unspecified";
    }

    // Route tag
    typedef ospf_RtTag {
        type uint32;
    }

    typedef ospf_SleepCnt {
        type uint32 {
            range "1..4294967295";
        }
        default "5";
    }

    typedef ospf_SleepIntvl {
        type uint16 {
            range "1..1440";
        }
        default "5";
    }

    // Spf computation hold interval
    typedef ospf_SpfCompHoldIntvl {
        type uint32 {
            range "1..600000";
        }
        default "1000";
    }

    // Spf computation initial wait interval
    typedef ospf_SpfCompInitIntvl {
        type uint32 {
            range "1..600000";
        }
        default "200";
    }

    // Spf computation maximum wait interval
    typedef ospf_SpfCompMaxIntvl {
        type uint32 {
            range "1..600000";
        }
        default "5000";
    }

    typedef ospf_StartupIntvl {
        type uint32 {
            range "5..86400";
        }
        default "600";
    }

    // Summary Control
    // Default Value computed from unspecified
    typedef ospf_SumControl {

        // bits- Using string
        type string;
        default "unspecified";
    }

    // Area range cost
    // Default Value "4294967295" Removed - out of range 0..16777215
    typedef ospf_SumCost {
        type uint32 {
            range "0..16777215";
        }
    }

    // Vrf-Lite Control
    typedef ospf_VrfLiteControl {
        type enumeration {

            // Unconfigure Vrf-Lite configuration
            enum unspecified {
                value 0;
            }

            // Configure Vrf-Lite for L3VPN
            enum l3vpn {
                value 1;
            }

            // Configure Vrf-Lite for Ethernet VPN
            enum evpn {
                value 2;
            }
        }
        default "unspecified";
    }

    // Tramist delay
    typedef ospf_XmitDelay {
        type uint16 {
            range "1..450";
        }
        default "1";
    }

    // Active member ports
    typedef pc_ActivePorts {
        type uint32;
    }

    // Bundle port number
    typedef pc_BdlPortNum {
        type uint32;
    }

    // Channeling Status
    typedef pc_ChannelingSt {
        type enumeration {
            enum unknown {
                value 0;
            }
            enum channeling {
                value 1;
            }
            enum individual {
                value 2;
            }
            enum failed {
                value 3;
            }
            enum suspended {
                value 4;
            }
            enum hot-standby {
                value 5;
            }
        }
    }

    // force channel-group
    typedef pc_ChnlGrpForce {
        type boolean;
    }

    // Member port flags
    typedef pc_Flags {

        // bits- Using string
        type string;
    }

    // Hash distribution type
    typedef pc_HashDist {
        type enumeration {

            // None
            enum none {
                value 0;
            }

            // Adaptive
            enum adaptive {
                value 1;
            }

            // Fixed
            enum fixed {
                value 2;
            }
        }
        default "none";
    }

    // Default Value computed from susp-individual,graceful-conv
    typedef pc_IfControl {

        // bits- Using string
        type string;
        default "susp-individual,graceful-conv";
    }

    // Interface ordinal
    typedef pc_Iod {
        type uint32;
    }

    // Last Status
    typedef pc_LastSt {
        type enumeration {
            enum successful {
                value 0;
            }
            enum failed {
                value 1;
            }
        }
    }

    // LIF
    typedef pc_Lif {
        type uint32;
    }

    // Load balance algorithm
    typedef pc_LoadBalance {

        // bits- Using string
        type string;
    }

    // Load defer timeout
    typedef pc_LoadDeferTime {
        type uint32 {
            range "1..1800";
        }
        default "120";
    }

    // LTL
    typedef pc_Ltl {
        type uint32;
    }

    // LTL programmed
    typedef pc_LtlProgrammed {
        type boolean;
    }

    // Max possible active members
    typedef pc_MaxActive {
        type uint32;
    }

    // Maximum links
    typedef pc_MaxLinks {
        type uint32 {
            range "1..32";
        }
        default "32";
    }

    // Minimum links
    typedef pc_MinLinks {
        type uint32 {
            range "1..32";
        }
        default "1";
    }

    // Port channel mode
    typedef pc_Mode {
        type enumeration {

            // on
            enum on {
                value 0;
            }

            // Static
            enum static {
                value 1;
            }

            // lacp-active
            enum active {
                value 2;
            }

            // lacp-passive
            enum passive {
                value 3;
            }

            // Mac Pinning
            enum mac-pin {
                value 4;
            }
        }
        default "on";
    }

    // Number of port-channels
    typedef pc_NumChannels {
        type uint32;
    }

    // Operational State
    typedef pc_OperSt {
        type enumeration {

            // Up
            enum up {
                value 0;
            }

            // Down
            enum down {
                value 1;
            }

            // Bringup in Progress
            enum bringup-in-progress {
                value 2;
            }

            // Module Removed
            enum module-removed {
                value 3;
            }
        }
    }

    // Hash distribution type
    typedef pc_PCHashDist {
        type enumeration {

            // None
            enum none {
                value 0;
            }

            // Adaptive
            enum adaptive {
                value 1;
            }

            // Fixed
            enum fixed {
                value 2;
            }
        }
        default "adaptive";
    }

    // Port channel id
    typedef pc_PcId {
        type uint16 {
            range "1..65535";
        }
    }

    // Percentage of used port-channels
    typedef pc_PcntChannels {
        type uint8 {
            range "0..100";
        }
    }

    // Summarized Operational State
    typedef pc_SummOperSt {
        type enumeration {

            // Up
            enum up {
                value 0;
            }

            // Down
            enum down {
                value 1;
            }

            // Module-removed
            enum module-removed {
                value 2;
            }

            // Individual
            enum individual {
                value 3;
            }

            // Suspended
            enum suspended {
                value 4;
            }

            // Hot-standby
            enum hot-standby {
                value 5;
            }
        }
        default "down";
    }

    // suspended due to min-links
    typedef pc_SuspMinlinks {
        type boolean;
    }

    // Time
    typedef pc_Time {
        type uint64;
    }

    // Counter
    typedef ping_Counter {
        type uint32;
    }

    // Round trip time
    typedef ping_Rtt {
        type uint32;
    }

    typedef pki_AES128IV {
        type string;
    }

    typedef pki_AES128Key {
        type string;
    }

    typedef pki_Cert {
        type string;
    }

    typedef pki_CertValidity {
        type string;
    }

    typedef pki_Csync2KeyType {
        type string;
    }

    typedef pki_CsyncActivationStateType {
        type enumeration {

            // Disabled
            enum disabled {
                value 0;
            }

            // Enabled
            enum enabled {
                value 1;
            }
        }
        default "enabled";
    }

    typedef pki_CsyncElementType {
        type enumeration {

            // exclude
            enum exclude {
                value 0;
            }

            // include
            enum include {
                value 1;
            }
        }
        default "include";
    }

    typedef pki_CsyncRefreshIntervalType {
        type uint16 {
            range "30..600";
        }
        default "30";
    }

    typedef pki_FP {
        type string;
    }

    typedef pki_GuiIdleTimeoutType {
        type uint16 {
            range "60..65525";
        }
        default "1200";
    }

    typedef pki_KeyringState {
        type enumeration {

            // Started
            enum started {
                value 1;
            }

            // Created
            enum created {
                value 2;
            }

            // Request Created
            enum reqCreated {
                value 3;
            }

            // Trust Provider Set
            enum tpSet {
                value 4;
            }

            // Completed
            enum completed {
                value 5;
            }
        }
        default "started";
    }

    typedef pki_Modulus {
        type enumeration {

            // MOD 512
            enum mod512 {
                value 512;
            }

            // MOD 1024
            enum mod1024 {
                value 1024;
            }

            // MOD 1536
            enum mod1536 {
                value 1536;
            }

            // MOD 2048
            enum mod2048 {
                value 2048;
            }
        }
        default "mod2048";
    }

    typedef pki_PrivateKey {
        type string {
            length "0..4096";
        }
    }

    typedef pki_SHA256_SharedSecret16 {
        type string;
    }

    // Default Value computed from 7
    typedef pki_SessionRecordFlags {

        // bits- Using string
        type string;
        default "7";
    }

    typedef pki_WebTokenTimeoutType {
        type uint16 {
            range "300..9600";
        }
        default "600";
    }

    // Units are in hours - minimum 4 hours, maximum 24 hours
    typedef pki_WebTokenValidityPeriodType {
        type uint16 {
            range "4..24";
        }
        default "24";
    }

    typedef platform_HwProfile {
        type enumeration {
            enum Default {
                value 0;
            }
            enum QS_PORT_MODE_64X10G {
                value 1;
            }
            enum QS_PORT_MODE_48X10G_4X40G {
                value 2;
            }
            enum QS_PORT_MODE_52X10G_3X40g {
                value 3;
            }
            enum QS_PORT_MODE_56X10G_2X40G {
                value 4;
            }
            enum QS_PORT_MODE_60X10G_1X40G {
                value 5;
            }
            enum QS_PORT_MODE {
                value 6;
            }
            enum QG_PORT_MODE_32X10G_8X40G {
                value 9;
            }
            enum QG_PORT_MODE_16X40G {
                value 10;
            }
            enum QG_PORT_MODE_16X10G_12X40G {
                value 11;
            }
            enum QG_PORT_MODE_8X10G_14X40G {
                value 12;
            }
            enum NEP_PORT_MODE_32X40G {
                value 13;
            }
            enum NEP_PORT_MODE_24X40G {
                value 14;
            }
            enum NEP_PORT_MODE_26X40G {
                value 15;
            }
            enum NEP_PORT_MODE_32X40G_FIXED {
                value 16;
            }
            enum QI2_PORT_MODE_72X10G {
                value 17;
            }
            enum QI2_PORT_MODE_48X10G_6x40G {
                value 18;
            }
            enum QI2_PORT_MODE_BKOUT {
                value 19;
            }
            enum DV_PORT_MODE_48X25G_4X100G {
                value 20;
            }
            enum DV_PORT_MODE_48X25G_2X100G_4X40G {
                value 21;
            }
            enum PB_PORT_MODE_48X10G_6X100G {
                value 22;
            }
            enum PB_PORT_MODE_48X10G_4X100G_2X40G {
                value 23;
            }
        }
        default "Default";
    }

    typedef platform_IPV6alpmCarveValues {
        type uint16 {
            range "0..4096";
        }
        default "0";
    }

    typedef platform_LpmMaxLimits {
        type uint16 {
            range "0..4096";
        }
    }

    typedef platform_MulticastMaxLimit {
        type uint16 {
            range "0..8000";
        }
    }

    typedef platform_PcLbAlgo {
        type enumeration {
            enum PC_LB_ALGO_DLB {
                value 1;
            }
            enum PC_LB_ALGO_RTAG7 {
                value 2;
            }
            enum PC_LB_ALGO_RTAG7_MURMUR {
                value 3;
            }
            enum PC_LB_ALGO_RTAG7_LOCAL_CRC {
                value 4;
            }
            enum PC_LB_ALGO_DYNAMIC_PIN {
                value 5;
            }
        }
        default "PC_LB_ALGO_DLB";
    }

    typedef platform_Percentage {
        type uint16 {
            range "1..100";
        }
    }

    typedef platform_QosMinBuffer {
        type enumeration {
            enum all {
                value 0;
            }
            enum none {
                value 1;
            }
            enum default {
                value 2;
            }
        }
        default "all";
    }

    typedef platform_RoutingMode {
        type enumeration {
            enum DEFAULT {
                value 0;
            }
            enum NON_HIER_DEFAULT {
                value 1;
            }
            enum NON_HIER_MAX_L3 {
                value 2;
            }
            enum MAX_HOST {
                value 3;
            }
            enum TOR_MAX_L3 {
                value 4;
            }
            enum DEFAULT_64B {
                value 5;
            }
            enum NON_HIER_MAX_L3_64B {
                value 6;
            }
            enum TOR_MAX_L3_64B {
                value 7;
            }
            enum TOR_MAX_L2 {
                value 8;
            }
            enum TOR_MAX_L2L3 {
                value 9;
            }
            enum TOR_TEMPLATE_OVL_HOST_SCALE {
                value 21;
            }
            enum TEMPLATE_LPM_HEAVY {
                value 22;
            }
            enum TOR_TEMPLATE_LPM_SCALE_V6_64 {
                value 23;
            }
            enum TOR_TEMPLATE_DUAL_STACK_HOST_SCALE {
                value 24;
            }
            enum TEMPLATE_DYNAMIC_TRIE_SCALE {
                value 25;
            }
            enum TEMPLATE_MULTICAST_HEAVY {
                value 26;
            }
            enum TEMPLATE_VXLAN_SCALE {
                value 27;
            }
            enum TEMPLATE_MPLS_SCALE {
                value 28;
            }
            enum TEMPLATE_IPV6_LPM_HEAVY {
                value 29;
            }
        }
        default "DEFAULT";
    }

    typedef platform_Tuple {
        type enumeration {
            enum Disable {
                value 0;
            }
            enum Enable {
                value 1;
            }
        }
        default "Disable";
    }

    typedef platform_UnicastMaxLimit {
        type uint16 {
            range "0..8000";
        }
    }

    typedef platform_tcamRegionSize {
        type uint32 {
            range "0..2147483647";
        }
    }

    // Burst size
    typedef policer_Burst {
        type uint32;
    }

    // Committed rate
    typedef policer_Rate {
        type uint32;
    }

    // CPU Usage
    // Default Value "0" Removed - out of range 1..100
    typedef proc_CpuUsage {
        type uint32 {
            range "1..100";
        }
    }

    // Operational Status
    typedef proc_OperSt {
        type enumeration {

            // Interruptible sleep
            enum intr-sleep {
                value 0;
            }

            // Stopped
            enum stopped {
                value 1;
            }

            // Uninterruptible sleep
            enum unintr-sleep {
                value 2;
            }

            // Running
            enum running {
                value 3;
            }

            // Dead
            enum dead {
                value 4;
            }

            // Defunct
            enum defunct {
                value 5;
            }
        }
        default "intr-sleep";
    }

    // Process operational state
    typedef proc_OperState {
        type enumeration {

            // Up
            enum up {
                value 0;
            }

            // down
            enum down {
                value 1;
            }
        }
        default "up";
    }

    // Process id
    typedef proc_ProcId {
        type uint32;
    }

    // Process memory units
    typedef proc_ProcMem {
        type uint64;
    }

    // Program counter
    typedef proc_ProgCntr {
        type uint64;
    }

    // Stack
    typedef proc_Stack {
        type uint64;
    }

    // Process start count
    typedef proc_StartCnt {
        type uint32;
    }

    // TTY
    typedef proc_TTY {
        type string;
    }

    typedef qos_Prio {
        type enumeration {

            // Unspecified
            enum unspecified {
                value 0;
            }

            // Level3
            enum level3 {
                value 1;
            }

            // Level2
            enum level2 {
                value 2;
            }

            // Level1
            enum level1 {
                value 3;
            }
            enum policy-plane {
                value 4;
            }
            enum control-plane {
                value 5;
            }
            enum span {
                value 6;
            }
        }
    }

    // User configurable classes
    typedef qos_TenantPrio {
        type enumeration {

            // Unspecified
            enum unspecified {
                value 0;
            }

            // Level3
            enum level3 {
                value 1;
            }

            // Level2
            enum level2 {
                value 2;
            }

            // Level1
            enum level1 {
                value 3;
            }
        }
        default "unspecified";
    }

    // PPF Node id
    typedef qosm_PpfNodeId {
        type uint32;
    }

    // State id
    typedef qosm_StateId {
        type enumeration {

            // Unidentified
            enum unidentified {
                value 0;
            }

            // Unverified
            enum unverified {
                value 1;
            }

            // Verified
            enum verified {
                value 2;
            }

            // Committed
            enum committed {
                value 3;
            }

            // Failed
            enum failed {
                value 4;
            }
        }
        default "unidentified";
    }

    // Bandwidth percentage
    typedef qosp_BwPercent {
        type uint8 {
            range "0..100";
        }
        default "20";
    }

    // Congestion algorithm
    typedef qosp_CongAlgo {
        type enumeration {

            // Weighted random early detection
            enum wred {
                value 0;
            }

            // Tail drop
            enum tail-drop {
                value 1;
            }
        }
        default "tail-drop";
    }

    // Control method
    typedef qosp_CtrlMeth {
        type enumeration {

            // Static
            enum static {
                value 0;
            }

            // Dynamic
            enum dynamic {
                value 1;
            }
        }
        default "dynamic";
    }

    // Dot1p
    // Default Value "8" Removed - out of range 0..7
    typedef qosp_Dot1P {
        type uint8 {
            range "0..7";
        }
    }

    // Dscp code point values
    // Default Value "64" Removed - out of range 0..63
    typedef qosp_Dscp {
        type qosp_DscpCP {
            range "0..63";
        }
    }

    // DSCP
    typedef qosp_DscpCP {
        type uint8 {
            range "0..63";
        }
    }

    // ECN
    typedef qosp_ECN {
        type enumeration {

            // Disabled
            enum disabled {
                value 0;
            }

            // Enabled
            enum enabled {
                value 1;
            }
        }
        default "disabled";
    }

    // MTU
    typedef qosp_MTU {
        type uint16 {
            range "1500..9216";
        }
        default "9216";
    }

    // Min buffers
    typedef qosp_MinBuf {
        type uint8 {
            range "0..3";
        }
        default "0";
    }

    // Operational state of Qos Class
    typedef qosp_OperSt {
        type enumeration {

            // enabled
            enum enabled {
                value 1;
            }

            // disabled
            enum disabled {
                value 2;
            }
        }
        default "disabled";
    }

    // Reasons for rule being disabled.
    typedef qosp_OperStQual {
        type enumeration {

            // Unspecified
            enum unspecified {
                value 0;
            }

            // Hardware Programming Failed
            enum hwprog-fail;

            // Invalid Parameters
            enum Invalid;
        }
        default "unspecified";
    }

    // Queue limit
    typedef qosp_QueueLimit {
        type uint16 {
            range "1500..9216";
        }
        default "1522";
    }

    // Scheduling Algorithm
    typedef qosp_SchedAlgo {
        type enumeration {

            // Weighted round robin
            enum wrr {
                value 0;
            }

            // Strict priority
            enum sp {
                value 1;
            }
        }
        default "wrr";
    }

    typedef reference_URI {
        type string;
    }

    // Enum types
    typedef regress_EnumT {
        type enumeration {

            // val1
            enum val1 {
                value 1;
            }

            // val2
            enum val2 {
                value 2;
            }

            // val3
            enum val3 {
                value 3;
            }
        }
        default "val2";
    }

    typedef reln_ClassId {
        type enumeration {
            enum unspecified {
                value 0;
            }
        }
        default "unspecified";
    }

    typedef reln_Dn {
        type string;
    }

    typedef reln_ResolverType {
        type enumeration {
            enum mo {
                value 1;
            }
            enum service {
                value 2;
            }
            enum local {
                value 3;
            }
        }
        default "mo";
    }

    typedef reln_State {
        type enumeration {
            enum unformed {
                value 0;
            }
            enum formed {
                value 1;
            }
            enum missing-target {
                value 2;
            }
            enum invalid-target {
                value 4;
            }
        }
        default "unformed";
    }

    typedef reln_StateQual {
        type enumeration {
            enum none {
                value 0;
            }
            enum mismatch-target {
                value 1;
            }
            enum default-target {
                value 2;
            }
        }
        default "none";
    }

    typedef reln_TargetType {
        type enumeration {
            enum name {
                value 0;
            }
            enum mo {
                value 1;
            }
            enum all {
                value 2;
            }
        }
        default "mo";
    }

    // Create time stamp type
    typedef rib_CreateTs {
        type uint64;
    }

    // Database type
    typedef rib_DbT {
        type enumeration {

            // Route Database
            enum rt {
                value 1;
            }

            // Nexthop Database
            enum nh {
                value 2;
            }

            // Adjacency Database
            enum adj {
                value 3;
            }
        }
        default "rt";
    }

    // Domain operational state
    typedef rib_DomOperSt {
        type enumeration {

            // Up
            enum up {
                value 1;
            }

            // Down pending
            enum down-pending {
                value 2;
            }

            // Purging
            enum purged {
                value 3;
            }

            // Down
            enum down {
                value 4;
            }

            // Down pending
            enum del-pending {
                value 5;
            }

            // Deleted
            enum deleted {
                value 6;
            }
        }
        default "down";
    }

    // Metric type
    typedef rib_Metric {

        // MAX Converted to int from 0xffff
        type uint16 {
            range "1..65535";
        }
        default "1";
    }

    // Next-hop type
    // Default Value computed from attached
    typedef rib_NhT {

        // bits- Using string
        type string;
        default "attached";
    }

    // Owner type
    typedef rib_OwnerT {
        type string;
    }

    // Preference type
    typedef rib_Pref {

        // MAX Converted to int from 0xffff
        type uint16 {
            range "1..65535";
        }
        default "1";
    }

    // Route type
    typedef rib_RouteT {
        type enumeration {

            // Direct
            enum direct {
                value 1;
            }

            // Static
            enum static {
                value 2;
            }

            // Multicast Static
            enum mcast-static {
                value 3;
            }

            // RIP
            enum rip {
                value 4;
            }

            // ISIS L1
            enum isis-l1 {
                value 5;
            }

            // ISIS L2
            enum isis-l2 {
                value 6;
            }

            // OSPF Intra
            enum ospf-intra {
                value 7;
            }

            // OSPF Inter
            enum ospf-inter {
                value 8;
            }

            // OSPF Type1
            enum ospf-type1 {
                value 9;
            }

            // OSPF Type2
            enum ospf-type2 {
                value 10;
            }

            // OSPF NSSA Type1
            enum ospf-nssa-type1 {
                value 11;
            }

            // OSPF NSSA Type2
            enum ospf-nssa-type2 {
                value 12;
            }

            // OSPFv3 Intra
            enum ospfv3-intra {
                value 13;
            }

            // OSPFv3 Inter
            enum ospfv3-inter {
                value 14;
            }

            // OSPFv3 Type1
            enum ospfv3-type1 {
                value 15;
            }

            // OSPFv3 Type2
            enum ospfv3-type2 {
                value 16;
            }

            // OSPFv3 NSSA Type1
            enum ospfv3-nssa-type1 {
                value 17;
            }

            // OSPFv3 NSSA Type2
            enum ospfv3-nssa-type2 {
                value 18;
            }

            // IBGP
            enum ibgp {
                value 19;
            }

            // EBGP
            enum ebgp {
                value 20;
            }

            // IMBGP
            enum imbgp {
                value 21;
            }

            // EMBGP
            enum embgp {
                value 22;
            }

            // Discard
            enum discard {
                value 23;
            }

            // EIGRP Internal
            enum eigrp-internal {
                value 24;
            }

            // EIGRP External
            enum eigrp-external {
                value 25;
            }
        }
        default "direct";
    }

    // Tag
    typedef rib_Tag {

        // MAX Converted to int from 0xffff
        type uint16 {
            range "0..65535";
        }
        default "0";
    }

    // Preference
    typedef rt_Preference {
        type uint8 {
            range "1..255";
        }
        default "1";
    }

    // Tag
    typedef rt_Tag {

        // MAX Converted to int from 0xffffffff
        type uint32 {
            range "0..4294967295";
        }
        default "0";
    }

    // Autonomous system
    typedef rtcom_AS {

        // MAX Converted to int from 0xffffffff
        type uint32 {
            range "1..4294967295";
        }
    }

    // Community type
    typedef rtcom_ComT {
        type enumeration {

            // Regular community
            enum regular {
                value 1;
            }

            // Extended community
            enum extended {
                value 2;
            }
        }
        default "regular";
    }

    // Mode
    typedef rtcom_Mode {
        type enumeration {

            // Standard
            enum standard {
                value 1;
            }

            // Regular expression
            enum regex {
                value 2;
            }
        }
        default "standard";
    }

    // Route control direction
    typedef rtctrl_RtCtrlDir {
        type enumeration {

            // Incoming
            enum in {
                value 1;
            }

            // Outgoing
            enum out {
                value 2;
            }
        }
        default "in";
    }

    // Route target policy type
    typedef rtctrl_RttPType {
        type enumeration {

            // Import
            enum import {
                value 1;
            }

            // Export
            enum export {
                value 2;
            }
        }
        default "import";
    }

    // ASM Control
    typedef rtdmc_ASMCtrl {

        // bits- Using string
        type string;
    }

    // Adjacency flags
    typedef rtdmc_AdjFlags {

        // bits- Using string
        type string;
    }

    // Adjancency operational state
    typedef rtdmc_AdjOperSt {
        type enumeration {

            // Up
            enum up {
                value 0;
            }

            // Inactive
            enum inactive {
                value 1;
            }
        }
    }

    // Authentication key
    typedef rtdmc_AuthKey {
        type string;
    }

    // Authentication type
    typedef rtdmc_AuthT {
        type enumeration {

            // No authentication
            enum none {
                value 0;
            }

            // MD5 HMAC authentication
            enum ah-md5 {
                value 1;
            }
        }
        default "none";
    }

    typedef rtdmc_AutoEnable {
        type boolean;
        default "true";
    }

    // Auto-RP Control
    typedef rtdmc_AutoRPCtrl {

        // bits- Using string
        type string;
    }

    // Auto-RP Scope
    typedef rtdmc_AutoRPScope {
        type uint16 {
            range "1..255";
        }
        default "32";
    }

    // Bootstrap Router (BSR) Control
    typedef rtdmc_BSRCtrl {

        // bits- Using string
        type string;
    }

    // BSR Hash Mask Len
    typedef rtdmc_BSRHashLen {
        type uint16;
    }

    // Max Rate    TODO: Is there a default?
    typedef rtdmc_BSRInterval {
        type uint16 {
            range "1..65535";
        }
        default "60";
    }

    // BSR Priority
    typedef rtdmc_BSRPrio {
        type uint16 {
            range "1..255";
        }
        default "64";
    }

    // BFD state
    typedef rtdmc_BfdInstSt {
        type enumeration {

            // Enabled
            enum enabled {
                value 1;
            }

            // Disabled
            enum disabled {
                value 2;
            }

            // None
            enum none {
                value 0;
            }
        }
        default "none";
    }

    // BFD state
    typedef rtdmc_BfdOperSt {
        type enumeration {

            // Down
            enum down {
                value 0;
            }

            // Remove Pending
            enum rem-pend {
                value 1;
            }

            // Up
            enum up {
                value 2;
            }
        }
    }

    // BiDir RP Limit
    typedef rtdmc_BidirRPLimit {
        type uint16 {
            range "1..8";
        }
        default "6";
    }

    // Byte Count type
    typedef rtdmc_ByteCntType {

        // MAX Converted to int from 0xffffffff
        type uint32 {
            range "1..4294967295";
        }
    }

    // Counter
    typedef rtdmc_Counter32 {
        type uint32;
    }

    // Designated Forwarder Offer Burst Interval
    typedef rtdmc_DFOBItvl {
        type uint16 {
            range "1..10000";
        }
        default "20";
    }

    // Designated Router Delay    TODO: Not present on N3548 or N9K
    // verify naming based on purpose, range and default
    typedef rtdmc_DRDelay {
        type uint16 {
            range "1..65520";
        }
        default "3";
    }

    // Designated Router Priority
    typedef rtdmc_DRPrio {
        type uint32 {
            range "1..4294967295";
        }
        default "1";
    }

    // Database type
    typedef rtdmc_DbT {
        type enumeration {

            // RP database
            enum rp {
                value 0;
            }

            // Grange database
            enum grange {
                value 1;
            }

            // Route database
            enum route {
                value 2;
            }

            // Dynamic RP Srouce database
            enum dynrpsrc {
                value 3;
            }
        }
    }

    // Domain Control
    typedef rtdmc_DomCtrl {

        // bits- Using string
        type string;
    }

    // PIM Route types
    typedef rtdmc_GRangeFlags {

        // bits- Using string
        type string;
    }

    // Generation Id
    typedef rtdmc_GenId {
        type uint32;
    }

    // Hello Message Interval
    typedef rtdmc_HelloItvl {
        type uint32 {
            range "1..18724286";
        }
        default "30000";
    }

    // Hold Time
    typedef rtdmc_HoldTime {
        type uint16;
    }

    // Interface Ctrl
    typedef rtdmc_IfCtrl {

        // bits- Using string
        type string;
    }

    // Join Prune Inter packet delay    TODO: Get the max delay
    typedef rtdmc_JPDelay {
        type uint32 {
            range "1..1000";
        }
        default "100";
    }

    // Join Prune Interval Used between Peers    TODO: Validate this is correct
    typedef rtdmc_JPItvl {
        type uint16 {
            range "1..65520";
        }
        default "60";
    }

    // Protocol Packet MTU
    typedef rtdmc_Mtu {
        type uint32 {
            range "1500..65536";
        }
        default "1500";
    }

    // Null Register Inter batch delay    TODO: Is there a default?
    typedef rtdmc_NRDelay {
        type uint16 {
            range "1..50000";
        }
    }

    // Number of Routes in a Null Register    TODO: Is there a default?
    typedef rtdmc_NRNumRt {
        type uint16 {
            range "1..32000";
        }
    }

    // route oif list types
    typedef rtdmc_OifFlags {

        // bits- Using string
        type string;
    }

    // Pkt Count type
    typedef rtdmc_PktCntType {

        // MAX Converted to int from 0xffffffff
        type uint32 {
            range "1..4294967295";
        }
    }

    typedef rtdmc_PolicyDirType {
        type enumeration {

            // none
            enum none {
                value 0;
            }

            // in
            enum in {
                value 1;
            }

            // out
            enum out {
                value 2;
            }
        }
        default "none";
    }

    // PIM RP types
    typedef rtdmc_RPSourceType {

        // bits- Using string
        type string;
    }

    // Max Rate    TODO: Is there a default?
    typedef rtdmc_RegRate {
        type uint16 {
            range "0..65535";
        }
        default "0";
    }

    // PIM Route types   PIM Route types
    typedef rtdmc_RouteBits {

        // bits- Using string
        type string;
    }

    // PIM Route types
    typedef rtdmc_RtFlags {

        // bits- Using string
        type string;
    }

    // (S,G) Entry Inactivity Expiry Timer
    typedef rtdmc_SGExpItvl {
        type uint32 {
            range "180..604801";
        }
        default "180";
    }

    // Scope of the community
    typedef rtextcom_Scope {
        type enumeration {

            // Transitive
            enum transitive {
                value 0;
            }

            // Non Transitive
            enum non-transitive {
                value 1;
            }
        }
        default "transitive";
    }

    typedef rtextcom_Type {
        type enumeration {

            // Route target community type
            enum rttarget {
                value 1;
            }

            // Generic extended community type
            enum generic {
                value 2;
            }
        }
        default "generic";
    }

    // Action
    typedef rtflt_Action {
        type enumeration {

            // Deny
            enum deny {
                value 0;
            }

            // Permit
            enum permit {
                value 1;
            }
        }
        default "permit";
    }

    // Order
    typedef rtflt_Order {

        // MAX Converted to int from 0xffffffff
        type uint32 {
            range "0..4294967295";
        }
    }

    // filter option for RibLeak
    typedef rtleak_Always {
        type boolean;
        default "true";
    }

    // Asn number
    typedef rtleak_Asn {
        type string {
        }
        default "none";
    }

    // Controls on what to do when the number of routes cross
    // the maximum prefix limit
    typedef rtleak_Ctrl {
        type enumeration {

            // Unspecified
            enum unspecified {
                value 0;
            }

            // Warning
            enum warning {
                value 1;
            }

            // Withdraw
            enum withdraw {
                value 2;
            }
        }
        default "unspecified";
    }

    // Duration between the retries
    typedef rtleak_Duration {
        type uint16 {
            range "60..600";
        }
        default "300";
    }

    // Routing protocol instance
    typedef rtleak_Inst {
        type string {
            length "1..20";
        }
    }

    // Maximum prefix leaked
    typedef rtleak_MaxPfx {

        // MAX Converted to int from 0xffff
        type uint16 {
            range "1..65535";
        }
    }

    // Source protocol type of the leak policy
    typedef rtleak_Proto {
        type enumeration {

            // Unspecified
            enum unspecified {
                value 0;
            }

            // Static
            enum static {
                value 1;
            }

            // Direct
            enum direct {
                value 2;
            }

            // BGP
            enum bgp {
                value 3;
            }

            // ISIS
            enum isis {
                value 4;
            }

            // OSPF
            enum ospf {
                value 5;
            }

            // OSPFv3
            enum ospfv3 {
                value 6;
            }

            // EIGRP
            enum eigrp {
                value 7;
            }

            // HOST
            enum host {
                value 8;
            }

            // RIP
            enum rip {
                value 9;
            }

            // AMT
            enum amt {
                value 10;
            }

            // LISP
            enum lisp {
                value 11;
            }

            // HMM
            enum hmm {
                value 12;
            }

            // AM
            enum am {
                value 13;
            }
        }
        default "unspecified";
    }

    // Maximum number of retries to retrieve the leaked routes
    typedef rtleak_Retries {
        type uint16 {
            range "1..12";
        }
        default "1";
    }

    // Policy Direction
    typedef rtleak_RtCtrlDir {
        type enumeration {

            // in
            enum in {
                value 0;
            }

            // out
            enum out {
                value 1;
            }
        }
        default "in";
    }

    // Scope of the leak policy
    typedef rtleak_Scope {
        type enumeration {

            // Intra protocol leak
            enum intra {
                value 1;
            }

            // Inter protocol leak
            enum inter {
                value 2;
            }

            // Default route leak
            enum defrt {
                value 3;
            }
        }
        default "intra";
    }

    // Threshold at which warning is issued when number of prefixes
    // crosses the threshold, units in percentage
    typedef rtleak_Thresh {
        type uint8 {
            range "1..100";
        }
        default "75";
    }

    // Action
    typedef rtmap_Action {
        type enumeration {

            // Deny
            enum deny {
                value 0;
            }

            // Permit
            enum permit {
                value 1;
            }
        }
        default "permit";
    }

    // Administrative state
    typedef rtmap_AdminSt {
        type enumeration {

            // Enabled
            enum enabled {
                value 1;
            }

            // Disabled
            enum disabled {
                value 2;
            }
        }
        default "disabled";
    }

    // Community Id
    typedef rtmap_CommunityId {
        type uint8 {
            range "0..255";
        }
    }

    // Community Value
    typedef rtmap_CommunityVal {
        type uint32 {
            range "0..4294967295";
        }
    }

    // Criteria
    typedef rtmap_Criteria {
        type enumeration {

            // Exact
            enum exact {
                value 1;
            }

            // Sub group
            enum sub-group {
                value 2;
            }
        }
        default "sub-group";
    }

    // Dampening Half-life
    // Time in minutes. Once the route has been assigned a penalty,
    // the penalty is decreased by half after half life period
    // Default Value "0" Removed - out of range 1..45
    typedef rtmap_DampHalfLife {
        type uint8 {
            range "1..45";
        }
    }

    // Dampening Max Suppress Time
    // Time in minutes. Maximum time that a route can be suppressed.
    // Default Value "0" Removed - out of range 1..255
    typedef rtmap_DampMaxSuppressTime {
        type uint8 {
            range "1..255";
        }
    }

    // Dampening Reuse Limit
    // Route that is unsuppressed if the penalty for a flapping route
    // decreases enough to fall below this value.
    // Default Value "0" Removed - out of range 1..20000
    typedef rtmap_DampReuse {
        type uint16 {
            range "1..20000";
        }
    }

    // Dampening Suppress Limit
    // Route that is suppressed when its penalty exceeds this limit.
    // Default Value "0" Removed - out of range 1..20000
    typedef rtmap_DampSuppress {
        type uint16 {
            range "1..20000";
        }
    }

    // Duration
    typedef rtmap_Duration {
        type uint8 {
            range "1..255";
        }
    }

    // HalfLife
    typedef rtmap_HalfLife {
        type uint8 {
            range "1..45";
        }
    }

    // Label Index
    typedef rtmap_Index {
        type uint32 {
            range "0..471788";
        }
    }

    // Local preference
    typedef rtmap_LocalPref {
        type uint32;
    }

    // Match type
    typedef rtmap_MatchT {
        type enumeration {

            // Regular community
            enum reg-community {
                value 1;
            }

            // Extended community
            enum ext-community {
                value 2;
            }

            // Route destinations
            enum rt-dst {
                value 3;
            }

            // Route nexthops
            enum rt-nh {
                value 4;
            }

            // Route sources
            enum rt-src {
                value 5;
            }

            // Route type
            enum rt-type {
                value 6;
            }

            // Route tag
            enum rt-tag {
                value 7;
            }

            // Route pervasive
            enum rt-pervasive {
                value 8;
            }

            // AS Path Access List
            enum as-path {
                value 9;
            }

            // V6 Route destinations
            enum rt-dst-v6 {
                value 10;
            }

            // Route ASN
            enum rt-asn {
                value 11;
            }

            // Route IF
            enum rt-if {
                value 12;
            }

            // Route Metric
            enum rt-metric {
                value 13;
            }

            // Source Protocol
            enum src-proto {
                value 14;
            }

            // OSPFArea
            enum rt-ospf {
                value 15;
            }

            // Route nexthops ipv6
            enum rt-nh-v6 {
                value 16;
            }

            // Route route source ipv6
            enum rt-src-v6 {
                value 17;
            }

            // Match IPv4 multicast
            enum rt-ipv4-mcast {
                value 18;
            }

            // Match IPv6 multicast
            enum rt-ipv6-mcast {
                value 19;
            }
        }
        default "reg-community";
    }

    // Metric
    typedef rtmap_Metric {
        type uint32;
    }

    // Metric Delay
    typedef rtmap_MetricD {
        type uint32 {
            range "0..4294967295";
        }
        default "0";
    }

    // Metric Load
    typedef rtmap_MetricL {
        type uint8 {
            range "0..255";
        }
        default "0";
    }

    // Metric MTU
    typedef rtmap_MetricM {
        type uint32 {
            range "0..16777215";
        }
        default "0";
    }

    // Metric Reliability
    typedef rtmap_MetricR {
        type uint8 {
            range "0..255";
        }
        default "0";
    }

    // MetricS
    typedef rtmap_MetricS {
        type string;
    }

    // Metric type
    typedef rtmap_MetricT {
        type enumeration {

            // OSPF type1 metric
            enum type-1 {
                value 1;
            }

            // OSPF type2 metric
            enum type-2 {
                value 2;
            }

            // BGP internal metric
            enum internal {
                value 3;
            }

            // ISIS external metric
            enum external {
                value 4;
            }
        }
        default "type-1";
    }

    // OSPFArea
    typedef rtmap_OSPFArea {
        type uint32 {
            range "0..4294967295";
        }
    }

    // Route-map Continue
    typedef rtmap_Order {
        type uint16 {
            range "0..65535";
        }
    }

    // Origin type
    typedef rtmap_OriginT {
        type enumeration {

            // Remote EGP Origin
            enum egp {
                value 1;
            }

            // Local IGP Origin
            enum igp {
                value 2;
            }

            // Unknown Heritage
            enum incomplete {
                value 3;
            }
        }
        default "egp";
    }

    // Precedence Properties
    typedef rtmap_PrecName {
        type enumeration {

            // Routine
            enum routine {
                value 0;
            }

            // Priority
            enum priority {
                value 1;
            }

            // Immediate
            enum immediate {
                value 2;
            }

            // Flash
            enum flash {
                value 3;
            }

            // Flash-Override
            enum flash-override {
                value 4;
            }

            // Critical
            enum critical {
                value 5;
            }

            // Internet
            enum internet {
                value 6;
            }

            // Network
            enum network {
                value 7;
            }
        }
    }

    // is BGP config
    typedef rtmap_Proto {
        type boolean;
    }

    // Reuse
    typedef rtmap_Reuse {
        type uint16 {
            range "1..20000";
        }
    }

    // Route Distance
    typedef rtmap_RouteDist {
        type uint8 {
            range "0..255";
        }
    }

    // Route Last As
    typedef rtmap_RouteLastAs {
        type uint16 {
            range "1..10";
        }
    }

    // Pervasive route
    typedef rtmap_RoutePervasive {
        type enumeration {

            // Match all non-pervasive routes
            enum non-pervasive {
                value 0;
            }

            // Match all pervasive routes
            enum pervasive {
                value 1;
            }

            // Match all pervasive except external BD routes
            enum pervasive-non-ext-bd {
                value 2;
            }
        }
        default "pervasive-non-ext-bd";
    }

    // Route type
    typedef rtmap_RouteT {
        type enumeration {

            // External
            enum external {
                value 1;
            }

            // Internal
            enum internal {
                value 2;
            }

            // OSPF inter area
            enum ospf-inter-area {
                value 3;
            }

            // OSPF intra area
            enum ospf-intra-area {
                value 4;
            }

            // ISIS level 1
            enum isis-l1 {
                value 5;
            }

            // ISIS level 2
            enum isis-l2 {
                value 6;
            }

            // Local
            enum local {
                value 7;
            }

            // OSPF nssa external
            enum ospf-nssa-external {
                value 8;
            }

            // OSPF type1 external
            enum ospf-type1 {
                value 9;
            }

            // OSPF type2 external
            enum ospf-type2 {
                value 10;
            }
        }
        default "external";
    }

    // Route tag
    typedef rtmap_RouteTag {
        type uint32;
    }

    // Set criteria
    typedef rtmap_SetCriteria {
        type enumeration {

            // No community
            enum none {
                value 1;
            }

            // Append community
            enum append {
                value 2;
            }

            // Replace community
            enum replace {
                value 3;
            }

            // IGP Cost
            enum igp {
                value 4;
            }

            // Pre-bestpath Cost
            enum pre-bestpath {
                value 5;
            }
        }
        default "none";
    }

    // Set type
    typedef rtmap_SetT {
        type enumeration {

            // Regular community
            enum reg-community {
                value 1;
            }

            // Extended generic community
            enum ext-gen-community {
                value 2;
            }

            // Route target community
            enum rtt-community {
                value 3;
            }

            // Route tag
            enum rt-tag {
                value 4;
            }

            // Route weight
            enum rt-weight {
                value 5;
            }

            // Local preference
            enum local-pref {
                value 6;
            }

            // Metric
            enum metric {
                value 7;
            }

            // OSPF NSSA area
            enum ospf-nssa {
                value 8;
            }

            // OSPF fowarding address
            enum ospf-fwd-addr {
                value 9;
            }

            // IP nexthop
            enum ip-nh {
                value 10;
            }

            // Metric Type
            enum metric-type {
                value 11;
            }

            // Route distance
            enum rt-dist {
                value 12;
            }

            // Next Hop Peer Address
            enum nh-pa {
                value 13;
            }

            // Origin
            enum origin {
                value 14;
            }

            // Community List (for deletion)
            enum list-community {
                value 15;
            }

            // Dampening value
            enum dampening {
                value 16;
            }

            // Extcommunity Cost
            enum extcommunity-cost {
                value 17;
            }

            // IP Precedence value
            enum ip-prec {
                value 18;
            }

            // Continue Value
            enum continue {
                value 19;
            }

            // Label Index
            enum rt-index {
                value 20;
            }

            // Extended Community List (for deletion)
            enum list-extcommunity {
                value 21;
            }

            // IPv6 Precedence value
            enum ipv6-prec {
                value 22;
            }

            // Prepend Value
            enum prepend {
                value 23;
            }

            // Prepend Last-as Value
            enum lastas {
                value 24;
            }

            // As-Path tag Value
            enum as-pathtag {
                value 25;
            }
        }
        default "reg-community";
    }

    // Supress
    typedef rtmap_Supress {
        type uint16 {
            range "1..20000";
        }
    }

    // Weight
    typedef rtmap_Weight {
        type uint16;
    }

    // rp-type
    typedef rtmap_rpTypeT {
        type enumeration {

            // unspecified
            enum unspecified {
                value 0;
            }

            // ASM
            enum ASM {
                value 1;
            }

            // Bidir
            enum Bidir {
                value 2;
            }
        }
        default "unspecified";
    }

    // Criteria
    typedef rtpfx_Criteria {
        type enumeration {

            // Exact match
            enum exact {
                value 0;
            }

            // Inexact match
            enum inexact {
                value 1;
            }
        }
        default "exact";
    }

    // Extended chassis state
    typedef satm_ExtChOperSt {
        type enumeration {

            // Unknown
            enum unknown {
                value 0;
            }

            // Initializing
            enum initializing {
                value 1;
            }

            // Discovered
            enum discovered {
                value 2;
            }

            // Connected
            enum connected {
                value 3;
            }

            // Registering
            enum registering {
                value 4;
            }

            // Registered
            enum registered {
                value 5;
            }

            // Ready
            enum ready {
                value 6;
            }

            // Online Sequence
            enum online-seq {
                value 7;
            }

            // Online
            enum online {
                value 8;
            }

            // Offline Request
            enum offline-req {
                value 9;
            }

            // Offline Sequence
            enum offline-seq {
                value 10;
            }

            // Offline
            enum offline {
                value 11;
            }

            // Image Download
            enum img-download {
                value 12;
            }

            // Failed
            enum failed {
                value 13;
            }

            // Removed
            enum removed {
                value 14;
            }

            // Hitless Upgrade Sequence
            enum hl-upg-seq {
                value 15;
            }

            // Check Upgrade Sequence
            enum chk-upg-seq {
                value 16;
            }

            // Ready for Upgrade
            enum upg-start {
                value 17;
            }

            // Hitless Upgrade Idle
            enum hl-upg-idle {
                value 18;
            }

            // Check Insert Sequence
            enum chk-ins-seq {
                value 19;
            }

            // Hitless Upgrade Failed
            enum hl-upg-fail {
                value 20;
            }

            // Active Active Upgrade Ready
            enum aa-upg-rdy {
                value 21;
            }

            // Active Active Upgrade Idle
            enum aa-upg-idle {
                value 22;
            }

            // Active Active Upgrade Done
            enum aa-upg-done {
                value 23;
            }

            // Active Active Upgrade Fail
            enum aa-upg-fail {
                value 24;
            }

            // Active Active Version Mismatch
            enum aa-ver-mismatch {
                value 25;
            }

            // Extended Chassis Type Mismatch
            enum ch-type-mismatch {
                value 26;
            }
        }
        default "unknown";
    }

    // Fabric port FSM status
    typedef satm_FpFsmSt {
        type enumeration {

            // Unknown
            enum unknown {
                value 0;
            }

            // Created
            enum created {
                value 1;
            }

            // Discovered
            enum discovered {
                value 2;
            }

            // Configured
            enum configured {
                value 3;
            }

            // Up
            enum up {
                value 4;
            }

            // Connecting
            enum connecting {
                value 5;
            }

            // Active
            enum active {
                value 6;
            }

            // Incompatible topology
            enum incompatible {
                value 7;
            }

            // Disconnected
            enum disconnected {
                value 8;
            }

            // Identity mismatch
            enum id-mismatch {
                value 9;
            }
        }
        default "unknown";
    }

    // Fabri port flags
    typedef satm_FportFlags {

        // bits- Using string
        type string;
    }

    // Host Port operational status
    typedef satm_HpOperSt {
        type enumeration {

            // Unknown
            enum unknown {
                value 0;
            }

            // Up
            enum up {
                value 1;
            }

            // Down
            enum down {
                value 2;
            }

            // Failed
            enum fail {
                value 3;
            }
        }
        default "unknown";
    }

    // Port operational status
    typedef satm_OperSt {
        type enumeration {

            // Unknown
            enum unknown {
                value 0;
            }

            // Up
            enum up {
                value 1;
            }

            // Down
            enum down {
                value 2;
            }

            // Failed
            enum failed {
                value 3;
            }
        }
        default "unknown";
    }

    typedef satm_SwGen {
        type uint16;
    }

    // Action
    typedef scrtchpd_Action {
        type enumeration {

            // Create
            enum create {
                value 1;
            }

            // Delete
            enum delete {
                value 2;
            }
        }
        default "create";
    }

    // AAA Cache User Timeout
    typedef snmp_AaaUserCacheTimeout {
        type uint32 {
            range "1..86400";
        }
        default "3600";
    }

    // ACL Name
    typedef snmp_AclNameT {
        type string {
        }
    }

    // Authentication key
    typedef snmp_AuthKey {
        type string;
    }

    typedef snmp_AuthPasswd {
        type string {
            length "0..130";
        }
    }

    // Authentication Type
    typedef snmp_AuthType {
        type enumeration {

            // HMAC-MD5-96
            enum hmac-md5-96 {
                value 1;
            }

            // HMAC-SHA1-96
            enum hmac-sha1-96 {
                value 2;
            }
        }
        default "hmac-md5-96";
    }

    // Auth Type
    typedef snmp_AuthTypeT {
        type enumeration {

            // No auth
            enum no {
                value 0;
            }

            // MD5 algorithm
            enum md5 {
                value 1;
            }

            // SHA algorithm
            enum sha {
                value 2;
            }
        }
        default "no";
    }

    typedef snmp_Boolean {
        type enumeration {

            // No
            enum no {
                value 0;
            }

            // Yes
            enum yes {
                value 1;
            }
        }
        default "yes";
    }

    // Type of access to the type of community
    typedef snmp_CommAcessT {
        type enumeration {

            // Read-only Access
            enum ro {
                value 0;
            }

            // Read-Write Access
            enum rw {
                value 1;
            }

            // Unspecified value
            enum unspecified {
                value 2;
            }
        }
        default "unspecified";
    }

    typedef snmp_Contact {
        type string {
            length "0..255";
        }
    }

    // Port Counter Cache Timeout
    // Default Value "0" Removed - out of range 10..3600
    typedef snmp_CounterCacheTimeout {
        type uint16 {
            range "10..3600";
        }
    }

    // RMON EVENT Description
    typedef snmp_DescType {
        type string;
    }

    // Default enabled trap bits
    typedef snmp_EnableTrapBit {
        type uint64;
    }

    typedef snmp_EncryptedAuthArray {
        type mtx_array_uint8;
    }

    typedef snmp_EncryptedPrivArray {
        type mtx_array_uint8;
    }

    // Engine ID
    typedef snmp_EngId {
        type string;
    }

    // Engine ID Length
    typedef snmp_EngIdLen {
        type uint8 {
            range "0..162";
        }
        default "0";
    }

    // Event Number
    // Default Value "0" Removed - out of range 1..65535
    typedef snmp_EventIndx {
        type uint16 {
            range "1..65535";
        }
    }

    // Event Number
    typedef snmp_EventNum {
        type uint16 {
            range "1..65535";
        }
    }

    // RMON Related oper data
    typedef snmp_EventSetBitT {
        type uint32;
    }

    // Group Name to which community belongs
    typedef snmp_GrpNameT {
        type string;
    }

    typedef snmp_Location {
        type string;
    }

    // Logging enable
    typedef snmp_LogEnableType {
        type enumeration {

            // Generate RMON log when the event fires
            enum no {
                value 0;
            }

            // Do not Generate RMON log when the event fires
            enum yes {
                value 1;
            }
        }
        default "no";
    }

    // Notification type
    typedef snmp_NotificationType {
        type enumeration {
            enum traps {
                value 1;
            }
            enum informs {
                value 2;
            }
        }
        default "traps";
    }

    // RMON EVENT OWNER
    typedef snmp_OwnerType {
        type string;
    }

    // SNMP Packet Size
    // Default Value "0" Removed - out of range 484..17382
    typedef snmp_PktSizeT {
        type uint16 {
            range "484..17382";
        }
    }

    // UDP PORT
    typedef snmp_PortIdT {
        type uint32 {
            range "0..65535";
        }
        default "162";
    }

    // Privacy (encryption) key
    typedef snmp_PrivKey {
        type string;
    }

    typedef snmp_PrivPasswd {
        type string {
            length "0..130";
        }
    }

    // Privacy (encryption) Type
    typedef snmp_PrivType {
        type enumeration {

            // None
            enum none {
                value 0;
            }

            // DES
            enum des {
                value 1;
            }

            // AES-128
            enum aes-128 {
                value 2;
            }
        }
        default "none";
    }

    // Priv Type
    typedef snmp_PrivTypeT {
        type enumeration {

            // No auth
            enum no {
                value 0;
            }

            // DES algorithm
            enum des {
                value 1;
            }

            // AES-128 algorithm
            enum aes128 {
                value 2;
            }
        }
        default "no";
    }

    // System Contact
    typedef snmp_SnmpSysContact {
        type string;
    }

    // System Description
    typedef snmp_SnmpSysDescr {
        type string;
    }

    // System Location
    typedef snmp_SnmpSysLoc {
        type string;
    }

    // Snmp trap administrative state
    typedef snmp_SnmpTrapSt {
        type enumeration {

            // Enable
            enum enable {
                value 1;
            }

            // Disable
            enum disable {
                value 2;
            }
        }
        default "disable";
    }

    // Trap Community type
    typedef snmp_TrapCommType {
        type string;
    }

    typedef snmp_TrapConfigErrorType {
        type enumeration {

            // Config Successful
            enum success {
                value 0;
            }

            // Config Failed
            enum failed {
                value 1;
            }
        }
        default "success";
    }

    // SNMP Trap Rate
    typedef snmp_TrapRateT {
        type uint16 {
            range "0..1000";
        }
        default "0";
    }

    // SNMPv3 security level
    typedef snmp_V3SecLvl {
        type enumeration {
            enum unspecified {
                value 0;
            }
            enum noauth {
                value 1;
            }
            enum auth {
                value 2;
            }
            enum priv {
                value 3;
            }
        }
        default "unspecified";
    }

    // SNMP version
    typedef snmp_Version {
        type enumeration {
            enum v1 {
                value 1;
            }
            enum v2c {
                value 2;
            }
            enum v3 {
                value 3;
            }
        }
        default "v1";
    }

    typedef snmp_alarmConfigErrorType {
        type enumeration {

            // Config Successful
            enum success {
                value 0;
            }

            // Config Failed
            enum failed {
                value 1;
            }
        }
        default "success";
    }

    typedef snmp_cfgStatus {
        type enumeration {

            // Config Successful
            enum success {
                value 0;
            }

            // Config Failed
            enum failed {
                value 1;
            }
        }
        default "success";
    }

    // Community name
    typedef snmp_commNameT {
        type string;
    }

    typedef snmp_hostConfigErrorType {
        type enumeration {

            // Config Successful
            enum success {
                value 0;
            }

            // Config Failed
            enum failed {
                value 1;
            }
        }
        default "success";
    }

    // host name
    typedef snmp_hostNameT {
        type string;
    }

    // RMON ALARM Sample interval
    // Default Value "0" Removed - out of range 1..700000
    typedef snmp_smplIntvl {
        type uint32 {
            range "1..700000";
        }
    }

    // Rmon alarm sample type
    typedef snmp_smplType {
        type enumeration {

            // Unspecified
            enum unspecified {
                value 0;
            }

            // Test each sample directly
            enum absolute {
                value 1;
            }

            // Test delta between samples
            enum delta {
                value 2;
            }
        }
        default "unspecified";
    }

    // Type for snmp-server tcp-session auth config
    typedef snmp_tcpSessionAuthT {
        type enumeration {

            // Unspecified
            enum no {
                value 0;
            }

            // tcp-session config
            enum tcpSess {
                value 1;
            }

            // tcp-session auth config
            enum tcpSessAuth {
                value 2;
            }
        }
        default "tcpSessAuth";
    }

    // RMON ALARM Threshold Type
    // Default Value "0" Removed - out of range -2147483648..2147483647
    typedef snmp_thrshld {
        type int32 {
            range "-2147483648..2147483647";
        }
    }

    // Database type
    typedef span_DbT {
        type enumeration {

            // IP endpoint resolution database
            enum ipep-resolve {
                value 1;
            }
        }
        default "ipep-resolve";
    }

    // Destination encapsulation
    typedef span_DestEncapT {
        type enumeration {

            // Gre encapsulated
            enum gre {
                value 1;
            }
        }
        default "gre";
    }

    // Direction, to figure out the direction in which the traffic
    // is monitored on the span source
    typedef span_Direction {
        type enumeration {

            // Incoming
            enum in {
                value 1;
            }

            // Outgoing
            enum out {
                value 2;
            }

            // Both
            enum both {
                value 3;
            }
        }
        default "both";
    }

    // ErSpan Version
    typedef span_ErSpanVer {
        type enumeration {

            // Version 1
            enum ver1 {
                value 1;
            }

            // Version 2
            enum ver2 {
                value 2;
            }
        }
        default "ver2";
    }

    // Flow id
    typedef span_FlowId {
        type uint16 {
            range "1..1023";
        }
        default "1";
    }

    // Mode
    typedef span_Mode {
        type enumeration {

            // Access
            enum access {
                value 1;
            }

            // Fabric
            enum fabric {
                value 2;
            }
        }
        default "access";
    }

    // Mtu
    typedef span_Mtu {
        type uint16 {
            range "64..9216";
        }
        default "1518";
    }

    // Operational state
    typedef span_OperSt {
        type enumeration {

            // Unspecified
            enum unspecified {
                value 0;
            }

            // Up
            enum up {
                value 1;
            }

            // Down
            enum down {
                value 2;
            }

            // Failed
            enum failed {
                value 3;
            }

            // Partial
            enum partial {
                value 4;
            }
        }
        default "down";
    }

    // Operational state qualifier
    typedef span_OperStQual {
        type enumeration {

            // The session is up
            enum active {
                value 1;
            }

            // No hardware resource
            enum no-hw-res {
                value 2;
            }

            // No operational src/dst
            enum no-oper-src-dst {
                value 3;
            }

            // Generic error
            enum error {
                value 4;
            }

            // No sources configured
            enum no-src {
                value 5;
            }

            // No dest configured
            enum no-dst {
                value 6;
            }

            // No src/dst configured
            enum no-src-dst {
                value 7;
            }

            // Session admin shut
            enum shut {
                value 8;
            }

            // Dst in wrong mode
            enum invalid-dst-mode {
                value 9;
            }

            // Src in wrong mode
            enum invalid-src-mode {
                value 10;
            }

            // No valid VRF
            enum invalid-vrf {
                value 11;
            }

            // No valid IP address
            enum invalid-ip {
                value 12;
            }

            // No route to destination IP address
            enum no-route {
                value 13;
            }

            // Egress interface not resolved
            enum no-eg-intf {
                value 14;
            }

            // Hardware error
            enum hw-err {
                value 15;
            }
        }
        default "no-oper-src-dst";
    }

    // Session id
    typedef span_SessionId {
        type uint8 {
            range "1..48";
        }
    }

    // Source id
    typedef span_SrcId {

        // MAX Converted to int from 0xffff
        type uint16 {
            range "1..65535";
        }
    }

    // Source type
    typedef span_SrcT {
        type enumeration {

            // Port
            enum port {
                value 1;
            }

            // Encap
            enum encap {
                value 2;
            }

            // Port and encap
            enum port-encap {
                value 3;
            }
        }
        default "port";
    }

    // Administrative state
    typedef stp_AdminSt {
        type enumeration {

            // Enabled
            enum enabled {
                value 1;
            }

            // Disabled
            enum disabled {
                value 2;
            }
        }
        default "enabled";
    }

    // BPDUGuard
    typedef stp_BPDUGuard {
        type enumeration {

            // Default
            enum default {
                value 0;
            }

            // Enable
            enum enable {
                value 1;
            }

            // Disable
            enum disable {
                value 2;
            }
        }
        default "default";
    }

    // bpdufilter type
    typedef stp_Bpdufilter {
        type enumeration {

            // Default
            enum default {
                value 0;
            }

            // Enable
            enum enable {
                value 1;
            }

            // Disable
            enum disable {
                value 2;
            }
        }
        default "default";
    }

    // bridge priority, incremental of 4096
    typedef stp_BridgePriority {
        type uint16 {
            range "0..61440";
        }
        default "32768";
    }

    // Path Cost    0 means auto
    typedef stp_Cost {
        type uint32 {
            range "0..200000000";
        }
        default "5";
    }

    typedef stp_Diameter {
        type uint8 {
            range "2..7";
        }
        default "2";
    }

    // Forward Delay Time in Second
    typedef stp_FwdTime {
        type uint8 {
            range "4..30";
        }
        default "15";
    }

    // port guard
    typedef stp_Guard {
        type enumeration {

            // Default
            enum default {
                value 0;
            }

            // Root
            enum root {
                value 1;
            }

            // Loop
            enum loop {
                value 2;
            }

            // None
            enum none {
                value 3;
            }
        }
        default "default";
    }

    // Hello Interval in Second
    typedef stp_HelloTime {
        type uint8 {
            range "1..10";
        }
        default "2";
    }

    // Interface controls
    // Default Value computed from unspecified
    typedef stp_IfControl {

        // bits- Using string
        type string;
        default "unspecified";
    }

    // Mode
    typedef stp_IfMode {
        type enumeration {

            // Default
            enum default {
                value 0;
            }

            // Edge (host) port
            enum edge {
                value 1;
            }

            // Network port
            enum network {
                value 2;
            }

            // Normal port
            enum normal {
                value 3;
            }

            // Edge port in trunk mode
            enum trunk {
                value 4;
            }
        }
        default "default";
    }

    // LC Issu Option
    typedef stp_LcIssu {
        type enumeration {

            // Auto
            enum auto {
                value 1;
            }

            // Disruptive
            enum disruptive {
                value 2;
            }

            // Non-disruptive
            enum non-disruptive {
                value 3;
            }
        }
        default "auto";
    }

    // Link Type
    typedef stp_LinkType {
        type enumeration {

            // Auto
            enum auto {
                value 1;
            }

            // point-to-point
            enum p2p {
                value 2;
            }

            // Shared
            enum shared {
                value 3;
            }
        }
        default "auto";
    }

    // Hello Interval in Second
    typedef stp_MaxAge {
        type uint8 {
            range "6..40";
        }
        default "20";
    }

    // Max Hops
    typedef stp_MaxHops {
        type uint8 {
            range "1..255";
        }
        default "20";
    }

    // Default Value computed from pvrst
    typedef stp_Mode {

        // bits- Using string
        type string;
        default "pvrst";
    }

    // Mst Id
    typedef stp_MstId {
        type uint16 {
            range "0..4094";
        }
        default "0";
    }

    // Path cost option
    typedef stp_PathcostOp {
        type enumeration {

            // Auto
            enum auto {
                value 0;
            }

            // Short
            enum short {
                value 1;
            }

            // Long
            enum long {
                value 2;
            }
        }
        default "short";
    }

    // port fast
    typedef stp_PortFast {
        type enumeration {

            // Default
            enum default {
                value 0;
            }

            // Trunk
            enum trunk {
                value 1;
            }

            // Disable
            enum disable {
                value 2;
            }
        }
        default "default";
    }

    // port priority, incremental of 32
    typedef stp_PortPriority {
        type uint8 {
            range "0..224";
        }
        default "128";
    }

    // STP port roles.
    typedef stp_PortRole {
        type enumeration {

            // Unknown role
            enum unknown {
                value 0;
            }

            // Root port
            enum root {
                value 1;
            }

            // Alternate port
            enum alternate {
                value 2;
            }

            // Designated port
            enum designated {
                value 3;
            }

            // Backup port
            enum backup {
                value 4;
            }

            // Master port
            enum master {
                value 5;
            }
        }
    }

    // STP port states.
    typedef stp_PortState {
        type enumeration {

            // Unknown state
            enum unknown {
                value 0;
            }

            // Discarding state
            enum discarding {
                value 1;
            }

            // Learning state
            enum learning {
                value 2;
            }

            // Forwarding state
            enum forwarding {
                value 3;
            }

            // Disabled state
            enum disabled {
                value 4;
            }
        }
    }

    // bridge priority, incremental of 4096
    typedef stp_Priority {
        type enumeration {

            // Priority_0
            enum 0 {
                value 0;
            }

            // Priority_4096
            enum 4096 {
                value 1;
            }

            // Priority_8192
            enum 8192 {
                value 2;
            }

            // Priority_12288
            enum 12288 {
                value 3;
            }

            // Priority_16384
            enum 16384 {
                value 4;
            }

            // Priority_20480
            enum 20480 {
                value 5;
            }

            // Priority_24576
            enum 24576 {
                value 6;
            }

            // Priority_28672
            enum 28672 {
                value 7;
            }

            // Priority_32768
            enum 32768 {
                value 8;
            }

            // Priority_36864
            enum 36864 {
                value 9;
            }

            // Priority_40960
            enum 40960 {
                value 10;
            }

            // Priority_45056
            enum 45056 {
                value 11;
            }

            // Priority_49152
            enum 49152 {
                value 12;
            }

            // Priority_53248
            enum 53248 {
                value 13;
            }

            // Priority_57344
            enum 57344 {
                value 14;
            }

            // Priority_61440
            enum 61440 {
                value 15;
            }
        }
        default "32768";
    }

    // Spanning tree protocols.
    typedef stp_Protocol {
        type enumeration {

            // Unknown protocol
            enum unknown {
                value 0;
            }

            // MSTP
            enum mstp {
                value 1;
            }

            // RSTP
            enum rstp {
                value 2;
            }
        }
    }

    // MST region name
    typedef stp_RegName {
        type string {
            length "0..32";
        }
    }

    // MST region revision number
    typedef stp_RegRev {

        // MAX Converted to int from 0xffff
        type uint16 {
            range "0..65535";
        }
        default "0";
    }

    // Root Options
    typedef stp_Root {
        type enumeration {

            // Primary
            enum primary {
                value 1;
            }

            // Secondary
            enum secondary {
                value 2;
            }
        }
        default "primary";
    }

    // Mst simulate pvst
    typedef stp_Simulate {
        type enumeration {

            // Enabled
            enum enabled {
                value 1;
            }

            // Disabled
            enum disabled {
                value 2;
            }
        }
        default "enabled";
    }

    // vlan id
    typedef stp_VlanId {
        type uint16 {
            range "1..4096";
        }
        default "1";
    }

    // Chain ID
    typedef sts_ChainId {
        type uint32;
    }

    // Node control
    typedef sts_NodeCtrl {

        // bits- Using string
        type string;
    }

    // Node ID
    typedef sts_NodeId {
        type uint32;
    }

    // Network reachability state
    typedef sts_NwReachSt {
        type enumeration {

            // Unreachable
            enum unreachable {
                value 0;
            }

            // Reachable
            enum reachable {
                value 1;
            }
        }
        default "unreachable";
    }

    // Path controls
    typedef sts_PathCtrl {

        // bits- Using string
        type string;
    }

    // Path encap
    typedef sts_PathEncap {
        type string;
    }

    // Path id
    typedef sts_PathId {

        // MAX Converted to int from 0xffffffff
        type uint32 {
            range "1..4294967295";
        }
        default "1";
    }

    // Stage control
    typedef sts_StageCtrl {

        // bits- Using string
        type string;
    }

    // Stage Id
    typedef sts_StageId {

        // MAX Converted to int from 0xffff
        type uint16 {
            range "1..65535";
        }
        default "1";
    }

    // VNode control
    typedef sts_VNodeCtrl {

        // bits- Using string
        type string;
    }

    // VNode Id
    typedef sts_VNodeId {

        // MAX Converted to int from 0xffff
        type uint16 {
            range "1..65535";
        }
        default "1";
    }

    // VNode order
    typedef sts_VNodeOrder {
        type uint16;
    }

    // VNode weight
    typedef sts_VNodeWeight {
        type uint8 {
            range "1..10";
        }
        default "1";
    }

    // Bandwidth metric  of the SVI in kilobits per second.
    typedef svi_Bw {
        type uint32 {
            range "1..400000000";
        }
        default "1000000";
    }

    // Carrier Transition Delay (like L2 interface going down in
    // milliseconds
    typedef svi_CarrDelay {
        type uint32 {
            range "0..60000";
        }
        default "100";
    }

    // Delay metric of the SVI in tens of microseconds
    typedef svi_Delay {
        type uint32 {
            range "1..16777215";
        }
        default "1";
    }

    // Load averaging delay interval 1 in seconds
    typedef svi_LoadIntvl1 {
        type uint32 {
            range "60..600";
        }
        default "60";
    }

    // Load averaging delay interval 2 in seconds
    typedef svi_LoadIntvl2 {
        type uint32 {
            range "60..600";
        }
        default "300";
    }

    // Load averaging delay interval 3 in seconds
    typedef svi_LoadIntvl3 {
        type uint32 {
            range "60..600";
        }
        default "60";
    }

    // Medium mode  of the SVI
    typedef svi_Medium {
        type enumeration {

            // broadcast
            enum bcast {
                value 0;
            }

            // p2p
            enum p2p {
                value 1;
            }
        }
        default "bcast";
    }

    // MTU of the SVI
    typedef svi_Mtu {
        type uint32 {
            range "64..9216";
        }
        default "1500";
    }

    // Line operational state
    typedef svi_OperSt {
        type enumeration {

            // unknown
            enum unknown {
                value 0;
            }

            // up
            enum up {
                value 1;
            }

            // down
            enum down {
                value 2;
            }

            // shutdown
            enum shutdown {
                value 3;
            }

            // out of service
            enum out-of-srvc {
                value 4;
            }
        }
        default "down";
    }

    // Reason for operational state being down
    typedef svi_OperStQual {
        type enumeration {

            // None
            enum unknown {
                value 0;
            }

            // administratively shut down
            enum admin-shut {
                value 1;
            }

            // vlan does not exist.
            enum no-vlan {
                value 2;
            }

            // invalid vlan type
            enum bad-vlan_t {
                value 3;
            }

            // vlan is down
            enum vlan-down {
                value 4;
            }

            // hardware programming failed (l2fm)
            enum hwprog-flfm {
                value 5;
            }

            // hardware programming failed (event Sequence)
            enum hwprog-fles {
                value 6;
            }

            // out of service
            enum oos {
                value 7;
            }

            // service is down or being brought down
            enum reinit {
                value 8;
            }

            // mtu programming failed
            enum mtuprog-fail {
                value 9;
            }

            // VRF not usable
            enum vrf-unusable {
                value 10;
            }

            // underlying l2 interface state us down
            enum l2st-change {
                value 11;
            }

            // Operationally shut down
            enum suspended {
                value 12;
            }

            // mac address allocation failed
            enum macalloc-fail {
                value 13;
            }

            // non-routable VDC mode
            enum nonrouted-vdc {
                value 14;
            }

            // interface vlan-create process failed
            enum int-vlan-create-fail {
                value 15;
            }

            // inbMgmt Config failed
            enum inbMgmt-cfg-fail {
                value 16;
            }
        }
        default "unknown";
    }

    // Default Value "0" Removed - out of range 1..4095
    typedef svi_VlanId {
        type uint16 {
            range "1..4095";
        }
    }

    // Default Value computed from 0
    typedef synthetic_TestBitmask64 {

        // bits- Using string
        type string;
        default "0";
    }

    // Default Value computed from 0
    typedef synthetic_TestBitmask8 {

        // bits- Using string
        type string;
        default "0";
    }

    typedef synthetic_TestEnum16 {
        type enumeration {
            enum generic {
                value 0;
            }
            enum first {
                value 1;
            }
            enum second {
                value 2;
            }
            enum third {
                value 3;
            }
            enum last {
                value 65535;
            }
        }
        default "generic";
    }

    // Core File admin state values are enumerated here.
    typedef sysdebug_CoreFileAdminState {
        type enumeration {
            enum init {
                value 0;
            }
            enum prepare-download {
                value 1;
            }
            enum downloaded {
                value 2;
            }
        }
        default "init";
    }

    // Core File oper state values are enumerated here.
    typedef sysdebug_CoreFileOperState {
        type enumeration {
            enum unavailable {
                value 0;
            }
            enum available {
                value 1;
            }
            enum available-on-subordinate {
                value 2;
            }
            enum in-progress {
                value 3;
            }
            enum failed {
                value 4;
            }
        }
        default "unavailable";
    }

    typedef sysdebug_LogControlDestinationFileBackupCount {
        type uint16 {
            range "1..9";
        }
        default "2";
    }

    // type name="EpLogClearAction"
    // base="scalar:Bitmask32"
    // >
    // <const name="none" value="0"/>
    // <const name="log-full" label="Log Full" value="1"/>
    // <const name="on-backup" label="On Clear" value="2"/>
    // <const name="timer" label="Timer" value="4"/>
    // <const name="on-assoc-change" label="On Change of Association" value="8"/>
    // <default value="none"/>
    // </type
    // Log Control destination file size
    // and back-up count.
    typedef sysdebug_LogControlDestinationFileSize {
        type uint32 {
            range "1000000..20000000";
        }
        default "5242880";
    }

    // Log Control is divided into domains.
    // Currently the system management domain
    // is identified.
    typedef sysdebug_LogControlDomainEnum {
        type enumeration {

            // sysmgmt
            enum sysmgmt {
                value 0;
            }
        }
        default "sysmgmt";
    }

    // Log Control severity levels
    // are enumerated here.
    typedef sysdebug_LogControlLevel {
        type enumeration {
            enum debug0 {
                value 0;
            }
            enum debug1 {
                value 1;
            }
            enum debug2 {
                value 2;
            }
            enum debug3 {
                value 3;
            }
            enum debug4 {
                value 4;
            }
            enum info {
                value 5;
            }
            enum warn {
                value 6;
            }
            enum minor {
                value 7;
            }
            enum major {
                value 8;
            }
            enum crit {
                value 9;
            }
        }
        default "info";
    }

    // Type to hold CIMC adapter ID
    typedef sysdebug_TSCmdOptChassisCIMCAdapterId {
        type uint16 {
            range "0..8";
        }
        default "0";
    }

    // Type to hold CIMC ID
    typedef sysdebug_TSCmdOptChassisCIMCId {
        type uint16 {
            range "0..8";
        }
        default "0";
    }

    // Type to hold IOM ID
    typedef sysdebug_TSCmdOptChassisIOMId {
        type uint16 {
            range "0..2";
        }
        default "0";
    }

    // Type to hold Chassis-ID
    typedef sysdebug_TSCmdOptChassisId {
        type uint16 {
            range "1..255";
        }
        default "1";
    }

    // Type to hold Fex-ID
    typedef sysdebug_TSCmdOptFexId {
        type uint16 {
            range "1..255";
        }
        default "1";
    }

    // Type to represent the first level option in tech-support command
    typedef sysdebug_TSCmdOptMajorType {
        type enumeration {
            enum chassis {
                value 0;
            }
            enum fex {
                value 1;
            }
            enum server {
                value 2;
            }
            enum ucsm {
                value 3;
            }
            enum ucsm-mgmt {
                value 4;
            }
        }
        default "ucsm";
    }

    // Type to hold adapter-ID
    typedef sysdebug_TSCmdOptServerAdapterId {
        type uint16 {
            range "0..8";
        }
        default "0";
    }

    // Type to hold Server-ID
    typedef sysdebug_TSCmdOptServerId {
        type uint16 {
            range "1..255";
        }
        default "1";
    }

    // TechSupport File admin state values are enumerated here.
    typedef sysdebug_TechSupportAdminState {
        type enumeration {
            enum init {
                value 0;
            }
            enum start {
                value 1;
            }
            enum created {
                value 2;
            }
            enum prepare-download {
                value 3;
            }
            enum delete {
                value 4;
            }
        }
        default "init";
    }

    // TechSupport File oper state values are enumerated here.
    typedef sysdebug_TechSupportOperState {
        type enumeration {
            enum unavailable {
                value 0;
            }
            enum available {
                value 1;
            }
            enum available-on-subordinate {
                value 2;
            }
            enum in-progress {
                value 3;
            }
            enum failed {
                value 4;
            }
        }
        default "unavailable";
    }

    // Reset reason
    typedef syshist_RstRsn {
        type enumeration {

            // Unknown
            enum unknown {
                value 0;
            }

            // Kernel Reboot
            enum reboot {
                value 1;
            }

            // Watchdog Timeout
            enum watchdog {
                value 2;
            }

            // Reset Requested due to Fatal System Error
            enum sysmgr {
                value 3;
            }

            // Reset Requested due to Fatal Module Error
            enum mod-err {
                value 4;
            }

            // Configured Power down
            enum pwr-cfg {
                value 5;
            }

            // Power down due to temperature sensor policy trigger
            enum temp-alaram {
                value 6;
            }

            // Reset triggered due to Switchover Request by User
            enum user-switchover {
                value 7;
            }

            // Reset Requested due to Fatal Upgrade Error
            enum upg-err {
                value 8;
            }

            // Reset Requested by CLI command reload
            enum reload {
                value 9;
            }

            // Reset Requested due to SPROM update
            enum sprom-upd {
                value 10;
            }

            // System Reset due to Element Manager
            enum sys-cfg-dwn {
                value 11;
            }

            // System Reset due to Clock failure
            enum clock {
                value 12;
            }

            // Kernel Halt
            enum halt {
                value 13;
            }

            // Reset Requested by Redundancy
            enum redundancy {
                value 14;
            }

            // Reset triggered due to HA policy of Switchover
            enum ha-switchover {
                value 15;
            }

            // Reset triggered due to HA policy of Reset
            enum ha-reset {
                value 16;
            }

            // Power down triggered due to Platform manager runtime error
            enum pfm-rtime {
                value 17;
            }

            // Power down triggered due to Platform manager event
            enum pfm-power-dwn {
                value 18;
            }

            // Kernel Panic
            enum panic {
                value 19;
            }

            // Reset Requested by management application
            enum mgmt-app {
                value 20;
            }

            // Reset triggered due to Hardware Error
            enum hw {
                value 21;
            }

            // Reset performed due to component Error
            enum asic {
                value 22;
            }

            // Reset triggered due to bad redundancy channel
            enum redun-channel {
                value 23;
            }

            // Reset due to bad HW detected by System Health
            enum sys-health {
                value 24;
            }

            // Reset triggered due to bad backplane communication channel
            enum eobc {
                value 25;
            }

            // Reset (powered-down) because module does not boot
            enum boot-err {
                value 27;
            }

            // Reset (powered-down) because there is no bootflash
            enum no-bootflash {
                value 28;
            }

            // Reset (powered-down) because netboot failed
            enum netboot-err {
                value 29;
            }

            // Reset (powered-down) because bootflash access failed
            enum bootflash-corrupt {
                value 30;
            }

            // Reset by installer
            enum installer {
                value 31;
            }

            // Power Down/UP epld upgrade process
            enum epld {
                value 33;
            }

            // Reset triggered due to failure to respond to SIGKILL
            enum sigkill-fail {
                value 34;
            }

            // Reset triggered by System Manager for generic failure
            enum sys-gen-fail {
                value 35;
            }

            // VegasLC Reset due to Clock SwitchOver
            enum clock-switchover {
                value 37;
            }

            // Reset (powered-down) because of insufficient resources (DI)
            enum insufficient-resource {
                value 38;
            }

            // Reset (powered-down) because of incompatible configuration
            enum incompat-config {
                value 43;
            }

            // Unknown reason
            enum lcm-unknown {
                value 44;
            }

            // HA System restart
            enum lcm-ha-restart {
                value 45;
            }

            // HA-Switchover done
            enum lcm-haswitchover-done {
                value 46;
            }

            // SRG info response timeout
            enum lcm-boot-srg-timeout {
                value 47;
            }

            // Core dump initiation
            enum lcm-coredump {
                value 48;
            }

            // Disruptive upgrade
            enum lcm-disruptive-upg {
                value 49;
            }

            // Line card failure
            enum lcm-lc-fail {
                value 50;
            }

            // Hitless module removal
            enum lcm-hitless-mod-rem {
                value 51;
            }

            // Hitless power down
            enum lcm-hitless-pwr-dwn {
                value 52;
            }

            // Catastrophic error from LC
            enum lcm-hitless-proc-notice {
                value 53;
            }

            // Hitless registration failed
            enum lcm-hitless-reg-fail {
                value 54;
            }

            // Hitless upgrade timeout
            enum lcm-hitless-timeout {
                value 55;
            }

            // Line card image upgrade (failure)
            enum lcm-img-upg-timeout {
                value 56;
            }

            // Line card image upgrade (success)
            enum lcm-img-upgsuccess {
                value 57;
            }

            // LC insertion sequence failure
            enum lcm-lc-ins-seq-fail {
                value 58;
            }

            // Hitless upgrade failed
            enum lcm-hitless-upg-fail {
                value 59;
            }

            // Line card not responding
            enum lcm-lc-no-resp {
                value 60;
            }

            // Line card 3+ registration
            enum lcm-lc-reg-more3 {
                value 61;
            }

            // Line card registration timeout
            enum lcm-lc-reg-timeout {
                value 62;
            }

            // Runtime diagnostic failure
            enum lcm-runtime-diag-fail {
                value 63;
            }

            // Runtime diagnostic timeout
            enum lcm-runtime-diag-timeout {
                value 64;
            }

            // Line card SEEPROM contents response timeout
            enum lcm-seeprom-timeout {
                value 65;
            }

            // Line card catastrophic error
            enum lcm-proc-notice {
                value 66;
            }

            // Save state response (failure)
            enum lcm-save-state-fail {
                value 67;
            }

            // Hitful image compatibility check
            enum lcm-hitfull-img-check {
                value 68;
            }

            // Image compatibility check (action:powercycle)
            enum lcm-img-check-pwr-cycle {
                value 69;
            }

            // Image compatibility check (action:powerdown)
            enum lcm-img-check-pwr-dwn {
                value 70;
            }

            // Switchover : Image compatibility check
            enum lcm-img-check-switch-over {
                value 71;
            }

            // Module is powered down or power cycled
            enum lcm-power-down {
                value 72;
            }

            // Supervisor card is removed or power cycled
            enum lcm-sup-rem {
                value 73;
            }

            // Module is removed
            enum lcm-lc-rem {
                value 74;
            }

            // Unknown line card insertion
            enum lcm-unknown-mod {
                value 75;
            }

            // SRG infor response timeout
            enum lcm-srg-timeout {
                value 76;
            }

            // Stop async notice failed
            enum lcm-async-notice-fail {
                value 77;
            }

            // Switchover failed
            enum lcm-switchover-fail {
                value 78;
            }

            // Addon image response timeout
            enum lcm-timeout {
                value 79;
            }

            // Upgraded SRG incompatible
            enum lcm-srg-incompat {
                value 80;
            }

            // Out of service
            enum outofservice {
                value 86;
            }

            // Supervisor Device Error
            enum sup-dev-err {
                value 87;
            }

            // Reset due to upgrade
            enum issu-restart {
                value 88;
            }

            // Reset (powered-down) due to insertion sequence failed
            enum ins-seq-fail-pwr-dwn {
                value 89;
            }

            // Reset due to no sup
            enum no-sup {
                value 92;
            }

            // Reset due to Bad Voltage
            enum bad-volt {
                value 93;
            }

            // Reset due to bad system bus voltage
            enum bad-bus-volt {
                value 94;
            }

            // Reset due to bad intermediate bus voltage
            enum bad-intermediate-bus-volt {
                value 95;
            }

            // Reset due to CMP
            enum psp {
                value 96;
            }

            // Powered-down due to EEM event policy trigger
            enum eem-pwr-dwn {
                value 97;
            }

            // Reset due to USD Failure
            enum usd-fail {
                value 98;
            }

            // All the ejectors are OPEN
            enum ejector {
                value 99;
            }

            // System reset by active sup (by writing to PMFPGA regs)
            enum sys-rst {
                value 100;
            }

            // linecard reset by push button
            enum push-button {
                value 101;
            }

            // Policy trigger initiated reset:
            enum policy-reset {
                value 103;
            }

            // Powered-down due to fan policy trigger
            enum policy-fan {
                value 104;
            }

            // Chassis reset by Sup
            enum chassis-rst {
                value 105;
            }

            // Reset (powered-down) since maximum number of swovers were exceeded
            enum max-switchover {
                value 107;
            }

            // Reset since switchover timeout
            enum switchover-timeout {
                value 108;
            }

            // Reset of standby by active sup due to sysmgr timeout
            enum sysmgr-timeout {
                value 109;
            }

            // Unsupported/Unknown Module
            enum unknown-mod {
                value 110;
            }

            // Module Failed
            enum mod-fail {
                value 111;
            }

            // Module PowerCycled
            enum mod-pwr-cycle {
                value 112;
            }

            // Module not supported in this chassis
            enum card-incompat {
                value 113;
            }

            // Bootup error accessing module IDPROM
            enum idprom-err {
                value 114;
            }

            // Non-specific deadend error, check platform int error
            enum unspecified {
                value 115;
            }

            // plugin absent/ not loaded
            enum no-plugin {
                value 117;
            }

            // Unknown card (Could not get software-card-id)
            enum sw-card-id-unknown {
                value 118;
            }

            // Unable to power up card (Power-OK not set)
            enum mod-fail-pwr-up {
                value 119;
            }

            // failure(powered-down) since maximum number of bringups were exceeded
            enum max-bring-up-exceed {
                value 120;
            }

            // Power Down/UP epld upgrade process
            enum epld-upg-nw-crd-mode {
                value 125;
            }

            // Preparing to enter deep sleep mode
            enum deep-sleep {
                value 126;
            }

            // EPC failure
            enum epc-fail {
                value 130;
            }

            // KLM load failure
            enum klm-fail {
                value 131;
            }

            // Dme clean config reset
            enum dme-clean-config-reset {
                value 132;
            }

            // Reloading linecard on removal of last fabric card
            enum last-fc-down {
                value 133;
            }

            // Decommissioned
            enum decommissioned {
                value 134;
            }
        }
    }

    // Reset reason qualifier
    typedef syshist_RstRsnQual {
        type string;
    }

    typedef syslog_Facility {
        type enumeration {
            enum kern {
                value 0;
            }
            enum user {
                value 1;
            }
            enum mail {
                value 2;
            }
            enum daemon {
                value 3;
            }
            enum auth {
                value 4;
            }
            enum syslog {
                value 5;
            }
            enum lpr {
                value 6;
            }
            enum news {
                value 7;
            }
            enum uucp {
                value 8;
            }
            enum cron {
                value 9;
            }
            enum authpriv {
                value 10;
            }
            enum ftp {
                value 11;
            }
            enum local0 {
                value 16;
            }
            enum local1 {
                value 17;
            }
            enum local2 {
                value 18;
            }
            enum local3 {
                value 19;
            }
            enum local4 {
                value 20;
            }
            enum local5 {
                value 21;
            }
            enum local6 {
                value 22;
            }
            enum local7 {
                value 23;
            }
        }
        default "local7";
    }

    typedef syslog_FileSize {
        type uint32 {
            range "4096..4194304";
        }
        default "4194304";
    }

    // Syslog level
    typedef syslog_Level {
        type enumeration {

            // Emergency
            enum emerg {
                value 0;
            }

            // Alert
            enum alert {
                value 1;
            }

            // Critical
            enum crit {
                value 2;
            }

            // Error
            enum err {
                value 3;
            }

            // Warning
            enum warn {
                value 4;
            }

            // Notification
            enum notif {
                value 5;
            }

            // Informational
            enum inform {
                value 6;
            }

            // Debug
            enum debug {
                value 7;
            }
        }
        default "err";
    }

    typedef syslog_OperState {
        type enumeration {
            enum unknown {
                value 0;
            }
            enum available {
                value 1;
            }
            enum errored {
                value 2;
            }
        }
        default "unknown";
    }

    typedef syslog_Severity {
        type enumeration {

            // emergencies
            enum emergencies {
                value 0;
            }

            // alerts
            enum alerts {
                value 1;
            }

            // critical
            enum critical {
                value 2;
            }

            // errors
            enum errors {
                value 3;
            }

            // warnings
            enum warnings {
                value 4;
            }

            // notifications
            enum notifications {
                value 5;
            }

            // information
            enum information {
                value 6;
            }

            // debugging
            enum debugging {
                value 7;
            }
        }
        default "notifications";
    }

    // SyslogPort
    typedef syslog_SyslogPort {
        type uint32 {
            range "1..65535";
        }
        default "514";
    }

    typedef syslog_TimeStampFormat {
        type enumeration {
            enum microseconds {
                value 0;
            }
            enum milliseconds {
                value 1;
            }
            enum seconds {
                value 2;
            }
        }
        default "seconds";
    }

    // Config mode
    typedef sysmgr_CfgMode {
        type enumeration {

            // Init
            enum init {
                value 1;
            }

            // Replay
            enum replay {
                value 2;
            }

            // Done
            enum done {
                value 4;
            }
        }
        default "init";
    }

    // Firmware mode
    typedef sysmgr_FwMode {
        type enumeration {

            // Recovery mode
            enum recovery {
                value 1;
            }

            // Regular
            enum regular {
                value 2;
            }
        }
        default "regular";
    }

    // Firmware type
    typedef sysmgr_FwT {
        type enumeration {

            // BIOS
            enum bios {
                value 1;
            }

            // Kickstart
            enum kickstart {
                value 2;
            }

            // System
            enum system {
                value 3;
            }
        }
        default "system";
    }

    // Firmware version
    typedef sysmgr_FwVer {
        type string;
    }

    // Operational data publish mode
    typedef sysmgr_OperDataMode {
        type enumeration {

            // Init
            enum init {
                value 1;
            }

            // Publish
            enum publish {
                value 2;
            }

            // Done
            enum done {
                value 4;
            }
        }
        default "init";
    }

    // Redundancy mode
    typedef sysmgr_RdMode {
        type enumeration {

            // Hot standby
            enum hot {
                value 0;
            }

            // Warm standby
            enum warm {
                value 1;
            }

            // No HA
            enum none {
                value 2;
            }
        }
        default "none";
    }

    // Redundancy state
    typedef sysmgr_RdSt {
        type enumeration {

            // Unknown
            enum unknown {
                value 0;
            }

            // Absent
            enum absent {
                value 1;
            }

            // Initializing
            enum init {
                value 2;
            }

            // Active
            enum active {
                value 3;
            }

            // Standby
            enum stdby {
                value 4;
            }

            // In BIOS
            enum bios {
                value 5;
            }

            // Offline
            enum offline {
                value 6;
            }

            // Failed
            enum fail {
                value 7;
            }
        }
        default "absent";
    }

    // Supervisor state
    typedef sysmgr_SupSt {
        type enumeration {

            // Unknown
            enum unknown {
                value 0;
            }

            // Local
            enum active {
                value 1;
            }

            // Hot standby
            enum hot-stdby {
                value 2;
            }

            // Cold standby
            enum cold-stdby {
                value 3;
            }

            // Offline
            enum offline {
                value 4;
            }

            // Normal
            enum normal {
                value 5;
            }

            // Non disruptive upgrade
            enum non-dis-upg {
                value 6;
            }
        }
        default "unknown";
    }

    // Supervisor type
    typedef sysmgr_SupT {
        type enumeration {

            // Local
            enum local {
                value 0;
            }

            // Remote
            enum remote {
                value 1;
            }
        }
        default "local";
    }

    // TCPUDP Synwait Time
    typedef tcpudp_SynwaitTime {
        type uint16 {
            range "5..300";
        }
        default "30";
    }

    // Admin State
    typedef telemetry_AdminState {
        type enumeration {

            // enabled
            enum enabled {
                value 1;
            }
        }
        default "enabled";
    }

    // Data Source Type
    typedef telemetry_DataSource {
        type enumeration {

            // DME
            enum DME {
                value 1;
            }

            // NX-API
            enum NX-API {
                value 3;
            }

            // DEFAULT
            enum DEFAULT {
                value 16;
            }
        }
        default "DEFAULT";
    }

    // No equivalent type in YANG
    typedef telemetry_Encoding {
        type enumeration {

            // GPB
            enum GPB {
                value 1;
            }

            // JSON
            enum JSON {
                value 2;
            }

            // XML
            enum XML {
                value 3;
            }
        }
        default "GPB";
    }

    // telemetry-stream-protocol
    typedef telemetry_Protocol {
        type enumeration {

            // UDP
            enum UDP {
                value 1;
            }

            // TCP
            enum TCP {
                value 2;
            }

            // gRPC
            enum gRPC {
                value 3;
            }

            // HTTP
            enum HTTP {
                value 4;
            }
        }
        default "gRPC";
    }

    // Retrieve Depth
    typedef telemetry_RetrieveDepth {

        // MAX Converted to int from 0xffffffff
        type uint32 {
            range "0..4294967295";
        }
        default "0";
    }

    typedef terminal_Limit {
        type uint32;
    }

    typedef terminal_TermSize {
        type uint32;
    }

    typedef terminal_TimeoutT {
        type uint32 {
            range "0..525600";
        }
        default "30";
    }

    // Frequency of the test in milliseconds
    typedef test_Freq {
        type uint64;
        default "0";
    }

    // Status of the test
    typedef test_OperSt {
        type enumeration {

            // Fail
            enum fail {
                value 0;
            }

            // Indeterminate
            enum indeterminate {
                value 1;
            }

            // Interrupted
            enum interrupted {
                value 2;
            }

            // Pending
            enum pending {
                value 3;
            }

            // Not supported
            enum not-supp {
                value 4;
            }

            // Not accessible
            enum not-acc {
                value 5;
            }

            // Pass
            enum pass {
                value 6;
            }

            // Not tested
            enum not-tested {
                value 7;
            }
        }
        default "pending";
    }

    // Qualifier
    typedef test_OperStQual {
        type string;
    }

    // IFC team needs to provide generic instance id type
    typedef test_PInstId {
        type naming_PrimKey;
    }

    // Test trigger
    typedef test_Trig {
        type enumeration {

            // Unspecified
            enum unspecified {
                value 0;
            }

            // On demand
            enum on-demand {
                value 1;
            }

            // Bootup
            enum boot {
                value 2;
            }

            // Ongoing
            enum forever {
                value 4;
            }
        }
        default "unspecified";
    }

    // Represents a TLV Code
    // The code comes from the application & hence no validation is performed on it
    typedef tlv_Code {
        type uint16;
    }

    // Configuartion Issues
    // Default Value computed from none
    typedef top_ConfigIssues {

        // bits- Using string
        type string;
        default "none";
    }

    // Fabric Identifier
    typedef top_FabricId {
        type uint8;
        default "1";
    }

    // Specifies the HA mode in which this system is configured
    typedef top_Mode {
        type enumeration {
            enum unspecified {
                value 0;
            }
            enum stand-alone {
                value 1;
            }
            enum cluster {
                value 2;
            }
        }
        default "unspecified";
    }

    // Specifies the Role of this system
    typedef top_NodeRole {
        type enumeration {
            enum unsupported {
                value 0;
            }
            enum controller {
                value 1;
            }
            enum leaf {
                value 2;
            }
            enum spine {
                value 3;
            }
            enum vleaf {
                value 4;
            }
            enum vip {
                value 5;
            }
            enum protection-chain {
                value 6;
            }
        }
        default "unsupported";
    }

    // POD Identifier
    typedef top_PodId {
        type uint8;
        default "1";
    }

    // Remote Network Identifier
    typedef top_RemoteNetworkId {
        type uint32;
        default "0";
    }

    // System State
    typedef top_SystemSt {
        type enumeration {
            enum out-of-service {
                value 0;
            }
            enum invalid-ver {
                value 1;
            }
            enum in-service {
                value 2;
            }
        }
        default "out-of-service";
    }

    // Represents the Fabric MAC address "00:22:BD:F8:19:FF"
    // reserved for SUP Tx packets across the Fabric.
    typedef top_fabricMacAddr {
        type address_Mac;
        default "280487012409856";
    }

    // Dynamic Load balancer mode
    typedef topoctrl_DLbMode {
        type enumeration {

            // Off
            enum off {
                value 0;
            }

            // Conservative
            enum conservative {
                value 1;
            }

            // Aggressive
            enum aggressive {
                value 2;
            }
        }
        default "off";
    }

    // Load balancer mode
    typedef topoctrl_LbMode {
        type enumeration {

            // Traditional
            enum traditional {
                value 1;
            }

            // Link Failure Resiliency
            enum lfr {
                value 2;
            }
        }
        default "traditional";
    }

    // Prioritization
    typedef topoctrl_Prioritization {
        type enumeration {

            // Off
            enum off {
                value 0;
            }

            // On
            enum on {
                value 1;
            }
        }
        default "off";
    }

    // Shard redudancy node
    typedef topoctrl_ShardChNode {
        type address_Ip;
    }

    // Shard redundancy factor
    typedef topoctrl_ShardRdnFac {
        type uint8 {
            range "1..32";
        }
        default "2";
    }

    // Hop count
    typedef traceroute_Hops {
        type uint8 {
            range "1..255";
        }
        default "32";
    }

    // Order
    typedef traceroute_Order {
        type uint8;
    }

    // Path flags
    typedef traceroute_PathFlags {

        // bits- Using string
        type string;
    }

    // Path Group id
    typedef traceroute_PathGrpId {
        type uint8;
    }

    // Path id
    typedef traceroute_PathId {
        type uint8;
    }

    // Type of the path
    typedef traceroute_PathT {
        type enumeration {

            // External
            enum external {
                value 1;
            }

            // Internal
            enum internal {
                value 2;
            }
        }
        default "internal";
    }

    // Path count
    typedef traceroute_Paths {
        type uint16 {
            range "1..512";
        }
        default "50";
    }

    // Address family type
    typedef track_Af {
        type enumeration {
            enum none {
                value 0;
            }

            // IPv4 address family
            enum ipv4 {
                value 1;
            }

            // IPv6 address family
            enum ipv6 {
                value 2;
            }
        }
        default "none";
    }

    // Interface object protocol state
    typedef track_IntfProtocolType {
        type enumeration {
            enum none {
                value 0;
            }
            enum ipv4-routing {
                value 1;
            }
            enum ipv6-routing {
                value 2;
            }
            enum line-protocol {
                value 3;
            }
        }
        default "none";
    }

    // Type of List objects threshold/boolean
    typedef track_ListObj {
        type enumeration {
            enum none {
                value 0;
            }

            // Boolean 'and' function
            enum and {
                value 1;
            }

            // Boolean 'or' function
            enum or {
                value 2;
            }

            // Threshold percentage
            enum percentage {
                value 3;
            }

            // Threshold weight
            enum weight {
                value 4;
            }
        }
        default "none";
    }

    // Probe type for Sla
    typedef track_ProbeState {
        type enumeration {

            // probe state is reachable or over threshold
            enum reachability {
                value 0;
            }

            // probe state is reachable and within threshold
            enum state {
                value 1;
            }
        }
        default "state";
    }

    // Route Owner type
    // Process owning the route
    typedef track_RouteOwner {
        type enumeration {
            enum none {
                value 0;
            }

            // Host Mobility Manager
            enum hmm {
                value 1;
            }
        }
        default "none";
    }

    typedef track_RouteState {
        type enumeration {
            enum reachability {
                value 0;
            }
        }
        default "reachability";
    }

    // This type represents track Object ID.
    typedef track_TrackId {
        type uint16 {
            range "1..512";
        }
    }

    // Administrative state of tunnel
    typedef tunnel_AdminSt {
        type enumeration {

            // up
            enum up {
                value 1;
            }

            // down
            enum down {
                value 2;
            }
        }
        default "up";
    }

    // Configured MTU
    typedef tunnel_ConfMtu {
        type uint32 {
            range "1..9000";
        }
        default "9000";
    }

    // Tunnel encapsulation type
    typedef tunnel_EncapT {
        type enumeration {

            // unknown
            enum unknown {
                value 0;
            }

            // VXLAN encap
            enum vxlan {
                value 1;
            }

            // iVXLAN encap
            enum ivxlan {
                value 2;
            }

            // NV-GRE encap
            enum nvgre {
                value 3;
            }
        }
        default "ivxlan";
    }

    // Tunnel endpoint identifier
    typedef tunnel_EpId {
        type address_Ip;
    }

    // Tunnel endpoint type
    // Default Value computed from physical
    typedef tunnel_EpT {

        // bits- Using string
        type string;
        default "physical";
    }

    // Keep alive period
    typedef tunnel_KeepAlvIntvl {
        type uint32 {
            range "0..32767";
        }
        default "10";
    }

    // Keep alive retry count
    typedef tunnel_KeepAlvRetries {
        type uint32 {
            range "1..255";
        }
        default "3";
    }

    // Tunnel layer type (L2 or L3)
    typedef tunnel_LayerT {
        type enumeration {

            // l2 tunnel
            enum l2 {
                value 1;
            }

            // l3 tunnel
            enum l3 {
                value 2;
            }
        }
        default "l2";
    }

    // Operational state of tunnel
    typedef tunnel_OperSt {
        type enumeration {

            // up
            enum up {
                value 1;
            }

            // down
            enum down {
                value 2;
            }
        }
        default "down";
    }

    // Reasons for line protcol state being down.
    typedef tunnel_OperStQual {
        type enumeration {

            // unknown
            enum unknown {
                value 0;
            }

            // No reason
            enum none {
                value 1;
            }

            // Initializing hardware
            enum initing {
                value 2;
            }

            // Tunnel configuration is incomplete
            enum incomp-conf {
                value 3;
            }

            // Duplicate tunnel config
            enum dup-conf {
                value 4;
            }

            // Encap type is not configured
            enum no-encap {
                value 5;
            }

            // Admin state is down
            enum admin-down;

            // Tunnel source down
            enum src-down {
                value 7;
            }

            // Source IP is could not be resolved
            enum src-unres {
                value 8;
            }

            // Destination is not configured
            enum no-dest {
                value 9;
            }

            // Destination IP address unresolvable
            enum desip-unres {
                value 10;
            }

            // Destination unreachable
            enum dest-unreach;

            // Source interface and tunnl VRF mismatch
            enum vrf-mismatch {
                value 12;
            }

            // Tunnel transport VRF is forward referencing
            enum vrf-fwdref {
                value 13;
            }

            // VRF is down
            enum vrf-down {
                value 14;
            }

            // MTU programming failed
            enum mtu-error {
                value 15;
            }

            // Hardware programming failed
            enum hwprog-fail;
        }
        default "unknown";
    }

    // Tunnel types
    typedef tunnel_TunnelQual {
        type enumeration {

            // unknown
            enum unknown {
                value 0;
            }

            // ivxlan
            enum ivxlan {
                value 1;
            }

            // vxlan
            enum vxlan {
                value 2;
            }
        }
        default "ivxlan";
    }

    // Snmp trap state
    typedef tunnelif_SnmpTrapSt {
        type enumeration {
            enum enabled {
                value 1;
            }
            enum disabled {
                value 2;
            }
        }
        default "enabled";
    }

    // Tunnel Bandwidth in kilobits per second.
    typedef tunnelif_TunnelBW {
        type uint32 {
            range "1..10000000";
        }
        default "9";
    }

    // Tunnel mode types
    typedef tunnelif_TunnelMode {
        type enumeration {

            // GRE/IP
            enum gre/ip {
                value 1;
            }

            // GRE/IPV6
            enum gre/ipv6 {
                value 6;
            }

            // IPIP/IP
            enum ipip/ip {
                value 7;
            }

            // IPIP/IPV6
            enum ipip/ipv6 {
                value 8;
            }

            // IPIP/Decapsulate Any/IP
            enum ipip/dcapany/ip {
                value 9;
            }

            // IPIP/Decapsulate Any/IPV6
            enum ipip/dcapany/ipv6 {
                value 10;
            }

            // IPV6IP
            enum ipv6ip {
                value 11;
            }

            // IPV6IP/Decapsulate Any
            enum ipv6ip/dcapany {
                value 12;
            }

            // IPV6/IPV6
            enum ipv6ipv6 {
                value 13;
            }

            // IPV6IPV6/Decapsulate Any
            enum ipv6ipv6/dcapany {
                value 14;
            }
        }
        default "gre/ip";
    }

    // Configured MTU
    typedef tunnelif_TunnelMtu {
        type uint32 {
            range "64..9196";
        }
        default "1476";
    }

    // Operational state of tunnel
    typedef tunnelif_TunnelOperSt {
        type enumeration {

            // up
            enum up {
                value 1;
            }

            // down
            enum down {
                value 2;
            }
        }
        default "down";
    }

    // Reasons for line protcol state being down.
    typedef tunnelif_TunnelOperStQual {
        type enumeration {

            // unknown
            enum unknown {
                value 0;
            }

            // No reason
            enum none {
                value 1;
            }

            // Initializing hardware
            enum initing {
                value 2;
            }

            // Tunnel configuration is incomplete
            enum incomp-conf {
                value 3;
            }

            // Duplicate tunnel config
            enum dup-conf {
                value 4;
            }

            // tunnel mode is not configured
            enum no-mode {
                value 5;
            }

            // Admin state is down
            enum admin-down;

            // Tunnel source down
            enum src-down {
                value 7;
            }

            // Source IP could not be resolved
            enum src-unres {
                value 8;
            }

            // Destination is not configured
            enum no-dest {
                value 9;
            }

            // Destination IP address unresolvable
            enum desip-unres {
                value 10;
            }

            // Destination unreachable
            enum dest-unreach;

            // Source interface and tunnel VRF mismatch
            enum vrf-mismatch {
                value 12;
            }

            // Tunnel transport VRF is forward referencing
            enum vrf-fwdref {
                value 13;
            }

            // VRF is down
            enum vrf-down {
                value 14;
            }

            // MTU programming failed
            enum mtu-error {
                value 15;
            }

            // Hardware programming failed
            enum hwprog-fail;

            // Source is not configured
            enum no-src {
                value 17;
            }
        }
        default "unknown";
    }

    // Tunnel Interface Options
    typedef tunnelif_TunnelOption {
        type enumeration {

            // unknown
            enum unknown {
                value 0;
            }

            // delete on failure
            enum del_on_fail {
                value 1;
            }

            // user configured mtu
            enum usr_cfg_mtu {
                value 2;
            }
        }
        default "unknown";
    }

    // Configured age timer for Tunnel PMTU
    typedef tunnelif_TunnelPMTUAge {
        type uint32 {
            range "0..30";
        }
        default "10";
    }

    // Tunnel Path MTU Discovery
    typedef tunnelif_TunnelPMTUD {
        type enumeration {

            // enabled
            enum enabled {
                value 1;
            }

            // disabled
            enum disabled {
                value 2;
            }
        }
        default "disabled";
    }

    // Tunnel Source Direct
    typedef tunnelif_TunnelSrcDirect {
        type enumeration {

            // enabled
            enum enabled {
                value 1;
            }

            // disabled
            enum disabled {
                value 2;
            }
        }
        default "disabled";
    }

    // Tunnel TTL (from 0 to 255)
    typedef tunnelif_TunnelTTL {
        type uint32 {
            range "0..255";
        }
        default "0";
    }

    // Configured Tunnel transport VRF
    typedef tunnelif_TunnelTransVRF {
        type l3_VrfName;
        default "default";
    }

    // Configured min-MTU for Tunnel PMTU
    typedef tunnelif_TunnelminPMTU {
        type uint32 {
            range "64..9196";
        }
        default "64";
    }

    // Administrative state
    typedef udld_AdminSt {
        type enumeration {

            // Enabled
            enum enabled {
                value 1;
            }

            // Disabled
            enum disabled {
                value 2;
            }
        }
        default "disabled";
    }

    typedef udld_FsmState {
        type enumeration {

            // Link-up
            enum link-up {
                value 0;
            }

            // Link-down
            enum link-down {
                value 1;
            }

            // Detection
            enum detection {
                value 2;
            }

            // Advertisement
            enum advertisement {
                value 3;
            }

            // Disable-port
            enum disable-port {
                value 4;
            }

            // Disabled-link-up
            enum disabled-link-up {
                value 5;
            }

            // Disabled-link-down
            enum disabled-link-down {
                value 6;
            }

            // Udld-init
            enum init {
                value 7;
            }

            // Extended-detection
            enum extended-detection {
                value 8;
            }
        }
        default "init";
    }

    // Msg Interval
    typedef udld_MsgIntvl {
        type uint8 {
            range "7..90";
        }
        default "15";
    }

    typedef udld_NeighborState {
        type enumeration {

            // Unknown
            enum unknown {
                value 0;
            }

            // Unidirectional
            enum unidir-detected {
                value 1;
            }

            // Bidirectional
            enum bidir-detected {
                value 2;
            }

            // Tx-Rx-Loop
            enum tx-rx-loop {
                value 3;
            }

            // Neighbor Mismatch
            enum mismatch {
                value 4;
            }

            // Empty-Echo
            enum empty-echo {
                value 5;
            }
        }
        default "unknown";
    }

    // Operational state
    typedef udld_OperSt {
        type enumeration {

            // Enabled
            enum enabled {
                value 1;
            }

            // Disabled
            enum disabled {
                value 2;
            }
        }
        default "disabled";
    }

    typedef udld_PktDirection {
        type enumeration {

            // send
            enum send {
                value 0;
            }

            // recv
            enum recv {
                value 1;
            }
        }
        default "send";
    }

    typedef udld_PortEnable {
        type enumeration {

            // Port Enabled
            enum port-enabled {
                value 0;
            }

            // Port Fiber Disabled
            enum port-fiber-disabled {
                value 1;
            }

            // Port Default
            enum port-default {
                value 2;
            }
        }
        default "port-default";
    }

    // Label Table Client Flags
    typedef ulib_ClientFlag {

        // bits- Using string
        type string;
    }

    // Max Dynamic label
    typedef ulib_DynLblMax {
        type uint32 {
            range "16..471804";
        }
        default "471804";
    }

    // Min Dynamic label
    typedef ulib_DynLblMin {
        type uint32 {
            range "16..471804";
        }
        default "16";
    }

    // Label Count Value
    typedef ulib_LabelCnt {
        type uint32 {
            range "0..471804";
        }
        default "0";
    }

    // Label Range Value
    // Default Value "0" Removed - out of range 16..471804
    typedef ulib_LabelVal {
        type uint32 {
            range "16..471804";
        }
    }

    typedef urib_BitMask64 {
        type uint64;
    }

    typedef urib_Client6State {
        type enumeration {

            // Invalid state
            enum invalid {
                value 0;
            }

            // Passive state
            enum passive {
                value 1;
            }

            // Register state
            enum register {
                value 2;
            }

            // Deregister state
            enum deregister {
                value 3;
            }

            // Stale state
            enum stale {
                value 4;
            }

            // Dead state
            enum dead {
                value 5;
            }
        }
    }

    // 32 bit Counter
    typedef urib_Counter32 {
        type uint32;
    }

    // 32 bit Counter
    typedef urib_Counter64 {
        type uint32;
    }

    typedef urib_NextHopEncapType {
        type enumeration {

            // Not set
            enum none {
                value 0;
            }

            // Vxlan encapsulation
            enum vxlan {
                value 1;
            }

            // Invalid
            enum invalid {
                value 2;
            }
        }
    }

    typedef urib_NhFlags4 {

        // bits- Using string
        type string;
    }

    typedef urib_NhFlags6 {

        // bits- Using string
        type string;
    }

    typedef urib_NhlfeFlags4 {

        // bits- Using string
        type string;
    }

    typedef urib_NhlfeFlags6 {

        // bits- Using string
        type string;
    }

    typedef urib_RouteFlags4 {

        // bits- Using string
        type string;
    }

    typedef urib_RouteFlags6 {

        // bits- Using string
        type string;
    }

    // All these flags but "converged" are passed to rib on
    // registration.
    typedef urib_RoutingVrfFlags4 {

        // bits- Using string
        type string;
    }

    // All these flags but "converged" are passed to rib on
    // registration.
    typedef urib_RoutingVrfFlags6 {

        // bits- Using string
        type string;
    }

    typedef urib_TableState {
        type enumeration {

            // State invalid
            enum invalid {
                value 0;
            }

            // State up
            enum up {
                value 1;
            }

            // State down pending
            enum down-pending {
                value 2;
            }

            // State purging
            enum purging {
                value 3;
            }

            // State down
            enum down {
                value 4;
            }

            // State delete pending
            enum delete-pending {
                value 5;
            }

            // State deleted
            enum deleted {
                value 6;
            }
        }
    }

    // The format of this string depends on the time left.
    // If time left is:
    // - Less than 1 sec: format is 0.UUUUUU
    // - >= 1 sec and < 24 hrs: HH:MM:SS
    // - >= 24hrs and < 1 week: DD'd'HH'h' e.g.: 12d03h
    // - >= 1 week and < 1 year: WW'w'DD'd'
    // - >= 1 year: YY'y'WW'w'
    typedef urib_TimeStr {
        type string;
    }

    typedef urib_TlvType4 {
        type enumeration {

            // none
            enum none {
                value 0;
            }

            // Connector attribute
            enum connector-attrib {
                value 2;
            }

            // VRF Route Import
            enum vri {
                value 3;
            }
        }
    }

    typedef urib_TlvType6 {
        type enumeration {

            // none
            enum none {
                value 0;
            }

            // Connector attribute
            enum connector-attrib {
                value 2;
            }

            // VRF Route Import
            enum vri {
                value 3;
            }
        }
    }

    typedef urib_UpDown {
        type enumeration {

            // State down
            enum down {
                value 0;
            }

            // State up
            enum up {
                value 1;
            }
        }
    }

    typedef urib_YesNo {
        type enumeration {

            // No
            enum No {
                value 0;
            }

            // Yes
            enum Yes {
                value 1;
            }
        }
    }

    // Application Sap Id
    typedef vpc_AppId {
        type uint32;
    }

    // Track Object
    typedef vpc_AutoRecoveryIntvl {
        type uint16 {
            range "240..3600";
        }
        default "240";
    }

    // Batched vpc inventory
    typedef vpc_BatchedVpcInv {

        // bits- Using string
        type string;
    }

    // vPC Compatibility Reason Code
    typedef vpc_CompatQual {
        type uint32;
    }

    // vPC Compatability Status
    typedef vpc_CompatSt {
        type enumeration {

            // success
            enum pass {
                value 0;
            }

            // failed
            enum fail {
                value 1;
            }

            // Not Applicable
            enum notDone {
                value 2;
            }
        }
        default "notDone";
    }

    // Counter
    typedef vpc_Counter {
        type uint32;
    }

    // Peer dead interval in seconds
    typedef vpc_DeadIntvl {
        type uint32 {
            range "5..600";
        }
        default "200";
    }

    // Delay Peer Link Bringup
    typedef vpc_DelayPeerLinkBringup {
        type uint16 {
            range "0..7200";
        }
        default "0";
    }

    // Delay Restore SVI
    typedef vpc_DelayRestoreSVI {
        type uint16 {
            range "1..3600";
        }
        default "10";
    }

    // Delay Restore vPC
    typedef vpc_DelayRestoreVPC {
        type uint16 {
            range "1..3600";
        }
        default "30";
    }

    // VPC domain ID
    typedef vpc_DomId {
        type uint16 {
            range "1..1000";
        }
    }

    // Domain operational state
    // Default Value computed from not-applicable
    typedef vpc_DomOperSt {

        // bits- Using string
        type string;
        default "not-applicable";
    }

    // Dual Active Status
    typedef vpc_DualActiveSt {
        type enumeration {

            // 0
            enum false {
                value 0;
            }

            // 1
            enum true {
                value 1;
            }
        }
    }

    typedef vpc_ExcludeSVI {
        type l2_VlanBitmap;
        default "0";
    }

    // Flush Timeout in seconds
    typedef vpc_FlushTout {
        type uint32 {
            range "3..10";
        }
        default "3";
    }

    // vPC number
    typedef vpc_Id {
        type uint16 {
            range "1..16384";
        }
    }

    // Keepalive Interval in milli-seconds
    typedef vpc_KeepaliveInterval {
        type uint32 {
            range "400..10000";
        }
        default "1000";
    }

    // Keepalive operational state
    // Default Value computed from 0
    typedef vpc_KeepaliveOperSt {

        // bits- Using string
        type string;
        default "0";
    }

    // Keepalive Timeout in seconds
    typedef vpc_KeepaliveTout {
        type uint32 {
            range "3..20";
        }
        default "5";
    }

    // vPC operational Status
    typedef vpc_OperSt {
        type enumeration {

            // Unknown
            enum unknown {
                value 0;
            }

            // Down
            enum down {
                value 1;
            }

            // Up
            enum up {
                value 2;
            }

            // Not configured
            enum noCfg {
                value 3;
            }
        }
        default "unknown";
    }

    // Orphan port list    TODO: change this to be an array of uint32 once we have the
    // required datatype defined by Shrey.
    typedef vpc_OrphanPortList {
        type uint32;
    }

    // Param Length
    typedef vpc_ParamLen {
        type uint32;
    }

    // Param Type
    typedef vpc_ParamType {
        type enumeration {

            // Unknown
            enum unknown {
                value 0;
            }

            // Type 1
            enum type-1 {
                value 1;
            }

            // Type 2
            enum type-2 {
                value 2;
            }
        }
        default "unknown";
    }

    // Param Value
    typedef vpc_ParamVal {
        type mtx_array_uint8;
    }

    // vPC peer Status
    typedef vpc_PeerSt {
        type enumeration {

            // Not configured
            enum noCfg {
                value 0;
            }

            // Down
            enum down {
                value 1;
            }

            // Up
            enum up {
                value 2;
            }
        }
    }

    // vPC peer status reason code
    typedef vpc_PeerStQual {
        type enumeration {

            // Success
            enum success {
                value 0;
            }

            // Uplinks down
            enum uplinks-down {
                value 1;
            }

            // Route down
            enum route-down {
                value 2;
            }

            // Peer unreachable
            enum peer-unrch {
                value 3;
            }

            // Compatibility Failed
            enum compat-fail {
                value 4;
            }

            // Election error
            enum election-err {
                value 5;
            }

            // Keepalive not Operational
            enum oob-not-up {
                value 6;
            }
        }
    }

    // Peer version
    typedef vpc_PeerVersion {
        type uint32;
    }

    // Precedence type
    typedef vpc_PrecType {
        type enumeration {

            // Network
            enum network {
                value 0;
            }

            // Internet
            enum internet {
                value 1;
            }

            // Critical
            enum critical {
                value 2;
            }

            // Flash override
            enum flash-override {
                value 3;
            }

            // Flash
            enum flash {
                value 4;
            }

            // Immediate
            enum immediate {
                value 5;
            }

            // Priority
            enum priority {
                value 6;
            }

            // Routine
            enum routine {
                value 7;
            }
        }
        default "routine";
    }

    // Precedence value
    typedef vpc_PrecValue {
        type uint8 {
            range "0..7";
        }
        default "6";
    }

    // Role
    typedef vpc_Role {
        type enumeration {

            // Election-not-done
            enum election-not-done {
                value 0;
            }

            // Master
            enum master {
                value 1;
            }

            // Slave
            enum slave {
                value 2;
            }
        }
        default "election-not-done";
    }

    // Role Priority
    typedef vpc_RolePrio {
        type uint16 {
            range "1..65535";
        }
        default "32667";
    }

    // Summarized Role
    typedef vpc_SummRole {
        type enumeration {

            // None Established
            enum election-not-done {
                value 0;
            }

            // Primary
            enum cfg-master-oper-master {
                value 1;
            }

            // Primary, Operational Secondary
            enum cfg-master-oper-slave {
                value 2;
            }

            // Secondary, Operational Primary
            enum cfg-slave-oper-master {
                value 3;
            }

            // Secondary
            enum cfg-slave-oper-slave {
                value 4;
            }
        }
        default "election-not-done";
    }

    // System Priority
    typedef vpc_SysPrio {
        type uint16 {
            range "1..65535";
        }
        default "32667";
    }

    // Time
    typedef vpc_Time {
        type uint64;
    }

    // ToS byte
    typedef vpc_TosByte {
        type uint8 {
            range "0..255";
        }
        default "0";
    }

    // ToS config type
    typedef vpc_TosCfgType {
        type enumeration {

            // No configuration
            enum noCfg {
                value 0;
            }

            // ToS byte
            enum tos-byte {
                value 1;
            }

            // ToS value
            enum tos-value {
                value 2;
            }

            // ToS type
            enum tos-type {
                value 3;
            }

            // Precedence Type
            enum precedence-type {
                value 4;
            }

            // Precedence Value
            enum precedence-value {
                value 5;
            }
        }
        default "noCfg";
    }

    // ToS type
    typedef vpc_TosType {
        type enumeration {

            // Min delay
            enum min-delay {
                value 0;
            }

            // Max throughput
            enum max-throughput {
                value 1;
            }

            // Max Reliability
            enum max-reliability {
                value 2;
            }

            // Min Monetary Cost
            enum min-monetary-cost {
                value 3;
            }

            // Normal
            enum normal {
                value 4;
            }
        }
        default "normal";
    }

    // ToS value
    typedef vpc_TosValue {
        type uint8 {
            range "0..15";
        }
        default "0";
    }

    // Track Object
    typedef vpc_Track {
        type uint16 {
            range "0..500";
        }
        default "0";
    }

    // Virtual IP Announcement Delay
    typedef vpc_VIpAnnounceDelay {
        type uint16 {
            range "30..600";
        }
        default "45";
    }

    // admin state
    typedef vrrp_AdminSt {
        type enumeration {

            // Vrrp id shut
            enum disabled {
                value 1;
            }

            // Vrrp id no shut
            enum enabled {
                value 2;
            }
        }
        default "disabled";
    }

    // advertise interval
    typedef vrrp_AdvIntvl {
        type uint8 {
            range "1..255";
        }
        default "1";
    }

    // authentication text type
    typedef vrrp_AuthTextType {
        type string {
            length "0..8";
        }
    }

    // authentication type
    typedef vrrp_AuthType {
        type enumeration {

            // no authentication
            enum none {
                value 1;
            }

            // plain text
            enum simple {
                value 2;
            }
        }
        default "none";
    }

    // group state
    typedef vrrp_GroupSt {
        type enumeration {

            // Vrrp Group state Init
            enum init {
                value 0;
            }

            // vrrp group state backup
            enum backup {
                value 1;
            }

            // vrrp group state master
            enum master {
                value 2;
            }
        }
    }

    // group state qualifier
    typedef vrrp_GroupStQual {
        type enumeration {

            // Vrrp group state up
            enum up {
                value 0;
            }

            // Vrrp group state down
            enum down {
                value 1;
            }

            // vrrp group state down no ip primary vip
            enum no-primary-vip {
                value 2;
            }

            // vrrp group state down admin down
            enum admin-down {
                value 3;
            }

            // vrrp group state down inteface down
            enum interface-down {
                value 4;
            }

            // vrrp group state down no intf ip cfgd
            enum no-intf-ip-cfgd {
                value 5;
            }

            // vrrp group down no vrf info for intf
            enum no-vrf-info-for-intf {
                value 6;
            }

            // vrrp group down BD not allocated
            enum bd-not-allocated {
                value 7;
            }

            // vrrp group down vmac not added
            enum vmac-not-added {
                value 8;
            }

            // vrrp group down invalid vip
            enum invalid-vip {
                value 9;
            }

            // vrrp group down IfId vIp subnet mismatch
            enum IfIp-vip-subnet-mismatch {
                value 10;
            }

            // vrrp group down internal error
            enum internal_error {
                value 11;
            }
        }
    }

    // Configuration state    vrrp id
    typedef vrrp_Id {
        type uint8 {
            range "1..255";
        }
    }

    // Preempt
    typedef vrrp_Preempt {
        type enumeration {

            // preempt enabled
            enum enabled {
                value 1;
            }

            // preempt disabled
            enum disabled {
                value 2;
            }
        }
        default "enabled";
    }

    // priority values
    typedef vrrp_PriVal {
        type uint8 {
            range "1..254";
        }
    }

    // upper threshold
    typedef vrrp_UprThrshld {
        type uint8 {
            range "0..254";
        }
        default "0";
    }

    // bfd session status
    typedef vrrp_bfdSessionSt {
        type enumeration {

            // vrrp bfd session is disabled
            enum disabled {
                value 0;
            }

            // vrrp bfd session status inactive
            enum inactive {
                value 1;
            }

            // vrrp bfd session status deleted
            enum deleted {
                value 2;
            }

            // vrrp bfd session status unknown state
            enum unknown {
                value 3;
            }

            // vrrp bfd session status active
            enum active {
                value 4;
            }
        }
        default "disabled";
    }

    // Admin State
    typedef vrrpv3_AdminSt {
        type boolean;
    }

    // Advertisement Interval
    typedef vrrpv3_AdvIntvl {
        type uint32 {
            range "100..40950";
        }
        default "1000";
    }

    // Virtual Router Name
    typedef vrrpv3_Desc {
        type string {
            length "0..80";
        }
    }

    // Configuration state    vrrpv3 id
    typedef vrrpv3_Id {
        type uint32 {
            range "1..255";
        }
    }

    // Preempt
    typedef vrrpv3_Preempt {
        type boolean;
        default "true";
    }

    // Delay before preempting a lower priority Master
    typedef vrrpv3_PreemptDelay {
        type uint32 {
            range "0..3600";
        }
        default "0";
    }

    // Priority Value
    typedef vrrpv3_PriVal {
        type uint32 {
            range "1..254";
        }
    }

    // Virtual Router Address family type
    typedef vrrpv3_VrAf {
        type enumeration {

            // IPv4 address family
            enum ipv4 {
                value 1;
            }

            // IPv6 address family
            enum ipv6 {
                value 2;
            }
        }
        default "ipv4";
    }

    // TODO Pirabhu - Remove Permit and redir directives from the logical model type
    // once sanity is fixed. These can be derived implicitly
    // Default Value computed from permit
    typedef vz_Action {

        // bits- Using string
        type string;
        default "permit";
    }

    // A shorthand for GroupPolicyClassTag:
    // A tag that is used to identify and classify
    // a particular group of resources/end-points
    // for policy enforcement purposes
    typedef vz_GPCTag {
        type vz_GroupPolicyClassTag;
    }

    // A tag that is used to identify and classify
    // a particular group of resources/end-points
    // for policy enforcement purposes
    typedef vz_GroupPolicyClassTag {
        type uint32;
    }

    // Type is a Local-MO-Defined-Type
    typedef sts_PathCtrl_FabOut_ctrl {

        // bits- Using string
        type string;
    }

    // Type is a Local-MO-Defined-Type
    typedef sts_PathCtrl_FabOutRev_ctrl {

        // bits- Using string
        type string;
    }

    // Type is a Local-MO-Defined-Type
    // Default Value computed from fastExtFallover
    typedef nw_InstCtrl_Inst_ctrl {

        // bits- Using string
        type string;
        default "fastExtFallover";
    }

    // Type is a Local-MO-Defined-Type
    typedef bgp_NhTimeout_DomAf_critNhTimeout {
        type uint32;
        default "3000";
    }

    // Type is a Local-MO-Defined-Type
    typedef bgp_NhTimeout_DomAf_nonCritNhTimeout {
        type uint32;
        default "10000";
    }

    // Type is a Local-MO-Defined-Type
    typedef nw_OperErrQual_Inst_operErr {

        // bits- Using string
        type string;
    }

    // Type is a Local-MO-Defined-Type
    typedef syslog_Severity_Level_severity {
        type enumeration {

            // emergencies
            enum emergencies {
                value 0;
            }

            // alerts
            enum alerts {
                value 1;
            }

            // critical
            enum critical {
                value 2;
            }

            // errors
            enum errors {
                value 3;
            }

            // warnings
            enum warnings {
                value 4;
            }

            // notifications
            enum notifications {
                value 5;
            }

            // information
            enum information {
                value 6;
            }

            // debugging
            enum debugging {
                value 7;
            }

            // unspecified
            enum unspecified {
                value 8;
            }
        }
        default "unspecified";
    }

    // Type is a Local-MO-Defined-Type
    typedef aaa_KeyEnc_RadiusProvider_keyEnc {
        type enumeration {

            // Clear Text
            enum 0 {
                value 0;
            }

            // Type-6 Encrypted
            enum 6 {
                value 6;
            }

            // Encrypted
            enum 7 {
                value 7;
            }
            enum inherit-from-global {
                value 255;
            }
        }
        default "inherit-from-global";
    }

    // Type is a Local-MO-Defined-Type
    typedef aaa_TimeSec_RadiusProvider_timeout {
        type uint32;
        default "4294967295";
    }

    // Type is a Local-MO-Defined-Type
    typedef aaa_Retries_RadiusProvider_retries {
        type uint32;
        default "4294967295";
    }

    // Type is a Local-MO-Defined-Type
    typedef aaa_KeyEnc_LdapProvider_keyEnc {
        type enumeration {

            // Clear Text
            enum 0 {
                value 0;
            }

            // Type-6 Encrypted
            enum 6 {
                value 6;
            }

            // Encrypted
            enum 7 {
                value 7;
            }
            enum inherit-from-global {
                value 255;
            }
        }
        default "inherit-from-global";
    }

    // Type is a Local-MO-Defined-Type
    typedef aaa_TimeSec_LdapProvider_timeout {
        type uint32;
        default "30";
    }

    // Type is a Local-MO-Defined-Type
    typedef aaa_Retries_LdapProvider_retries {
        type uint32;
        default "4294967295";
    }

    // Type is a Local-MO-Defined-Type
    typedef aaa_KeyEnc_TacacsPlusProvider_keyEnc {
        type enumeration {

            // Clear Text
            enum 0 {
                value 0;
            }

            // Type-6 Encrypted
            enum 6 {
                value 6;
            }

            // Encrypted
            enum 7 {
                value 7;
            }
            enum inherit-from-global {
                value 255;
            }
        }
        default "inherit-from-global";
    }

    // Type is a Local-MO-Defined-Type
    typedef aaa_TimeSec_TacacsPlusProvider_timeout {
        type uint32;
        default "0";
    }

    // Type is a Local-MO-Defined-Type
    typedef aaa_Retries_TacacsPlusProvider_retries {
        type uint32;
        default "4294967295";
    }

    // Type is a Local-MO-Defined-Type
    typedef aaa_Realm_DomainAuth_realm {
        type enumeration {

            // Local
            enum local {
                value 0;
            }

            // RADIUS
            enum radius {
                value 1;
            }

            // TACACS+
            enum tacacs {
                value 2;
            }

            // LDAP
            enum ldap {
                value 3;
            }
            enum none {
                value 4;
            }
        }
    }

    // Type is a Local-MO-Defined-Type
    typedef aaa_Date_User_expiration {
        type uint64;
        default "0";
    }

    // Type is a Local-MO-Defined-Type
    typedef l1_Layer_AggrIf_layer {
        type enumeration {

            // switched
            enum Layer2 {
                value 1;
            }

            // routed
            enum Layer3 {
                value 2;
            }
            enum pltfmDfltLayer {
                value 3;
            }
        }
        default "pltfmDfltLayer";
    }

    // Type is a Local-MO-Defined-Type
    typedef nw_AdminSt_IfStat_proxyArp {
        type enumeration {

            // Enabled
            enum enabled {
                value 1;
            }

            // Disabled
            enum disabled {
                value 2;
            }
        }
    }

    // Type is a Local-MO-Defined-Type
    typedef nw_AdminSt_IfStat_localProxyArp {
        type enumeration {

            // Enabled
            enum enabled {
                value 1;
            }

            // Disabled
            enum disabled {
                value 2;
            }
        }
    }

    // Type is a Local-MO-Defined-Type
    typedef nw_AdminSt_IfStat_mRouting {
        type enumeration {

            // Enabled
            enum enabled {
                value 1;
            }

            // Disabled
            enum disabled {
                value 2;
            }
        }
    }

    // Type is a Local-MO-Defined-Type
    typedef nw_AdminSt_IfStat_icmpRedirect {
        type enumeration {

            // Enabled
            enum enabled {
                value 1;
            }

            // Disabled
            enum disabled {
                value 2;
            }
        }
    }

    // Type is a Local-MO-Defined-Type
    typedef nw_AdminSt_IfStat_directBcast {
        type enumeration {

            // Enabled
            enum enabled {
                value 1;
            }

            // Disabled
            enum disabled {
                value 2;
            }
        }
    }

    // Type is a Local-MO-Defined-Type
    typedef nw_AdminSt_IfStat_ipUnreach {
        type enumeration {

            // Enabled
            enum enabled {
                value 1;
            }

            // Disabled
            enum disabled {
                value 2;
            }
        }
    }

    // Type is a Local-MO-Defined-Type
    typedef nw_AdminSt_IfStat_portUnreach {
        type enumeration {

            // Enabled
            enum enabled {
                value 1;
            }

            // Disabled
            enum disabled {
                value 2;
            }
        }
    }

    // Type is a Local-MO-Defined-Type
    typedef nw_AdminSt_ProcessStat_autoDisc {
        type enumeration {

            // Enabled
            enum enabled {
                value 1;
            }

            // Disabled
            enum disabled {
                value 2;
            }
        }
    }

    // Type is a Local-MO-Defined-Type
    typedef nw_AdminSt_ProcessStat_autoDiscAdd {
        type enumeration {

            // Enabled
            enum enabled {
                value 1;
            }

            // Disabled
            enum disabled {
                value 2;
            }
        }
    }

    // Type is a Local-MO-Defined-Type
    typedef nw_AdminSt_ProcessStat_nullBcast {
        type enumeration {

            // Enabled
            enum enabled {
                value 1;
            }

            // Disabled
            enum disabled {
                value 2;
            }
        }
    }

    // Type is a Local-MO-Defined-Type
    typedef nw_AdminSt_ProcessStat_autoPuntBcast {
        type enumeration {

            // Enabled
            enum enabled {
                value 1;
            }

            // Disabled
            enum disabled {
                value 2;
            }
        }
    }

    // Type is a Local-MO-Defined-Type
    typedef nw_AdminSt_ProcessStat_staticDisc {
        type enumeration {

            // Enabled
            enum enabled {
                value 1;
            }

            // Disabled
            enum disabled {
                value 2;
            }
        }
    }

    // Type is a Local-MO-Defined-Type
    typedef eqpt_Arch_CPU_arch {
        type enumeration {

            // x86_32
            enum x86_32 {
                value 1;
            }

            // x86_64
            enum x86_64 {
                value 2;
            }

            // any
            enum any {
                value 0;
            }
        }
    }

    // Type is a Local-MO-Defined-Type
    typedef im_BreakoutMapT_LeafP_breakoutMap {
        type enumeration {

            // 10g-4x
            enum 10g-4x {
                value 5;
            }

            // 10g-2x
            enum 10g-2x {
                value 9;
            }

            // 25g-4x
            enum 25g-4x {
                value 8;
            }

            // 50g-2x
            enum 50g-2x {
                value 7;
            }
            enum no-breakout {
                value 0;
            }
        }
        default "no-breakout";
    }

    // Type is a Local-MO-Defined-Type
    typedef eqpt_Arch_ExtChCPU_arch {
        type enumeration {

            // x86_32
            enum x86_32 {
                value 1;
            }

            // x86_64
            enum x86_64 {
                value 2;
            }

            // any
            enum any {
                value 0;
            }
        }
    }

    // Type is a Local-MO-Defined-Type
    // Default Value computed from redirect,port-unreachable
    typedef icmp_IfControl_If_ctrl {

        // bits- Using string
        type string;
        default "redirect,port-unreachable";
    }

    // Type is a Local-MO-Defined-Type
    typedef nd_DNSServerLifeTime_RouteAdvDNSServer_dnsServerLifeTime {
        type uint32;
        default "0";
    }

    // Type is a Local-MO-Defined-Type
    typedef nd_DNSServerLifeTime_RouteAdvDNSSearchList_dnsSearchListLifeTime {
        type uint32;
        default "0";
    }

    grouping aaa_IDomainRef-group {

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping l2cap_Prov-group {

        // Subject consuming the capability
        // Type is an MO-Defined-Type
        leaf subj {
            config "false";
            description "Subject";

            // Type is an MO-Defined-Type
            type l2cap_Subj;
        }

        // Every Consumer has a Subject.
        // Subject represents the entity which consumes the capability.
        // Namespaces which have concrete consumers, define the Subject property
        // and its types
        // Max capability available
        // Inherited From cap:Prov
        // Type is an MO-Defined-Type
        leaf total {
            config "false";
            description "TBD";

            // Type is an MO-Defined-Type
            type cap_Counter;
        }

        // Remaining capability available
        // Inherited From cap:Prov
        // Type is an MO-Defined-Type
        leaf remaining {
            config "false";
            description "TBD";

            // Type is an MO-Defined-Type
            type cap_Counter;
        }

        // utilization indicator in percentages of consiumption
        // Inherited From cap:Prov
        // Type is an MO-Defined-Type
        leaf utilization {
            config "false";
            description "TBD";

            // Type is an MO-Defined-Type
            type cap_StorageHint;
        }

        // Type of the Rule consumed by this consumer.
        // Inherited From cap:Prov
        // Type is an MO-Defined-Type
        leaf type {
            config "false";
            description "TBD";

            // Type is an MO-Defined-Type
            type cap_RuleT;
        }
    }

    grouping actrlcap_Rule-group {

        // Subject consuming the capability.
        // Type is an MO-Defined-Type
        leaf subj {
            config "false";
            description "TBD";

            // Type is an MO-Defined-Type
            type actrlcap_Subj;
        }

        // Every Rule has a Subject.
        // Subject represents the entity which consumes the capability.
        // Namespaces which have concrete rules, define the Subject property
        // and its types
        // Constraints of the capability.
        // Inherited From cap:Rule
        // Type is an MO-Defined-Type
        leaf constraint {
            config "false";
            description "TBD";

            // Type is an MO-Defined-Type
            type cap_Constraint;
        }

        // Domain applicable to the capability.
        // Inherited From cap:Rule
        // Type is an MO-Defined-Type
        leaf scope {
            config "false";
            description "TBD";

            // Type is an MO-Defined-Type
            type cap_Scope;
        }

        // Type of the Rule.
        // Inherited From cap:Rule
        // Type is an MO-Defined-Type
        leaf type {
            config "false";
            description "TBD";

            // Type is an MO-Defined-Type
            type cap_RuleT;
        }

        // From Interface naming:Described
        // Inherited From cap:Rule
        // Type is an MO-Defined-Type
        leaf descr {
            description "Description";

            // Type is an MO-Defined-Type
            type naming_Descr;
        }
    }

    grouping l1cap_Rule-group {

        // Subject consuming the capability.
        // Type is an MO-Defined-Type
        leaf subj {
            config "false";
            description "TBD";

            // Type is an MO-Defined-Type
            type l1cap_Subj;
        }

        // Every Rule has a Subject.
        // Subject represents the entity which consumes the capability.
        // Namespaces which have concrete rules, define the Subject property
        // and its types
        // Constraints of the capability.
        // Inherited From cap:Rule
        // Type is an MO-Defined-Type
        leaf constraint {
            config "false";
            description "TBD";

            // Type is an MO-Defined-Type
            type cap_Constraint;
        }

        // Domain applicable to the capability.
        // Inherited From cap:Rule
        // Type is an MO-Defined-Type
        leaf scope {
            config "false";
            description "TBD";

            // Type is an MO-Defined-Type
            type cap_Scope;
        }

        // Type of the Rule.
        // Inherited From cap:Rule
        // Type is an MO-Defined-Type
        leaf type {
            config "false";
            description "TBD";

            // Type is an MO-Defined-Type
            type cap_RuleT;
        }

        // From Interface naming:Described
        // Inherited From cap:Rule
        // Type is an MO-Defined-Type
        leaf descr {
            description "Description";

            // Type is an MO-Defined-Type
            type naming_Descr;
        }
    }

    grouping l2cap_Rule-group {

        // Type is an MO-Defined-Type
        leaf faultState {
            config "false";
            description "Fault State";

            // Type is an MO-Defined-Type
            type cap_RaiseFaultState;
        }

        // Subject consuming the capability
        // Type is an MO-Defined-Type
        leaf subj {
            config "false";
            description "Subject";

            // Type is an MO-Defined-Type
            type l2cap_Subj;
        }

        // Every Rule has a Subject.
        // Subject represents the entity which consumes the capability.
        // Namespaces which have concrete rules, define the Subject property
        // and its types
        // Constraints of the capability.
        // Inherited From cap:Rule
        // Type is an MO-Defined-Type
        leaf constraint {
            config "false";
            description "TBD";

            // Type is an MO-Defined-Type
            type cap_Constraint;
        }

        // Domain applicable to the capability.
        // Inherited From cap:Rule
        // Type is an MO-Defined-Type
        leaf scope {
            config "false";
            description "TBD";

            // Type is an MO-Defined-Type
            type cap_Scope;
        }

        // Type of the Rule.
        // Inherited From cap:Rule
        // Type is an MO-Defined-Type
        leaf type {
            config "false";
            description "TBD";

            // Type is an MO-Defined-Type
            type cap_RuleT;
        }

        // From Interface naming:Described
        // Inherited From cap:Rule
        // Type is an MO-Defined-Type
        leaf descr {
            description "Description";

            // Type is an MO-Defined-Type
            type naming_Descr;
        }
    }

    grouping l3cap_Rule-group {

        // Type is an MO-Defined-Type
        leaf faultState {
            config "false";
            description "Fault State";

            // Type is an MO-Defined-Type
            type cap_RaiseFaultState;
        }

        // Subject consuming the capability
        // Type is an MO-Defined-Type
        leaf subj {
            config "false";
            description "Subject";

            // Type is an MO-Defined-Type
            type l3cap_Subj;
        }

        // Every Rule has a Subject.
        // Subject represents the entity which consumes the capability.
        // Namespaces which have concrete rules, define the Subject property
        // and its types
        // Constraints of the capability.
        // Inherited From cap:Rule
        // Type is an MO-Defined-Type
        leaf constraint {
            config "false";
            description "TBD";

            // Type is an MO-Defined-Type
            type cap_Constraint;
        }

        // Domain applicable to the capability.
        // Inherited From cap:Rule
        // Type is an MO-Defined-Type
        leaf scope {
            config "false";
            description "TBD";

            // Type is an MO-Defined-Type
            type cap_Scope;
        }

        // Type of the Rule.
        // Inherited From cap:Rule
        // Type is an MO-Defined-Type
        leaf type {
            config "false";
            description "TBD";

            // Type is an MO-Defined-Type
            type cap_RuleT;
        }

        // From Interface naming:Described
        // Inherited From cap:Rule
        // Type is an MO-Defined-Type
        leaf descr {
            description "Description";

            // Type is an MO-Defined-Type
            type naming_Descr;
        }
    }

    grouping syslog_RemoteDest-group {

        // Type is an MO-Defined-Type
        leaf severity {
            description "Severity";

            // Type is an MO-Defined-Type
            type syslog_Severity;
        }

        // Type is an MO-Defined-Type
        leaf port {
            description "Port";

            // Type is an MO-Defined-Type
            type syslog_SyslogPort;
        }

        // Type is an MO-Defined-Type
        leaf forwardingFacility {
            description "Forward Facility";

            // Type is an MO-Defined-Type
            type syslog_Facility;
        }

        // Type is an MO-Defined-Type
        leaf adminState {
            description "TBD";

            // Type is an MO-Defined-Type
            type mon_AdminState;
        }
        leaf vrfId {
            type uint32;
        }

        // Type is an MO-Defined-Type
        leaf ip {
            description "ip address";

            // Type is an MO-Defined-Type
            type address_HostNameOrDottedQuad;
        }

        // Type is an MO-Defined-Type
        leaf operState {
            config "false";
            description "TBD";

            // Type is an MO-Defined-Type
            type syslog_OperState;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Hostname or IP for export destination
        // Inherited From file:ARemoteHost
        // Type is an MO-Defined-Type
        leaf host {
            description "Host";

            // Type is an MO-Defined-Type
            type address_HostNameOrDottedQuad {
                length "1..255";
            }
        }
        leaf epgDn {
            config "false";
            type string;
        }

        // The vrf that remote host belongs to
        // Inherited From file:ARemoteHost
        // Type is an MO-Defined-Type
        leaf vrfName {
            description "Vrf Name";

            // Type is an MO-Defined-Type
            type l3_VrfName;
        }

        // Syslog Dest state
        container destst-items {
            list DestState-list {
                key "name";

                // Added containment: Prefix=destst
                // Acquired From Package syslog
                uses syslog_DestState-group;
            }
        }
    }

    grouping syslog_DestState-group {

        // Type is an MO-Defined-Type
        leaf operState {
            description "TBD";

            // Type is an MO-Defined-Type
            type syslog_OperState;
        }
        leaf vrfId {
            type uint32;
        }

        // Type is an MO-Defined-Type
        leaf ip {
            description "ip address";

            // Type is an MO-Defined-Type
            type address_HostNameOrDottedQuad;
        }
        leaf totalBufferedMsgs {
            type uint32;
        }
        leaf totalDroppedMsgs {
            type uint32;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Syslog Log Message
        container msg-items {
            list LogMsg-list {
                key "index";

                // Added containment: Prefix=msg
                // Acquired From Package syslog
                uses syslog_LogMsg-group;
            }
        }
    }

    grouping syslog_LogMsg-group {
        leaf index {
            type uint32;
        }
        leaf message {
            type string;
        }
        leaf facility {
            type string;
        }
        leaf severity {
            type uint16;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
    }

    grouping syslog_File-group {

        // Type is an MO-Defined-Type
        leaf adminState {
            description "TBD";

            // Type is an MO-Defined-Type
            type mon_AdminState;
        }

        // Type is an MO-Defined-Type
        leaf severity {
            description "Severity";

            // Type is an MO-Defined-Type
            type syslog_Severity;
        }

        // Type is an MO-Defined-Type
        leaf size {
            description "Size";

            // Type is an MO-Defined-Type
            type syslog_FileSize;
        }

        // From Interface naming:Named
        // Inherited From naming:NamedObject
        // Modified by Override: syslog:File->name
        // Modified by Override: pol:Obj->name
        // Type is an MO-Defined-Type
        leaf name {
            description "Name";

            // Type is an MO-Defined-Type
            type naming_Name {
                length "1..200";
            }
        }

        // From Interface naming:Described
        // Inherited From pol:Comp
        // Type is an MO-Defined-Type
        leaf descr {
            description "Description";

            // Type is an MO-Defined-Type
            type naming_Descr;
        }
    }

    grouping syslog_Console-group {

        // Type is an MO-Defined-Type
        leaf adminState {
            description "TBD";

            // Type is an MO-Defined-Type
            type mon_AdminState;
        }

        // Type is an MO-Defined-Type
        leaf severity {
            description "Severity";

            // Type is an MO-Defined-Type
            type syslog_Severity;
        }
    }

    grouping dhcp_OptionDef-group {

        // From Interface naming:Named
        // Inherited From naming:NamedObject
        // Modified by Override: pol:Obj->name
        // Modified by Override: dhcp:AOption->name
        // Type is an MO-Defined-Type
        leaf name {
            description "Name";

            // Type is an MO-Defined-Type
            type naming_Name {
                length "0..64";
            }
        }

        // DHCP OPTION ID
        // Inherited From dhcp:AOption
        // Type is an MO-Defined-Type
        leaf id {
            description "TBD";

            // Type is an MO-Defined-Type
            type dhcp_OptionId;
        }

        // DHCP OPTION ID
        // Inherited From dhcp:AOption
        // Type is an MO-Defined-Type
        leaf data {
            description "Model Regex";

            // Type is an MO-Defined-Type
            type naming_Regex;
        }

        // Discovered DHCP client node
        container bd-items {
            list DiscNode-list {
                config "false";
                key "encap mac ciAddr";

                // Added containment: Prefix=bd
                // Acquired From Package dhcp
                uses dhcp_DiscNode-group;
            }
        }
    }

    grouping dhcp_DiscNode-group {
        leaf mac {
            config "false";
            type address_Mac;
        }
        leaf ciAddr {
            config "false";
            type address_Ip;
        }
        leaf siAddr {
            config "false";
            type address_Ip;
        }

        // Interface on which the client was discovered
        // Type is an MO-Defined-Type
        leaf ifId {
            config "false";
            description "Interface ID";

            // Type is an MO-Defined-Type
            type nw_IfId;
        }
        leaf ctxEncap {
            config "false";
            type string;
        }
        leaf fabEncap {
            config "false";
            type string;
        }
        leaf encap {
            config "false";
            type string;
        }

        // Notification status
        // Type is an MO-Defined-Type
        leaf notifSt {
            config "false";
            description "Status of Notification";

            // Type is an MO-Defined-Type
            type dhcp_NotifStatus;
        }
    }

    grouping fv_DomDef-group {

        // Type is an MO-Defined-Type
        leaf domPKey {
            config "false";
            description "TBD";

            // Type is an MO-Defined-Type
            type fv_PrimKey;
        }

        // Type is an MO-Defined-Type
        leaf instrImedcy {
            config "false";
            description "TBD";

            // Type is an MO-Defined-Type
            type fv_InstrImedcy;
        }

        // Type is an MO-Defined-Type
        leaf resImedcy {
            description "TBD";

            // Type is an MO-Defined-Type
            type fv_ResImedcy;
        }
        leaf mcastAddr {
            type address_Ip;
        }
        leaf updateTs {
            config "false";
            type uint64;
        }

        // From Interface naming:Named
        // Inherited From naming:NamedObject
        // Type is an MO-Defined-Type
        leaf name {
            description "Name";

            // Type is an MO-Defined-Type
            type naming_Name;
        }

        // Rel-def from domDefNs
        container rsdomDefNs-items {

            // Added containment as a singleton: Prefix=rsdomDefNs
            // Acquired From Package fv
            uses fv_RsDomDefNs_source-group;
        }

        // Rel-def from domDefNsLocal
        container rsdomDefNsLocal-items {

            // Added containment as a singleton: Prefix=rsdomDefNsLocal
            // Acquired From Package fv
            uses fv_RsDomDefNsLocal_source-group;
        }

        // Rel-def target from toDomDef
        // Inherited From fv:DomDef
        container rtfvToDomDef-items {

            // Abstract containment of rtfvToDomDef derived from fv:DomDef
            list RtFvToDomDef-list {
                config "false";
                key "tDn";

                // Added containment: Prefix=rtfvToDomDef
                // Acquired From Package fv
                uses fv_RtFvToDomDef_target-group;
            }
        }
    }

    grouping fv_DEp-group {

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From fv:ATp
        // Type is an MO-Defined-Type
        leaf lcC {
            description "TBD";

            // Type is an MO-Defined-Type
            type fv_LcC;
        }
        leaf ip {
            type address_Ip;
        }
        leaf mac {
            type address_Mac;
        }
        leaf encap {
            type string;
        }
        leaf uuid {
            config "false";
            type string;
        }
    }

    grouping opflex_IDEp-group {

        // Vendor id
        // Type is an MO-Defined-Type
        leaf vendorId {
            description "TBD";

            // Type is an MO-Defined-Type
            type comp_Vendor;
        }

        // Name of the domain
        // Type is an MO-Defined-Type
        leaf domName {
            description "TBD";

            // Type is an MO-Defined-Type
            type naming_LongDescr;
        }

        // Name of the controller
        // Type is an MO-Defined-Type
        leaf ctrlrName {
            description "TBD";

            // Type is an MO-Defined-Type
            type naming_LongDescr;
        }
        leaf eppdn {
            config "false";
            type string;
        }
        leaf compVmDn {
            config "false";
            type string;
        }
        leaf compHvDn {
            config "false";
            type string;
        }
        leaf epgID {
            config "false";
            type string;
        }
        leaf epHostAddr {
            type string;
        }
        leaf hypervisorName {
            type string;
        }
        leaf portId {
            type uint32;
        }
        leaf gtag {
            type uint32;
        }

        // Physical Interface ID on which this EP was attached
        // Type is an MO-Defined-Type
        leaf brIfId {
            description "TBD";

            // Type is an MO-Defined-Type
            type nw_IfId;
        }
        leaf containerName {
            config "false";
            type string;
        }

        // ep transition status
        // Type is an MO-Defined-Type
        leaf transitionStatus {
            config "false";
            description "TBD";

            // Type is an MO-Defined-Type
            type opflex_EpTransitionStatus;
        }

        // epp push policy
        // Type is an MO-Defined-Type
        leaf eppDownloadHint {
            config "false";
            description "TBD";

            // Type is an MO-Defined-Type
            type opflex_EppDownloadHint;
        }
        leaf handle {
            config "false";
            type uint64;
        }

        // instType
        // Type is an MO-Defined-Type
        leaf instType {
            config "false";
            description "TBD";

            // Type is an MO-Defined-Type
            type comp_NicInstType;
        }
        leaf pcIfId {
            config "false";
            type uint32;
        }

        // type of the device
        // Type is an MO-Defined-Type
        leaf state {
            description "TBD";

            // Type is an MO-Defined-Type
            type comp_NicState;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From fv:ATp
        // Type is an MO-Defined-Type
        leaf lcC {
            description "TBD";

            // Type is an MO-Defined-Type
            type fv_LcC;
        }
        leaf ip {
            type address_Ip;
        }
        leaf mac {
            type address_Mac;
        }
        leaf encap {
            type string;
        }
        leaf uuid {
            config "false";
            type string;
        }

        // IDEp stats is the object exchanged between opflex agent
        // and opflex controller for the end point stats
        container idepcntr-items {
            list IDEpCntr-list {
                key "mac encap";

                // Added containment: Prefix=idepcntr
                // Acquired From Package opflex
                uses opflex_IDEpCntr-group;
            }
        }
        container vdep-items {
            list VDEp-list {
                key "mac encap brIfId";

                // Added containment: Prefix=vdep
                // Acquired From Package fv
                uses fv_VDEp-group;
            }
        }
    }

    grouping opflex_IDEpCntr-group {
        leaf mac {
            type address_Mac;
        }
        leaf encap {
            type string;
        }
        leaf drop {
            type uint64;
        }
        leaf ucast {
            type uint64;
        }
        leaf mcast {
            type uint64;
        }
        leaf bcast {
            type uint64;
        }
        leaf pkts {
            type uint64;
        }
        leaf bytes {
            type uint64;
        }

        // Type is an MO-Defined-Type
        leaf direction {
            description "TBD";

            // Type is an MO-Defined-Type
            type opflex_Direction;
        }
        leaf pktsResetMask {
            type uint32;
        }
        leaf bytesResetMask {
            type uint32;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }
    }

    grouping fv_VDEp-group {
        leaf eppdn {
            type string;
        }
        leaf epgID {
            config "false";
            type string;
        }
        leaf portId {
            type uint32;
        }
        leaf gtag {
            type uint32;
        }

        // Physical Interface ID on which this EP was attached
        // Type is an MO-Defined-Type
        leaf brIfId {
            description "TBD";

            // Type is an MO-Defined-Type
            type nw_IfId;
        }

        // instType
        // Type is an MO-Defined-Type
        leaf instType {
            config "false";
            description "TBD";

            // Type is an MO-Defined-Type
            type comp_NicInstType;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From fv:ATp
        // Type is an MO-Defined-Type
        leaf lcC {
            description "TBD";

            // Type is an MO-Defined-Type
            type fv_LcC;
        }
        leaf ip {
            type address_Ip;
        }
        leaf mac {
            type address_Mac;
        }
        leaf encap {
            type string;
        }
        leaf uuid {
            config "false";
            type string;
        }

        // Rel-def from vNode
        container rsvNode-items {

            // Abstract containment of rsvNode derived from fv:VDEp
            list RsVNode-list {
                key "tDn";

                // Added containment: Prefix=rsvNode
                // Acquired From Package fv
                uses fv_RsVNode_source-group;
            }
        }
    }

    grouping sts_FabIn-group {

        // From Interface naming:Named
        // Inherited From naming:NamedObject
        // Type is an MO-Defined-Type
        leaf name {
            description "Name";

            // Type is an MO-Defined-Type
            type naming_Name;
        }

        // Control
        // Inherited From sts:Path
        // Type is an MO-Defined-Type
        leaf ctrl {
            config "false";
            description "TBD";

            // Type is an MO-Defined-Type
            type sts_PathCtrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }

        // Tap
        container tap-items {
            list Tap-list {
                config "false";
                key "port encap";

                // Added containment: Prefix=tap
                // Acquired From Package sts
                uses sts_Tap-group;
            }
        }
    }

    grouping sts_Tap-group {

        // Tap port
        // Type is an MO-Defined-Type
        leaf port {
            config "false";
            description "TBD";

            // Type is an MO-Defined-Type
            type nw_IfId;
        }
        leaf encap {
            config "false";
            type string;
        }
    }

    grouping sts_FabInRev-group {

        // From Interface naming:Named
        // Inherited From naming:NamedObject
        // Type is an MO-Defined-Type
        leaf name {
            description "Name";

            // Type is an MO-Defined-Type
            type naming_Name;
        }

        // Control
        // Inherited From sts:Path
        // Type is an MO-Defined-Type
        leaf ctrl {
            config "false";
            description "TBD";

            // Type is an MO-Defined-Type
            type sts_PathCtrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }
    }

    grouping sts_FabOut-group {

        // From Interface naming:Named
        // Inherited From naming:NamedObject
        // Type is an MO-Defined-Type
        leaf name {
            description "Name";

            // Type is an MO-Defined-Type
            type naming_Name;
        }

        // Control
        // Inherited From sts:Path
        // Modified by Override: sts:FabOutBase->ctrl
        // Type is an MO-Defined-Type
        leaf ctrl {
            config "false";
            description "Path Controls";

            // Type is a Local-MO-Defined-Type
            type sts_PathCtrl_FabOut_ctrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }

        // Source policy tag
        // Inherited From sts:FabOutBase
        // Type is an MO-Defined-Type
        leaf sPcTag {
            config "false";
            description "TBD";

            // Type is an MO-Defined-Type
            type actrl_PcTag;
        }

        // Desired slot order for ECMP
        // Inherited From sts:FabOutBase
        // Type is an MO-Defined-Type
        leaf order {
            config "false";
            description "TBD";

            // Type is an MO-Defined-Type
            type sts_VNodeOrder;
        }

        // Fabric output port (tunnel endpoint) for pen-ultimate stage/node    Spine Proxy's vrf
        // Inherited From sts:FabOutBase
        // Type is an MO-Defined-Type
        leaf vrf {
            config "false";
            description "TBD";

            // Type is an MO-Defined-Type
            type l3_VrfName;
        }
        leaf vrfEncap {
            type string;
        }
        leaf ip {
            config "false";
            type address_Ip;
        }

        // Tap
        container tap-items {
            list Tap-list {
                config "false";
                key "port encap";

                // Added containment: Prefix=tap
                // Acquired From Package sts
                uses sts_Tap-group;
            }
        }
    }

    grouping sts_FabOutRev-group {

        // From Interface naming:Named
        // Inherited From naming:NamedObject
        // Type is an MO-Defined-Type
        leaf name {
            description "Name";

            // Type is an MO-Defined-Type
            type naming_Name;
        }

        // Control
        // Inherited From sts:Path
        // Modified by Override: sts:FabOutBase->ctrl
        // Type is an MO-Defined-Type
        leaf ctrl {
            config "false";
            description "Path Controls";

            // Type is a Local-MO-Defined-Type
            type sts_PathCtrl_FabOutRev_ctrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }

        // Source policy tag
        // Inherited From sts:FabOutBase
        // Type is an MO-Defined-Type
        leaf sPcTag {
            config "false";
            description "TBD";

            // Type is an MO-Defined-Type
            type actrl_PcTag;
        }

        // Desired slot order for ECMP
        // Inherited From sts:FabOutBase
        // Type is an MO-Defined-Type
        leaf order {
            config "false";
            description "TBD";

            // Type is an MO-Defined-Type
            type sts_VNodeOrder;
        }

        // Fabric output port (tunnel endpoint) for pen-ultimate stage/node    Spine Proxy's vrf
        // Inherited From sts:FabOutBase
        // Type is an MO-Defined-Type
        leaf vrf {
            config "false";
            description "TBD";

            // Type is an MO-Defined-Type
            type l3_VrfName;
        }
        leaf vrfEncap {
            type string;
        }
        leaf ip {
            config "false";
            type address_Ip;
        }
    }

    grouping sts_ExtIn-group {

        // From Interface naming:Named
        // Inherited From naming:NamedObject
        // Type is an MO-Defined-Type
        leaf name {
            description "Name";

            // Type is an MO-Defined-Type
            type naming_Name;
        }

        // Control
        // Inherited From sts:Path
        // Type is an MO-Defined-Type
        leaf ctrl {
            config "false";
            description "TBD";

            // Type is an MO-Defined-Type
            type sts_PathCtrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }

        // External input outgoing interface (tunnel endpoint)    Service node's vrf
        // Inherited From sts:ExtInBase
        // Type is an MO-Defined-Type
        leaf vrf {
            config "false";
            description "TBD";

            // Type is an MO-Defined-Type
            type l3_VrfName;
        }
        leaf vrfEncap {
            type string;
        }
        leaf ip {
            config "false";
            type address_Ip;
        }
    }

    grouping sts_ExtOut-group {

        // From Interface naming:Named
        // Inherited From naming:NamedObject
        // Type is an MO-Defined-Type
        leaf name {
            description "Name";

            // Type is an MO-Defined-Type
            type naming_Name;
        }

        // Control
        // Inherited From sts:Path
        // Type is an MO-Defined-Type
        leaf ctrl {
            config "false";
            description "TBD";

            // Type is an MO-Defined-Type
            type sts_PathCtrl;
        }

        // Encapsulation
        // Inherited From sts:Path
        // Type is an MO-Defined-Type
        leaf encap {
            config "false";
            description "TBD";

            // Type is an MO-Defined-Type
            type sts_PathEncap;
        }

        // Identifier
        // Inherited From sts:Path
        // Type is an MO-Defined-Type
        leaf id {
            config "false";
            description "TBD";

            // Type is an MO-Defined-Type
            type sts_PathId;
        }

        // External output outgoing interface (src tep)    Service node's vrf
        // Inherited From sts:ExtOutBase
        // Type is an MO-Defined-Type
        leaf vrf {
            config "false";
            description "TBD";

            // Type is an MO-Defined-Type
            type l3_VrfName;
        }
        leaf vrfEncap {
            type string;
        }
        leaf ip {
            config "false";
            type address_Ip;
        }
    }

    grouping maint_NodeInMaint-group {
        leaf nodeId {
            type uint32;
        }
        leaf nodeIp {
            type address_Ip;
        }
        leaf peerNodeIp {
            type address_Ip;
        }

        // Current upgrade status of node (can only be inprogress).
        // NodeInMaint is created when node upgrade status changes from
        // inqueue to inprogress and is deleted when upgrade status
        // changes from inprogress to completeok/completenok.
        // Type is an MO-Defined-Type
        leaf upgradeStatus {
            description "Upgrade Status";

            // Type is an MO-Defined-Type
            type maint_NodeUpgradeStatus;
        }
        leaf windowStartTime {
            config "false";
            type uint64;
        }
        leaf windowTimeCap {
            config "false";
            type uint64;
        }

        // Name of the maintenance policy currently being enforced on
        // the node.
        // Type is an MO-Defined-Type
        leaf polName {
            description "Maintenance Policy Name";

            // Type is an MO-Defined-Type
            type naming_Name;
        }

        // Name of the firmware being upgraded to
        // Type is an MO-Defined-Type
        leaf fwName {
            description "Firmware Policy Name";

            // Type is an MO-Defined-Type
            type firmware_Name;
        }
    }

    grouping synthetic_IfcCTestObj-group {
        leaf ifcCTestOnly {
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From synthetic:ATestObj
        // Type is an MO-Defined-Type
        leaf descr {
            description "TBD";

            // Type is an MO-Defined-Type
            type naming_Descr;
        }
        leaf propUint64 {
            type uint64;
        }
        leaf propUint32 {
            type uint32;
        }
        leaf propUByte {
            type uint8;
        }
        leaf propDate {
            type uint64;
        }
        leaf propString {
            type string;
        }

        // Inherited From synthetic:ATestObj
        // Type is an MO-Defined-Type
        leaf propBmp64 {
            description "TBD";

            // Type is an MO-Defined-Type
            type synthetic_TestBitmask64;
        }

        // Inherited From synthetic:ATestObj
        // Type is an MO-Defined-Type
        leaf propBmp8 {
            description "TBD";

            // Type is an MO-Defined-Type
            type synthetic_TestBitmask8;
        }

        // Inherited From synthetic:ATestObj
        // Type is an MO-Defined-Type
        leaf propEnum16 {
            description "TBD";

            // Type is an MO-Defined-Type
            type synthetic_TestEnum16;
        }
        leaf objDn {
            type string;
        }

        // Rel-def target from toObj
        // Inherited From synthetic:IfcTLTestObj
        // Inherited From synthetic:SwTLTestObj
        // Inherited From synthetic:IfcCTestObj
        container rttoObj-items {

            // Added containment as a singleton: Prefix=rttoObj
            // Acquired From Package synthetic
            uses synthetic_RtToObj_target-group;
        }
    }

    grouping synthetic_SwCTestObj-group {
        leaf swCTestOnly {
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From synthetic:ATestObj
        // Type is an MO-Defined-Type
        leaf descr {
            description "TBD";

            // Type is an MO-Defined-Type
            type naming_Descr;
        }
        leaf propUint64 {
            type uint64;
        }
        leaf propUint32 {
            type uint32;
        }
        leaf propUByte {
            type uint8;
        }
        leaf propDate {
            type uint64;
        }
        leaf propString {
            type string;
        }

        // Inherited From synthetic:ATestObj
        // Type is an MO-Defined-Type
        leaf propBmp64 {
            description "TBD";

            // Type is an MO-Defined-Type
            type synthetic_TestBitmask64;
        }

        // Inherited From synthetic:ATestObj
        // Type is an MO-Defined-Type
        leaf propBmp8 {
            description "TBD";

            // Type is an MO-Defined-Type
            type synthetic_TestBitmask8;
        }

        // Inherited From synthetic:ATestObj
        // Type is an MO-Defined-Type
        leaf propEnum16 {
            description "TBD";

            // Type is an MO-Defined-Type
            type synthetic_TestEnum16;
        }
        leaf objDn {
            type string;
        }

        // Rel-def from toObj
        container rstoObj-items {

            // Added containment as a singleton: Prefix=rstoObj
            // Acquired From Package synthetic
            uses synthetic_RsToObj_source-group;
        }

        // Rel-def target from toObj
        // Inherited From synthetic:IfcTLTestObj
        // Inherited From synthetic:SwTLTestObj
        // Inherited From synthetic:IfcCTestObj
        // Inherited From synthetic:SwCTestObj
        container rttoObj-items {

            // Added containment as a singleton: Prefix=rttoObj
            // Acquired From Package synthetic
            uses synthetic_RtToObj_target-group;
        }
    }

    grouping System-group {
        leaf id {
            type uint32;
        }

        // Specifies if this system is configured in standalone mode or HA pair
        // Type is an MO-Defined-Type
        leaf mode {
            config "false";
            description "Mode";

            // Type is an MO-Defined-Type
            type top_Mode;
        }
        leaf address {
            type address_Ipv4;
        }
        leaf oobMgmtAddr {
            config "false";
            type address_Ipv4;
        }
        leaf inbMgmtAddr {
            config "false";
            type address_Ipv4;
        }

        // Role of this system
        // Type is an MO-Defined-Type
        leaf role {
            description "Role";

            // Type is an MO-Defined-Type
            type top_NodeRole;
        }
        leaf currentTime {
            config "false";
            type uint64;
        }
        leaf systemUpTime {
            config "false";
            type uint64;
        }

        // Serial Number of the system
        // Type is an MO-Defined-Type
        leaf serial {
            config "false";
            description "TBD";

            // Type is an MO-Defined-Type
            type eqpt_Serial;
        }

        // POD Idenitfier
        // Type is an MO-Defined-Type
        leaf podId {
            config "false";
            description "TBD";

            // Type is an MO-Defined-Type
            type top_PodId;
        }

        // Fabric Identifier
        // Type is an MO-Defined-Type
        leaf fabricId {
            config "false";
            description "TBD";

            // Type is an MO-Defined-Type
            type top_FabricId;
        }

        // Fabric MAC Address
        // Type is an MO-Defined-Type
        leaf fabricMAC {
            config "false";
            description "TBD";

            // Type is an MO-Defined-Type
            type top_fabricMacAddr;
        }

        // Operational state of this system
        // Type is an MO-Defined-Type
        leaf state {
            config "false";
            description "TBD";

            // Type is an MO-Defined-Type
            type top_SystemSt;
        }

        // Configuration issues for this system
        // Type is an MO-Defined-Type
        leaf configIssues {
            config "false";
            description "TBD";

            // Type is an MO-Defined-Type
            type top_ConfigIssues;
        }

        // From Interface naming:Named
        // Inherited From naming:NamedObject
        // Modified by Override: top:System->name
        // Type is an MO-Defined-Type
        leaf name {
            description "Name";

            // Type is an MO-Defined-Type
            type naming_Name {
            }
        }

        // Holds bgp control plane entity information
        container bgp-items {

            // Added containment as a singleton: Prefix=bgp
            // Acquired From Package bgp
            uses bgp_Entity-group;
        }

        // Firmware Versions compatible with running version
        // Created on node to maintain list of compatible firmwares
        container sfw-items {
            list SuppFw-list {
                key "name";

                // Added containment: Prefix=sfw
                // Acquired From Package compat
                uses compat_SuppFw-group;
            }
        }

        // Capability Catalogue
        container capabilities-items {

            // Added containment as a singleton: Prefix=capabilities
            // Acquired From Package cap
            uses cap_Cat-group;
        }

        // Holds coop control plane entity information.
        container coop-items {

            // Added containment as a singleton: Prefix=coop
            // Acquired From Package coop
            uses coop_Entity-group;
        }

        container clock-items {

            // Added containment as a singleton: Prefix=clock
            // Acquired From Package datetime
            uses datetime_Clock-group;
        }

        // Datetime policy
        container time-items {

            // Added containment as a singleton: Prefix=time
            // Acquired From Package datetime
            uses datetime_ClkPol-group;
        }
        container ntpq-items {
            list Ntpq-list {
                config "false";
                key "remote";

                // Added containment: Prefix=ntpq
                // Acquired From Package datetime
                uses datetime_Ntpq-group;
            }
        }

        // Holds span global accounting information
        container acct-items {

            // Added containment as a singleton: Prefix=acct
            // Acquired From Package span
            uses span_Acct-group;
        }

        // Holds span retry information
        container retry-items {

            // Added containment as a singleton: Prefix=retry
            // Acquired From Package span
            uses span_RetryCont-group;
        }

        // Holds span manager control plane entity information
        container span-items {

            // Added containment as a singleton: Prefix=span
            // Acquired From Package span
            uses span_Entity-group;
        }

        // Holds dhcp control plane entity information
        container dhcp-items {

            // Added containment as a singleton: Prefix=dhcp
            // Acquired From Package dhcp
            uses dhcp_Entity-group;
        }

        // Holds dns control plane entity information
        container dns-items {

            // Added containment as a singleton: Prefix=dns
            // Acquired From Package dns
            uses dns_Entity-group;
        }

        container decommission-items {

            // Added containment as a singleton: Prefix=decommission
            // Acquired From Package fabric
            uses fabric_Decommission-group;
        }

        // Inband (sup) Interface
        container inb-items {
            list InbandIf-list {
                key "id";

                // Added containment: Prefix=inb
                // Acquired From Package l2
                uses l2_InbandIf-group;
            }
        }

        // Fex fabric Interface
        container ext-items {
            list ExtIf-list {
                key "id";

                // Added containment: Prefix=ext
                // Acquired From Package l2
                uses l2_ExtIf-group;
            }
        }

        // Bridged Interface
        container br-items {
            list BrIf-list {
                key "id";

                // Added containment: Prefix=br
                // Acquired From Package l2
                uses l2_BrIf-group;
            }
        }

        // Holds cdp control plane entity information
        container cdp-items {

            // Added containment as a singleton: Prefix=cdp
            // Acquired From Package cdp
            uses cdp_Entity-group;
        }

        // Holds lldp control plane entity information
        container lldp-items {

            // Added containment as a singleton: Prefix=lldp
            // Acquired From Package lldp
            uses lldp_Entity-group;
        }

        // Holds MCP control plane entity information
        container mcp-items {

            // Added containment as a singleton: Prefix=mcp
            // Acquired From Package mcp
            uses mcp_Entity-group;
        }

        // Holds VPC control plane entity information
        container vpc-items {

            // Added containment as a singleton: Prefix=vpc
            // Acquired From Package vpc
            uses vpc_Entity-group;
        }

        // Holder of PE specific information of endpoints
        container epns-items {

            // Added containment as a singleton: Prefix=epns
            // Acquired From Package fv
            uses fv_EpNs-group;
        }

        // Holds igmp control plane entity information
        container igmp-items {

            // Added containment as a singleton: Prefix=igmp
            // Acquired From Package igmp
            uses igmp_Entity-group;
        }

        // Firmware status container object for a controller. Contains objects which represent status of firmware management of a controller.
        container ctrlrfwstatuscont-items {

            // Added containment as a singleton: Prefix=ctrlrfwstatuscont
            // Acquired From Package firmware
            uses firmware_CtrlrFwStatusCont-group;
        }

        // Firmware status container object for a node. Contains objects which represent status of firmware management of a node.
        container fwstatuscont-items {

            // Added containment as a singleton: Prefix=fwstatuscont
            // Acquired From Package firmware
            uses firmware_FwStatusCont-group;
        }

        // Catalog status container object for a controller. Contains objects which represent status of catalog on a controller.
        container catfwstatuscont-items {

            // Added containment as a singleton: Prefix=catfwstatuscont
            // Acquired From Package firmware
            uses firmware_CatFwStatusCont-group;
        }

        // Holds isis control plane entity information
        container isis-items {

            // Added containment as a singleton: Prefix=isis
            // Acquired From Package isis
            uses isis_Entity-group;
        }

        // Holds lacp control plane entity information
        container lacp-items {

            // Added containment as a singleton: Prefix=lacp
            // Acquired From Package lacp
            uses lacp_Entity-group;
        }

        // Mgmt interface
        container mgmt-items {
            list MgmtIf-list {
                key "id";

                // Added containment: Prefix=mgmt
                // Acquired From Package mgmt
                uses mgmt_MgmtIf-group;
            }
        }

        container mitOper-items {

            // Added containment as a singleton: Prefix=mitOper
            // Acquired From Package mit
            uses mit_MitOperRoot-group;
        }

        // Holds snmp control plane entity information
        container snmp-items {

            // Added containment as a singleton: Prefix=snmp
            // Acquired From Package snmp
            uses snmp_Entity-group;
        }

        // Holds syslog global accounting information
        container syslogacct-items {

            // Added containment as a singleton: Prefix=syslogacct
            // Acquired From Package syslog
            uses syslog_Acct-group;
        }

        container syslog-items {

            // Added containment as a singleton: Prefix=syslog
            // Acquired From Package syslog
            uses syslog_Syslog-group;
        }

        container nat-items {

            // Added containment as a singleton: Prefix=nat
            // Acquired From Package nat
            uses nat_Entity-group;
        }

        // Command to be executed on the device
        // This object is owned by the opflexelem
        container odcreq-items {
            list ODevCmdReq-list {
                config "false";
                key "devId sessId cmdId";

                // Added containment: Prefix=odcreq
                // Acquired From Package opflex
                uses opflex_ODevCmdReq-group;
            }
        }
        container odcresp-items {
            list ODevCmdResp-list {
                config "false";
                key "devId sessId cmdId";

                // Added containment: Prefix=odcresp
                // Acquired From Package opflex
                uses opflex_ODevCmdResp-group;
            }
        }

        // Holds ospf control plane entity information
        container ospf-items {

            // Added containment as a singleton: Prefix=ospf
            // Acquired From Package ospf
            uses ospf_Entity-group;
        }

        // L2EVPN instance definition
        container evpn-items {

            // Added containment as a singleton: Prefix=evpn
            // Acquired From Package rtctrl
            uses rtctrl_L2Evpn-group;
        }

        container userext-items {

            // Added containment as a singleton: Prefix=userext
            // Acquired From Package aaa
            uses aaa_UserEp-group;
        }

        // statsmock root objects
        container mockroot-items {

            // Added containment as a singleton: Prefix=mockroot
            // Acquired From Package mock
            uses mock_MockRoot-group;
        }

        // Holds stp control plane entity information
        container stp-items {

            // Added containment as a singleton: Prefix=stp
            // Acquired From Package stp
            uses stp_Entity-group;
        }

        // Aggregate BdTable
        container bdTable-items {

            // Added containment as a singleton: Prefix=bdTable
            // Acquired From Package aggregate
            uses aggregate_BdTable-group;
        }

        // Aggregate VlanTable
        container globalConfTable-items {

            // Added containment as a singleton: Prefix=globalConfTable
            // Acquired From Package aggregate
            uses aggregate_GlobalConfTable-group;
        }

        // Aggregate InterfaceTable
        container intfTable-items {

            // Added containment as a singleton: Prefix=intfTable
            // Acquired From Package aggregate
            uses aggregate_IntfTable-group;
        }

        // Aggregate MacTable
        container macTable-items {

            // Added containment as a singleton: Prefix=macTable
            // Acquired From Package aggregate
            uses aggregate_MacTable-group;
        }

        container systemTable-items {

            // Added containment as a singleton: Prefix=systemTable
            // Acquired From Package aggregate
            uses aggregate_SystemTable-group;
        }

        // Aggregate InterfaceTable
        container tunnelIntfTable-items {

            // Added containment as a singleton: Prefix=tunnelIntfTable
            // Acquired From Package aggregate
            uses aggregate_TunnelIntfTable-group;
        }

        // Aggregate VlanTable
        container vlanTable-items {

            // Added containment as a singleton: Prefix=vlanTable
            // Acquired From Package aggregate
            uses aggregate_VlanTable-group;
        }

        // VPCDOMTAB
        container vpcDomTable-items {

            // Added containment as a singleton: Prefix=vpcDomTable
            // Acquired From Package aggregate
            uses aggregate_VpcDomTable-group;
        }

        container vrfTable-items {

            // Added containment as a singleton: Prefix=vrfTable
            // Acquired From Package aggregate
            uses aggregate_VrfTable-group;
        }

        // Holds atomic counters control plane entity information
        container ac-items {

            // Added containment as a singleton: Prefix=ac
            // Acquired From Package ac
            uses ac_Entity-group;
        }

        // Holds ACL control plane configuration
        container acl-items {

            // Added containment as a singleton: Prefix=acl
            // Acquired From Package acl
            uses acl_Entity-group;
        }

        // Holds actrl control plane entity information
        container actrl-items {

            // Added containment as a singleton: Prefix=actrl
            // Acquired From Package actrl
            uses actrl_Entity-group;
        }
        container actrlcapprov-items {
            list Prov-list {
                config "false";
                key "subj type";

                // Added containment: Prefix=actrlcapprov
                // Acquired From Package actrlcap
                uses actrlcap_Prov-group;
            }
        }

        container analytics-items {

            // Added containment as a singleton: Prefix=analytics
            // Acquired From Package analytics
            uses analytics_Entity-group;
        }

        // Holds copp control plane entity information
        container copp-items {

            // Added containment as a singleton: Prefix=copp
            // Acquired From Package copp
            uses copp_Entity-group;
        }

        // Holds glean control plane entity information
        container glean-items {

            // Added containment as a singleton: Prefix=glean
            // Acquired From Package glean
            uses glean_Entity-group;
        }

        // Holds HMM entity information
        container hmm-items {

            // Added containment as a singleton: Prefix=hmm
            // Acquired From Package hmm
            uses hmm_Entity-group;
        }

        container ipqos-items {

            // Added containment as a singleton: Prefix=ipqos
            // Acquired From Package ipqos
            uses ipqos_Entity-group;
        }

        // Holds span manager control plane entity information
        container monitor-items {

            // Added containment as a singleton: Prefix=monitor
            // Acquired From Package monitor
            uses monitor_Entity-group;
        }

        container flow-items {

            // Added containment as a singleton: Prefix=flow
            // Acquired From Package flow
            uses flow_Entity-group;
        }

        // Holds NGOAM entity information
        container ngoam-items {

            // Added containment as a singleton: Prefix=ngoam
            // Acquired From Package ngoam
            uses ngoam_Entity-group;
        }

        // Holds qos manager control plane entity information
        container qosm-items {

            // Added containment as a singleton: Prefix=qosm
            // Acquired From Package qosm
            uses qosm_Entity-group;
        }

        // Holds sts control plane entity information
        container sts-items {

            // Added containment as a singleton: Prefix=sts
            // Acquired From Package sts
            uses sts_Entity-group;
        }

        container tm-items {

            // Added containment as a singleton: Prefix=tm
            // Acquired From Package telemetry
            uses telemetry_Entity-group;
        }

        // Topology control policy container
        container topoctrl-items {

            // Added containment as a singleton: Prefix=topoctrl
            // Acquired From Package topoctrl
            uses topoctrl_Entity-group;
        }

        // Holds object tracking entity information
        container track-items {

            // Added containment as a singleton: Prefix=track
            // Acquired From Package track
            uses track_Entity-group;
        }

        container udld-items {

            // Added containment as a singleton: Prefix=udld
            // Acquired From Package udld
            uses udld_Entity-group;
        }

        // Holds Acllog entity information
        container acllog-items {

            // Added containment as a singleton: Prefix=acllog
            // Acquired From Package acllog
            uses acllog_Entity-group;
        }

        // Entity information
        container aib-items {

            // Added containment as a singleton: Prefix=aib
            // Acquired From Package aib
            uses aib_Entity-group;
        }

        // Container for all the BDs in the system.
        container bd-items {

            // Added containment as a singleton: Prefix=bd
            // Acquired From Package bd
            uses bd_Entity-group;
        }

        // Holds feature entity information
        container fm-items {

            // Added containment as a singleton: Prefix=fm
            // Acquired From Package fm
            uses fm_Entity-group;
        }

        // This object information is common to featureSet
        container fset-items {
            list FeatureSet-list {
                key "name";

                // Added containment: Prefix=fset
                // Acquired From Package fset
                uses fset_FeatureSet-group;
            }
        }

        // Container for all the interfaces in the system.
        container intf-items {

            // Added containment as a singleton: Prefix=intf
            // Acquired From Package interface
            uses interface_Entity-group;
        }

        // Holds ipv4 control plane entity information
        container ipv4-items {

            // Added containment as a singleton: Prefix=ipv4
            // Acquired From Package ipv4
            uses ipv4_Entity-group;
        }

        // Holds ipv6 control plane entity information
        container ipv6-items {

            // Added containment as a singleton: Prefix=ipv6
            // Acquired From Package ipv6
            uses ipv6_Entity-group;
        }
        container l1capprov-items {
            list Prov-list {
                config "false";
                key "subj type";

                // Added containment: Prefix=l1capprov
                // Acquired From Package l1cap
                uses l1cap_Prov-group;
            }
        }

        container ethpm-items {

            // Added containment as a singleton: Prefix=ethpm
            // Acquired From Package ethpm
            uses ethpm_Entity-group;
        }

        container breakout-items {

            // Added containment as a singleton: Prefix=breakout
            // Acquired From Package im
            uses im_Breakout-group;
        }

        container im-items {

            // Added containment as a singleton: Prefix=im
            // Acquired From Package im
            uses im_Entity-group;
        }

        container pc-items {

            // Added containment as a singleton: Prefix=pc
            // Acquired From Package pc
            uses pc_Entity-group;
        }
        container l2capprov-items {
            list Prov-list {
                config "false";
                key "subj type";

                // Added containment: Prefix=l2capprov
                // Acquired From Package l2cap
                uses l2cap_Prov-group;
            }
        }

        // L2RIB control plane entity information
        container l2rib-items {

            // Added containment as a singleton: Prefix=l2rib
            // Acquired From Package l2rib
            uses l2rib_Entity-group;
        }

        // Holds Vlan-mgr control plane entity information
        container vlanmgr-items {

            // Added containment as a singleton: Prefix=vlanmgr
            // Acquired From Package vlanmgr
            uses vlanmgr_Entity-group;
        }
        container epId-items {
            list Ep-list {
                key "epId";

                // Added containment: Prefix=epId
                // Acquired From Package nvo
                uses nvo_Ep-group;
            }
        }

        // tenant context object
        container ctx-items {
            list Ctx-list {
                key "encap";

                // Added containment: Prefix=ctx
                // Acquired From Package l3
                uses l3_Ctx-group;
            }
        }

        // Overlay instance object
        container inst-items {
            list Inst-list {
                key "name";

                // Added containment: Prefix=inst
                // Acquired From Package l3
                uses l3_Inst-group;
            }
        }
        container l3capprov-items {
            list Prov-list {
                config "false";
                key "subj type";

                // Added containment: Prefix=l3capprov
                // Acquired From Package l3cap
                uses l3cap_Prov-group;
            }
        }

        // Holds l3vm entity information
        container l3vm-items {

            // Added containment as a singleton: Prefix=l3vm
            // Acquired From Package l3vm
            uses l3vm_Entity-group;
        }

        container urib-items {

            // Added containment as a singleton: Prefix=urib
            // Acquired From Package urib
            uses urib_Entity4-group;
        }

        container u6rib-items {

            // Added containment as a singleton: Prefix=u6rib
            // Acquired From Package urib
            uses urib_Entity6-group;
        }

        // Entity information
        container uribv4-items {

            // Added containment as a singleton: Prefix=uribv4
            // Acquired From Package uribv4
            uses uribv4_Entity-group;
        }

        // Entity information
        container uribv6-items {

            // Added containment as a singleton: Prefix=uribv6
            // Acquired From Package uribv6
            uses uribv6_Entity-group;
        }

        // Connection group
        container conng-items {

            // Added containment as a singleton: Prefix=conng
            // Acquired From Package nw
            uses nw_ConnGrp-group;
        }

        // DEPRICATE: CONTROLLED VI AINSTANCES ETC. virtual device Context (vdc)    TODO: should derive from  super="naming:NamedDerivedObject"
        container vdc-items {
            list Vdc-list {
                key "id";

                // Added containment: Prefix=vdc
                // Acquired From Package nw
                uses nw_Vdc-group;
            }
        }

        // Container of processes in the system
        container procsys-items {

            // Added containment as a singleton: Prefix=procsys
            // Acquired From Package proc
            uses proc_System-group;
        }

        // Container of processes in the system
        container proc-items {

            // Added containment as a singleton: Prefix=proc
            // Acquired From Package proc
            uses proc_Entity-group;
        }
        container regr-items {
            list If-list {
                key "id";

                // Added containment: Prefix=regr
                // Acquired From Package regress
                uses regress_If-group;
            }
        }

        // Holds rpm control plane entity information
        container rpm-items {

            // Added containment as a singleton: Prefix=rpm
            // Acquired From Package rpm
            uses rpm_Entity-group;
        }

        container ipSrcIf-items {

            // Added containment as a singleton: Prefix=ipSrcIf
            // Acquired From Package srcintf
            uses srcintf_Entity-group;
        }

        // Holds sysmgr control plane entity information
        container sysmgr-items {

            // Added containment as a singleton: Prefix=sysmgr
            // Acquired From Package sysmgr
            uses sysmgr_Entity-group;
        }

        // Holds tcpudp entity information
        container tcpudp-items {

            // Added containment as a singleton: Prefix=tcpudp
            // Acquired From Package tcpudp
            uses tcpudp_Entity-group;
        }

        // Terminal MO to form the base, which means the user terminal base
        container terml-items {

            // Added containment as a singleton: Prefix=terml
            // Acquired From Package terminal
            uses terminal_Terminal-group;
        }

        // Organizes the terminal log-all specific property
        container termlog-items {

            // Added containment as a singleton: Prefix=termlog
            // Acquired From Package terminal
            uses terminal_TerminalLog-group;
        }

        // Rule for concrete test app
        container test_rule-items {
            list CRule-list {
                key "name";

                // Added containment: Prefix=test_rule
                // Acquired From Package test
                uses test_CRule-group;
            }
        }

        // Result for concrete test app
        container test_rslt_-items {
            list CRslt-list {
                config "false";
                key "name ts";

                // Added containment: Prefix=test_rslt_
                // Acquired From Package test
                uses test_CRslt-group;
            }
        }
        container tunnel-items {
            list If-list {
                key "id";

                // Added containment: Prefix=tunnel
                // Acquired From Package tunnel
                uses tunnel_If-group;
            }
        }

        // Top MO for branching everything under
        container nbmFlowsTable-items {

            // Added containment as a singleton: Prefix=nbmFlowsTable
            // Acquired From Package nbm
            uses nbm_NbmFlowsTable-group;
        }

        // Top MO for branching everything under
        container nbmStats-items {

            // Added containment as a singleton: Prefix=nbmStats
            // Acquired From Package nbm
            uses nbm_NbmStats-group;
        }

        container boot-items {

            // Added containment as a singleton: Prefix=boot
            // Acquired From Package boot
            uses boot_Boot-group;
        }

        // Hardware chassis container
        container ch-items {

            // Added containment as a singleton: Prefix=ch
            // Acquired From Package eqpt
            uses eqpt_Ch-group;
        }

        // Extension chassis
        container extch-items {
            list ExtCh-list {
                config "false";
                key "id";

                // Added containment: Prefix=extch
                // Acquired From Package eqpt
                uses eqpt_ExtCh-group;
            }
        }

        // Equipment policy container
        container ops-items {

            // Added containment as a singleton: Prefix=ops
            // Acquired From Package eqpt
            uses eqpt_Entity-group;
        }

        // Container to hold equipment capacity related
        // objects and statistics
        container eqptcapacity-items {

            // Added containment as a singleton: Prefix=eqptcapacity
            // Acquired From Package eqptcapacity
            uses eqptcapacity_Entity-group;
        }

        // Holds diag related entity information
        container diag-items {

            // Added containment as a singleton: Prefix=diag
            // Acquired From Package eqptdiag
            uses eqptdiag_Entity-group;
        }

        // Loose Node
        // @@@ Represents a External Connected Node.
        // @@@ for eg: Blade Switch attached to a Leaf Node
        container lsnode-items {
            list LooseNode-list {
                config "false";
                key "id";

                // Added containment: Prefix=lsnode
                // Acquired From Package leqpt
                uses leqpt_LooseNode-group;
            }
        }

        // Container for all the interfaces in the system.
        container pltfm-items {

            // Added containment as a singleton: Prefix=pltfm
            // Acquired From Package platform
            uses platform_Entity-group;
        }

        // Satellite manager entity information
        container satm-items {

            // Added containment as a singleton: Prefix=satm
            // Acquired From Package satm
            uses satm_Entity-group;
        }

        // Holds adjacency information
        container adjacency-items {

            // Added containment as a singleton: Prefix=adjacency
            // Acquired From Package adjacency
            uses adjacency_Entity-group;
        }

        // Holds arp control plane entity information
        container arp-items {

            // Added containment as a singleton: Prefix=arp
            // Acquired From Package arp
            uses arp_Entity-group;
        }

        // Holds bfd control plane entity information
        container bfd-items {

            // Added containment as a singleton: Prefix=bfd
            // Acquired From Package bfd
            uses bfd_Entity-group;
        }

        // Holds EIGRP control plane entity information
        container eigrp-items {

            // Added containment as a singleton: Prefix=eigrp
            // Acquired From Package eigrp
            uses eigrp_Entity-group;
        }

        // Holds HSRP control plane entity information
        container hsrp-items {

            // Added containment as a singleton: Prefix=hsrp
            // Acquired From Package hsrp
            uses hsrp_Entity-group;
        }

        // Holds icmpv4 control plane entity information
        container icmpv4-items {

            // Added containment as a singleton: Prefix=icmpv4
            // Acquired From Package icmpv4
            uses icmpv4_Entity-group;
        }

        // Holds icmpv6 control plane entity information
        container icmpv6-items {

            // Added containment as a singleton: Prefix=icmpv6
            // Acquired From Package icmpv6
            uses icmpv6_Entity-group;
        }

        // Holds igmp control plane entity information
        container igmpsnoop-items {

            // Added containment as a singleton: Prefix=igmpsnoop
            // Acquired From Package igmpsnoop
            uses igmpsnoop_Entity-group;
        }

        // Holds macsec control plane entity information
        container macsec-items {

            // Added containment as a singleton: Prefix=macsec
            // Acquired From Package macsec
            uses macsec_Entity-group;
        }

        // Holds mld control plane entity information
        container mldsnoop-items {

            // Added containment as a singleton: Prefix=mldsnoop
            // Acquired From Package mldsnoop
            uses mldsnoop_Entity-group;
        }

        // Mpls
        container mpls-items {

            // Added containment as a singleton: Prefix=mpls
            // Acquired From Package mpls
            uses mpls_Entity-group;
        }

        // Mpls
        container mplsstatic-items {

            // Added containment as a singleton: Prefix=mplsstatic
            // Acquired From Package mplsstatic
            uses mplsstatic_Entity-group;
        }

        // Label Table
        container labeltable-items {

            // Added containment as a singleton: Prefix=labeltable
            // Acquired From Package ulib
            uses ulib_LabelTable-group;
        }

        // Holds mrib entity information
        container mrib-items {

            // Added containment as a singleton: Prefix=mrib
            // Acquired From Package mrib
            uses mrib_Entity-group;
        }

        // Holds MSDP control plane entity information
        container msdp-items {

            // Added containment as a singleton: Prefix=msdp
            // Acquired From Package msdp
            uses msdp_Entity-group;
        }

        // Holds nd control plane entity information
        container nd-items {

            // Added containment as a singleton: Prefix=nd
            // Acquired From Package nd
            uses nd_Entity-group;
        }

        // Holds ospf control plane entity information
        container ospfv3-items {

            // Added containment as a singleton: Prefix=ospfv3
            // Acquired From Package ospfv3
            uses ospfv3_Entity-group;
        }

        // Holds pim control plane entity information
        container pim-items {

            // Added containment as a singleton: Prefix=pim
            // Acquired From Package pim
            uses pim_Entity-group;
        }

        // Holds vrrp control plane entity information
        container vrrp-items {

            // Added containment as a singleton: Prefix=vrrp
            // Acquired From Package vrrp
            uses vrrp_Entity-group;
        }

        // Holds vrrpv3 control plane entity information
        container vrrpv3-items {

            // Added containment as a singleton: Prefix=vrrpv3
            // Acquired From Package vrrpv3
            uses vrrpv3_Entity-group;
        }

        // Root node for scratchpad subtree
        container scrtchpdrt-items {

            // Added containment as a singleton: Prefix=scrtchpdrt
            // Acquired From Package scrtchpd
            uses scrtchpd_Root-group;
        }
        container sectl-items {
            list SwTLTestObj-list {
                key "name";

                // Added containment: Prefix=sectl
                // Acquired From Package synthetic
                uses synthetic_SwTLTestObj-group;
            }
        }

        // Container for system debug information.
        container sysdebug-items {

            // Added containment as a singleton: Prefix=sysdebug
            // Acquired From Package sysdebug
            uses sysdebug_Ep-group;
        }

        container corefiles-items {

            // Added containment as a singleton: Prefix=corefiles
            // Acquired From Package sysdebug
            uses sysdebug_CoreFileRepository-group;
        }

        // Repository for tech-support files
        container techsupportfiles-items {

            // Added containment as a singleton: Prefix=techsupportfiles
            // Acquired From Package sysdebug
            uses sysdebug_TechSupFileRepository-group;
        }
        container caggr-items {
            list AggrIf-list {
                key "id";

                // Added containment: Prefix=caggr
                // Acquired From Package cnw
                uses cnw_AggrIf-group;
            }
        }

        // Physical ethernet interface information holder
        container cphys-items {
            list PhysIf-list {
                key "id";

                // Added containment: Prefix=cphys
                // Acquired From Package cnw
                uses cnw_PhysIf-group;
            }
        }

        container action-items {

            // Added containment as a singleton: Prefix=action
            // Acquired From Package action
            uses action_LCont-group;
        }

        // Rel-def target from tsSrc
        // Inherited From top:System
        container rtdbgexpTsSrc-items {

            // Abstract containment of rtdbgexpTsSrc derived from top:System
            list RtDbgexpTsSrc-list {
                key "tDn";

                // Added containment: Prefix=rtdbgexpTsSrc
                // Acquired From Package dbgexp
                uses dbgexp_RtDbgexpTsSrc_target-group;
            }
        }

        // Rel-def target from trSrc
        // Inherited From top:System
        container rttraceroutepTrSrc-items {

            // Abstract containment of rttraceroutepTrSrc derived from top:System
            list RtTraceroutepTrSrc-list {
                key "tDn";

                // Added containment: Prefix=rttraceroutepTrSrc
                // Acquired From Package traceroutep
                uses traceroutep_RtTraceroutepTrSrc_target-group;
            }
        }

        // Rel-def target from trDst
        // Inherited From top:System
        container rttraceroutepTrDst-items {

            // Abstract containment of rttraceroutepTrDst derived from top:System
            list RtTraceroutepTrDst-list {
                key "tDn";

                // Added containment: Prefix=rttraceroutepTrDst
                // Acquired From Package traceroutep
                uses traceroutep_RtTraceroutepTrDst_target-group;
            }
        }

        // Rel-def target from fwinstlsrc
        // Inherited From top:System
        container rtmaintFwinstlsrc-items {

            // Abstract containment of rtmaintFwinstlsrc derived from top:System
            list RtMaintFwinstlsrc-list {
                key "tDn";

                // Added containment: Prefix=rtmaintFwinstlsrc
                // Acquired From Package maint
                uses maint_RtMaintFwinstlsrc_target-group;
            }
        }
    }

    grouping bgp_Entity-group {

        // Inherited From nw:Conn
        // Modified by Override: bgp:Entity->name
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per bgp instance information. There is only
        // instance supported in bgp
        container inst-items {

            // Added containment as a singleton: Prefix=inst
            // Acquired From Package bgp
            uses bgp_Inst-group;
        }
    }

    grouping bgp_Inst-group {

        // Autonomous system number
        // Type is an MO-Defined-Type
        leaf asn {
            description "Autonomous System Number";

            // Type is an MO-Defined-Type
            type bgp_AsnNum;
        }

        // BGP version
        // Type is an MO-Defined-Type
        leaf ver {
            config "false";
            description "BGP Version";

            // Type is an MO-Defined-Type
            type bgp_Ver;
        }

        // syslog level    @@@ This should come from syslog policy in IFC
        // Type is an MO-Defined-Type
        leaf syslogLvl {
            config "false";
            description "Syslog Level";

            // Type is an MO-Defined-Type
            type syslog_Level;
        }

        // Administrative port snmp trap state    @@@ This should come from SNMP policy in IFC
        // Type is an MO-Defined-Type
        leaf snmpTrapSt {
            config "false";
            description "Snmp Trap State";

            // Type is an MO-Defined-Type
            type snmp_SnmpTrapSt;
        }

        // Disable Policy Batching
        // Type is an MO-Defined-Type
        leaf disPolBatch {
            description "Disable Batching Evaluation To All Peers";

            // Type is an MO-Defined-Type
            type bgp_AdminSt;
        }
        leaf disPolBatchv4PfxLst {
            type string {
            }
        }
        leaf disPolBatchv6PfxLst {
            type string {
            }
        }
        leaf createTs {
            config "false";
            type uint64;
        }
        leaf activateTs {
            config "false";
            type uint64;
        }
        leaf waitDoneTs {
            config "false";
            type uint64;
        }

        // Memory alert level
        // Type is an MO-Defined-Type
        leaf memAlert {
            config "false";
            description "Memory Alert Level";

            // Type is an MO-Defined-Type
            type nw_MemAlertLevel;
        }

        // Number of route attribute entries learned
        // Type is an MO-Defined-Type
        leaf numRtAttrib {
            config "false";
            description "Route Attributes";

            // Type is an MO-Defined-Type
            type cap_Quant;
        }

        // Current size of attribute database
        // Type is an MO-Defined-Type
        leaf attribDbSz {
            config "false";
            description "Attribute Database Size";

            // Type is an MO-Defined-Type
            type bgp_AttribDbSz;
        }

        // Number of AS path entries learned
        // Type is an MO-Defined-Type
        leaf numAsPath {
            config "false";
            description "AS Paths";

            // Type is an MO-Defined-Type
            type cap_Quant;
        }

        // Current size of AS path database
        // Type is an MO-Defined-Type
        leaf asPathDbSz {
            config "false";
            description "AS Path Database Size";

            // Type is an MO-Defined-Type
            type bgp_AsPathDbSz;
        }

        // Enable/Disable isolate bgp
        // Type is an MO-Defined-Type
        leaf isolate {
            description "Isolate router from BGP perspective";

            // Type is an MO-Defined-Type
            type bgp_AdminSt;
        }

        // MED dampening interval
        // Type is an MO-Defined-Type
        leaf medDampIntvl {
            description "Setting med dampening interval";

            // Type is an MO-Defined-Type
            type bgp_MedIntvl;
        }
        leaf fabricSoo {
            type mtx_array_community;
        }

        // Enable/Disable flush-routes bgp
        // Type is an MO-Defined-Type
        leaf flushRoutes {
            description "Flush routes in RIB upon controlled restart";

            // Type is an MO-Defined-Type
            type bgp_AdminSt;
        }

        // Activate the affinity group activate
        // Type is an MO-Defined-Type
        leaf affGrpActv {
            description "Activate the affinity group";

            // Type is an MO-Defined-Type
            type bgp_AffGrpActv;
        }

        // Segment routing global block min range value
        // Type is an MO-Defined-Type
        leaf srgbMinLbl {
            config "false";
            description "Segment Routing Global Block Min Label";

            // Type is an MO-Defined-Type
            type bgp_SRGBRange;
        }

        // Segment routing global block max range value
        // Type is an MO-Defined-Type
        leaf srgbMaxLbl {
            config "false";
            description "Segment Routing Global Block Max Label";

            // Type is an MO-Defined-Type
            type bgp_SRGBRange;
        }

        // EPE Configured Peers
        // Type is an MO-Defined-Type
        leaf epeConfiguredPeers {
            config "false";
            description "EPE Configured Peers";

            // Type is an MO-Defined-Type
            type bgp_NumPeers;
        }

        // EPE Active Peers
        // Type is an MO-Defined-Type
        leaf epeActivePeers {
            config "false";
            description "EPE Active Peers";

            // Type is an MO-Defined-Type
            type bgp_NumPeers;
        }

        // Link-State Server
        // Type is an MO-Defined-Type
        leaf lnkStSrvr {
            config "false";
            description "EPE Link-State Server";

            // Type is an MO-Defined-Type
            type bgp_LsAdminSt;
        }

        // Link-State Client
        // Type is an MO-Defined-Type
        leaf lnkStClnt {
            config "false";
            description "EPE Link-State Server";

            // Type is an MO-Defined-Type
            type bgp_LsAdminSt;
        }

        // Inherited From nw:Conn
        // Modified by Override: bgp:Inst->name
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Modified by Override: bgp:Inst->ctrl
        // Type is an MO-Defined-Type
        // Default value handled in local MO type
        leaf ctrl {
            description "fastExtFallover";

            // Type is a Local-MO-Defined-Type
            type nw_InstCtrl_Inst_ctrl;
        }

        // Operational errors qualifier
        // Inherited From nw:CpInst
        // Type is an MO-Defined-Type
        leaf operErr {
            config "false";
            description "Operational Errors Qualifier";

            // Type is an MO-Defined-Type
            type nw_OperErrQual;
        }

        // This objects hold per bgp domain (vrf) information
        container dom-items {
            list Dom-list {
                key "name";

                // Added containment: Prefix=dom
                // Acquired From Package bgp
                uses bgp_Dom-group;
            }
        }

        // This object holds global BGP customized buffer for event-history
        container evthist-items {
            list EvtHist-list {
                key "type";

                // Added containment: Prefix=evthist
                // Acquired From Package bgp
                uses bgp_EvtHist-group;
            }
        }
    }

    grouping bgp_Dom-group {

        // Mode, (external | fabric)
        // Type is an MO-Defined-Type
        leaf mode {
            config "false";
            description "Mode";

            // Type is an MO-Defined-Type
            type bgp_Mode;
        }

        // Router id
        // Type is an MO-Defined-Type
        leaf rtrId {
            description "Router ID";

            // Type is an MO-Defined-Type
            type ip_RtrId;
        }

        // Route refelector id (cluster id) identifies the cluster
        // of the route reflector domain.
        // The regular expression allows (1) a cluster id of value between
        // 1-4294967295 or (2) an IPv4 address.
        // Type is an MO-Defined-Type
        leaf clusterId {
            description "Cluster ID";

            // Type is an MO-Defined-Type
            type bgp_ClusterId {
            }
        }

        // Keepalive interval, how often you send keepalives
        // Type is an MO-Defined-Type
        leaf kaIntvl {
            description "Keepalive Interval";

            // Type is an MO-Defined-Type
            type bgp_KaIntvl;
        }

        // Hold interval, how long you wait before you declare the
        // neighbor down
        // Type is an MO-Defined-Type
        leaf holdIntvl {
            description "Hold Interval";

            // Type is an MO-Defined-Type
            type bgp_HoldIntvl;
        }

        // Prefix Peer Timeout
        // Type is an MO-Defined-Type
        leaf pfxPeerTimeout {
            description "Prefix Peer Timeout";

            // Type is an MO-Defined-Type
            type bgp_PfxPeerTimeout;
        }

        // Prefix Peer Wait Time
        // Type is an MO-Defined-Type
        leaf pfxPeerWaitTime {
            description "Prefix Peer Wait Time";

            // Type is an MO-Defined-Type
            type bgp_PfxPeerWaitTime;
        }

        // Maximum AS limit, to discard routes that have excessive
        // AS numbers
        // Type is an MO-Defined-Type
        leaf maxAsLimit {
            description "Max AS Limit";

            // Type is an MO-Defined-Type
            type bgp_MaxAsLimit;
        }
        leaf rd {
            config "false";
            type mtx_array_community;
        }

        // Timeout for first bestpath after restart
        // Type is an MO-Defined-Type
        leaf bestPathIntvl {
            description "Bestpath Timeout";

            // Type is an MO-Defined-Type
            type bgp_BestPathIntvl;
        }

        // Update Delay Option for first bestpath timeout
        // Type is an MO-Defined-Type
        leaf always {
            description "Update Delay Option";

            // Type is an MO-Defined-Type
            type bgp_AdminSt;
        }

        // Configure connection reconnect interval in secs
        // Type is an MO-Defined-Type
        leaf reConnIntvl {
            description "Connection reconnect interval in secs";

            // Type is an MO-Defined-Type
            type bgp_ReConnectIntvl;
        }

        // Config source set by controller
        // Type is an MO-Defined-Type
        leaf cfgSrcCtrlr {
            description "Config Source set by controller";

            // Type is an MO-Defined-Type
            type bgp_AdminSt;
        }

        // Operational state
        // Type is an MO-Defined-Type
        leaf operSt {
            config "false";
            description "Operational State";

            // Type is an MO-Defined-Type
            type bgp_DomOperSt;
        }

        // Operational router id
        // Type is an MO-Defined-Type
        leaf operRtrId {
            config "false";
            description "Operational Router ID";

            // Type is an MO-Defined-Type
            type ip_RtrId;
        }
        leaf firstPeerUpTs {
            config "false";
            type uint64;
        }

        // Number of Peers
        // Type is an MO-Defined-Type
        leaf numPeers {
            config "false";
            description "Number of Peers";

            // Type is an MO-Defined-Type
            type bgp_NumPeers;
        }

        // Number of Configured Peers pending
        // Type is an MO-Defined-Type
        leaf numPeersPending {
            config "false";
            description "Number of Configured Peers pending";

            // Type is an MO-Defined-Type
            type bgp_NumPeers;
        }

        // Number of Established Peers
        // Type is an MO-Defined-Type
        leaf numEstPeers {
            config "false";
            description "Number of Established Peers";

            // Type is an MO-Defined-Type
            type bgp_NumPeers;
        }

        // VRF Id
        // Type is an MO-Defined-Type
        leaf id {
            config "false";
            description "VRF Id";

            // Type is an MO-Defined-Type
            type bgp_DomId;
        }

        // VRF Vnid
        // Type is an MO-Defined-Type
        leaf vnid {
            config "false";
            description "Dom Vnid";

            // Type is an MO-Defined-Type
            type bgp_Vnid;
        }
        leaf vtepIp {
            config "false";
            type address_Ip;
        }
        leaf vtepVirtIp {
            config "false";
            type address_Ip;
        }
        leaf routerMac {
            config "false";
            type address_Mac;
        }

        // Local ASN
        // Type is an MO-Defined-Type
        leaf localAsn {
            description "Local Asn";

            // Type is an MO-Defined-Type
            type bgp_AsnNum;
        }

        // Inherited From nw:Conn
        // Modified by Override: bgp:Dom->name
        // Modified by Override: nw:CpDom->name
        // Type is an MO-Defined-Type
        leaf name {
            description "Name";

            // Type is an MO-Defined-Type
            type naming_Name {
                length "1..64";
            }
        }

        // This object holds global BGP knobs at Dom level
        container rtctrl-items {

            // Added containment as a singleton: Prefix=rtctrl
            // Acquired From Package bgp
            uses bgp_RtCtrl-group;
        }

        // This object holds global BGP bestpath knobs at Dom level
        container pathctrl-items {

            // Added containment as a singleton: Prefix=pathctrl
            // Acquired From Package bgp
            uses bgp_PathCtrl-group;
        }

        // AS Confed are needed to club ASNs together to look like a single ASN
        container confed-items {

            // Added containment as a singleton: Prefix=confed
            // Acquired From Package bgp
            uses bgp_Confederation-group;
        }

        // This object holds per address family bgp vrf information
        container af-items {
            list DomAf-list {
                key "type";

                // Added containment: Prefix=af
                // Acquired From Package bgp
                uses bgp_DomAf-group;
            }
        }

        // This object holds Bridge Domain
        // Ethernet VPN instance information
        container bdevi-items {
            list BDEvi-list {
                key "encap";

                // Added containment: Prefix=bdevi
                // Acquired From Package bgp
                uses bgp_BDEvi-group;
            }
        }

        // This objects hold per domain graceful restart information
        container gr-items {

            // Added containment as a singleton: Prefix=gr
            // Acquired From Package bgp
            uses bgp_Gr-group;
        }

        // This object holds bgp information pertaining to a peer
        container peer-items {
            list Peer-list {
                key "addr";

                // Added containment: Prefix=peer
                // Acquired From Package bgp
                uses bgp_Peer-group;
            }
        }

        // This object holds parameters pertaining to peer templates
        container peercont-items {
            list PeerCont-list {
                key "name";

                // Added containment: Prefix=peercont
                // Acquired From Package bgp
                uses bgp_PeerCont-group;
            }
        }

        // This object holds parameters related to session templates
        container sessioncont-items {
            list SessionCont-list {
                key "name";

                // Added containment: Prefix=sessioncont
                // Acquired From Package bgp
                uses bgp_SessionCont-group;
            }
        }

        // This object holds parameters pertaining to policy templates
        container policycont-items {
            list PolicyCont-list {
                key "name";

                // Added containment: Prefix=policycont
                // Acquired From Package bgp
                uses bgp_PolicyCont-group;
            }
        }
    }

    grouping bgp_RtCtrl-group {

        // Advertise only routes that are programmed in hardware to peers
        // Type is an MO-Defined-Type
        leaf supprRt {
            description "Suppress Routes";

            // Type is an MO-Defined-Type
            type bgp_AdminSt;
        }

        // Shrink Next-Hop groups when a session goes down
        // Type is an MO-Defined-Type
        leaf withdrawNh {
            config "false";
            description "Withdraw Next Hop From All Next-Hop Groups";

            // Type is an MO-Defined-Type
            type bgp_AdminSt;
        }

        // Generate system message when any neighbor state changes
        // Type is an MO-Defined-Type
        leaf logNeighborChanges {
            description "Log Neighbor Changes";

            // Type is an MO-Defined-Type
            type bgp_AdminSt;
        }

        // Enforce the neighbor AS to be the first AS listed in the AS_path attribute for eBGP.
        // Type is an MO-Defined-Type
        leaf enforceFirstAs {
            description "Enforce First AS For EBgp";

            // Type is an MO-Defined-Type
            type bgp_AdminSt;
        }

        // Handle BGP neighbor down event
        // Type is an MO-Defined-Type
        leaf fibAccelerate {
            description "Accelerate the hardware updates for IP/IPv6 adjacencies for neighbor";

            // Type is an MO-Defined-Type
            type bgp_AdminSt;
        }
    }

    grouping bgp_PathCtrl-group {

        // Compare MED on paths from different AS
        // Type is an MO-Defined-Type
        leaf alwaysCompMed {
            description "Compare MED";

            // Type is an MO-Defined-Type
            type bgp_AdminSt;
        }

        // Allow load sharing across providers with different AS paths
        // Type is an MO-Defined-Type
        leaf asPathMultipathRelax {
            description "AS Path Relax";

            // Type is an MO-Defined-Type
            type bgp_AdminSt;
        }

        // Compare router-id for identical EBGP paths
        // Type is an MO-Defined-Type
        leaf compRtrId {
            description "Compare Router Id";

            // Type is an MO-Defined-Type
            type bgp_AdminSt;
        }

        // Compare neighbor-id for identical EBGP paths
        // Type is an MO-Defined-Type
        leaf compNbrId {
            description "Compare Neighbor Id";

            // Type is an MO-Defined-Type
            type bgp_AdminSt;
        }

        // Ignore cost communities
        // Type is an MO-Defined-Type
        leaf costCommunityIgnore {
            description "Ignore Cost Communities";

            // Type is an MO-Defined-Type
            type bgp_AdminSt;
        }

        // Compare MED for paths originated from within a confederation
        // Type is an MO-Defined-Type
        leaf medConfed {
            description "Med Confed";

            // Type is an MO-Defined-Type
            type bgp_AdminSt;
        }

        // Treat missing MED as highest MED
        // Type is an MO-Defined-Type
        leaf medMissingAsWorst {
            description "Med Missing As Worst";

            // Type is an MO-Defined-Type
            type bgp_AdminSt;
        }

        // Do not always pick the best-MED path among paths from same AS
        // Type is an MO-Defined-Type
        leaf medNonDeter {
            description "Med Non-Deterministic";

            // Type is an MO-Defined-Type
            type bgp_AdminSt;
        }
    }

    grouping bgp_Confederation-group {

        // Autonomous system number
        // Type is an MO-Defined-Type
        leaf asn {
            description "Autonomous System Number";

            // Type is an MO-Defined-Type
            type bgp_AsnNum;
        }

        // AS Confed are needed to club ASNs together to look like a single ASN
        container peer-items {
            list ConfederationPeer-list {
                key "asn";

                // Added containment: Prefix=peer
                // Acquired From Package bgp
                uses bgp_ConfederationPeer-group;
            }
        }
    }

    grouping bgp_ConfederationPeer-group {

        // Autonomous system in the confederation
        // Type is an MO-Defined-Type
        leaf asn {
            description "Autonomous System Number";

            // Type is an MO-Defined-Type
            type bgp_AsnNum;
        }
    }

    grouping bgp_DomAf-group {

        // Maximum number of equal-cost paths for load sharing
        // Type is an MO-Defined-Type
        leaf maxEcmp {
            description "Max ECMP";

            // Type is an MO-Defined-Type
            type bgp_MaxEcmp;
        }

        // Maximum number of equal-cost paths for eBGP
        // Type is an MO-Defined-Type
        leaf maxExtEcmp {
            description "Max External ECMP";

            // Type is an MO-Defined-Type
            type bgp_MaxEcmp;
        }

        // Default Value "0" Removed - out of range 100..3000
        leaf tmrBstpthDfr {
            type uint32 {
                range "100..3000";
            }
        }

        // Default Value "0" Removed - out of range 300..300000
        leaf tmrMax {
            type uint32 {
                range "300..300000";
            }
        }
        leaf tblMap {
            type string {
            }
        }

        // Configure table-map for Selective route download
        // Type is an MO-Defined-Type
        leaf tblMapFltr {
            description "Selective route download";

            // Type is an MO-Defined-Type
            type bgp_AdminSt;
        }

        // Allow VNI in Ethernet Tag field in EVPN route
        // Type is an MO-Defined-Type
        leaf vniEthTag {
            description "Allow VNI in Ethernet Tag field in EVPN route";

            // Type is an MO-Defined-Type
            type bgp_AdminSt;
        }

        // Advertise extra EVPN RT-2 with system MAC
        // Type is an MO-Defined-Type
        leaf advSysMac {
            description "Advertise extra EVPN RT-2 with system MAC";

            // Type is an MO-Defined-Type
            type bgp_AdminSt;
        }
        leaf bestPathSigTs {
            config "false";
            type uint64;
        }
        leaf bestPathCmpltTs {
            config "false";
            type uint64;
        }

        // Critical NH timeout
        // Type is an MO-Defined-Type
        // Default value handled in local MO type
        leaf critNhTimeout {
            description "Critical Next-hop Trigger-delay";

            // Type is a Local-MO-Defined-Type
            type bgp_NhTimeout_DomAf_critNhTimeout;
        }

        // Non-Critical NH timeout
        // Type is an MO-Defined-Type
        // Default value handled in local MO type
        leaf nonCritNhTimeout {
            description "Non-Critical Next-hop Trigger-delay";

            // Type is a Local-MO-Defined-Type
            type bgp_NhTimeout_DomAf_nonCritNhTimeout;
        }

        // Local BGP table version
        // Type is an MO-Defined-Type
        leaf tblVer {
            config "false";
            description "Table Version";

            // Type is an MO-Defined-Type
            type bgp_TblVer;
        }
        leaf nhRtMap {
            type string {
            }
        }

        // client-to-client route reflection
        // Type is an MO-Defined-Type
        leaf clReflection {
            description "client-to-client Reflection of routes";

            // Type is an MO-Defined-Type
            type bgp_AdminSt;
        }

        // Advertise l2vpn evpn - Originate Type 5 L2VPN EVPN route
        // correspoinding to VRF route or not
        // Type is an MO-Defined-Type
        leaf advertL2vpnEvpn {
            description "Advertise L2vpn Evpn";

            // Type is an MO-Defined-Type
            type bgp_AdvertL2vpnEvpn;
        }

        // Type is an MO-Defined-Type
        leaf allocLblAll {
            description "Allocate labels for all routes";

            // Type is an MO-Defined-Type
            type bgp_AdminSt;
        }
        leaf allocLblRtMap {
            type string {
            }
        }

        // Configure label allocation mode
        // Type is an MO-Defined-Type
        leaf lblAllocMod {
            description "per VRF label allocation mode";

            // Type is an MO-Defined-Type
            type bgp_AdminSt;
        }
        leaf retainRttRtMap {
            type string {
            }
        }

        // Retain Route Target All
        // Type is an MO-Defined-Type
        leaf retainRttAll {
            description "Retain Route Target All";

            // Type is an MO-Defined-Type
            type bgp_AdminSt;
        }
        leaf defMetric {
            type string {
            }
        }

        // Local BGP table Id
        // Type is an MO-Defined-Type
        leaf tblId {
            config "false";
            description "Table Id in hex display";

            // Type is an MO-Defined-Type
            type bgp_TblVer;
        }

        // Local BGP table state
        // Type is an MO-Defined-Type
        leaf tblSt {
            config "false";
            description "Table State";

            // Type is an MO-Defined-Type
            type bgp_DomOperSt;
        }

        // Number of Peers
        // Type is an MO-Defined-Type
        leaf numPeers {
            config "false";
            description "Number of Peers";

            // Type is an MO-Defined-Type
            type bgp_NumPeers;
        }

        // Number of Active Peers
        // Type is an MO-Defined-Type
        leaf numPeersActive {
            config "false";
            description "Number of Active Peers";

            // Type is an MO-Defined-Type
            type bgp_NumPeers;
        }

        // Number of Routes
        // Type is an MO-Defined-Type
        leaf numRoutes {
            config "false";
            description "Number of Routes";

            // Type is an MO-Defined-Type
            type bgp_NumPaths;
        }

        // Number of Paths
        // Type is an MO-Defined-Type
        leaf numPaths {
            config "false";
            description "Number of Paths";

            // Type is an MO-Defined-Type
            type bgp_NumPaths;
        }
        leaf numNetworks {
            config "false";
            type uint32;
        }
        leaf numAggregates {
            config "false";
            type uint32;
        }

        // default-information originate command
        // Type is an MO-Defined-Type
        leaf defInfOriginate {
            description "default-information originate";

            // Type is an MO-Defined-Type
            type bgp_AdminSt;
        }
        leaf defInfOrigRd {
            type mtx_array_community;
        }
        leaf defInfOrigRtt {
            type mtx_array_community;
        }

        // Dampen IGP metric
        // Type is an MO-Defined-Type
        leaf igpMetric {
            description "Dampen IGP metric-related changes";

            // Type is an MO-Defined-Type
            type bgp_igpMetric;
        }

        // Suppress inactive
        // Type is an MO-Defined-Type
        leaf supprInactive {
            description "Suppress Inactive";

            // Type is an MO-Defined-Type
            type bgp_AdminSt;
        }

        // Config source set by controller
        // Type is an MO-Defined-Type
        leaf cfgSrcCtrlr {
            description "Config Source set by controller";

            // Type is an MO-Defined-Type
            type bgp_AdminSt;
        }

        // Inherited From nw:Conn
        // Modified by Override: bgp:DomAf->name
        // Modified by Override: nw:CpDom->name
        // Type is an MO-Defined-Type
        leaf name {
            description "bgp DomAf";

            // Type is an MO-Defined-Type
            type naming_Name {
                length "1..64";
            }
        }

        // Type
        // Inherited From bgp:Af
        // Type is an MO-Defined-Type
        leaf type {
            description "Type";

            // Type is an MO-Defined-Type
            type bgp_AfT;
        }

        // This object holds policy to control vpn af
        // information for a given vrf
        container ctrl-items {
            list VpnCtrlP-list {
                key "type";

                // Added containment: Prefix=ctrl
                // Acquired From Package bgp
                uses bgp_VpnCtrlP-group;
            }
        }

        // Administrative distance is used by routers to select the best path when
        // there are two or more different routes to the same destination from
        // two different routing protocols
        container adminDist-items {

            // Added containment as a singleton: Prefix=adminDist
            // Acquired From Package bgp
            uses bgp_AdminDist-group;
        }

        // Dampening is a BGP feature to suppress unstable routes
        container dampening-items {

            // Added containment as a singleton: Prefix=dampening
            // Acquired From Package bgp
            uses bgp_DampeningCtrl-group;
        }

        // Bgp advertise to IP
        container prefix-items {
            list AdvPrefix-list {
                key "addr";

                // Added containment: Prefix=prefix
                // Acquired From Package bgp
                uses bgp_AdvPrefix-group;
            }
        }

        // This object holds per address family per bgp vrf aggregate address information
        container aggaddr-items {
            list AggAddr-list {
                key "addr";

                // Added containment: Prefix=aggaddr
                // Acquired From Package bgp
                uses bgp_AggAddr-group;
            }
        }

        // BGP Additional Paths feature allows the advertisement of multiple
        // paths through the same peering session for the same prefix without
        // the new paths implicitly replacing any previous paths
        container addlpath-items {

            // Added containment as a singleton: Prefix=addlpath
            // Acquired From Package bgp
            uses bgp_AddlPath-group;
        }

        // This object holds the bgp route information
        container nhdb-items {
            list NextHop-list {
                config "false";
                key "addr";

                // Added containment: Prefix=nhdb
                // Acquired From Package bgp
                uses bgp_NextHop-group;
            }
        }

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }

        // Show only Imported Routes
        container importedrt-items {

            // Added containment as a singleton: Prefix=importedrt
            // Acquired From Package bgp
            uses bgp_ImportedRoutes-group;
        }

        // Show only Self-originated Routes
        container selforigrt-items {

            // Added containment as a singleton: Prefix=selforigrt
            // Acquired From Package bgp
            uses bgp_SelfOrigRoutes-group;
        }

        // Show only Injected Routes
        container injectedrt-items {

            // Added containment as a singleton: Prefix=injectedrt
            // Acquired From Package bgp
            uses bgp_InjectedRoutes-group;
        }

        container exportedrt-items {

            // Added containment as a singleton: Prefix=exportedrt
            // Acquired From Package bgp
            uses bgp_ExportedRoutes-group;
        }

        // Show only Received Paths Routes
        container rcvdpathsrt-items {

            // Added containment as a singleton: Prefix=rcvdpathsrt
            // Acquired From Package bgp
            uses bgp_RcvdPathsRoutes-group;
        }

        // This object holds the bgp routes matching route-map
        container rtmap-items {
            list RtMapRoutes-list {
                config "false";
                key "name";

                // Added containment: Prefix=rtmap
                // Acquired From Package bgp
                uses bgp_RtMapRoutes-group;
            }
        }

        // This object holds the bgp routes matching filter-list
        container fltrlist-items {
            list FltrListRoutes-list {
                config "false";
                key "name";

                // Added containment: Prefix=fltrlist
                // Acquired From Package bgp
                uses bgp_FltrListRoutes-group;
            }
        }

        // This object holds the bgp routes matching prefix-list
        container pfxlist-items {
            list PfxListRoutes-list {
                config "false";
                key "name";

                // Added containment: Prefix=pfxlist
                // Acquired From Package bgp
                uses bgp_PfxListRoutes-group;
            }
        }

        // Show only Dampening Paths Routes
        container damppathsrt-items {

            // Added containment as a singleton: Prefix=damppathsrt
            // Acquired From Package bgp
            uses bgp_DampPathsRoutes-group;
        }

        // Show only Dampening History Paths Routes
        container damphstpathsrt-items {

            // Added containment as a singleton: Prefix=damphstpathsrt
            // Acquired From Package bgp
            uses bgp_DampHistPathsRoutes-group;
        }

        // Show Routes by route-type
        container rttype-items {
            list RtTypeRoutes-list {
                config "false";
                key "rtType";

                // Added containment: Prefix=rttype
                // Acquired From Package bgp
                uses bgp_RtTypeRoutes-group;
            }
        }

        // Show Evpn routes by vni-id
        container vnid-items {
            list EvpnVnIdRoutes-list {
                config "false";
                key "vnid";

                // Added containment: Prefix=vnid
                // Acquired From Package bgp
                uses bgp_EvpnVnIdRoutes-group;
            }
        }

        // Show Evpn routes by mac address
        container mac-items {
            list EvpnMacAddrRoutes-list {
                config "false";
                key "macaddr";

                // Added containment: Prefix=mac
                // Acquired From Package bgp
                uses bgp_EvpnMacAddrRoutes-group;
            }
        }

        // Show routes by RD
        container rd-items {
            list RdRoutes-list {
                config "false";
                key "rd";

                // Added containment: Prefix=rd
                // Acquired From Package bgp
                uses bgp_RdRoutes-group;
            }
        }

        // Show routes by exact Prefix
        container pfx-items {
            list PfxRoutes-list {
                config "false";
                key "pfx";

                // Added containment: Prefix=pfx
                // Acquired From Package bgp
                uses bgp_PfxRoutes-group;
            }
        }

        // Show Evpn routes by Ethernet Segment
        container esid-items {
            list EvpnEsRoutes-list {
                config "false";
                key "esid";

                // Added containment: Prefix=esid
                // Acquired From Package bgp
                uses bgp_EvpnEsRoutes-group;
            }
        }

        // Show nexthop routes
        container nh-items {
            list NextHopRoutes-list {
                config "false";
                key "pfx";

                // Added containment: Prefix=nh
                // Acquired From Package bgp
                uses bgp_NextHopRoutes-group;
            }
        }

        // This objects holds default route leak policy,
        // this is not needed for FCS in our solution
        container defrtleak-items {

            // Added containment as a singleton: Prefix=defrtleak
            // Acquired From Package bgp
            uses bgp_DefRtLeakP-group;
        }

        // Inter protocol route leak policy. This defines distribution
        // of routes from one protocol to another protocol
        container interleak-items {
            list InterLeakP-list {
                key "proto inst";

                // Added containment: Prefix=interleak
                // Acquired From Package bgp
                uses bgp_InterLeakP-group;
            }
        }

        // Inject route leak policy route map
        container injname-items {
            list InjLeakP-list {
                key "name rtMap";

                // Added containment: Prefix=injname
                // Acquired From Package bgp
                uses bgp_InjLeakP-group;
            }
        }

        // Route target policy
        container rttp-items {
            list RttP-list {
                config "false";
                key "type";

                // Added containment: Prefix=rttp
                // Acquired From Package bgp
                uses bgp_RttP-group;
            }
        }
    }

    grouping bgp_VpnCtrlP-group {

        // Inherited From nw:Conn
        // Modified by Override: nw:CpDom->name
        // Type is an MO-Defined-Type
        leaf name {
            description "Name";

            // Type is an MO-Defined-Type
            type naming_Name {
                length "1..64";
            }
        }

        // Type
        // Inherited From bgp:Af
        // Type is an MO-Defined-Type
        leaf type {
            description "Type";

            // Type is an MO-Defined-Type
            type bgp_AfT;
        }

        // Route policy holds all route targets and route controls
        container rtp-items {
            list RtP-list {
                config "false";
                key "type";

                // Added containment: Prefix=rtp
                // Acquired From Package bgp
                uses bgp_RtP-group;
            }
        }
    }

    grouping bgp_RtP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From bgp:ARtP
        // Type is an MO-Defined-Type
        leaf type {
            config "false";
            description "Type";

            // Type is an MO-Defined-Type
            type bgp_RttPType;
        }
        leaf operRttAuto {
            type mtx_array_community;
        }

        // List of route targets
        container ent-items {
            list RttEntry-list {
                config "false";
                key "rtt";

                // Added containment: Prefix=ent
                // Acquired From Package bgp
                uses bgp_RttEntry-group;
            }
        }
    }

    grouping bgp_RttEntry-group {
        leaf rtt {
            config "false";
            type mtx_array_community;
        }

        // Route target admin state
        // Type is an MO-Defined-Type
        leaf adminSt {
            config "false";
            description "Administrative State";

            // Type is an MO-Defined-Type
            type bgp_AdminSt;
        }
    }

    grouping bgp_AdminDist-group {

        // eBGP Distance
        // Type is an MO-Defined-Type
        leaf eDist {
            description "eBGP Distance";

            // Type is an MO-Defined-Type
            type bgp_Distance;
        }

        // iBGP Distance
        // Type is an MO-Defined-Type
        leaf iDist {
            description "iBGP Distance";

            // Type is an MO-Defined-Type
            type bgp_Distance;
        }

        // Local Distance
        // Type is an MO-Defined-Type
        leaf localDist {
            description "Local Distance";

            // Type is an MO-Defined-Type
            type bgp_Distance;
        }
    }

    grouping bgp_DampeningCtrl-group {
        leaf rtMap {
            type string {
            }
        }

        // Dampening decay half life
        // Type is an MO-Defined-Type
        leaf halfLife {
            description "Decay Half Life";

            // Type is an MO-Defined-Type
            type rtmap_DampHalfLife;
        }

        // Dampening reuse limit
        // Type is an MO-Defined-Type
        leaf reuse {
            description "Reuse Limit";

            // Type is an MO-Defined-Type
            type rtmap_DampReuse;
        }

        // Dampening suppress limit
        // Type is an MO-Defined-Type
        leaf suppress {
            description "Suppress Limit";

            // Type is an MO-Defined-Type
            type rtmap_DampSuppress;
        }
        leaf maxSupprPenalty {
            config "false";
            type uint32;
        }

        // Dampening max suppress time
        // Type is an MO-Defined-Type
        leaf maxSuppressTime {
            description "Max Suppress Time";

            // Type is an MO-Defined-Type
            type rtmap_DampMaxSuppressTime;
        }
    }

    grouping bgp_AdvPrefix-group {
        leaf addr {
            type address_Ip;
        }
        leaf rtMap {
            type string {
            }
        }
    }

    grouping bgp_AggAddr-group {
        leaf addr {
            type address_Ip;
        }
        leaf adverMap {
            type string {
            }
        }
        leaf attrMap {
            type string {
            }
        }

        // Generate AS set path info and community info from contributing paths
        // Type is an MO-Defined-Type
        leaf asSet {
            description "AS-SET";

            // Type is an MO-Defined-Type
            type bgp_AsSet;
        }

        // Aggregate Address Summary only
        // Type is an MO-Defined-Type
        leaf summaryOnly {
            description "Summary only";

            // Type is an MO-Defined-Type
            type bgp_SummaryOnly;
        }
        leaf supprMap {
            type string {
            }
        }
    }

    grouping bgp_AddlPath-group {

        // Capability
        // Type is an MO-Defined-Type
        leaf capability {
            description "Capability";

            // Type is an MO-Defined-Type
            type bgp_AddlPathCapT;
        }
        leaf rtMap {
            type string {
            }
        }
    }

    grouping bgp_NextHop-group {
        leaf addr {
            config "false";
            type address_Ip;
        }

        // How many routes pointing to this nexthop?
        // Type is an MO-Defined-Type
        leaf rtRefCount {
            config "false";
            description "Refernce Count";

            // Type is an MO-Defined-Type
            type cap_Quant;
        }

        // IGP metric
        // Type is an MO-Defined-Type
        leaf igpMetric {
            config "false";
            description "IGP Metric";

            // Type is an MO-Defined-Type
            type bgp_Metric;
        }

        // Flags
        // Type is an MO-Defined-Type
        leaf flags {
            config "false";
            description "Flags";

            // Type is an MO-Defined-Type
            type bgp_NhFlags;
        }

        // Last resolved timestamp
        // Type is an MO-Defined-Type
        leaf lastResolv {
            config "false";
            description "Last Resolved Timestamp";

            // Type is an MO-Defined-Type
            type bgp_LastResolvTs;
        }
        leaf resolvedRt {
            config "false";
            type address_Ip;
        }

        // IGP Preference
        // Type is an MO-Defined-Type
        leaf igpPref {
            config "false";
            description "IGP Preference";

            // Type is an MO-Defined-Type
            type bgp_IgpPref;
        }

        // IGP Route type
        // Type is an MO-Defined-Type
        leaf igpRtType {
            config "false";
            description "IGP Route Type";

            // Type is an MO-Defined-Type
            type bgp_IgpRtType;
        }

        // Next advertised timestamp
        // Type is an MO-Defined-Type
        leaf nextAdv {
            config "false";
            description "Next Advertised Timestamp";

            // Type is an MO-Defined-Type
            type bgp_NextAdvTs;
        }

        // Active RNH Epoch
        // Type is an MO-Defined-Type
        leaf activeRnhEpoch {
            config "false";
            description "Active RNH Epoch";

            // Type is an MO-Defined-Type
            type bgp_RnhEpoch;
        }

        // Pending RNH Epoch
        // Type is an MO-Defined-Type
        leaf pendingRnhEpoch {
            config "false";
            description "Pending RNH Epoch";

            // Type is an MO-Defined-Type
            type bgp_RnhEpoch;
        }

        // Inherited From nw:Conn
        // Modified by Override: nw:Db->name
        // Type is an MO-Defined-Type
        leaf name {
            description "Name";

            // Type is an MO-Defined-Type
            type naming_Name {
                length "1..64";
            }
        }
        container attnh-items {
            list AttNextHop-list {
                config "false";
                key "addr";

                // Added containment: Prefix=attnh
                // Acquired From Package bgp
                uses bgp_AttNextHop-group;
            }
        }
    }

    grouping bgp_AttNextHop-group {
        leaf addr {
            config "false";
            type address_Ip;
        }

        // Attached NH interface
        // Type is an MO-Defined-Type
        leaf ifId {
            config "false";
            description "Attached Interface";

            // Type is an MO-Defined-Type
            type nw_IfId;
        }
    }

    grouping bgp_Route-group {
        leaf rd {
            config "false";
            type mtx_array_community;
        }

        // Inherited From nw:Conn
        // Modified by Override: nw:Db->name
        // Type is an MO-Defined-Type
        leaf name {
            description "Name";

            // Type is an MO-Defined-Type
            type naming_Name {
                length "1..64";
            }
        }

        // Version of the route
        // Inherited From bgp:ARoute
        // Type is an MO-Defined-Type
        leaf ver {
            config "false";
            description "Version";

            // Type is an MO-Defined-Type
            type bgp_RtVer;
        }

        // Route flags
        // Inherited From bgp:ARoute
        // Type is an MO-Defined-Type
        leaf rtFlags {
            config "false";
            description "Flags";

            // Type is an MO-Defined-Type
            type bgp_RtFlags;
        }
        leaf numPaths {
            config "false";
            type uint32;
        }

        // Bestpath Id
        // Inherited From bgp:ARoute
        // Type is an MO-Defined-Type
        leaf bestPathId {
            config "false";
            description "Bestpath Id";

            // Type is an MO-Defined-Type
            type bgp_PathId;
        }
        leaf pfx {
            config "false";
            type address_Ip;
        }

        // This object holds the bgp AS path information
        container path-items {
            list Path-list {
                config "false";
                key "peer id nh";

                // Added containment: Prefix=path
                // Acquired From Package bgp
                uses bgp_Path-group;
            }
        }
    }

    grouping bgp_Path-group {
        leaf peer {
            config "false";
            type address_Ip;
        }

        // Path id
        // Type is an MO-Defined-Type
        leaf id {
            config "false";
            description "ID";

            // Type is an MO-Defined-Type
            type bgp_PathId;
        }
        leaf nh {
            config "false";
            type address_Ip;
        }

        // Nexthop metric
        // Type is an MO-Defined-Type
        leaf nhMetric {
            config "false";
            description "Nexthop Metric";

            // Type is an MO-Defined-Type
            type bgp_Metric;
        }

        // Path type
        // Type is an MO-Defined-Type
        leaf type {
            config "false";
            description "Type";

            // Type is an MO-Defined-Type
            type bgp_PathT;
        }

        // Path status
        // Type is an MO-Defined-Type
        leaf operSt {
            config "false";
            description "Operational State";

            // Type is an MO-Defined-Type
            type bgp_PathSt;
        }

        // Path flags
        // Type is an MO-Defined-Type
        leaf flags {
            config "false";
            description "Flags";

            // Type is an MO-Defined-Type
            type bgp_PathFlags;
        }

        // Origin
        // Type is an MO-Defined-Type
        leaf origin {
            config "false";
            description "Origin";

            // Type is an MO-Defined-Type
            type bgp_Origin;
        }

        // Metric
        // Type is an MO-Defined-Type
        leaf metric {
            config "false";
            description "Metric";

            // Type is an MO-Defined-Type
            type rtmap_Metric;
        }

        // Local preference
        // Type is an MO-Defined-Type
        leaf localPref {
            config "false";
            description "Local Preference";

            // Type is an MO-Defined-Type
            type rtmap_LocalPref;
        }

        // Weight
        // Type is an MO-Defined-Type
        leaf weight {
            config "false";
            description "Weight";

            // Type is an MO-Defined-Type
            type rtmap_Weight;
        }
        leaf aggr {
            config "false";
            type address_Ip;
        }

        // Aggregator AS
        // Type is an MO-Defined-Type
        leaf aggrAs {
            config "false";
            description "Aggregator ASN";

            // Type is an MO-Defined-Type
            type bgp_AsnNum;
        }
        leaf importedRd {
            config "false";
            type mtx_array_community;
        }
        leaf unknownAttrData {
            config "false";
            type string;
        }

        // Unknown Attribute Data
        // Type is an MO-Defined-Type
        leaf unknownAttrLen {
            config "false";
            description "Unknown Attribute Length";

            // Type is an MO-Defined-Type
            type bgp_UnknownAttrLen;
        }
        leaf regComm {
            config "false";
            type string;
        }
        leaf extComm {
            config "false";
            type string;
        }
        leaf asPath {
            config "false";
            type string;
        }
        leaf rcvdLbl {
            config "false";
            type string;
        }
        leaf originatorId {
            config "false";
            type address_Ip;
        }
        leaf clusterLst {
            config "false";
            type string;
        }
        leaf peerRtrId {
            config "false";
            type string;
        }

        // This object holds the bgp path AS segment information
        container seg-items {
            list AsSeg-list {
                config "false";
                key "order";

                // Added containment: Prefix=seg
                // Acquired From Package bgp
                uses bgp_AsSeg-group;
            }
        }
        container rcomm-items {
            list RegComm-list {
                config "false";
                key "community";

                // Added containment: Prefix=rcomm
                // Acquired From Package bgp
                uses bgp_RegComm-group;
            }
        }

        container ecomm-items {

            // Added containment as a singleton: Prefix=ecomm
            // Acquired From Package bgp
            uses bgp_ExtComm-group;
        }

        // Link-state Attribute
        container lnkstattr-items {

            // Added containment as a singleton: Prefix=lnkstattr
            // Acquired From Package bgp
            uses bgp_LnkStAttr-group;
        }

        // Prefix-SID Attribute
        container pfxsid-items {

            // Added containment as a singleton: Prefix=pfxsid
            // Acquired From Package bgp
            uses bgp_PfxSidAttr-group;
        }

        // PMSI Tunnel Attribute
        container pmsi-items {

            // Added containment as a singleton: Prefix=pmsi
            // Acquired From Package bgp
            uses bgp_PmsiTunAttr-group;
        }
    }

    grouping bgp_AsSeg-group {

        // type
        // Type is an MO-Defined-Type
        leaf type {
            config "false";
            description "Type";

            // Type is an MO-Defined-Type
            type bgp_AsSegT;
        }

        // Order
        // Type is an MO-Defined-Type
        leaf order {
            config "false";
            description "Order";

            // Type is an MO-Defined-Type
            type bgp_Order;
        }

        // This object holds the AS segment items
        container asn-items {
            list AsItem-list {
                config "false";
                key "order";

                // Added containment: Prefix=asn
                // Acquired From Package bgp
                uses bgp_AsItem-group;
            }
        }
    }

    grouping bgp_AsItem-group {

        // Order
        // Type is an MO-Defined-Type
        leaf order {
            config "false";
            description "Order";

            // Type is an MO-Defined-Type
            type bgp_Order;
        }

        // AS number
        // Type is an MO-Defined-Type
        leaf asn {
            config "false";
            description "Autonomous System Number";

            // Type is an MO-Defined-Type
            type bgp_AsnNum;
        }
    }

    grouping bgp_RegComm-group {
        leaf community {
            config "false";
            type mtx_array_community;
        }
    }

    grouping bgp_ExtComm-group {
        leaf encap {
            config "false";
            type string;
        }
        leaf rtrMac {
            config "false";
            type address_Mac;
        }

        // Extended community route-target attribute entry
        container rt-items {
            list ExtCommRt-list {
                config "false";
                key "community";

                // Added containment: Prefix=rt
                // Acquired From Package bgp
                uses bgp_ExtCommRt-group;
            }
        }
    }

    grouping bgp_ExtCommRt-group {
        leaf community {
            config "false";
            type mtx_array_community;
        }
    }

    grouping bgp_LnkStAttr-group {

        // Attribute Type
        // Type is an MO-Defined-Type
        leaf attrType {
            config "false";
            description "Link-state Attribute type";

            // Type is an MO-Defined-Type
            type bgp_LsNlriType;
        }

        // Node attribute flags
        // Type is an MO-Defined-Type
        leaf nodeAttrFlags {
            config "false";
            description "Link-state Node TLV attribute flags";

            // Type is an MO-Defined-Type
            type bgp_NodeLsAttrFlags;
        }

        // Link attribute TLV flags
        // Type is an MO-Defined-Type
        leaf lnkAttrFlags {
            config "false";
            description "Link-state Link TLV attribute flags";

            // Type is an MO-Defined-Type
            type bgp_LnkLsAttrFlags;
        }

        // Node attribute flags
        // Type is an MO-Defined-Type
        leaf pfxAttrFlags {
            config "false";
            description "Link-state Prefix TLV attribute flags";

            // Type is an MO-Defined-Type
            type bgp_PfxLsAttrFlags;
        }
        leaf attrLen {
            config "false";
            type uint16;
        }

        // Link-state Attribute Entry
        container tlv-items {
            list LnkStAttrEntry-list {
                key "type";

                // Added containment: Prefix=tlv
                // Acquired From Package bgp
                uses bgp_LnkStAttrEntry-group;
            }
        }
    }

    grouping bgp_LnkStAttrEntry-group {

        // Type
        // Type is an MO-Defined-Type
        leaf type {
            description "Link-state TLV code point";

            // Type is an MO-Defined-Type
            type bgp_LsAttrEntryType;
        }
        leaf len {
            config "false";
            type uint16;
        }
        leaf val {
            config "false";
            type string;
        }
    }

    grouping bgp_PfxSidAttr-group {
        leaf pfxSidAttrLen {
            config "false";
            type uint16;
        }

        // Prefix-SID Attribute Entry
        container tlv-items {
            list PfxSidAttrEntry-list {
                key "type";

                // Added containment: Prefix=tlv
                // Acquired From Package bgp
                uses bgp_PfxSidAttrEntry-group;
            }
        }
    }

    grouping bgp_PfxSidAttrEntry-group {

        // Type
        // Type is an MO-Defined-Type
        leaf type {
            description "Link-state TLV code point";

            // Type is an MO-Defined-Type
            type bgp_PfxSidAttrEntryType;
        }
        leaf len {
            config "false";
            type uint16;
        }
        leaf val {
            config "false";
            type string;
        }
    }

    grouping bgp_PmsiTunAttr-group {
        leaf flags {
            config "false";

            // bits- Using string
            type string;
        }

        // Tunnel Type
        // Type is an MO-Defined-Type
        leaf tunType {
            config "false";
            description "PMSI Tunnel Type";

            // Type is an MO-Defined-Type
            type bgp_PmsiTunType;
        }
        leaf lbl {
            config "false";
            type uint32;
        }
        leaf tunId {
            config "false";
            type address_Ip;
        }
    }

    grouping bgp_VpnRoute-group {
        leaf rd {
            config "false";
            type mtx_array_community;
        }

        // Inherited From nw:Conn
        // Modified by Override: nw:Db->name
        // Type is an MO-Defined-Type
        leaf name {
            description "Name";

            // Type is an MO-Defined-Type
            type naming_Name {
                length "1..64";
            }
        }

        // Version of the route
        // Inherited From bgp:ARoute
        // Type is an MO-Defined-Type
        leaf ver {
            config "false";
            description "Version";

            // Type is an MO-Defined-Type
            type bgp_RtVer;
        }

        // Route flags
        // Inherited From bgp:ARoute
        // Type is an MO-Defined-Type
        leaf rtFlags {
            config "false";
            description "Flags";

            // Type is an MO-Defined-Type
            type bgp_RtFlags;
        }
        leaf numPaths {
            config "false";
            type uint32;
        }

        // Bestpath Id
        // Inherited From bgp:ARoute
        // Type is an MO-Defined-Type
        leaf bestPathId {
            config "false";
            description "Bestpath Id";

            // Type is an MO-Defined-Type
            type bgp_PathId;
        }
        leaf pfx {
            config "false";
            type address_Ip;
        }

        // This object holds the bgp AS path information
        container path-items {
            list Path-list {
                config "false";
                key "peer id nh";

                // Added containment: Prefix=path
                // Acquired From Package bgp
                uses bgp_Path-group;
            }
        }
    }

    grouping bgp_LblRoute-group {
        leaf rd {
            config "false";
            type mtx_array_community;
        }

        // Labeled address-family route flags
        // Type is an MO-Defined-Type
        leaf rtLblAfFlags {
            config "false";
            description "Labeled address-family route flags";

            // Type is an MO-Defined-Type
            type bgp_RtLblAfFlags;
        }
        leaf rtLblAfVer {
            config "false";
            type uint32;
        }

        // Local label
        // Type is an MO-Defined-Type
        leaf locLbl {
            config "false";
            description "Local label";

            // Type is an MO-Defined-Type
            type bgp_Lbl;
        }
        leaf pfxLblHoldDownDelTs {
            config "false";
            type uint64;
        }

        // Inherited From nw:Conn
        // Modified by Override: nw:Db->name
        // Type is an MO-Defined-Type
        leaf name {
            description "Name";

            // Type is an MO-Defined-Type
            type naming_Name {
                length "1..64";
            }
        }

        // Version of the route
        // Inherited From bgp:ARoute
        // Type is an MO-Defined-Type
        leaf ver {
            config "false";
            description "Version";

            // Type is an MO-Defined-Type
            type bgp_RtVer;
        }

        // Route flags
        // Inherited From bgp:ARoute
        // Type is an MO-Defined-Type
        leaf rtFlags {
            config "false";
            description "Flags";

            // Type is an MO-Defined-Type
            type bgp_RtFlags;
        }
        leaf numPaths {
            config "false";
            type uint32;
        }

        // Bestpath Id
        // Inherited From bgp:ARoute
        // Type is an MO-Defined-Type
        leaf bestPathId {
            config "false";
            description "Bestpath Id";

            // Type is an MO-Defined-Type
            type bgp_PathId;
        }
        leaf pfx {
            config "false";
            type address_Ip;
        }

        // This object holds the bgp AS path information
        container path-items {
            list Path-list {
                config "false";
                key "peer id nh";

                // Added containment: Prefix=path
                // Acquired From Package bgp
                uses bgp_Path-group;
            }
        }
    }

    grouping bgp_LnkStRoute-group {
        leaf pfx {
            config "false";
            type string;
        }

        // NLRI Type
        // Type is an MO-Defined-Type
        leaf nlriType {
            config "false";
            description "Link-state NLRI type";

            // Type is an MO-Defined-Type
            type bgp_LsNlriType;
        }

        // Protocol Id
        // Type is an MO-Defined-Type
        leaf protoId {
            config "false";
            description "Link-state NLRI Protocol ID";

            // Type is an MO-Defined-Type
            type bgp_LsProtoId;
        }

        // Inherited From nw:Conn
        // Modified by Override: nw:Db->name
        // Type is an MO-Defined-Type
        leaf name {
            description "Name";

            // Type is an MO-Defined-Type
            type naming_Name {
                length "1..64";
            }
        }

        // Version of the route
        // Inherited From bgp:ARoute
        // Type is an MO-Defined-Type
        leaf ver {
            config "false";
            description "Version";

            // Type is an MO-Defined-Type
            type bgp_RtVer;
        }

        // Route flags
        // Inherited From bgp:ARoute
        // Type is an MO-Defined-Type
        leaf rtFlags {
            config "false";
            description "Flags";

            // Type is an MO-Defined-Type
            type bgp_RtFlags;
        }
        leaf numPaths {
            config "false";
            type uint32;
        }

        // Bestpath Id
        // Inherited From bgp:ARoute
        // Type is an MO-Defined-Type
        leaf bestPathId {
            config "false";
            description "Bestpath Id";

            // Type is an MO-Defined-Type
            type bgp_PathId;
        }

        // This object holds the bgp AS path information
        container path-items {
            list Path-list {
                config "false";
                key "peer id nh";

                // Added containment: Prefix=path
                // Acquired From Package bgp
                uses bgp_Path-group;
            }
        }
    }

    grouping bgp_EvpnRoute-group {
        leaf rd {
            config "false";
            type mtx_array_community;
        }
        leaf pfx {
            config "false";
            type string;
        }

        // EVPN route-type
        // Type is an MO-Defined-Type
        leaf rtType {
            config "false";
            description "EVPN route-type";

            // Type is an MO-Defined-Type
            type bgp_EvpnRtType;
        }

        // Inherited From nw:Conn
        // Modified by Override: nw:Db->name
        // Type is an MO-Defined-Type
        leaf name {
            description "Name";

            // Type is an MO-Defined-Type
            type naming_Name {
                length "1..64";
            }
        }

        // Version of the route
        // Inherited From bgp:ARoute
        // Type is an MO-Defined-Type
        leaf ver {
            config "false";
            description "Version";

            // Type is an MO-Defined-Type
            type bgp_RtVer;
        }

        // Route flags
        // Inherited From bgp:ARoute
        // Type is an MO-Defined-Type
        leaf rtFlags {
            config "false";
            description "Flags";

            // Type is an MO-Defined-Type
            type bgp_RtFlags;
        }
        leaf numPaths {
            config "false";
            type uint32;
        }

        // Bestpath Id
        // Inherited From bgp:ARoute
        // Type is an MO-Defined-Type
        leaf bestPathId {
            config "false";
            description "Bestpath Id";

            // Type is an MO-Defined-Type
            type bgp_PathId;
        }

        // This object holds the bgp AS path information
        container path-items {
            list Path-list {
                config "false";
                key "peer id nh";

                // Added containment: Prefix=path
                // Acquired From Package bgp
                uses bgp_Path-group;
            }
        }
    }

    grouping bgp_ImportedRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
    }

    grouping bgp_SelfOrigRoutes-group {

        // This object holds the bgp route information
        container rt-items {
            list Route-list {
                config "false";
                key "pfx";

                // Added containment: Prefix=rt
                // Acquired From Package bgp
                uses bgp_Route-group;
            }
        }
    }

    grouping bgp_InjectedRoutes-group {

        // This object holds the bgp route information
        container rt-items {
            list Route-list {
                config "false";
                key "pfx";

                // Added containment: Prefix=rt
                // Acquired From Package bgp
                uses bgp_Route-group;
            }
        }
    }

    grouping bgp_ExportedRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
    }

    grouping bgp_RcvdPathsRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_RtMapRoutes-group {
        leaf name {
            config "false";
            type string {
            }
        }

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_FltrListRoutes-group {
        leaf name {
            config "false";
            type string {
            }
        }

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_PfxListRoutes-group {
        leaf name {
            config "false";
            type string {
            }
        }

        // This object holds the bgp route information
        container rt-items {
            list Route-list {
                config "false";
                key "pfx";

                // Added containment: Prefix=rt
                // Acquired From Package bgp
                uses bgp_Route-group;
            }
        }
    }

    grouping bgp_DampPathsRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_DampHistPathsRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_RtTypeRoutes-group {

        // EVPN and Linkstate route-type
        // Type is an MO-Defined-Type
        leaf rtType {
            config "false";
            description "EVPN route-type";

            // Type is an MO-Defined-Type
            type bgp_EvpnRtType;
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_EvpnVnIdRoutes-group {

        // EVPN route-type
        // Type is an MO-Defined-Type
        leaf vnid {
            config "false";
            description "EVPN vnid";

            // Type is an MO-Defined-Type
            type bgp_Vnid;
        }

        // EVPN route
        container evpnrt-items {
            list EvpnRoute-list {
                config "false";
                key "pfx rd";

                // Added containment: Prefix=evpnrt
                // Acquired From Package bgp
                uses bgp_EvpnRoute-group;
            }
        }
    }

    grouping bgp_EvpnMacAddrRoutes-group {
        leaf macaddr {
            config "false";
            type address_Mac;
        }

        // EVPN route
        container evpnrt-items {
            list EvpnRoute-list {
                config "false";
                key "pfx rd";

                // Added containment: Prefix=evpnrt
                // Acquired From Package bgp
                uses bgp_EvpnRoute-group;
            }
        }
    }

    grouping bgp_RdRoutes-group {
        leaf rd {
            config "false";
            type mtx_array_community;
        }

        // This object holds the bgp vpn route information
        container vpnrt-items {
            list VpnRoute-list {
                config "false";
                key "pfx rd";

                // Added containment: Prefix=vpnrt
                // Acquired From Package bgp
                uses bgp_VpnRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_PfxRoutes-group {
        leaf pfx {
            config "false";
            type address_Ip;
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_EvpnEsRoutes-group {
        leaf esid {
            config "false";
            type string {
            }
        }

        // EVPN route
        container evpnrt-items {
            list EvpnRoute-list {
                config "false";
                key "pfx rd";

                // Added containment: Prefix=evpnrt
                // Acquired From Package bgp
                uses bgp_EvpnRoute-group;
            }
        }
    }

    grouping bgp_NextHopRoutes-group {
        leaf pfx {
            config "false";
            type address_Ip;
        }

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_DefRtLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:DefRtLeakP->scope
        // Type is an MO-Defined-Type
        leaf scope {
            description "Scope";

            // Type is an MO-Defined-Type
            type rtleak_Scope;
        }
        leaf rtMap {
            type string;
        }
    }

    grouping bgp_InterLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:InterLeakP->scope
        // Type is an MO-Defined-Type
        leaf scope {
            description "Scope";

            // Type is an MO-Defined-Type
            type rtleak_Scope;
        }
        leaf rtMap {
            type string {
            }
        }

        // Protocol from where the routes are leaked
        // Inherited From rtleak:InterLeakP
        // Type is an MO-Defined-Type
        leaf proto {
            description "Protocol";

            // Type is an MO-Defined-Type
            type rtleak_Proto;
        }

        // Routing protocol instance, the routing instance of the
        // protocol from where the routes are being leaked
        // Inherited From rtleak:InterLeakP
        // Type is an MO-Defined-Type
        leaf inst {
            description "Instance";

            // Type is an MO-Defined-Type
            type rtleak_Inst;
        }

        // Leak BGP routes from this Autonomous System (AS)    <1-4294967295>|<1-65535>[.<0-65535>]  Autonomous system number
        // Inherited From rtleak:InterLeakP
        // Type is an MO-Defined-Type
        leaf asn {
            description "Autonomous System Number";

            // Type is an MO-Defined-Type
            type rtleak_Asn {
            }
        }
    }

    grouping bgp_InjLeakP-group {

        // Copy attributes from aggregate
        // Type is an MO-Defined-Type
        leaf copyAttr {
            description "Copy attributes from aggregate";

            // Type is an MO-Defined-Type
            type bgp_AdminSt;
        }

        // From Interface naming:Named
        // Inherited From naming:NamedObject
        // Modified by Override: bgp:InjLeakP->name
        // Modified by Override: pol:Obj->name
        // Type is an MO-Defined-Type
        leaf name {
            description "Inject Route Map Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Type is an MO-Defined-Type
        leaf scope {
            description "Scope";

            // Type is an MO-Defined-Type
            type rtleak_Scope;
        }
        leaf rtMap {
            type string {
            }
        }
    }

    grouping bgp_RttP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From bgp:ARtP
        // Type is an MO-Defined-Type
        leaf type {
            config "false";
            description "Type";

            // Type is an MO-Defined-Type
            type bgp_RttPType;
        }
        leaf operRttAuto {
            type mtx_array_community;
        }

        // List of route targets
        container ent-items {
            list RttEntry-list {
                config "false";
                key "rtt";

                // Added containment: Prefix=ent
                // Acquired From Package bgp
                uses bgp_RttEntry-group;
            }
        }
    }

    grouping bgp_BDEvi-group {

        // Inherited From nw:Conn
        // Modified by Override: nw:CpDom->name
        // Type is an MO-Defined-Type
        leaf name {
            description "Name";

            // Type is an MO-Defined-Type
            type naming_Name {
                length "1..64";
            }
        }
        leaf rd {
            config "false";
            type mtx_array_community;
        }
        leaf encap {
            type string;
        }

        // Route target policy
        container rttp-items {
            list RttP-list {
                config "false";
                key "type";

                // Added containment: Prefix=rttp
                // Acquired From Package bgp
                uses bgp_RttP-group;
            }
        }
    }

    grouping bgp_Gr-group {

        // Graceful restart controls
        // Type is an MO-Defined-Type
        leaf ctrl {
            description "Control";

            // Type is an MO-Defined-Type
            type bgp_GrCtrl;
        }

        // Restart interval
        // Type is an MO-Defined-Type
        leaf restartIntvl {
            description "Restart Time Advertised to Peer";

            // Type is an MO-Defined-Type
            type bgp_GrIntvl;
        }

        // Stale interval for routes advertised by peer
        // Type is an MO-Defined-Type
        leaf staleIntvl {
            description "Stale Time for Routes Advertised by Peer";

            // Type is an MO-Defined-Type
            type bgp_GrStaleIntvl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping bgp_Peer-group {
        leaf addr {
            type address_Ip;
        }

        // Administrative state
        // Type is an MO-Defined-Type
        leaf adminSt {
            description "Administrative State";

            // Type is an MO-Defined-Type
            type nw_AdminSt;
        }
        leaf asn {
            type string;
        }

        // Generate system message when any neighbor state changes
        // Type is an MO-Defined-Type
        leaf logNbrChgs {
            description "Log Neighbor Changes";

            // Type is an MO-Defined-Type
            type bgp_LogNbrSt;
        }

        // Peer Fabric type
        // Type is an MO-Defined-Type
        leaf peerType {
            description "Neighbor Fabric Type";

            // Type is an MO-Defined-Type
            type bgp_PeerFabType;
        }
        leaf dynRtMap {
            type string {
            }
        }

        // Source interface
        // Type is an MO-Defined-Type
        leaf srcIf {
            description "Source Interface";

            // Type is an MO-Defined-Type
            type nw_IfId;
        }
        leaf password {
            type string;
        }

        // Peer controls
        // Type is an MO-Defined-Type
        leaf ctrl {
            description "Control";

            // Type is an MO-Defined-Type
            type bgp_PeerControl;
        }

        // eBGP Multihop
        // Type is an MO-Defined-Type
        leaf ttl {
            description "eBGP Multihop";

            // Type is an MO-Defined-Type
            type bgp_TtlVal;
        }

        // Keepalive interval, how often you send keepalives
        // Type is an MO-Defined-Type
        leaf kaIntvl {
            description "Keepalive Interval";

            // Type is an MO-Defined-Type
            type bgp_KaIntvl;
        }

        // Hold interval, how long you wait before you declare the
        // neighbor down
        // Type is an MO-Defined-Type
        leaf holdIntvl {
            description "Hold Interval";

            // Type is an MO-Defined-Type
            type bgp_HoldIntvl;
        }

        // Connection Mode
        // Type is an MO-Defined-Type
        leaf connMode {
            description "Connection Mode";

            // Type is an MO-Defined-Type
            type bgp_ConnMode;
        }

        // Maximum peers for prefix
        // Type is an MO-Defined-Type
        leaf maxPeerCnt {
            description "Maximum Peers For Prefix";

            // Type is an MO-Defined-Type
            type bgp_MaxPeerCnt;
        }
        leaf sessionContImp {
            type string {
            }
        }
        leaf peerImp {
            type string {
            }
        }

        // Remove Private ASN
        // Type is an MO-Defined-Type
        leaf privateASctrl {
            description "Private AS Control";

            // Type is an MO-Defined-Type
            type bgp_PrivateASControl;
        }

        // Egress Peer Engineering (EPE) for neighbor
        // Type is an MO-Defined-Type
        leaf epe {
            description "Egress Peer Engineering EPE for neighbor";

            // Type is an MO-Defined-Type
            type bgp_AdminSt;
        }
        leaf epePeerSet {
            type string {
            }
        }

        // Low Memory Exempt
        // Type is an MO-Defined-Type
        leaf lowMemExempt {
            description "Low Memory Exempt";

            // Type is an MO-Defined-Type
            type bgp_AdminSt;
        }

        // Capability Suppress
        // Type is an MO-Defined-Type
        leaf capSuppr4ByteAsn {
            description "Capability Suppress 4-byte-as";

            // Type is an MO-Defined-Type
            type bgp_AdminSt;
        }
        leaf affGrp {
            type uint16;
        }

        // Default Value "0" Removed - out of range 1..254
        leaf ttlScrtyHops {
            type uint16 {
                range "1..254";
            }
        }

        // Operational state    Maximum Prefix Peers
        // Type is an MO-Defined-Type
        leaf maxPfxPeers {
            config "false";
            description "Maximum Prefix Peers";

            // Type is an MO-Defined-Type
            type bgp_PfxPeerCounts;
        }

        // Current Prefix Peers
        // Type is an MO-Defined-Type
        leaf curPfxPeers {
            config "false";
            description "Current Prefix Peers";

            // Type is an MO-Defined-Type
            type bgp_PfxPeerCounts;
        }

        // Active Prefix Peers
        // Type is an MO-Defined-Type
        leaf activePfxPeers {
            config "false";
            description "Active Prefix Peers";

            // Type is an MO-Defined-Type
            type bgp_PfxPeerCounts;
        }

        // Maximum Current Peers
        // Type is an MO-Defined-Type
        leaf maxCurPeers {
            config "false";
            description "Maximum Current Peers";

            // Type is an MO-Defined-Type
            type bgp_PfxPeerCounts;
        }

        // Total Prefix Peers
        // Type is an MO-Defined-Type
        leaf totalPfxPeers {
            config "false";
            description "Total Prefix Peers";

            // Type is an MO-Defined-Type
            type bgp_PfxPeerCounts;
        }

        // Bits in this property represent whether to inherit or
        // not to inherit from template.
        // To disable inheritance of an attribute from a template
        // of a neighbor, set the corresponding bit of this
        // property.
        // For example, to disable inheritance of 'keepalive and hold
        // timer' and BFD from a template, set this property with
        // values - 'timer' and 'bfd'.
        // A note that any attributes configured for the neighbor
        // take priority over any attributes inherited from a
        // template.
        // From Interface bgp:InheritContPeerCtrl
        // Type is an MO-Defined-Type
        leaf inheritContPeerCtrl {
            description "Inherit control of peer parameters";

            // Type is an MO-Defined-Type
            type bgp_InheritContPeerCtrlType;
        }

        // Inherited From nw:Conn
        // Modified by Override: bgp:Peer->name
        // Modified by Override: nw:Ep->name
        // Type is an MO-Defined-Type
        leaf name {
            description "Name";

            // Type is an MO-Defined-Type
            type naming_Name {
                length "1..64";
            }
        }

        // This object holds local AS information pertaining to a peer
        container localasn-items {

            // Added containment as a singleton: Prefix=localasn
            // Acquired From Package bgp
            uses bgp_LocalAsn-group;
        }

        // This object holds bgp peer operational status information.
        // We can potentially discover many peer entries for a given
        // configured prefix peer
        container ent-items {
            list PeerEntry-list {
                config "false";
                key "addr";

                // Added containment: Prefix=ent
                // Acquired From Package bgp
                uses bgp_PeerEntry-group;
            }
        }

        // This object holds operational state information for
        // bgp segment routing egress peer engineering
        container epe-items {

            // Added containment as a singleton: Prefix=epe
            // Acquired From Package bgp
            uses bgp_PeerEpeEntry-group;
        }

        // This object holds per address family bgp peer information
        container af-items {
            list PeerAf-list {
                key "type";

                // Added containment: Prefix=af
                // Acquired From Package bgp
                uses bgp_PeerAf-group;
            }
        }
    }

    grouping bgp_LocalAsn-group {

        // Local ASN
        // Type is an MO-Defined-Type
        leaf localAsn {
            description "Local Autonomous System Number";

            // Type is an MO-Defined-Type
            type bgp_AsnNum;
        }

        // local ASN config
        // Type is an MO-Defined-Type
        leaf asnPropagate {
            description "ASN Propagation";

            // Type is an MO-Defined-Type
            type bgp_AsnPropagation;
        }

        // Inherited From nw:Conn
        // Modified by Override: nw:Ep->name
        // Type is an MO-Defined-Type
        leaf name {
            description "Name";

            // Type is an MO-Defined-Type
            type naming_Name {
                length "1..64";
            }
        }
    }

    grouping bgp_PeerEntry-group {

        // Peer Type
        // Type is an MO-Defined-Type
        leaf type {
            config "false";
            description "Link";

            // Type is an MO-Defined-Type
            type bgp_PeerType;
        }
        leaf addr {
            config "false";
            type address_Ip;
        }

        // Peer router id
        // Type is an MO-Defined-Type
        leaf rtrId {
            config "false";
            description "Router ID";

            // Type is an MO-Defined-Type
            type ip_RtrId;
        }

        // Operational state
        // Type is an MO-Defined-Type
        leaf operSt {
            config "false";
            description "Operational State";

            // Type is an MO-Defined-Type
            type bgp_PeerOperSt;
        }

        // Previous Operational state
        // Type is an MO-Defined-Type
        leaf prevOperSt {
            config "false";
            description "Previous Operational State";

            // Type is an MO-Defined-Type
            type bgp_PeerOperSt;
        }

        // Shut state qualifier
        // Type is an MO-Defined-Type
        leaf shutStQual {
            config "false";
            description "Shut State Qualifier";

            // Type is an MO-Defined-Type
            type bgp_ShutStQual;
        }
        leaf lastFlapTs {
            config "false";
            type uint64;
        }
        leaf maxConnRetryIntvl {
            config "false";
            type uint16;
            default "60";
        }

        // Flags
        // Type is an MO-Defined-Type
        leaf flags {
            config "false";
            description "Flags";

            // Type is an MO-Defined-Type
            type bgp_PeerFlags;
        }

        // Advertised capability
        // Type is an MO-Defined-Type
        leaf advCap {
            config "false";
            description "Advertised Capability";

            // Type is an MO-Defined-Type
            type bgp_CapT;
        }

        // Received capability
        // Type is an MO-Defined-Type
        leaf rcvCap {
            config "false";
            description "Received Capability";

            // Type is an MO-Defined-Type
            type bgp_CapT;
        }

        // Connected interface
        // Type is an MO-Defined-Type
        leaf connIf {
            config "false";
            description "Directly Attached Interface";

            // Type is an MO-Defined-Type
            type nw_IfId;
        }

        // Negotiated hold time
        // Type is an MO-Defined-Type
        leaf holdIntvl {
            config "false";
            description "Hold Interval";

            // Type is an MO-Defined-Type
            type bgp_HoldIntvl;
        }

        // Negotiated keepalive interval
        // Type is an MO-Defined-Type
        leaf kaIntvl {
            config "false";
            description "Keepalive Interval";

            // Type is an MO-Defined-Type
            type bgp_KaIntvl;
        }
        leaf localIp {
            config "false";
            type address_Ip;
        }

        // Local L4 port
        // Type is an MO-Defined-Type
        leaf localPort {
            config "false";
            description "Local Port";

            // Type is an MO-Defined-Type
            type l4_Port;
        }

        // Remote L4 port
        // Type is an MO-Defined-Type
        leaf remotePort {
            config "false";
            description "Remote Port";

            // Type is an MO-Defined-Type
            type l4_Port;
        }

        // Number of times connections established
        // Type is an MO-Defined-Type
        leaf connEst {
            config "false";
            description "Connections Established";

            // Type is an MO-Defined-Type
            type cap_Quant;
        }

        // Number of times connections dropped
        // Type is an MO-Defined-Type
        leaf connDrop {
            config "false";
            description "Connections Dropped";

            // Type is an MO-Defined-Type
            type cap_Quant;
        }
        leaf updateElapsedTs {
            config "false";
            type uint64;
        }

        // FD to connect to peer
        // Type is an MO-Defined-Type
        leaf fd {
            config "false";
            description "FD to Connect to Peer";

            // Type is an MO-Defined-Type
            type bgp_SockFD;
        }

        // Peer Index
        // Type is an MO-Defined-Type
        leaf peerIdx {
            config "false";
            description "Peer Index";

            // Type is an MO-Defined-Type
            type bgp_PeerIdx;
        }

        // Connection Attempts
        // Type is an MO-Defined-Type
        leaf connAttempts {
            config "false";
            description "Connection Attempts";

            // Type is an MO-Defined-Type
            type bgp_ConnAttempts;
        }

        // Peer idle state reason
        // Type is an MO-Defined-Type
        leaf stReason {
            config "false";
            description "State Reason";

            // Type is an MO-Defined-Type
            type bgp_StReason;
        }

        // Indicate if password is set
        // Type is an MO-Defined-Type
        leaf passwdSet {
            config "false";
            description "TCP MD5 Authentication";

            // Type is an MO-Defined-Type
            type bgp_PasswdSet;
        }

        // Inherited From nw:Conn
        // Modified by Override: nw:Ep->name
        // Type is an MO-Defined-Type
        leaf name {
            description "Name";

            // Type is an MO-Defined-Type
            type naming_Name {
                length "1..64";
            }
        }

        // This objects hold graceful restart operational information. This
        // is valid per neighbor
        container gr-items {

            // Added containment as a singleton: Prefix=gr
            // Acquired From Package bgp
            uses bgp_GrSt-group;
        }

        // This object holds peer event information
        container ev-items {

            // Added containment as a singleton: Prefix=ev
            // Acquired From Package bgp
            uses bgp_PeerEvents-group;
        }

        // This object holds operational state information for
        // bgp segment routing egress peer engineering
        container epe-items {

            // Added containment as a singleton: Prefix=epe
            // Acquired From Package bgp
            uses bgp_PeerEpeEntry-group;
        }

        // This object holds bgp peer af operational status info
        container af-items {
            list PeerAfEntry-list {
                key "type";

                // Added containment: Prefix=af
                // Acquired From Package bgp
                uses bgp_PeerAfEntry-group;
            }
        }

        // This object holds bgp peer statistics operational information.
        // This is a singleton within a peerEntry
        container peerstats-items {

            // Added containment as a singleton: Prefix=peerstats
            // Acquired From Package bgp
            uses bgp_PeerEntryStats-group;
        }
    }

    grouping bgp_GrSt-group {

        // Graceful state
        // Type is an MO-Defined-Type
        leaf operSt {
            config "false";
            description "Operational State";

            // Type is an MO-Defined-Type
            type bgp_PeerGrSt;
        }

        // Graceful restart interval advertised by peer
        // Type is an MO-Defined-Type
        leaf restartIntvl {
            config "false";
            description "Restart Interval";

            // Type is an MO-Defined-Type
            type bgp_GrIntvl;
        }
        leaf grTs {
            config "false";
            type uint64;
        }
    }

    grouping bgp_PeerEvents-group {

        // Major error during last reset sent
        // Type is an MO-Defined-Type
        leaf majErrRstSent {
            config "false";
            description "Major Error During Last Resent Sent";

            // Type is an MO-Defined-Type
            type bgp_MajNotifErr;
        }

        // Minor error during last reset sent
        // Type is an MO-Defined-Type
        leaf minErrRstSent {
            config "false";
            description "Minor Error During Last Reset Sent";

            // Type is an MO-Defined-Type
            type bgp_MinNotifErr;
        }

        // Last error value sent
        // Type is an MO-Defined-Type
        leaf lastErrValSent {
            config "false";
            description "Last Error Value Sent";

            // Type is an MO-Defined-Type
            type bgp_LastErrVal;
        }
        leaf rstSentTs {
            config "false";
            type uint64;
        }

        // Major error during last reset received
        // Type is an MO-Defined-Type
        leaf majErrRstRsvd {
            config "false";
            description "Major Error During Last Reset Received";

            // Type is an MO-Defined-Type
            type bgp_MajNotifErr;
        }

        // Minor error during last reset received
        // Type is an MO-Defined-Type
        leaf minErrRstRsvd {
            config "false";
            description "Minor Error During Last Reset Received";

            // Type is an MO-Defined-Type
            type bgp_MinNotifErr;
        }

        // Last error value received
        // Type is an MO-Defined-Type
        leaf lastErrValRsvd {
            config "false";
            description "Last Error Value Received";

            // Type is an MO-Defined-Type
            type bgp_LastErrVal;
        }
        leaf rstRsvdTs {
            config "false";
            type uint64;
        }

        // Last error length received
        // Type is an MO-Defined-Type
        leaf lastErrLenRsvd {
            config "false";
            description "Last Error Length Received";

            // Type is an MO-Defined-Type
            type bgp_LastErrLen;
        }

        // Last error length sent
        // Type is an MO-Defined-Type
        leaf lastErrLenSent {
            config "false";
            description "Last Error Length Sent";

            // Type is an MO-Defined-Type
            type bgp_LastErrLen;
        }
        leaf lastErrDataRsvd {
            config "false";
            type string;
        }
        leaf lastErrDataSent {
            config "false";
            type string;
        }
    }

    grouping bgp_PeerEpeEntry-group {

        // Egress peer engineering
        // Type is an MO-Defined-Type
        leaf adminSt {
            config "false";
            description "Egress Peer Engineering State";

            // Type is an MO-Defined-Type
            type bgp_EgressPeerEng;
        }
        leaf sid {
            config "false";
            type uint32;
        }
        leaf rpcSetID {
            config "false";
            type uint32;
        }
        leaf peerSetName {
            config "false";
            type string {
            }
        }
        leaf peerSetSid {
            config "false";
            type uint32;
        }
        leaf peerSetRpcSetID {
            config "false";
            type uint32;
        }

        // Inherited From nw:Conn
        // Modified by Override: nw:Ep->name
        // Type is an MO-Defined-Type
        leaf name {
            description "Name";

            // Type is an MO-Defined-Type
            type naming_Name {
                length "1..64";
            }
        }

        // Egress Peer Engineering Peer Adjacencies
        container epeadj-items {
            list PeerEpeAdj-list {
                config "false";
                key "rpcSetID";

                // Added containment: Prefix=epeadj
                // Acquired From Package bgp
                uses bgp_PeerEpeAdj-group;
            }
        }
    }

    grouping bgp_PeerEpeAdj-group {
        leaf localAddr {
            config "false";
            type address_Ip;
        }
        leaf remoteAddr {
            config "false";
            type address_Ip;
        }

        // Interface index
        // Type is an MO-Defined-Type
        leaf ifIndex {
            config "false";
            description "Interface Index";

            // Type is an MO-Defined-Type
            type nw_IfId;
        }
        leaf rpcSetID {
            config "false";
            type uint32;
        }
        leaf sid {
            config "false";
            type uint32;
        }
    }

    grouping bgp_PeerAfEntry-group {

        // Local BGP table version
        // Type is an MO-Defined-Type
        leaf tblVer {
            config "false";
            description "Table Version";

            // Type is an MO-Defined-Type
            type bgp_TblVer;
        }

        // Peer table version
        // Type is an MO-Defined-Type
        leaf peerTblVer {
            config "false";
            description "Peer Table Version";

            // Type is an MO-Defined-Type
            type bgp_TblVer;
        }

        // Table state
        // Type is an MO-Defined-Type
        leaf tblSt {
            config "false";
            description "Table State";

            // Type is an MO-Defined-Type
            type bgp_TblSt;
        }

        // Number of accepted paths
        // Type is an MO-Defined-Type
        leaf acceptedPaths {
            config "false";
            description "Accepted Paths";

            // Type is an MO-Defined-Type
            type bgp_NumPaths;
        }

        // Number of denied paths
        // Type is an MO-Defined-Type
        leaf deniedPaths {
            config "false";
            description "Denied Paths";

            // Type is an MO-Defined-Type
            type bgp_NumPaths;
        }

        // Number of withDrawn paths
        // Type is an MO-Defined-Type
        leaf withDrawnPaths {
            config "false";
            description "withDrawn Paths";

            // Type is an MO-Defined-Type
            type bgp_NumPaths;
        }

        // Memory consumed by the number of accepted paths
        // Type is an MO-Defined-Type
        leaf memAccPaths {
            config "false";
            description "Accepted Paths Memory";

            // Type is an MO-Defined-Type
            type bgp_MemConsumed;
        }

        // Flags
        // Type is an MO-Defined-Type
        leaf flags {
            config "false";
            description "Flags";

            // Type is an MO-Defined-Type
            type bgp_PeerAfFlags;
        }

        // Prefixes Sent to peer
        // Type is an MO-Defined-Type
        leaf pfxSent {
            config "false";
            description "Prefixes Sent";

            // Type is an MO-Defined-Type
            type bgp_PfxSent;
        }

        // Prefixes Saved from peer
        // Type is an MO-Defined-Type
        leaf pfxSaved {
            config "false";
            description "Prefixes Saved";

            // Type is an MO-Defined-Type
            type bgp_PfxSaved;
        }

        // Prefixes Flushed from peer
        // Type is an MO-Defined-Type
        leaf pfxFlushed {
            config "false";
            description "Prefixes Flushed";

            // Type is an MO-Defined-Type
            type bgp_PfxFlushed;
        }
        leaf lastEorRcvdTs {
            config "false";
            type uint64;
        }
        leaf firstEorRcvdTs {
            config "false";
            type uint64;
        }

        // Inherited From nw:Conn
        // Modified by Override: nw:CpDom->name
        // Type is an MO-Defined-Type
        leaf name {
            description "Name";

            // Type is an MO-Defined-Type
            type naming_Name {
                length "1..64";
            }
        }

        // Type
        // Inherited From bgp:Af
        // Type is an MO-Defined-Type
        leaf type {
            description "Type";

            // Type is an MO-Defined-Type
            type bgp_AfT;
        }
    }

    grouping bgp_PeerEntryStats-group {

        // BGP Peer Stats    Number of BGP Open Messages sent
        // Type is an MO-Defined-Type
        leaf openSent {
            config "false";
            description "Number of Open Messages Sent";

            // Type is an MO-Defined-Type
            type bgp_PeerCount;
        }

        // Number of BGP Open Messages received
        // Type is an MO-Defined-Type
        leaf openRcvd {
            config "false";
            description "Number of Open Messages Received";

            // Type is an MO-Defined-Type
            type bgp_PeerCount;
        }

        // Number of BGP Update Messages sent
        // Type is an MO-Defined-Type
        leaf updateSent {
            config "false";
            description "Number of Update Messages Sent";

            // Type is an MO-Defined-Type
            type bgp_PeerCount;
        }

        // Number of BGP Update Messages received
        // Type is an MO-Defined-Type
        leaf updateRcvd {
            config "false";
            description "Number of Update Messages Received";

            // Type is an MO-Defined-Type
            type bgp_PeerCount;
        }

        // Number of BGP Keepalive Messages sent
        // Type is an MO-Defined-Type
        leaf kaSent {
            config "false";
            description "Number of Keepalive Messages Sent";

            // Type is an MO-Defined-Type
            type bgp_PeerCount;
        }

        // Number of BGP Keepalive Messages received
        // Type is an MO-Defined-Type
        leaf kaRcvd {
            config "false";
            description "Number of Keepalive Messages Received";

            // Type is an MO-Defined-Type
            type bgp_PeerCount;
        }

        // Number of BGP Route Refresh Messages sent
        // Type is an MO-Defined-Type
        leaf routeRefreshSent {
            config "false";
            description "Number of Route Refresh Messages Sent";

            // Type is an MO-Defined-Type
            type bgp_PeerCount;
        }

        // Number of BGP Route Refresh Messages received
        // Type is an MO-Defined-Type
        leaf routeRefreshRcvd {
            config "false";
            description "Number of Route Refresh Messages Received";

            // Type is an MO-Defined-Type
            type bgp_PeerCount;
        }

        // Number of BGP Capability Messages sent
        // Type is an MO-Defined-Type
        leaf capSent {
            config "false";
            description "Number of Capability Messages Sent";

            // Type is an MO-Defined-Type
            type bgp_PeerCount;
        }

        // Number of BGP Capability Messages received
        // Type is an MO-Defined-Type
        leaf capRcvd {
            config "false";
            description "Number of Capability Messages Received";

            // Type is an MO-Defined-Type
            type bgp_PeerCount;
        }

        // Number of BGP Notification Messages sent
        // Type is an MO-Defined-Type
        leaf notifSent {
            config "false";
            description "Number of Notification Messages Sent";

            // Type is an MO-Defined-Type
            type bgp_PeerCount;
        }

        // Number of BGP Notification Messages received
        // Type is an MO-Defined-Type
        leaf notifRcvd {
            config "false";
            description "Number of Notification Messages Received";

            // Type is an MO-Defined-Type
            type bgp_PeerCount;
        }

        // Number of BGP Messages sent
        // Type is an MO-Defined-Type
        leaf msgSent {
            config "false";
            description "Number of Messages Sent";

            // Type is an MO-Defined-Type
            type bgp_PeerCount;
        }

        // Number of BGP Messages received
        // Type is an MO-Defined-Type
        leaf msgRcvd {
            config "false";
            description "Number of Messages Received";

            // Type is an MO-Defined-Type
            type bgp_PeerCount;
        }

        // Number of BGP Message Bytes sent
        // Type is an MO-Defined-Type
        leaf byteSent {
            config "false";
            description "Number of Bytes Sent";

            // Type is an MO-Defined-Type
            type bgp_PeerCount;
        }

        // Number of BGP Message Bytes received
        // Type is an MO-Defined-Type
        leaf byteRcvd {
            config "false";
            description "Number of Bytes Received";

            // Type is an MO-Defined-Type
            type bgp_PeerCount;
        }

        // Bytes in send queue
        // Type is an MO-Defined-Type
        leaf byteInSendQ {
            config "false";
            description "Bytes in Send Queue";

            // Type is an MO-Defined-Type
            type bgp_PeerCount;
        }

        // Bytes in receive queue
        // Type is an MO-Defined-Type
        leaf byteInRecvQ {
            config "false";
            description "Bytes in Receive Queue";

            // Type is an MO-Defined-Type
            type bgp_PeerCount;
        }
        leaf connectRetryTs {
            config "false";
            type uint64;
        }
        leaf kaTs {
            config "false";
            type uint64;
        }
    }

    grouping bgp_PeerAf-group {

        // Peer address family controls
        // Type is an MO-Defined-Type
        leaf ctrl {
            description "Control";

            // Type is an MO-Defined-Type
            type bgp_PeerAfControl;
        }
        leaf allowedSelfAsCnt {
            type uint8 {
                range "0..10";
            }
            default "0";
        }

        // Soft Reconfiguration
        // Type is an MO-Defined-Type
        leaf softReconfigBackup {
            description "Soft Reconfiguration";

            // Type is an MO-Defined-Type
            type bgp_SoftReconfigBackup;
        }

        // Neighbor advertisement interval
        // Type is an MO-Defined-Type
        leaf advIntvl {
            description "Neighbor advertisement interval";

            // Type is an MO-Defined-Type
            type bgp_AdvInterval;
        }

        // Type is an MO-Defined-Type
        leaf defOrg {
            description "Default Originate is enabled";

            // Type is an MO-Defined-Type
            type bgp_AdminSt;
        }
        leaf defOrgRtMap {
            type string {
            }
        }

        // Capability Additional Paths
        // Type is an MO-Defined-Type
        leaf capAddlPaths {
            description "Capability Additional Paths";

            // Type is an MO-Defined-Type
            type bgp_CapAddlPathCapT;
        }
        leaf unSupprMap {
            type string {
            }
        }

        // as-override
        // Type is an MO-Defined-Type
        leaf asOverride {
            description "Override matching AS-number while sending update";

            // Type is an MO-Defined-Type
            type bgp_AdminSt;
        }

        // next-hop-third-party
        // Type is an MO-Defined-Type
        leaf nhThirdparty {
            description "Compute a third-party nexthop if possible";

            // Type is an MO-Defined-Type
            type bgp_AdminSt;
        }
        leaf wght {
            type string {
            }
        }
        leaf soo {
            type mtx_array_community;
        }

        // Send-community standard
        // Type is an MO-Defined-Type
        leaf sendComStd {
            description "Send-community standard";

            // Type is an MO-Defined-Type
            type bgp_AdminSt;
        }

        // Send-community extended
        // Type is an MO-Defined-Type
        leaf sendComExt {
            description "Send-community extended";

            // Type is an MO-Defined-Type
            type bgp_AdminSt;
        }

        // encapsulation mpls for L2Vpn Evpn PeerAf
        // Type is an MO-Defined-Type
        leaf encapMpls {
            description "Configure encapsulation type for EVPN routes";

            // Type is an MO-Defined-Type
            type bgp_AdminSt;
        }

        // Bits in this property represent whether to inherit or
        // not to inherit from template.
        // To disable inheritance of an attribute from a template
        // of a neighbor AF, set the corresponding bit of this
        // property.
        // For example, to disable inheritance of 'send community'
        // from a template, set this property with value -
        // 'send-com'.
        // A note that any attributes configured for the neighbor AF
        // take priority over any attributes inherited from a
        // template.
        // From Interface bgp:InheritContPeerPolicyCtrl
        // Type is an MO-Defined-Type
        leaf inheritContPeerPolicyCtrl {
            description "Inherit control of peer policy parameters";

            // Type is an MO-Defined-Type
            type bgp_InheritContPeerPolicyCtrlType;
        }

        // Inherited From nw:Conn
        // Modified by Override: bgp:PeerAf->name
        // Modified by Override: nw:CpDom->name
        // Type is an MO-Defined-Type
        leaf name {
            description "bgp PeerAf";

            // Type is an MO-Defined-Type
            type naming_Name {
                length "1..64";
            }
        }

        // Type
        // Inherited From bgp:Af
        // Type is an MO-Defined-Type
        leaf type {
            description "Type";

            // Type is an MO-Defined-Type
            type bgp_AfT;
        }

        // This policy tells on what to do when the number of prefixes
        // advertised by the peer crosses a maximum limit specified.
        // This is used as a defensive mechanism to protect resources
        // on the router
        container maxpfxp-items {

            // Added containment as a singleton: Prefix=maxpfxp
            // Acquired From Package bgp
            uses bgp_MaxPfxP-group;
        }

        // This object holds per advertise-map information
        container advtmap-items {

            // Added containment as a singleton: Prefix=advtmap
            // Acquired From Package bgp
            uses bgp_AdvtMap-group;
        }

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }

        container advtdrt-items {

            // Added containment as a singleton: Prefix=advtdrt
            // Acquired From Package bgp
            uses bgp_AdvtdRoutes-group;
        }

        container rcvdrt-items {

            // Added containment as a singleton: Prefix=rcvdrt
            // Acquired From Package bgp
            uses bgp_RcvdRoutes-group;
        }

        // Show only Dampening Paths Routes
        container damppathsrt-items {

            // Added containment as a singleton: Prefix=damppathsrt
            // Acquired From Package bgp
            uses bgp_DampPathsRoutes-group;
        }

        // Route control policy for routes coming/going to peers.
        // There are few ways to apply this policy, controlling
        // through route maps or prefix lists or filter lists.
        // If both are specified, the order is implicit. Prefix
        // lists are applied before route maps.
        // The direction specifies whether to apply this policy
        // in the incoming or outgoing direction
        container rtctrl-items {
            list RtCtrlP-list {
                key "direction";

                // Added containment: Prefix=rtctrl
                // Acquired From Package bgp
                uses bgp_RtCtrlP-group;
            }
        }

        // This objects holds default route leak policy,
        // this is not needed for FCS in our solution
        container defrtleak-items {

            // Added containment as a singleton: Prefix=defrtleak
            // Acquired From Package bgp
            uses bgp_DefRtLeakP-group;
        }
        container pfxctrl-items {
            list PfxCtrlP-list {
                key "direction";

                // Added containment: Prefix=pfxctrl
                // Acquired From Package bgp
                uses bgp_PfxCtrlP-group;
            }
        }
        container fltrctrl-items {
            list FltrCtrlP-list {
                key "direction";

                // Added containment: Prefix=fltrctrl
                // Acquired From Package bgp
                uses bgp_FltrCtrlP-group;
            }
        }

        // This object holds bgp peer af peer policy inherit
        container pol-items {
            list PolicyInheritRule-list {
                key "name";

                // Added containment: Prefix=pol
                // Acquired From Package bgp
                uses bgp_PolicyInheritRule-group;
            }
        }
    }

    grouping bgp_MaxPfxP-group {

        // Maximum number of prefixes allowed from the peer
        // Type is an MO-Defined-Type
        leaf maxPfx {
            description "Maximum Prefixes";

            // Type is an MO-Defined-Type
            type bgp_MaxPfx;
        }

        // Threshold at which warning is issued when number of
        // prefixes crosses the threshold
        // Type is an MO-Defined-Type
        leaf thresh {
            description "Threshold";

            // Type is an MO-Defined-Type
            type bgp_MaxPfxThresh;
        }

        // Action on what to do when the maximum prefix limit is
        // reached
        // Type is an MO-Defined-Type
        leaf action {
            description "Action";

            // Type is an MO-Defined-Type
            type bgp_MaxPfxAct;
        }

        // Duration before we restart the peer when the prefix
        // limit is reached (in minutes)
        // Type is an MO-Defined-Type
        leaf restartTime {
            description "Restart Time";

            // Type is an MO-Defined-Type
            type bgp_MaxPfxDuration;
        }

        // From Interface naming:Named
        // Inherited From naming:NamedObject
        // Modified by Override: bgp:MaxPfxP->name
        // Modified by Override: pol:Obj->name
        // Type is an MO-Defined-Type
        leaf name {
            description "bgp MaxPfxP";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping bgp_AdvtMap-group {
        leaf rtMap {
            type string {
            }
        }

        // Condition route-map
        // Type is an MO-Defined-Type
        leaf condition {
            description "Specify route-map for conditional advertisement";

            // Type is an MO-Defined-Type
            type bgp_AdvtMapCondition;
        }
        leaf condMap {
            type string {
            }
        }
    }

    grouping bgp_AdvtdRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_RcvdRoutes-group {

        // This object holds the bgp route information
        container rt-items {
            list Route-list {
                config "false";
                key "pfx";

                // Added containment: Prefix=rt
                // Acquired From Package bgp
                uses bgp_Route-group;
            }
        }

        // This object holds the bgp vpn route information
        container vpnrt-items {
            list VpnRoute-list {
                config "false";
                key "pfx rd";

                // Added containment: Prefix=vpnrt
                // Acquired From Package bgp
                uses bgp_VpnRoute-group;
            }
        }
        container lblrt-items {
            list LblRoute-list {
                config "false";
                key "pfx";

                // Added containment: Prefix=lblrt
                // Acquired From Package bgp
                uses bgp_LblRoute-group;
            }
        }
        container lsrt-items {
            list LnkStRoute-list {
                config "false";
                key "pfx";

                // Added containment: Prefix=lsrt
                // Acquired From Package bgp
                uses bgp_LnkStRoute-group;
            }
        }

        // EVPN route
        container evpnrt-items {
            list EvpnRoute-list {
                config "false";
                key "pfx rd";

                // Added containment: Prefix=evpnrt
                // Acquired From Package bgp
                uses bgp_EvpnRoute-group;
            }
        }
    }

    grouping bgp_RtCtrlP-group {

        // Operational state
        // Type is an MO-Defined-Type
        leaf operSt {
            config "false";
            description "Operational State";

            // Type is an MO-Defined-Type
            type bgp_RtCtrlOperSt;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Direction [in/out]
        // Inherited From rtctrl:RtCtrlP
        // Type is an MO-Defined-Type
        leaf direction {
            description "Direction";

            // Type is an MO-Defined-Type
            type rtctrl_RtCtrlDir;
        }
        leaf rtMap {
            type string {
            }
        }
    }

    grouping bgp_PfxCtrlP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Direction [in/out]
        // Inherited From bgp:RtListP
        // Type is an MO-Defined-Type
        leaf direction {
            description "Direction";

            // Type is an MO-Defined-Type
            type bgp_RtCtrlDir;
        }
        leaf list {
            type string {
            }
        }
    }

    grouping bgp_FltrCtrlP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Direction [in/out]
        // Inherited From bgp:RtListP
        // Type is an MO-Defined-Type
        leaf direction {
            description "Direction";

            // Type is an MO-Defined-Type
            type bgp_RtCtrlDir;
        }
        leaf list {
            type string {
            }
        }
    }

    grouping bgp_PolicyInheritRule-group {

        // Sequence number of the inheritted peer policy template
        // Type is an MO-Defined-Type
        leaf seq {
            description "Sequence Number";

            // Type is an MO-Defined-Type
            type bgp_Order {
                range "1..65535";
            }
        }

        // Inherited From nw:Conn
        // Modified by Override: bgp:PolicyInheritRule->name
        // Modified by Override: nw:Ep->name
        // Type is an MO-Defined-Type
        leaf name {
            description "Name";

            // Type is an MO-Defined-Type
            type naming_Name {
                length "1..64";
            }
        }
    }

    grouping bgp_PeerCont-group {

        // Bits in this property represent whether to inherit or
        // not to inherit from template.
        // To disable inheritance of an attribute from a template
        // of a neighbor, set the corresponding bit of this
        // property.
        // For example, to disable inheritance of 'keepalive and hold
        // timer' and BFD from a template, set this property with
        // values - 'timer' and 'bfd'.
        // A note that any attributes configured for the neighbor
        // take priority over any attributes inherited from a
        // template.
        // From Interface bgp:InheritContPeerCtrl
        // Type is an MO-Defined-Type
        leaf inheritContPeerCtrl {
            description "Inherit control of peer parameters";

            // Type is an MO-Defined-Type
            type bgp_InheritContPeerCtrlType;
        }

        // Inherited From nw:Conn
        // Modified by Override: nw:Ep->name
        // Modified by Override: bgp:Common->name
        // Type is an MO-Defined-Type
        leaf name {
            description "Name";

            // Type is an MO-Defined-Type
            type naming_Name {
                length "1..64";
            }
        }
        leaf desc {
            type string {
            }
        }

        // Inherited From bgp:Common
        // Type is an MO-Defined-Type
        leaf adminSt {
            description "Administrative State";

            // Type is an MO-Defined-Type
            type nw_AdminSt;
        }
        leaf asn {
            type string;
        }

        // Generate system message when any neighbor state changes
        // Inherited From bgp:Common
        // Type is an MO-Defined-Type
        leaf logNbrChgs {
            description "Log Neighbor Changes";

            // Type is an MO-Defined-Type
            type bgp_LogNbrSt;
        }

        // Source interface
        // Inherited From bgp:Common
        // Type is an MO-Defined-Type
        leaf srcIf {
            description "Source Interface";

            // Type is an MO-Defined-Type
            type nw_IfId;
        }
        leaf password {
            type string;
        }

        // Peer controls
        // Inherited From bgp:Common
        // Type is an MO-Defined-Type
        leaf ctrl {
            description "Control";

            // Type is an MO-Defined-Type
            type bgp_PeerControl;
        }

        // eBGP Multihop
        // Inherited From bgp:Common
        // Type is an MO-Defined-Type
        leaf ttl {
            description "eBGP Multihop";

            // Type is an MO-Defined-Type
            type bgp_TtlVal;
        }

        // Keepalive interval, how often you send keepalives
        // Inherited From bgp:Common
        // Type is an MO-Defined-Type
        leaf kaIntvl {
            description "Keepalive Interval";

            // Type is an MO-Defined-Type
            type bgp_KaIntvl;
        }

        // Hold interval, how long you wait before you declare the
        // neighbor down
        // Inherited From bgp:Common
        // Type is an MO-Defined-Type
        leaf holdIntvl {
            description "Hold Interval";

            // Type is an MO-Defined-Type
            type bgp_HoldIntvl;
        }

        // Connection Mode
        // Inherited From bgp:Common
        // Type is an MO-Defined-Type
        leaf connMode {
            description "Connection Mode";

            // Type is an MO-Defined-Type
            type bgp_ConnMode;
        }
        leaf sessionContImp {
            type string {
            }
        }

        // Remove Private ASN
        // Inherited From bgp:Common
        // Type is an MO-Defined-Type
        leaf privateASctrl {
            description "Private AS Control";

            // Type is an MO-Defined-Type
            type bgp_PrivateASControl;
        }

        // Peer Fabric type
        // Inherited From bgp:Common
        // Type is an MO-Defined-Type
        leaf peerType {
            description "Neighbor Fabric Type";

            // Type is an MO-Defined-Type
            type bgp_PeerFabType;
        }

        // Low Memory Exempt
        // Inherited From bgp:Common
        // Type is an MO-Defined-Type
        leaf lowMemExempt {
            description "Low Memory Exempt";

            // Type is an MO-Defined-Type
            type bgp_AdminSt;
        }

        // Capability Suppress
        // Inherited From bgp:Common
        // Type is an MO-Defined-Type
        leaf capSuppr4ByteAsn {
            description "Capability Suppress 4-byte-as";

            // Type is an MO-Defined-Type
            type bgp_AdminSt;
        }
        leaf affGrp {
            type uint16;
        }

        // Egress Peer Engineering (EPE) for neighbor
        // Inherited From bgp:Common
        // Type is an MO-Defined-Type
        leaf epe {
            description "Egress Peer Engineering EPE for neighbor";

            // Type is an MO-Defined-Type
            type bgp_AdminSt;
        }
        leaf epePeerSet {
            type string {
            }
        }

        // This object holds local AS information pertaining to a peer
        container localasn-items {

            // Added containment as a singleton: Prefix=localasn
            // Acquired From Package bgp
            uses bgp_LocalAsn-group;
        }

        // This object holds per address family bgp peer information
        container af-items {
            list PeerAf-list {
                key "type";

                // Added containment: Prefix=af
                // Acquired From Package bgp
                uses bgp_PeerAf-group;
            }
        }
    }

    grouping bgp_SessionCont-group {

        // Bits in this property represent whether to inherit or
        // not to inherit from template.
        // To disable inheritance of an attribute from a template
        // of a neighbor, set the corresponding bit of this
        // property.
        // For example, to disable inheritance of 'keepalive and hold
        // timer' and BFD from a template, set this property with
        // values - 'timer' and 'bfd'.
        // A note that any attributes configured for the neighbor
        // take priority over any attributes inherited from a
        // template.
        // From Interface bgp:InheritContPeerCtrl
        // Type is an MO-Defined-Type
        leaf inheritContPeerCtrl {
            description "Inherit control of peer parameters";

            // Type is an MO-Defined-Type
            type bgp_InheritContPeerCtrlType;
        }

        // Inherited From nw:Conn
        // Modified by Override: nw:Ep->name
        // Modified by Override: bgp:Common->name
        // Type is an MO-Defined-Type
        leaf name {
            description "Name";

            // Type is an MO-Defined-Type
            type naming_Name {
                length "1..64";
            }
        }
        leaf desc {
            type string {
            }
        }

        // Inherited From bgp:Common
        // Type is an MO-Defined-Type
        leaf adminSt {
            description "Administrative State";

            // Type is an MO-Defined-Type
            type nw_AdminSt;
        }
        leaf asn {
            type string;
        }

        // Generate system message when any neighbor state changes
        // Inherited From bgp:Common
        // Type is an MO-Defined-Type
        leaf logNbrChgs {
            description "Log Neighbor Changes";

            // Type is an MO-Defined-Type
            type bgp_LogNbrSt;
        }

        // Source interface
        // Inherited From bgp:Common
        // Type is an MO-Defined-Type
        leaf srcIf {
            description "Source Interface";

            // Type is an MO-Defined-Type
            type nw_IfId;
        }
        leaf password {
            type string;
        }

        // Peer controls
        // Inherited From bgp:Common
        // Type is an MO-Defined-Type
        leaf ctrl {
            description "Control";

            // Type is an MO-Defined-Type
            type bgp_PeerControl;
        }

        // eBGP Multihop
        // Inherited From bgp:Common
        // Type is an MO-Defined-Type
        leaf ttl {
            description "eBGP Multihop";

            // Type is an MO-Defined-Type
            type bgp_TtlVal;
        }

        // Keepalive interval, how often you send keepalives
        // Inherited From bgp:Common
        // Type is an MO-Defined-Type
        leaf kaIntvl {
            description "Keepalive Interval";

            // Type is an MO-Defined-Type
            type bgp_KaIntvl;
        }

        // Hold interval, how long you wait before you declare the
        // neighbor down
        // Inherited From bgp:Common
        // Type is an MO-Defined-Type
        leaf holdIntvl {
            description "Hold Interval";

            // Type is an MO-Defined-Type
            type bgp_HoldIntvl;
        }

        // Connection Mode
        // Inherited From bgp:Common
        // Type is an MO-Defined-Type
        leaf connMode {
            description "Connection Mode";

            // Type is an MO-Defined-Type
            type bgp_ConnMode;
        }
        leaf sessionContImp {
            type string {
            }
        }

        // Remove Private ASN
        // Inherited From bgp:Common
        // Type is an MO-Defined-Type
        leaf privateASctrl {
            description "Private AS Control";

            // Type is an MO-Defined-Type
            type bgp_PrivateASControl;
        }

        // Peer Fabric type
        // Inherited From bgp:Common
        // Type is an MO-Defined-Type
        leaf peerType {
            description "Neighbor Fabric Type";

            // Type is an MO-Defined-Type
            type bgp_PeerFabType;
        }

        // Low Memory Exempt
        // Inherited From bgp:Common
        // Type is an MO-Defined-Type
        leaf lowMemExempt {
            description "Low Memory Exempt";

            // Type is an MO-Defined-Type
            type bgp_AdminSt;
        }

        // Capability Suppress
        // Inherited From bgp:Common
        // Type is an MO-Defined-Type
        leaf capSuppr4ByteAsn {
            description "Capability Suppress 4-byte-as";

            // Type is an MO-Defined-Type
            type bgp_AdminSt;
        }
        leaf affGrp {
            type uint16;
        }

        // Egress Peer Engineering (EPE) for neighbor
        // Inherited From bgp:Common
        // Type is an MO-Defined-Type
        leaf epe {
            description "Egress Peer Engineering EPE for neighbor";

            // Type is an MO-Defined-Type
            type bgp_AdminSt;
        }
        leaf epePeerSet {
            type string {
            }
        }

        // This object holds local AS information pertaining to a peer
        container localasn-items {

            // Added containment as a singleton: Prefix=localasn
            // Acquired From Package bgp
            uses bgp_LocalAsn-group;
        }
    }

    grouping bgp_PolicyCont-group {

        // Peer address family controls
        // Type is an MO-Defined-Type
        leaf ctrl {
            description "Control";

            // Type is an MO-Defined-Type
            type bgp_PeerAfControl;
        }
        leaf allowedSelfAsCnt {
            type uint8 {
                range "0..10";
            }
            default "0";
        }

        // Soft Reconfiguration
        // Type is an MO-Defined-Type
        leaf softReconfigBackup {
            description "Soft Reconfiguration";

            // Type is an MO-Defined-Type
            type bgp_SoftReconfigBackup;
        }

        // Neighbor advertisement interval
        // Type is an MO-Defined-Type
        leaf advIntvl {
            description "Neighbor advertisement interval";

            // Type is an MO-Defined-Type
            type bgp_AdvInterval;
        }

        // Type is an MO-Defined-Type
        leaf defOrg {
            description "Default Originate is enabled";

            // Type is an MO-Defined-Type
            type bgp_AdminSt;
        }
        leaf defOrgRtMap {
            type string {
            }
        }

        // Capability Additional Paths
        // Type is an MO-Defined-Type
        leaf capAddlPaths {
            description "Capability Additional Paths";

            // Type is an MO-Defined-Type
            type bgp_CapAddlPathCapT;
        }
        leaf unSupprMap {
            type string {
            }
        }

        // as-override
        // Type is an MO-Defined-Type
        leaf asOverride {
            description "Override matching AS-number while sending update";

            // Type is an MO-Defined-Type
            type bgp_AdminSt;
        }

        // next-hop-third-party
        // Type is an MO-Defined-Type
        leaf nhThirdparty {
            description "Compute a third-party nexthop if possible";

            // Type is an MO-Defined-Type
            type bgp_AdminSt;
        }
        leaf wght {
            type string {
            }
        }
        leaf soo {
            type mtx_array_community;
        }

        // Send-community standard
        // Type is an MO-Defined-Type
        leaf sendComStd {
            description "Send-community standard";

            // Type is an MO-Defined-Type
            type bgp_AdminSt;
        }

        // Send-community extended
        // Type is an MO-Defined-Type
        leaf sendComExt {
            description "Send-community extended";

            // Type is an MO-Defined-Type
            type bgp_AdminSt;
        }

        // Bits in this property represent whether to inherit or
        // not to inherit from template.
        // To disable inheritance of an attribute from a template
        // of a neighbor AF, set the corresponding bit of this
        // property.
        // For example, to disable inheritance of 'send community'
        // from a template, set this property with value -
        // 'send-com'.
        // A note that any attributes configured for the neighbor AF
        // take priority over any attributes inherited from a
        // template.
        // From Interface bgp:InheritContPeerPolicyCtrl
        // Type is an MO-Defined-Type
        leaf inheritContPeerPolicyCtrl {
            description "Inherit control of peer policy parameters";

            // Type is an MO-Defined-Type
            type bgp_InheritContPeerPolicyCtrlType;
        }

        // Inherited From nw:Conn
        // Modified by Override: bgp:PolicyCont->name
        // Modified by Override: nw:Ep->name
        // Type is an MO-Defined-Type
        leaf name {
            description "Name";

            // Type is an MO-Defined-Type
            type naming_Name {
                length "1..64";
            }
        }

        // This policy tells on what to do when the number of prefixes
        // advertised by the peer crosses a maximum limit specified.
        // This is used as a defensive mechanism to protect resources
        // on the router
        container maxpfxp-items {

            // Added containment as a singleton: Prefix=maxpfxp
            // Acquired From Package bgp
            uses bgp_MaxPfxP-group;
        }

        // This object holds per advertise-map information
        container advtmap-items {

            // Added containment as a singleton: Prefix=advtmap
            // Acquired From Package bgp
            uses bgp_AdvtMap-group;
        }

        // Route control policy for routes coming/going to peers.
        // There are few ways to apply this policy, controlling
        // through route maps or prefix lists or filter lists.
        // If both are specified, the order is implicit. Prefix
        // lists are applied before route maps.
        // The direction specifies whether to apply this policy
        // in the incoming or outgoing direction
        container rtctrl-items {
            list RtCtrlP-list {
                key "direction";

                // Added containment: Prefix=rtctrl
                // Acquired From Package bgp
                uses bgp_RtCtrlP-group;
            }
        }
        container pfxctrl-items {
            list PfxCtrlP-list {
                key "direction";

                // Added containment: Prefix=pfxctrl
                // Acquired From Package bgp
                uses bgp_PfxCtrlP-group;
            }
        }
        container fltrctrl-items {
            list FltrCtrlP-list {
                key "direction";

                // Added containment: Prefix=fltrctrl
                // Acquired From Package bgp
                uses bgp_FltrCtrlP-group;
            }
        }

        // This object holds bgp peer af peer policy inherit
        container pol-items {
            list PolicyInheritRule-list {
                key "name";

                // Added containment: Prefix=pol
                // Acquired From Package bgp
                uses bgp_PolicyInheritRule-group;
            }
        }
    }

    grouping bgp_EvtHist-group {

        // Event-history buffer type
        // Type is an MO-Defined-Type
        leaf type {
            description "Configure event-history {cli | events | periodic | detail}";

            // Type is an MO-Defined-Type
            type bgp_EhType;
        }

        // Event-history buffer size
        // Type is an MO-Defined-Type
        leaf size {
            description "Configure event-history with buffer size";

            // Type is an MO-Defined-Type
            type bgp_Size;
        }
    }

    grouping compat_SuppFw-group {

        // Compatible version
        // Type is an MO-Defined-Type
        leaf version {
            description "Version";

            // Type is an MO-Defined-Type
            type cap_Version;
        }

        // status of filter check
        // Type is an MO-Defined-Type
        leaf filterCheckSt {
            description "Filter Check Status";

            // Type is an MO-Defined-Type
            type compat_FilterStatus;
        }
        leaf message {
            type string;
        }

        // From Interface naming:Named
        // Inherited From naming:NamedObject
        // Modified by Override: compat:SuppFw->name
        // Type is an MO-Defined-Type
        leaf name {
            description "Name";

            // Type is an MO-Defined-Type
            type naming_Name {
                length "1..64";
            }
        }
    }

    // Has Polymorphic containment of abstract object cap:Rule
    grouping cap_Cat-group {

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Card capability provider
        container card-items {
            list Card-list {
                config "false";
                key "vendor model version";

                // Added containment: Prefix=card
                // Acquired From Package eqptcap
                uses eqptcap_Card-group;
            }
        }

        // Port capability provider
        container port-items {
            list Port-list {
                config "false";
                key "vendor model version";

                // Added containment: Prefix=port
                // Acquired From Package eqptcap
                uses eqptcap_Port-group;
            }
        }

        // Psu capability provider
        container psu-items {
            list Psu-list {
                config "false";
                key "vendor model version";

                // Added containment: Prefix=psu
                // Acquired From Package eqptcap
                uses eqptcap_Psu-group;
            }
        }

        // Fan capability provider
        container fan-items {
            list Fan-list {
                config "false";
                key "vendor model version";

                // Added containment: Prefix=fan
                // Acquired From Package eqptcap
                uses eqptcap_Fan-group;
            }
        }

        // Sfp capability provider
        container sfp-items {
            list Sfp-list {
                config "false";
                key "vendor model version";

                // Added containment: Prefix=sfp
                // Acquired From Package eqptcap
                uses eqptcap_Sfp-group;
            }
        }
    }

    // Has Polymorphic containment of abstract object cap:Rule
    grouping eqptcap_Card-group {

        // Inherited From eqptcap:HwCapProvider
        // Type is an MO-Defined-Type
        leaf version {
            config "false";
            description "TBD";

            // Type is an MO-Defined-Type
            type cap_Version;
        }

        // Inherited From eqptcap:HwCapProvider
        // Type is an MO-Defined-Type
        leaf vendor {
            config "false";
            description "TBD";

            // Type is an MO-Defined-Type
            type cap_Vendor;
        }

        // Inherited From eqptcap:HwCapProvider
        // Type is an MO-Defined-Type
        leaf model {
            config "false";
            description "TBD";

            // Type is an MO-Defined-Type
            type cap_Model;
        }

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Manufacturing-related properties
        // such as PID and SKU.
        container mfg-items {

            // Added containment as a singleton: Prefix=mfg
            // Acquired From Package eqptcap
            uses eqptcap_MfgDef-group;
        }

        // Physical properties such as maximum temperature
        // and removal conditions.
        container phys-items {

            // Added containment as a singleton: Prefix=phys
            // Acquired From Package eqptcap
            uses eqptcap_PhysicalDef-group;
        }
    }

    grouping eqptcap_MfgDef-group {

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        leaf partNumber {
            config "false";
            type string;
        }
    }

    grouping eqptcap_PhysicalDef-group {

        // Type is an MO-Defined-Type
        leaf height {
            config "false";
            description "TBD";

            // Type is an MO-Defined-Type
            type eqptcap_Size;
        }

        // Type is an MO-Defined-Type
        leaf width {
            config "false";
            description "TBD";

            // Type is an MO-Defined-Type
            type eqptcap_Size;
        }

        // Type is an MO-Defined-Type
        leaf depth {
            config "false";
            description "TBD";

            // Type is an MO-Defined-Type
            type eqptcap_Size;
        }

        // Type is an MO-Defined-Type
        leaf weight {
            config "false";
            description "TBD";

            // Type is an MO-Defined-Type
            type eqptcap_Weight;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    // Has Polymorphic containment of abstract object cap:Rule
    grouping eqptcap_Port-group {

        // Inherited From eqptcap:HwCapProvider
        // Type is an MO-Defined-Type
        leaf version {
            config "false";
            description "TBD";

            // Type is an MO-Defined-Type
            type cap_Version;
        }

        // Inherited From eqptcap:HwCapProvider
        // Type is an MO-Defined-Type
        leaf vendor {
            config "false";
            description "TBD";

            // Type is an MO-Defined-Type
            type cap_Vendor;
        }

        // Inherited From eqptcap:HwCapProvider
        // Type is an MO-Defined-Type
        leaf model {
            config "false";
            description "TBD";

            // Type is an MO-Defined-Type
            type cap_Model;
        }

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Manufacturing-related properties
        // such as PID and SKU.
        container mfg-items {

            // Added containment as a singleton: Prefix=mfg
            // Acquired From Package eqptcap
            uses eqptcap_MfgDef-group;
        }

        // Physical properties such as maximum temperature
        // and removal conditions.
        container phys-items {

            // Added containment as a singleton: Prefix=phys
            // Acquired From Package eqptcap
            uses eqptcap_PhysicalDef-group;
        }
    }

    // Has Polymorphic containment of abstract object cap:Rule
    grouping eqptcap_Psu-group {

        // Inherited From eqptcap:HwCapProvider
        // Type is an MO-Defined-Type
        leaf version {
            config "false";
            description "TBD";

            // Type is an MO-Defined-Type
            type cap_Version;
        }

        // Inherited From eqptcap:HwCapProvider
        // Type is an MO-Defined-Type
        leaf vendor {
            config "false";
            description "TBD";

            // Type is an MO-Defined-Type
            type cap_Vendor;
        }

        // Inherited From eqptcap:HwCapProvider
        // Type is an MO-Defined-Type
        leaf model {
            config "false";
            description "TBD";

            // Type is an MO-Defined-Type
            type cap_Model;
        }

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Manufacturing-related properties
        // such as PID and SKU.
        container mfg-items {

            // Added containment as a singleton: Prefix=mfg
            // Acquired From Package eqptcap
            uses eqptcap_MfgDef-group;
        }

        // Physical properties such as maximum temperature
        // and removal conditions.
        container phys-items {

            // Added containment as a singleton: Prefix=phys
            // Acquired From Package eqptcap
            uses eqptcap_PhysicalDef-group;
        }
    }

    // Has Polymorphic containment of abstract object cap:Rule
    grouping eqptcap_Fan-group {

        // Inherited From eqptcap:HwCapProvider
        // Type is an MO-Defined-Type
        leaf version {
            config "false";
            description "TBD";

            // Type is an MO-Defined-Type
            type cap_Version;
        }

        // Inherited From eqptcap:HwCapProvider
        // Type is an MO-Defined-Type
        leaf vendor {
            config "false";
            description "TBD";

            // Type is an MO-Defined-Type
            type cap_Vendor;
        }

        // Inherited From eqptcap:HwCapProvider
        // Type is an MO-Defined-Type
        leaf model {
            config "false";
            description "TBD";

            // Type is an MO-Defined-Type
            type cap_Model;
        }

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Manufacturing-related properties
        // such as PID and SKU.
        container mfg-items {

            // Added containment as a singleton: Prefix=mfg
            // Acquired From Package eqptcap
            uses eqptcap_MfgDef-group;
        }

        // Physical properties such as maximum temperature
        // and removal conditions.
        container phys-items {

            // Added containment as a singleton: Prefix=phys
            // Acquired From Package eqptcap
            uses eqptcap_PhysicalDef-group;
        }
    }

    // Has Polymorphic containment of abstract object cap:Rule
    grouping eqptcap_Sfp-group {

        // Inherited From eqptcap:HwCapProvider
        // Type is an MO-Defined-Type
        leaf version {
            config "false";
            description "TBD";

            // Type is an MO-Defined-Type
            type cap_Version;
        }

        // Inherited From eqptcap:HwCapProvider
        // Type is an MO-Defined-Type
        leaf vendor {
            config "false";
            description "TBD";

            // Type is an MO-Defined-Type
            type cap_Vendor;
        }

        // Inherited From eqptcap:HwCapProvider
        // Type is an MO-Defined-Type
        leaf model {
            config "false";
            description "TBD";

            // Type is an MO-Defined-Type
            type cap_Model;
        }

        // SFP Manufacturing-related properties
        container mfg-items {
            list SfpMfgDef-list {
                config "false";
                key "partNumber";

                // Added containment: Prefix=mfg
                // Acquired From Package eqptcap
                uses eqptcap_SfpMfgDef-group;
            }
        }

        // Polymorphic containment of derivative object actrlcap:Rule (from cap:Rule)
        container actrlcaprule-items {

            // Abstract containment of actrlcap:Rule derived from cap:Rule
            list Rule-list {
                config "false";
                key "subj scope type";

                // Added containment: Prefix=actrlcaprule
                // Acquired From Package actrlcap
                uses actrlcap_Rule-group;
            }
        }

        // Polymorphic containment of derivative object l1cap:Rule (from cap:Rule)
        container l1caprule-items {

            // Abstract containment of l1cap:Rule derived from cap:Rule
            list Rule-list {
                config "false";
                key "subj scope type";

                // Added containment: Prefix=l1caprule
                // Acquired From Package l1cap
                uses l1cap_Rule-group;
            }
        }

        // Polymorphic containment of derivative object l2cap:Rule (from cap:Rule)
        container l2caprule-items {

            // Abstract containment of l2cap:Rule derived from cap:Rule
            list Rule-list {
                config "false";
                key "subj scope type";

                // Added containment: Prefix=l2caprule
                // Acquired From Package l2cap
                uses l2cap_Rule-group;
            }
        }

        // Polymorphic containment of derivative object l3cap:Rule (from cap:Rule)
        container l3caprule-items {

            // Abstract containment of l3cap:Rule derived from cap:Rule
            list Rule-list {
                config "false";
                key "subj scope type";

                // Added containment: Prefix=l3caprule
                // Acquired From Package l3cap
                uses l3cap_Rule-group;
            }
        }

        // Physical properties such as maximum temperature
        // and removal conditions.
        container phys-items {

            // Added containment as a singleton: Prefix=phys
            // Acquired From Package eqptcap
            uses eqptcap_PhysicalDef-group;
        }
    }

    grouping eqptcap_SfpMfgDef-group {
        leaf pnPattern {
            config "false";
            type string;
        }

        // Internal vendor id
        // Type is an MO-Defined-Type
        leaf intVendorId {
            config "false";
            description "Internal Vendor ID";

            // Type is an MO-Defined-Type
            type eqptcap_IntVendorId;
        }

        // Magic key
        // Type is an MO-Defined-Type
        leaf magicKey {
            config "false";
            description "Magic Key";

            // Type is an MO-Defined-Type
            type eqptcap_SfpVendorMagicKey;
        }

        // Transceiver Type
        // Type is an MO-Defined-Type
        leaf xcvr {
            config "false";
            description "Transceiver Type";

            // Type is an MO-Defined-Type
            type eqptcap_XcvrT;
        }

        // Connector Type
        // Type is an MO-Defined-Type
        leaf connector {
            config "false";
            description "Connector Type";

            // Type is an MO-Defined-Type
            type eqptcap_ConnT;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        leaf partNumber {
            config "false";
            type string;
        }
    }

    grouping coop_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per coop instance information. There is only
        // one instance of fvp running in the system today
        container inst-items {

            // Added containment as a singleton: Prefix=inst
            // Acquired From Package coop
            uses coop_Inst-group;
        }
    }

    grouping coop_Inst-group {

        // Role (oracle/citizen)
        // Type is an MO-Defined-Type
        leaf role {
            config "false";
            description "Role";

            // Type is an MO-Defined-Type
            type coop_Role;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This objects hold per coop domain (vrf) information
        container dom-items {
            list Dom-list {
                key "name";

                // Added containment: Prefix=dom
                // Acquired From Package coop
                uses coop_Dom-group;
            }
        }
    }

    grouping coop_Dom-group {
        leaf addr {
            config "false";
            type address_Ip;
        }

        // Operational state
        // Type is an MO-Defined-Type
        leaf operSt {
            config "false";
            description "Operational State";

            // Type is an MO-Defined-Type
            type coop_DomOperSt;
        }

        // Operational state qualifier
        // Type is an MO-Defined-Type
        leaf operStQual {
            config "false";
            description "Operational State Qualifier";

            // Type is an MO-Defined-Type
            type coop_DomOperStQual;
        }

        // Inherited From nw:Conn
        // Modified by Override: nw:CpDom->name
        // Type is an MO-Defined-Type
        leaf name {
            description "Name";

            // Type is an MO-Defined-Type
            type naming_Name {
                length "1..64";
            }
        }

        // Adjancency to the oracle node
        container oracle-items {
            list OracleAdj-list {
                config "false";
                key "addr";

                // Added containment: Prefix=oracle
                // Acquired From Package coop
                uses coop_OracleAdj-group;
            }
        }

        // Adjancency to the citizen node
        container citizen-items {
            list CitizenAdj-list {
                config "false";
                key "addr";

                // Added containment: Prefix=citizen
                // Acquired From Package coop
                uses coop_CitizenAdj-group;
            }
        }

        // Shard state
        container shard-items {

            // Added containment as a singleton: Prefix=shard
            // Acquired From Package coop
            uses coop_ShardSt-group;
        }

        // Repository policies
        container repp-items {
            list RepP-list {
                config "false";
                key "type";

                // Added containment: Prefix=repp
                // Acquired From Package coop
                uses coop_RepP-group;
            }
        }

        // Abstraction of coop database (repository)
        container db-items {
            list Db-list {
                config "false";
                key "type";

                // Added containment: Prefix=db
                // Acquired From Package coop
                uses coop_Db-group;
            }
        }
    }

    grouping coop_OracleAdj-group {

        // Inherited From nw:Conn
        // Modified by Override: nw:Ep->name
        // Type is an MO-Defined-Type
        leaf name {
            description "Name";

            // Type is an MO-Defined-Type
            type naming_Name {
                length "1..64";
            }
        }
        leaf addr {
            config "false";
            type address_Ip;
        }

        // Hello interval
        // Inherited From coop:AdjEp
        // Type is an MO-Defined-Type
        leaf helloIntvl {
            config "false";
            description "Hello Interval";

            // Type is an MO-Defined-Type
            type coop_HelloIntvl;
        }

        // Control flags
        // Inherited From coop:AdjEp
        // Type is an MO-Defined-Type
        leaf ctrl {
            config "false";
            description "Controls";

            // Type is an MO-Defined-Type
            type coop_PeerControl;
        }

        // Graceful restart timer
        // Inherited From coop:AdjEp
        // Type is an MO-Defined-Type
        leaf grTime {
            config "false";
            description "Graceful Restart Interval";

            // Type is an MO-Defined-Type
            type coop_GRTime;
        }

        // Operational state
        // Inherited From coop:AdjEp
        // Type is an MO-Defined-Type
        leaf operSt {
            config "false";
            description "Operational State";

            // Type is an MO-Defined-Type
            type coop_AdjOperSt;
        }

        // Operational state qualifier
        // Inherited From coop:AdjEp
        // Type is an MO-Defined-Type
        leaf operStQual {
            config "false";
            description "Operational State Qualifier";

            // Type is an MO-Defined-Type
            type coop_AdjOperStQual;
        }

        // Last update time (in NTP raw format)
        // Inherited From coop:AdjEp
        // Type is an MO-Defined-Type
        leaf lastContact {
            config "false";
            description "Last Contact";

            // Type is an MO-Defined-Type
            type coop_Timestamp;
        }

        // Flags
        // Inherited From coop:AdjEp
        // Type is an MO-Defined-Type
        leaf flags {
            config "false";
            description "Flags";

            // Type is an MO-Defined-Type
            type coop_AdjFlags;
        }

        // Shard state
        container shard-items {

            // Added containment as a singleton: Prefix=shard
            // Acquired From Package coop
            uses coop_ShardSt-group;
        }
    }

    grouping coop_ShardSt-group {

        // Shard master interval start
        // Type is an MO-Defined-Type
        leaf masterIntvlSt {
            config "false";
            description "Master Interval Start";

            // Type is an MO-Defined-Type
            type coop_ShardIntvl;
        }

        // Shard master interval end
        // Type is an MO-Defined-Type
        leaf masterIntvlEnd {
            config "false";
            description "Master Interval End";

            // Type is an MO-Defined-Type
            type coop_ShardIntvl;
        }

        // Shard backup interval start
        // Type is an MO-Defined-Type
        leaf bkupIntvlSt {
            config "false";
            description "Backup Interval Start";

            // Type is an MO-Defined-Type
            type coop_ShardIntvl;
        }

        // Shard backup interval end
        // Type is an MO-Defined-Type
        leaf bkupIntvlEnd {
            config "false";
            description "Backup Interval End";

            // Type is an MO-Defined-Type
            type coop_ShardIntvl;
        }

        // From Interface naming:Named
        // Inherited From naming:NamedObject
        // Type is an MO-Defined-Type
        leaf name {
            description "Name";

            // Type is an MO-Defined-Type
            type naming_Name;
        }
    }

    grouping coop_CitizenAdj-group {
        leaf vpcPeer {
            config "false";
            type address_Ip;
        }
        leaf vip {
            config "false";
            type address_Ip;
        }

        // Inherited From nw:Conn
        // Modified by Override: nw:Ep->name
        // Type is an MO-Defined-Type
        leaf name {
            description "Name";

            // Type is an MO-Defined-Type
            type naming_Name {
                length "1..64";
            }
        }
        leaf addr {
            config "false";
            type address_Ip;
        }

        // Hello interval
        // Inherited From coop:AdjEp
        // Type is an MO-Defined-Type
        leaf helloIntvl {
            config "false";
            description "Hello Interval";

            // Type is an MO-Defined-Type
            type coop_HelloIntvl;
        }

        // Control flags
        // Inherited From coop:AdjEp
        // Type is an MO-Defined-Type
        leaf ctrl {
            config "false";
            description "Controls";

            // Type is an MO-Defined-Type
            type coop_PeerControl;
        }

        // Graceful restart timer
        // Inherited From coop:AdjEp
        // Type is an MO-Defined-Type
        leaf grTime {
            config "false";
            description "Graceful Restart Interval";

            // Type is an MO-Defined-Type
            type coop_GRTime;
        }

        // Operational state
        // Inherited From coop:AdjEp
        // Type is an MO-Defined-Type
        leaf operSt {
            config "false";
            description "Operational State";

            // Type is an MO-Defined-Type
            type coop_AdjOperSt;
        }

        // Operational state qualifier
        // Inherited From coop:AdjEp
        // Type is an MO-Defined-Type
        leaf operStQual {
            config "false";
            description "Operational State Qualifier";

            // Type is an MO-Defined-Type
            type coop_AdjOperStQual;
        }

        // Last update time (in NTP raw format)
        // Inherited From coop:AdjEp
        // Type is an MO-Defined-Type
        leaf lastContact {
            config "false";
            description "Last Contact";

            // Type is an MO-Defined-Type
            type coop_Timestamp;
        }

        // Flags
        // Inherited From coop:AdjEp
        // Type is an MO-Defined-Type
        leaf flags {
            config "false";
            description "Flags";

            // Type is an MO-Defined-Type
            type coop_AdjFlags;
        }
    }

    grouping coop_RepP-group {

        // Type of the repository
        // Type is an MO-Defined-Type
        leaf type {
            config "false";
            description "Type";

            // Type is an MO-Defined-Type
            type coop_RepT;
        }

        // Administrative state
        // Type is an MO-Defined-Type
        leaf adminSt {
            config "false";
            description "Administrative State";

            // Type is an MO-Defined-Type
            type nw_AdminSt;
        }

        // Refresh interval
        // Type is an MO-Defined-Type
        leaf refreshIntvl {
            config "false";
            description "Refresh Interval";

            // Type is an MO-Defined-Type
            type coop_RefreshIntvl;
        }

        // WARN: Not used currently. May be used post FCS.
        // Dampening administrative state
        // Type is an MO-Defined-Type
        leaf dampAdminSt {
            config "false";
            description "Dampening Administrative State";

            // Type is an MO-Defined-Type
            type nw_AdminSt;
        }

        // Dampening action
        // Type is an MO-Defined-Type
        leaf dampAction {
            config "false";
            description "Dampening Action";

            // Type is an MO-Defined-Type
            type coop_DampAction;
        }

        // Dampening penalty
        // Type is an MO-Defined-Type
        leaf dampenPenalty {
            config "false";
            description "Dampening Penalty";

            // Type is an MO-Defined-Type
            type coop_DampPenalty;
        }

        // Dampening threshold
        // Type is an MO-Defined-Type
        leaf dampThresh {
            config "false";
            description "Dampening Threshold";

            // Type is an MO-Defined-Type
            type coop_DampThresh;
        }

        // Dampening reuse threshold
        // Type is an MO-Defined-Type
        leaf dampReuseThresh {
            config "false";
            description "Dampening Reuse Threshold";

            // Type is an MO-Defined-Type
            type coop_DampReuseThresh;
        }

        // Half life
        // Type is an MO-Defined-Type
        leaf dampHalfLife {
            config "false";
            description "Dampening Half Life";

            // Type is an MO-Defined-Type
            type coop_DampHalfLife;
        }

        // Dampening saturation threshold
        // Type is an MO-Defined-Type
        leaf dampSatThresh {
            config "false";
            description "Dampening Saturation Threshold";

            // Type is an MO-Defined-Type
            type coop_DampSatThresh;
        }

        // Collision load factor
        // Type is an MO-Defined-Type
        leaf loadFactor {
            config "false";
            description "Load Factor";

            // Type is an MO-Defined-Type
            type coop_CollLdFactor;
        }

        // Max repository size
        // Type is an MO-Defined-Type
        leaf maxRepSz {
            config "false";
            description "Maximum Repository Size";

            // Type is an MO-Defined-Type
            type coop_RepSz;
        }

        // Synthetic generator id (hash id)
        // Type is an MO-Defined-Type
        leaf synthGen {
            config "false";
            description "Synthetic Generator ID";

            // Type is an MO-Defined-Type
            type coop_SynthGen;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Static endpoint
        container ep-items {
            list Ep-list {
                config "false";
                key "vnid mac";

                // Added containment: Prefix=ep
                // Acquired From Package coop
                uses coop_Ep-group;
            }
        }
    }

    grouping coop_Ep-group {

        // Bridge domain vnid
        // Type is an MO-Defined-Type
        leaf vnid {
            config "false";
            description "VNID";

            // Type is an MO-Defined-Type
            type coop_Vnid;
        }
        leaf mac {
            config "false";
            type address_Mac;
        }

        // Publisher id
        // Type is an MO-Defined-Type
        leaf pubId {
            config "false";
            description "Publisher ID";

            // Type is an MO-Defined-Type
            type coop_PubId;
        }

        // controls
        // Type is an MO-Defined-Type
        leaf ctrl {
            config "false";
            description "Controls";

            // Type is an MO-Defined-Type
            type coop_EpControl;
        }

        // Inherited From nw:Conn
        // Modified by Override: nw:Ep->name
        // Type is an MO-Defined-Type
        leaf name {
            description "Name";

            // Type is an MO-Defined-Type
            type naming_Name {
                length "1..64";
            }
        }

        // IP entries in the static endpoint
        container ip-items {
            list IpAddr-list {
                config "false";
                key "addr";

                // Added containment: Prefix=ip
                // Acquired From Package coop
                uses coop_IpAddr-group;
            }
        }
    }

    grouping coop_IpAddr-group {
        leaf addr {
            config "false";
            type address_Ip;
        }

        // From Interface naming:Named
        // Inherited From naming:NamedObject
        // Type is an MO-Defined-Type
        leaf name {
            description "Name";

            // Type is an MO-Defined-Type
            type naming_Name;
        }
    }

    grouping coop_Db-group {

        // Type of the repository
        // Type is an MO-Defined-Type
        leaf type {
            config "false";
            description "Type";

            // Type is an MO-Defined-Type
            type coop_RepT;
        }

        // Inherited From nw:Conn
        // Modified by Override: nw:Db->name
        // Type is an MO-Defined-Type
        leaf name {
            description "Name";

            // Type is an MO-Defined-Type
            type naming_Name {
                length "1..64";
            }
        }
        container ctx-items {
            list CtxRec-list {
                config "false";
                key "vnid";

                // Added containment: Prefix=ctx
                // Acquired From Package coop
                uses coop_CtxRec-group;
            }
        }

        // Ep records
        container epr-items {
            list EpRec-list {
                config "false";
                key "vnid mac";

                // Added containment: Prefix=epr
                // Acquired From Package coop
                uses coop_EpRec-group;
            }
        }

        // IP Only records
        container vrf-items {
            list IpOnlyRec-list {
                config "false";
                key "vrfVnid addr";

                // Added containment: Prefix=vrf
                // Acquired From Package coop
                uses coop_IpOnlyRec-group;
            }
        }

        // Leaf records
        container leaf-items {
            list LeafRec-list {
                config "false";
                key "pubId";

                // Added containment: Prefix=leaf
                // Acquired From Package coop
                uses coop_LeafRec-group;
            }
        }

        // IPv4 multicast group records
        container mgv4-items {
            list McGrpv4Rec-list {
                config "false";
                key "version srcIp mcGrpIp vnid";

                // Added containment: Prefix=mgv4
                // Acquired From Package coop
                uses coop_McGrpv4Rec-group;
            }
        }

        // IPv6 multicast group records
        container mgv6-items {
            list McGrpv6Rec-list {
                config "false";
                key "version srcIp mcGrpIp vnid";

                // Added containment: Prefix=mgv6
                // Acquired From Package coop
                uses coop_McGrpv6Rec-group;
            }
        }

        // Mrouter records
        container mrtr-items {
            list MrtrRec-list {
                config "false";
                key "vnid";

                // Added containment: Prefix=mrtr
                // Acquired From Package coop
                uses coop_MrtrRec-group;
            }
        }

        // Vpc records
        container r-items {
            list VpcRec-list {
                config "false";
                key "swId portId";

                // Added containment: Prefix=r
                // Acquired From Package coop
                uses coop_VpcRec-group;
            }
        }
    }

    grouping coop_CtxRec-group {

        // Fabric VRF vnid
        // Type is an MO-Defined-Type
        leaf vnid {
            config "false";
            description "VNID";

            // Type is an MO-Defined-Type
            type coop_Vnid;
        }

        // Flags
        // Type is an MO-Defined-Type
        leaf flags {
            config "false";
            description "Flags";

            // Type is an MO-Defined-Type
            type coop_CtxFlags;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Rel-def from Ctx2Leaf
        container rsctx2Leaf-items {

            // Abstract containment of rsctx2Leaf derived from coop:CtxRec
            list RsCtx2Leaf-list {
                config "false";
                key "tDn";

                // Added containment: Prefix=rsctx2Leaf
                // Acquired From Package coop
                uses coop_RsCtx2Leaf_source-group;
            }
        }
    }

    grouping coop_EpRec-group {

        // Bridge domain vnid
        // Type is an MO-Defined-Type
        leaf vnid {
            config "false";
            description "VNID";

            // Type is an MO-Defined-Type
            type coop_Vnid;
        }
        leaf mac {
            config "false";
            type address_Mac;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Vrf vnid
        // Inherited From coop:EpRecBase
        // Type is an MO-Defined-Type
        leaf vrfVnid {
            config "false";
            description "VRF VNID";

            // Type is an MO-Defined-Type
            type coop_Vnid;
        }

        // Publisher id
        // Inherited From coop:EpRecBase
        // Type is an MO-Defined-Type
        leaf pubId {
            config "false";
            description "Published ID";

            // Type is an MO-Defined-Type
            type coop_PubId;
        }

        // Flags
        // Inherited From coop:EpRecBase
        // Type is an MO-Defined-Type
        leaf flags {
            config "false";
            description "Flags";

            // Type is an MO-Defined-Type
            type coop_EpFlags;
        }

        // Synthetic ip
        // Inherited From coop:EpRecBase
        // Type is an MO-Defined-Type
        leaf synthIp {
            config "false";
            description "Synthetic IP";

            // Type is an MO-Defined-Type
            type coop_SynthIp;
        }

        // Synthetic vrf
        // Inherited From coop:EpRecBase
        // Type is an MO-Defined-Type
        leaf synthVrf {
            config "false";
            description "Synthetic VRF";

            // Type is an MO-Defined-Type
            type coop_SynthVrf;
        }

        // Synthetic flags
        // Inherited From coop:EpRecBase
        // Type is an MO-Defined-Type
        leaf synthFlags {
            config "false";
            description "Sythetic Flags";

            // Type is an MO-Defined-Type
            type coop_SynthFlags;
        }

        // current citizen node
        // Inherited From coop:EpRecBase
        // Type is an MO-Defined-Type
        leaf currCitizen {
            config "false";
            description "Current Citizen";

            // Type is an MO-Defined-Type
            type coop_AdjAddr;
        }

        // previous citizen node
        // Inherited From coop:EpRecBase
        // Type is an MO-Defined-Type
        leaf prevCitizen {
            config "false";
            description "Previous Citizen";

            // Type is an MO-Defined-Type
            type coop_AdjAddr;
        }

        // Prior to previous citizen node
        // Inherited From coop:EpRecBase
        // Type is an MO-Defined-Type
        leaf pprevCitizen {
            config "false";
            description "Prior to Previous Citizen";

            // Type is an MO-Defined-Type
            type coop_AdjAddr;
        }

        // IPv4 entries in endpoint record
        container epip4-items {
            list Ipv4Rec-list {
                config "false";
                key "addr";

                // Added containment: Prefix=epip4
                // Acquired From Package coop
                uses coop_Ipv4Rec-group;
            }
        }

        // IPv6 entries in endpoint record
        container epip6-items {
            list Ipv6Rec-list {
                config "false";
                key "addr";

                // Added containment: Prefix=epip6
                // Acquired From Package coop
                uses coop_Ipv6Rec-group;
            }
        }

        // Ep VPC citizen record
        container epvpc-items {
            list EpVpcRec-list {
                config "false";
                key "virtSwId vpcPortId";

                // Added containment: Prefix=epvpc
                // Acquired From Package coop
                uses coop_EpVpcRec-group;
            }
        }
    }

    grouping coop_Ipv4Rec-group {
        leaf addr {
            config "false";
            type address_Ipv4;
        }

        // Inherited From nw:Conn
        // Modified by Override: nw:DbRec->name
        // Type is an MO-Defined-Type
        leaf name {
            description "Name";

            // Type is an MO-Defined-Type
            type naming_Name {
                length "1..64";
            }
        }

        // Synthetic ip
        // Inherited From coop:IpRec
        // Type is an MO-Defined-Type
        leaf synthIp {
            config "false";
            description "Synthetic IP";

            // Type is an MO-Defined-Type
            type coop_SynthIp;
        }

        // Synthetic vrf
        // Inherited From coop:IpRec
        // Type is an MO-Defined-Type
        leaf synthVrf {
            config "false";
            description "Synthetic VRF";

            // Type is an MO-Defined-Type
            type coop_SynthVrf;
        }

        // Synthetic flags
        // Inherited From coop:IpRec
        // Type is an MO-Defined-Type
        leaf synthFlags {
            config "false";
            description "Synthetic Flags";

            // Type is an MO-Defined-Type
            type coop_SynthFlags;
        }
    }

    grouping coop_Ipv6Rec-group {
        leaf addr {
            config "false";
            type address_Ipv6;
        }

        // Inherited From nw:Conn
        // Modified by Override: nw:DbRec->name
        // Type is an MO-Defined-Type
        leaf name {
            description "Name";

            // Type is an MO-Defined-Type
            type naming_Name {
                length "1..64";
            }
        }

        // Synthetic ip
        // Inherited From coop:IpRec
        // Type is an MO-Defined-Type
        leaf synthIp {
            config "false";
            description "Synthetic IP";

            // Type is an MO-Defined-Type
            type coop_SynthIp;
        }

        // Synthetic vrf
        // Inherited From coop:IpRec
        // Type is an MO-Defined-Type
        leaf synthVrf {
            config "false";
            description "Synthetic VRF";

            // Type is an MO-Defined-Type
            type coop_SynthVrf;
        }

        // Synthetic flags
        // Inherited From coop:IpRec
        // Type is an MO-Defined-Type
        leaf synthFlags {
            config "false";
            description "Synthetic Flags";

            // Type is an MO-Defined-Type
            type coop_SynthFlags;
        }
    }

    grouping coop_EpVpcRec-group {

        // Virtual switch id
        // Type is an MO-Defined-Type
        leaf virtSwId {
            config "false";
            description "Vritual Switch ID";

            // Type is an MO-Defined-Type
            type coop_SwId;
        }

        // vpc port id
        // Type is an MO-Defined-Type
        leaf vpcPortId {
            config "false";
            description "VPC Port ID";

            // Type is an MO-Defined-Type
            type coop_PortId;
        }

        // Inherited From nw:Conn
        // Modified by Override: nw:DbRec->name
        // Type is an MO-Defined-Type
        leaf name {
            description "Name";

            // Type is an MO-Defined-Type
            type naming_Name {
                length "1..64";
            }
        }
    }

    grouping coop_IpOnlyRec-group {
        leaf addr {
            config "false";
            type address_Ip;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Vrf vnid
        // Inherited From coop:EpRecBase
        // Type is an MO-Defined-Type
        leaf vrfVnid {
            config "false";
            description "VRF VNID";

            // Type is an MO-Defined-Type
            type coop_Vnid;
        }

        // Publisher id
        // Inherited From coop:EpRecBase
        // Type is an MO-Defined-Type
        leaf pubId {
            config "false";
            description "Published ID";

            // Type is an MO-Defined-Type
            type coop_PubId;
        }

        // Flags
        // Inherited From coop:EpRecBase
        // Type is an MO-Defined-Type
        leaf flags {
            config "false";
            description "Flags";

            // Type is an MO-Defined-Type
            type coop_EpFlags;
        }

        // Synthetic ip
        // Inherited From coop:EpRecBase
        // Type is an MO-Defined-Type
        leaf synthIp {
            config "false";
            description "Synthetic IP";

            // Type is an MO-Defined-Type
            type coop_SynthIp;
        }

        // Synthetic vrf
        // Inherited From coop:EpRecBase
        // Type is an MO-Defined-Type
        leaf synthVrf {
            config "false";
            description "Synthetic VRF";

            // Type is an MO-Defined-Type
            type coop_SynthVrf;
        }

        // Synthetic flags
        // Inherited From coop:EpRecBase
        // Type is an MO-Defined-Type
        leaf synthFlags {
            config "false";
            description "Sythetic Flags";

            // Type is an MO-Defined-Type
            type coop_SynthFlags;
        }

        // current citizen node
        // Inherited From coop:EpRecBase
        // Type is an MO-Defined-Type
        leaf currCitizen {
            config "false";
            description "Current Citizen";

            // Type is an MO-Defined-Type
            type coop_AdjAddr;
        }

        // previous citizen node
        // Inherited From coop:EpRecBase
        // Type is an MO-Defined-Type
        leaf prevCitizen {
            config "false";
            description "Previous Citizen";

            // Type is an MO-Defined-Type
            type coop_AdjAddr;
        }

        // Prior to previous citizen node
        // Inherited From coop:EpRecBase
        // Type is an MO-Defined-Type
        leaf pprevCitizen {
            config "false";
            description "Prior to Previous Citizen";

            // Type is an MO-Defined-Type
            type coop_AdjAddr;
        }
    }

    grouping coop_LeafRec-group {

        // Publisher id
        // Type is an MO-Defined-Type
        leaf pubId {
            config "false";
            description "Publisher ID";

            // Type is an MO-Defined-Type
            type coop_PubId;
        }

        // Inherited From nw:Conn
        // Modified by Override: nw:DbRec->name
        // Type is an MO-Defined-Type
        leaf name {
            description "Name";

            // Type is an MO-Defined-Type
            type naming_Name {
                length "1..64";
            }
        }
    }

    grouping coop_McGrpv4Rec-group {

        // IGMP version
        // Type is an MO-Defined-Type
        leaf version {
            config "false";
            description "Version";

            // Type is an MO-Defined-Type
            type coop_IGMPVersion;
        }
        leaf srcIp {
            config "false";
            type address_Ipv4;
        }
        leaf mcGrpIp {
            config "false";
            type address_Ipv4;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Vnid (BD vnid if bridging or L3Ctx vnid if routing)
        // Inherited From coop:McGrpRec
        // Type is an MO-Defined-Type
        leaf vnid {
            config "false";
            description "VNID";

            // Type is an MO-Defined-Type
            type coop_Vnid;
        }

        // Flags
        // Inherited From coop:McGrpRec
        // Type is an MO-Defined-Type
        leaf flags {
            config "false";
            description "Flags";

            // Type is an MO-Defined-Type
            type coop_McGrpFlags;
        }
    }

    grouping coop_McGrpv6Rec-group {

        // MLD version
        // Type is an MO-Defined-Type
        leaf version {
            config "false";
            description "Version";

            // Type is an MO-Defined-Type
            type coop_IGMPVersion;
        }
        leaf srcIp {
            config "false";
            type address_Ipv6;
        }
        leaf mcGrpIp {
            config "false";
            type address_Ipv6;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Vnid (BD vnid if bridging or L3Ctx vnid if routing)
        // Inherited From coop:McGrpRec
        // Type is an MO-Defined-Type
        leaf vnid {
            config "false";
            description "VNID";

            // Type is an MO-Defined-Type
            type coop_Vnid;
        }

        // Flags
        // Inherited From coop:McGrpRec
        // Type is an MO-Defined-Type
        leaf flags {
            config "false";
            description "Flags";

            // Type is an MO-Defined-Type
            type coop_McGrpFlags;
        }
    }

    grouping coop_MrtrRec-group {

        // Bridge domain vnid
        // Type is an MO-Defined-Type
        leaf vnid {
            config "false";
            description "VNID";

            // Type is an MO-Defined-Type
            type coop_Vnid;
        }

        // Flags
        // Type is an MO-Defined-Type
        leaf flags {
            config "false";
            description "Flags";

            // Type is an MO-Defined-Type
            type coop_MrtrFlags;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Rel-def from Mrtr2Leaf
        container rsmrtr2Leaf-items {

            // Abstract containment of rsmrtr2Leaf derived from coop:MrtrRec
            list RsMrtr2Leaf-list {
                config "false";
                key "tDn";

                // Added containment: Prefix=rsmrtr2Leaf
                // Acquired From Package coop
                uses coop_RsMrtr2Leaf_source-group;
            }
        }
    }

    grouping coop_VpcRec-group {

        // Switch Id
        // Type is an MO-Defined-Type
        leaf swId {
            config "false";
            description "Switch ID";

            // Type is an MO-Defined-Type
            type coop_SwId;
        }

        // vpc Port Id
        // Type is an MO-Defined-Type
        leaf portId {
            config "false";
            description "Port ID";

            // Type is an MO-Defined-Type
            type coop_PortId;
        }

        // Publisher id
        // Type is an MO-Defined-Type
        leaf pubId {
            config "false";
            description "Publisher ID";

            // Type is an MO-Defined-Type
            type coop_PubId;
        }

        // Inherited From nw:Conn
        // Modified by Override: nw:DbRec->name
        // Type is an MO-Defined-Type
        leaf name {
            description "Name";

            // Type is an MO-Defined-Type
            type naming_Name {
                length "1..64";
            }
        }

        // Record timestamp
        // Inherited From coop:CoopRec
        // Type is an MO-Defined-Type
        leaf recordTs {
            config "false";
            description "Record Timestamp";

            // Type is an MO-Defined-Type
            type coop_Timestamp;
        }

        // Last published timestamp
        // Inherited From coop:CoopRec
        // Type is an MO-Defined-Type
        leaf lastPub {
            config "false";
            description "Last Published";

            // Type is an MO-Defined-Type
            type coop_Timestamp;
        }

        // Last dampened timestamp
        // Inherited From coop:CoopRec
        // Type is an MO-Defined-Type
        leaf lastDampen {
            config "false";
            description "Last Dampened";

            // Type is an MO-Defined-Type
            type coop_Timestamp;
        }

        // Accumulated dampen penalty
        // Inherited From coop:CoopRec
        // Type is an MO-Defined-Type
        leaf dampPenalty {
            config "false";
            description "Damp Penalty";

            // Type is an MO-Defined-Type
            type coop_DampPenalty;
        }

        // Per node in vpc configuration record
        container vpcr-items {
            list VpcNodeRec-list {
                config "false";
                key "swId portId";

                // Added containment: Prefix=vpcr
                // Acquired From Package coop
                uses coop_VpcNodeRec-group;
            }
        }
    }

    grouping coop_VpcNodeRec-group {

        // Switch Id
        // Type is an MO-Defined-Type
        leaf swId {
            config "false";
            description "Switch ID";

            // Type is an MO-Defined-Type
            type coop_SwId;
        }

        // Port Id
        // Type is an MO-Defined-Type
        leaf portId {
            config "false";
            description "Port ID";

            // Type is an MO-Defined-Type
            type coop_PortId;
        }

        // Flags
        // Type is an MO-Defined-Type
        leaf flags {
            config "false";
            description "Flags";

            // Type is an MO-Defined-Type
            type coop_VpcFlags;
        }

        // Inherited From nw:Conn
        // Modified by Override: nw:DbRec->name
        // Type is an MO-Defined-Type
        leaf name {
            description "Name";

            // Type is an MO-Defined-Type
            type naming_Name {
                length "1..64";
            }
        }
    }

    grouping datetime_Clock-group {

        // Type is an MO-Defined-Type
        leaf protocol {
            description "Protocol Type";

            // Type is an MO-Defined-Type
            type datetime_ClockProtocol;
        }

        // Type is an MO-Defined-Type
        leaf vdcId {
            description "Vdc";

            // Type is an MO-Defined-Type
            type datetime_VdcId;
        }

        // Type is an MO-Defined-Type
        leaf format {
            description "Clock Format";

            // Type is an MO-Defined-Type
            type datetime_ClockFormat;
        }

        // From Interface naming:Named
        // Inherited From naming:NamedObject
        // Modified by Override: pol:Obj->name
        // Modified by Override: datetime:APol->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From datetime:APol
        // Type is an MO-Defined-Type
        leaf adminSt {
            description "Admin State";

            // Type is an MO-Defined-Type
            type datetime_AdminState;
        }

        // Inherited From datetime:APol
        // Type is an MO-Defined-Type
        leaf authSt {
            description "Authentication  State";

            // Type is an MO-Defined-Type
            type datetime_AdminState;
        }

        container set-items {

            // Added containment as a singleton: Prefix=set
            // Acquired From Package datetime
            uses datetime_ClockSet-group;
        }

        container timezone-items {

            // Added containment as a singleton: Prefix=timezone
            // Acquired From Package datetime
            uses datetime_Timezone-group;
        }

        container summertime-items {

            // Added containment as a singleton: Prefix=summertime
            // Acquired From Package datetime
            uses datetime_SummerT-group;
        }
    }

    grouping datetime_ClockSet-group {
        leaf time {
            type string;
        }

        // Type is an MO-Defined-Type
        leaf date {
            description "Day of the month";

            // Type is an MO-Defined-Type
            type datetime_Date;
        }

        // Type is an MO-Defined-Type
        leaf month {
            description "Month of the year";

            // Type is an MO-Defined-Type
            type datetime_Month;
        }

        // Type is an MO-Defined-Type
        leaf year {
            description "Year";

            // Type is an MO-Defined-Type
            type datetime_Year;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
    }

    grouping datetime_Timezone-group {

        // Type is an MO-Defined-Type
        leaf hours {
            description "Hours offset from UTC";

            // Type is an MO-Defined-Type
            type datetime_HourOffset;
        }

        // Type is an MO-Defined-Type
        leaf minutes {
            description "Minutes offset from UTC";

            // Type is an MO-Defined-Type
            type datetime_MinuteOffsetTz;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf nameT {
            type string;
        }
    }

    grouping datetime_SummerT-group {

        // Type is an MO-Defined-Type
        leaf startWeek {
            description "Week number to start";

            // Type is an MO-Defined-Type
            type datetime_WeekNum;
        }
        leaf startDay {
            type string;
            default "Sun";
        }
        leaf startMon {
            type string;
            default "Mar";
        }
        leaf startTime {
            type string;
            default "02:00";
        }

        // Type is an MO-Defined-Type
        leaf endWeek {
            description "Week number to end";

            // Type is an MO-Defined-Type
            type datetime_WeekNum;
        }
        leaf endDay {
            type string;
            default "Sun";
        }
        leaf endMon {
            type string;
            default "Nov";
        }
        leaf endTime {
            type string;
            default "02:00";
        }

        // Type is an MO-Defined-Type
        leaf offsetMin {
            description "Offset to add in minutes";

            // Type is an MO-Defined-Type
            type datetime_MinuteOffsetSt;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf nameT {
            type string;
        }
    }

    grouping datetime_ClkPol-group {

        // Type is an MO-Defined-Type
        leaf flags {
            config "false";
            description "Flags";

            // Type is an MO-Defined-Type
            type datetime_SysStatusFlags;
        }

        // Type is an MO-Defined-Type
        leaf leap {
            config "false";
            description "Leap";

            // Type is an MO-Defined-Type
            type datetime_NTPLeapIndicator;
        }

        // Type is an MO-Defined-Type
        leaf stratum {
            config "false";
            description "Stratum";

            // Type is an MO-Defined-Type
            type datetime_NTPStratum;
        }
        leaf precision {
            config "false";
            type int32;
        }

        // Type is an MO-Defined-Type
        leaf rootDelay {
            config "false";
            description "RootDelay";

            // Type is an MO-Defined-Type
            type datetime_NTPSignedTimeValue;
        }

        // Type is an MO-Defined-Type
        leaf rootDispersion {
            config "false";
            description "RootDispersion";

            // Type is an MO-Defined-Type
            type datetime_NTPUnsignedTimeValue;
        }

        // Type is an MO-Defined-Type
        leaf refId {
            config "false";
            description "RefId";

            // Type is an MO-Defined-Type
            type datetime_NTPRefId;
        }
        leaf refTime {
            config "false";
            type uint64;
        }
        leaf refTimeRaw {
            config "false";
            type uint64;
        }

        // Type is an MO-Defined-Type
        leaf poll {
            config "false";
            description "Poll";

            // Type is an MO-Defined-Type
            type datetime_NTPPollInterval;
        }

        // Type is an MO-Defined-Type
        leaf peer {
            config "false";
            description "Peer";

            // Type is an MO-Defined-Type
            type datetime_NTPAssocIdentifier;
        }
        leaf clock {
            config "false";
            type uint64;
        }
        leaf clockRaw {
            config "false";
            type uint64;
        }

        // Type is an MO-Defined-Type
        leaf srvStatus {
            config "false";
            description "SrvStatus";

            // Type is an MO-Defined-Type
            type datetime_NtpSrvStatus;
        }

        // Type is an MO-Defined-Type
        leaf logging {
            description "Logging";

            // Type is an MO-Defined-Type
            type datetime_AdminState;
        }

        // Type is an MO-Defined-Type
        leaf loggingLevel {
            description "LoggingLevel";

            // Type is an MO-Defined-Type
            type datetime_LoggingLevel;
        }

        // Type is an MO-Defined-Type
        leaf master {
            description "Master";

            // Type is an MO-Defined-Type
            type datetime_AdminState;
        }

        // Type is an MO-Defined-Type
        leaf masterStratum {
            description "MasterStratum";

            // Type is an MO-Defined-Type
            type datetime_Stratum;
        }

        // From Interface naming:Named
        // Inherited From naming:NamedObject
        // Modified by Override: datetime:ClkPol->name
        // Modified by Override: pol:Obj->name
        // Modified by Override: datetime:APol->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From datetime:APol
        // Modified by Override: datetime:ClkPol->adminSt
        // Type is an MO-Defined-Type
        leaf adminSt {
            description "Admin State";

            // Type is an MO-Defined-Type
            type datetime_AdminState;
        }

        // Inherited From datetime:APol
        // Modified by Override: datetime:ClkPol->authSt
        // Type is an MO-Defined-Type
        leaf authSt {
            description "Authentication  State";

            // Type is an MO-Defined-Type
            type datetime_AdminState;
        }

        // NTP Client Autentication    @@@ this is not exposed in logical model, we will start
        // @@@ using it when the logical model is enabled after all
        // @@@ the bug fixes
        container auth-items {
            list NtpAuth-list {
                key "id";

                // Added containment: Prefix=auth
                // Acquired From Package datetime
                uses datetime_NtpAuth-group;
            }
        }

        // NTP Providers
        container prov-items {
            list NtpProvider-list {
                key "name";

                // Added containment: Prefix=prov
                // Acquired From Package datetime
                uses datetime_NtpProvider-group;
            }
        }

        // NTP Access Group
        container accessgroup-items {

            // Added containment as a singleton: Prefix=accessgroup
            // Acquired From Package datetime
            uses datetime_AccessGroup-group;
        }

        // This is used to store IP address of source of NTP packets
        container srcIp-items {

            // Added containment as a singleton: Prefix=srcIp
            // Acquired From Package datetime
            uses datetime_NtpSrcIp-group;
        }

        // This is used to store interface sending NTP packets
        container srcIf-items {

            // Added containment as a singleton: Prefix=srcIf
            // Acquired From Package datetime
            uses datetime_NtpSrcIf-group;
        }
    }

    grouping datetime_NtpAuth-group {

        // encrypted key
        // Type is an MO-Defined-Type
        leaf encryptedKey {
            description "Encrypted Key";

            // Type is an MO-Defined-Type
            type datetime_Key;
        }

        // Type is an MO-Defined-Type
        leaf isEncrypt {
            description "Is Encrypted Flag";

            // Type is an MO-Defined-Type
            type datetime_Encrypt;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Inherited From datetime:ANtpAuthKey
        // Modified by Override: datetime:NtpAuth->key
        // Type is an MO-Defined-Type
        leaf key {
            description "Key";

            // Type is an MO-Defined-Type
            type datetime_Key;
        }

        // Inherited From datetime:ANtpAuthKey
        // Modified by Override: datetime:NtpAuth->id
        // Type is an MO-Defined-Type
        leaf id {
            description "Auth Key Id";

            // Type is an MO-Defined-Type
            type datetime_AuthKeyId;
        }
        leaf trusted {
            type boolean;
        }
    }

    grouping datetime_NtpProvider-group {

        // This property tells if the configured provider is NTP server  or peer
        // Type is an MO-Defined-Type
        leaf provT {
            description "NTP server or peer";

            // Type is an MO-Defined-Type
            type datetime_ProvT;
        }

        // vrf name
        // Type is an MO-Defined-Type
        leaf vrf {
            description "VRF";

            // Type is an MO-Defined-Type
            type l3_VrfName;
        }

        // From Interface naming:Named
        // Inherited From naming:NamedObject
        // Modified by Override: datetime:NtpProvider->name
        // Modified by Override: pol:Obj->name
        // Modified by Override: datetime:ANtpProv->name
        // Type is an MO-Defined-Type
        leaf name {
            description "Name";

            // Type is an MO-Defined-Type
            type naming_Name {

                // Restriction copied from aaa:NtpHostname type    NXOS has max limit of 80 chars, limiting to 64 here
                length "0..64";
            }
        }

        // From Interface naming:Described
        // Inherited From pol:Comp
        // Type is an MO-Defined-Type
        leaf descr {
            description "Description";

            // Type is an MO-Defined-Type
            type naming_Descr;
        }
        leaf preferred {
            type boolean;
        }

        // Inherited From datetime:ANtpProv
        // Modified by Override: datetime:NtpProvider->minPoll
        // Type is an MO-Defined-Type
        leaf minPoll {
            description "Min Poll";

            // Type is an MO-Defined-Type
            type datetime_Poll;
        }

        // Inherited From datetime:ANtpProv
        // Modified by Override: datetime:NtpProvider->maxPoll
        // Type is an MO-Defined-Type
        leaf maxPoll {
            description "Max Poll";

            // Type is an MO-Defined-Type
            type datetime_Poll;
        }

        // Inherited From datetime:ANtpProv
        // Modified by Override: datetime:NtpProvider->keyId
        // Type is an MO-Defined-Type
        leaf keyId {
            description "Key Id";

            // Type is an MO-Defined-Type
            type datetime_KeyId;
        }

        // Status for NTP Providers
        container status-items {

            // Added containment as a singleton: Prefix=status
            // Acquired From Package datetime
            uses datetime_NtpProviderStatus-group;
        }

        // Rel-def from NtpProviderToNtpAuth
        container rsntpProviderToNtpAuth-items {

            // Abstract containment of rsntpProviderToNtpAuth derived from datetime:NtpProvider
            list RsNtpProviderToNtpAuth-list {
                config "false";
                key "tDn";

                // Added containment: Prefix=rsntpProviderToNtpAuth
                // Acquired From Package datetime
                uses datetime_RsNtpProviderToNtpAuth_source-group;
            }
        }

        container dbgStatistics-items {

            // Added containment as a singleton: Prefix=dbgStatistics
            // Acquired From Package datetime
            uses datetime_Statistics-group;
        }
    }

    grouping datetime_NtpProviderStatus-group {

        // Type is an MO-Defined-Type
        leaf flags {
            config "false";
            description "Flags";

            // Type is an MO-Defined-Type
            type datetime_PeerStatusFlags;
        }

        // Type is an MO-Defined-Type
        leaf assocId {
            config "false";
            description "AssocId";

            // Type is an MO-Defined-Type
            type datetime_NTPAssocIdentifier;
        }
        leaf peerAddress {
            config "false";
            type address_Ipv4;
        }
        leaf peerPort {
            config "false";
            type uint32;
        }
        leaf hostAddress {
            config "false";
            type address_Ipv4;
        }
        leaf hostPort {
            config "false";
            type uint32;
        }

        // Type is an MO-Defined-Type
        leaf leap {
            config "false";
            description "Leap";

            // Type is an MO-Defined-Type
            type datetime_NTPLeapIndicator;
        }

        // Type is an MO-Defined-Type
        leaf mode {
            config "false";
            description "Mode";

            // Type is an MO-Defined-Type
            type datetime_NTPPeerMode;
        }

        // Type is an MO-Defined-Type
        leaf stratum {
            config "false";
            description "Stratum";

            // Type is an MO-Defined-Type
            type datetime_NTPStratum;
        }

        // Type is an MO-Defined-Type
        leaf peerPoll {
            config "false";
            description "PeerPoll";

            // Type is an MO-Defined-Type
            type datetime_NTPPollInterval;
        }

        // Type is an MO-Defined-Type
        leaf hostPoll {
            config "false";
            description "HostPoll";

            // Type is an MO-Defined-Type
            type datetime_NTPPollInterval;
        }
        leaf hostPollSeconds {
            config "false";
            type uint32;
        }
        leaf precision {
            config "false";
            type int32;
        }

        // Type is an MO-Defined-Type
        leaf rootDelay {
            config "false";
            description "RootDelay";

            // Type is an MO-Defined-Type
            type datetime_NTPSignedTimeValue;
        }

        // Type is an MO-Defined-Type
        leaf rootDispersion {
            config "false";
            description "RootDispersion";

            // Type is an MO-Defined-Type
            type datetime_NTPUnsignedTimeValue;
        }

        // Type is an MO-Defined-Type
        leaf refId {
            config "false";
            description "RefId";

            // Type is an MO-Defined-Type
            type datetime_NTPRefId;
        }
        leaf refTime {
            config "false";
            type uint64;
        }
        leaf refTimeRaw {
            config "false";
            type uint64;
        }
        leaf orgTime {
            config "false";
            type uint64;
        }
        leaf orgTimeRaw {
            config "false";
            type uint64;
        }
        leaf receiveTime {
            config "false";
            type uint64;
        }
        leaf receiveTimeRaw {
            config "false";
            type uint64;
        }
        leaf transmitTime {
            config "false";
            type uint64;
        }
        leaf transmitTimeRaw {
            config "false";
            type uint64;
        }
        leaf reach {
            config "false";
            type uint8;
        }
        leaf timer {
            config "false";
            type uint32;
        }
        leaf offset {
            config "false";
            type int32;
        }
        leaf delay {
            config "false";
            type string;
        }
        leaf delayRaw {
            config "false";
            type int32;
        }

        // Type is an MO-Defined-Type
        leaf dispersion {
            config "false";
            description "Dispersion";

            // Type is an MO-Defined-Type
            type datetime_NTPUnsignedTimeValue;
        }

        // Type is an MO-Defined-Type
        leaf filterValidEntries {
            config "false";
            description "FilterValidEntries";

            // Type is an MO-Defined-Type
            type datetime_Gauge32;
        }
        leaf updateTime {
            config "false";
            type uint32;
        }
        leaf updateTimeRaw {
            config "false";
            type uint64;
        }

        // Type is an MO-Defined-Type
        leaf peerType {
            config "false";
            description "PeerType";

            // Type is an MO-Defined-Type
            type datetime_InetAddressType;
        }
        leaf peerName {
            config "false";
            type string;
        }
    }

    grouping datetime_AccessGroup-group {
        leaf peer {
            type string;
        }
        leaf serveOnly {
            type string;
        }
        leaf serve {
            type string;
        }
        leaf queryOnly {
            type string;
        }
    }

    grouping datetime_NtpSrcIp-group {
        leaf srcIp {
            type address_Ipv4;
        }
        leaf srcIpv6 {
            type address_Ipv6;
        }
    }

    grouping datetime_NtpSrcIf-group {

        // Source interface
        // Type is an MO-Defined-Type
        leaf srcIf {
            description "Source Interface";

            // Type is an MO-Defined-Type
            type nw_IfId;
        }
    }

    grouping datetime_Ntpq-group {
        leaf tally {
            config "false";
            type string;
        }
        leaf remote {
            config "false";
            type string;
        }
        leaf refid {
            config "false";
            type string;
        }
        leaf stratum {
            config "false";
            type string;
        }
        leaf t {
            config "false";
            type string;
        }
        leaf when {
            config "false";
            type string;
        }
        leaf poll {
            config "false";
            type string;
        }
        leaf reach {
            config "false";
            type string;
        }
        leaf delay {
            config "false";
            type string;
        }
        leaf offset {
            config "false";
            type string;
        }
        leaf jitter {
            config "false";
            type string;
        }
    }

    grouping span_Acct-group {
        leaf sessionNum {
            type uint32;
        }
        leaf sessionId {
            type uint32;
        }
        leaf sourceId {
            type uint32;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }
    }

    grouping span_RetryCont-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }
        container src-items {
            list RetrySrc-list {
                config "false";
                key "srcDn";

                // Added containment: Prefix=src
                // Acquired From Package span
                uses span_RetrySrc-group;
            }
        }
    }

    grouping span_RetrySrc-group {

        // srcDn
        // Type is an MO-Defined-Type
        leaf srcDn {
            config "false";
            description "RetrySrc Dn";

            // Type is an MO-Defined-Type
            type fabric_PrimKey;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }
        container tgt-items {
            list RetryTarget-list {
                config "false";
                key "targetDn";

                // Added containment: Prefix=tgt
                // Acquired From Package span
                uses span_RetryTarget-group;
            }
        }
    }

    grouping span_RetryTarget-group {

        // targetDn
        // Type is an MO-Defined-Type
        leaf targetDn {
            config "false";
            description "RetryTarget Dn";

            // Type is an MO-Defined-Type
            type fabric_PrimKey;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }
    }

    grouping span_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Abstraction of span database
        container db-items {
            list Db-list {
                config "false";
                key "type";

                // Added containment: Prefix=db
                // Acquired From Package span
                uses span_Db-group;
            }
        }

        // Span session definition. Each session represents a
        // a set of sources on which the packets are monitored.
        // These packets are sent to a given destination that
        // is part of this session    @@@ There could be only 4 sessions active at a
        // @@@ given time
        container session-items {
            list Session-list {
                key "name";

                // Added containment: Prefix=session
                // Acquired From Package span
                uses span_Session-group;
            }
        }
    }

    grouping span_Db-group {

        // Type of the database
        // Type is an MO-Defined-Type
        leaf type {
            config "false";
            description "Type";

            // Type is an MO-Defined-Type
            type span_DbT;
        }

        // Inherited From nw:Conn
        // Modified by Override: nw:Db->name
        // Type is an MO-Defined-Type
        leaf name {
            description "Name";

            // Type is an MO-Defined-Type
            type naming_Name {
                length "1..64";
            }
        }

        // SPAN Endpoint resolution records
        container epr-items {
            list EpRec-list {
                config "false";
                key "vnid ip";

                // Added containment: Prefix=epr
                // Acquired From Package span
                uses span_EpRec-group;
            }
        }
    }

    grouping span_EpRec-group {
        leaf vnid {
            config "false";
            type string;
        }
        leaf ip {
            config "false";
            type address_Ip;
        }

        // Synthetic vrf
        // Type is an MO-Defined-Type
        leaf synthVrf {
            config "false";
            description "Synthetic VRF";

            // Type is an MO-Defined-Type
            type coop_SynthVrf;
        }

        // Synthetic ip
        // Type is an MO-Defined-Type
        leaf synthIp {
            config "false";
            description "Synthetic IP";

            // Type is an MO-Defined-Type
            type coop_SynthIp;
        }
        leaf tep {
            config "false";
            type address_Ip;
        }

        // Inherited From nw:Conn
        // Modified by Override: nw:DbRec->name
        // Type is an MO-Defined-Type
        leaf name {
            description "Name";

            // Type is an MO-Defined-Type
            type naming_Name {
                length "1..64";
            }
        }
    }

    grouping span_Session-group {

        // Identifier of the session
        // Type is an MO-Defined-Type
        leaf id {
            description "ID";

            // Type is an MO-Defined-Type
            type span_SessionId;
        }

        // Administrative state of the session
        // Type is an MO-Defined-Type
        leaf adminSt {
            config "false";
            description "Admin State";

            // Type is an MO-Defined-Type
            type nw_AdminSt;
        }
        leaf ASrcGrpDn {
            config "false";
            type string;
        }

        // From Interface naming:Named
        // Inherited From naming:NamedObject
        // Modified by Override: span:Session->name
        // Modified by Override: pol:Obj->name
        // Type is an MO-Defined-Type
        leaf name {
            description "Name";

            // Type is an MO-Defined-Type
            type naming_Name {
                length "1..128";
            }
        }

        // From Interface naming:Described
        // Inherited From pol:Comp
        // Type is an MO-Defined-Type
        leaf descr {
            description "Description";

            // Type is an MO-Defined-Type
            type naming_Descr;
        }

        // Access source
        container src-items {
            list Source-list {
                key "name";

                // Added containment: Prefix=src
                // Acquired From Package span
                uses span_Source-group;
            }
        }

        // Fabric source
        container fabsrc-items {
            list FabSource-list {
                key "name";

                // Added containment: Prefix=fabsrc
                // Acquired From Package span
                uses span_FabSource-group;
            }
        }

        // ERSpan destination information. The destination
        // is reachable via a GRE tunnel
        container erdst-items {

            // Added containment as a singleton: Prefix=erdst
            // Acquired From Package span
            uses span_ERDestination-group;
        }

        // Local span destination information. The destination
        // is locally attached to a port in the device
        container ldst-items {

            // Added containment as a singleton: Prefix=ldst
            // Acquired From Package span
            uses span_LDestination-group;
        }

        // Implicit DomainRef objects cannot be user created - they are implicitly created
        // and added to domainable objects created by the backend
        container idomain-items {
            list IDomainRef-list {
                key "name";

                // Added containment: Prefix=idomain
                // Acquired From Package aaa
                uses aaa_IDomainRef-group;
            }
        }

        // Rel-def from SessionToDomainRef
        container rssessionToDomainRef-items {

            // Added containment as a singleton: Prefix=rssessionToDomainRef
            // Acquired From Package span
            uses span_RsSessionToDomainRef_source-group;
        }
    }

    grouping span_Source-group {

        // From Interface naming:Named
        // Inherited From naming:NamedObject
        // Modified by Override: span:Source->name
        // Modified by Override: pol:Obj->name
        // Type is an MO-Defined-Type
        leaf name {
            description "Name";

            // Type is an MO-Defined-Type
            type naming_Name {
                length "1..128";
            }
        }

        // From Interface naming:Described
        // Inherited From pol:Comp
        // Type is an MO-Defined-Type
        leaf descr {
            description "Description";

            // Type is an MO-Defined-Type
            type naming_Descr;
        }

        // Type of the source
        // Inherited From span:ASource
        // Type is an MO-Defined-Type
        leaf type {
            config "false";
            description "Type";

            // Type is an MO-Defined-Type
            type span_SrcT;
        }

        // The direction of the packets to be monitored
        // Inherited From span:ASource
        // Type is an MO-Defined-Type
        leaf dir {
            config "false";
            description "Direction";

            // Type is an MO-Defined-Type
            type span_Direction;
        }

        // Mode of the source (access side or fabric side)
        // Inherited From span:ASource
        // Type is an MO-Defined-Type
        leaf mode {
            config "false";
            description "Mode";

            // Type is an MO-Defined-Type
            type span_Mode;
        }
        leaf domain {
            config "false";
            type string;
        }

        // Rel-def from spanSrcToL2CktEpAtt
        container rsspanSrcToL2CktEpAtt-items {

            // Added containment as a singleton: Prefix=rsspanSrcToL2CktEpAtt
            // Acquired From Package span
            uses span_RsSpanSrcToL2CktEpAtt_source-group;
        }
    }

    grouping span_FabSource-group {
        leaf ctxEncap {
            type string;
        }
        leaf bdEncap {
            type string;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Type of the source
        // Inherited From span:ASource
        // Type is an MO-Defined-Type
        leaf type {
            config "false";
            description "Type";

            // Type is an MO-Defined-Type
            type span_SrcT;
        }

        // The direction of the packets to be monitored
        // Inherited From span:ASource
        // Type is an MO-Defined-Type
        leaf dir {
            config "false";
            description "Direction";

            // Type is an MO-Defined-Type
            type span_Direction;
        }

        // Mode of the source (access side or fabric side)
        // Inherited From span:ASource
        // Type is an MO-Defined-Type
        leaf mode {
            config "false";
            description "Mode";

            // Type is an MO-Defined-Type
            type span_Mode;
        }
        leaf domain {
            config "false";
            type string;
        }
    }

    grouping span_ERDestination-group {

        // Encapsulation type, the encapsulation of the monitored
        // packet sent to the destination
        // Type is an MO-Defined-Type
        leaf type {
            config "false";
            description "Type";

            // Type is an MO-Defined-Type
            type span_DestEncapT;
        }
        leaf srcIp {
            config "false";
            type address_Ip;
        }
        leaf dstIp {
            config "false";
            type address_Ip;
        }

        // Erspan version
        // Type is an MO-Defined-Type
        leaf ver {
            config "false";
            description "Version";

            // Type is an MO-Defined-Type
            type span_ErSpanVer;
        }

        // Flow id of the erspan packet
        // Type is an MO-Defined-Type
        leaf flowId {
            config "false";
            description "Flow ID";

            // Type is an MO-Defined-Type
            type span_FlowId;
        }

        // Ttl used in the erspan packet
        // Type is an MO-Defined-Type
        leaf ttl {
            config "false";
            description "TTL";

            // Type is an MO-Defined-Type
            type l3_Ttl;
        }

        // the vrf on which the erspan packet is sent
        // Type is an MO-Defined-Type
        leaf vrfName {
            config "false";
            description "VRF";

            // Type is an MO-Defined-Type
            type l3_VrfName;
        }
        leaf vnid {
            config "false";
            type string;
        }

        // dscp value to be used when sending the monitored
        // packets using ERSpan
        // Type is an MO-Defined-Type
        leaf dscp {
            config "false";
            description "Dscp";

            // Type is an MO-Defined-Type
            type qosp_Dscp;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // mtu truncation size for the packets
        // Inherited From span:Destination
        // Type is an MO-Defined-Type
        leaf mtu {
            config "false";
            description "MTU";

            // Type is an MO-Defined-Type
            type span_Mtu;
        }

        // Operational state of the session
        // Inherited From span:Destination
        // Type is an MO-Defined-Type
        leaf operSt {
            config "false";
            description "Operational State";

            // Type is an MO-Defined-Type
            type span_OperSt;
        }

        // Operational state qualifier
        // Inherited From span:Destination
        // Type is an MO-Defined-Type
        leaf operStQual {
            config "false";
            description "Operational State Qualifier";

            // Type is an MO-Defined-Type
            type span_OperStQual;
        }
    }

    grouping span_LDestination-group {

        // Port
        // Type is an MO-Defined-Type
        leaf port {
            config "false";
            description "Port";

            // Type is an MO-Defined-Type
            type nw_IfId;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // mtu truncation size for the packets
        // Inherited From span:Destination
        // Type is an MO-Defined-Type
        leaf mtu {
            config "false";
            description "MTU";

            // Type is an MO-Defined-Type
            type span_Mtu;
        }

        // Operational state of the session
        // Inherited From span:Destination
        // Type is an MO-Defined-Type
        leaf operSt {
            config "false";
            description "Operational State";

            // Type is an MO-Defined-Type
            type span_OperSt;
        }

        // Operational state qualifier
        // Inherited From span:Destination
        // Type is an MO-Defined-Type
        leaf operStQual {
            config "false";
            description "Operational State Qualifier";

            // Type is an MO-Defined-Type
            type span_OperStQual;
        }
    }

    grouping dhcp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per dhcp instance information. There is only
        // one instance of dhcp relay running in the system today
        container inst-items {

            // Added containment as a singleton: Prefix=inst
            // Acquired From Package dhcp
            uses dhcp_Inst-group;
        }
    }

    grouping dhcp_Inst-group {
        leaf v4RelayEnabled {
            type boolean;
        }
        leaf v6RelayEnabled {
            type boolean;
        }
        leaf counter {
            type uint16;
        }
        leaf SnoopingEnabled {
            type boolean;
        }
        leaf SnoopingVerifyMacAddressEnabled {
            type boolean;
        }
        leaf SnoopingInformationOptionEnabled {
            type boolean;
        }
        leaf RelayInformationOptionEnabled {
            type boolean;
        }
        leaf RelayInformationOptionVpnEnabled {
            type boolean;
        }
        leaf RelayInformationOptionTrustEnabled {
            type boolean;
        }
        leaf RelayInformationTrustAllEnabled {
            type boolean;
        }
        leaf RelaySubOptionCircuitIdCustomizedEnabled {
            type boolean;
        }
        leaf RelaySubOptionTypeCiscoEnabled {
            type boolean;
        }
        leaf SmartRelayGlobalEnabled {
            type boolean;
        }
        leaf Ipv6RelayInformationOptionVpnEnabled {
            type boolean;
        }
        leaf Ipv6RelayOptionTypeCiscoEnabled {
            type boolean;
        }
        leaf daiValidateSrc {
            type boolean;
        }
        leaf daiValidateDst {
            type boolean;
        }
        leaf daiValidateIp {
            type boolean;
        }

        // Set DAI Log Buffer Entries
        // Type is an MO-Defined-Type
        leaf daiLogBufEntries {
            description "DAI Log Buffer Entries";

            // Type is an MO-Defined-Type
            type dhcp_NumLogBuffers;
        }
        leaf pktStrictVal {
            type boolean;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // IP ARP inspection on vlan, used for enabling ARP inspection on Vlan
        container daivlan-items {
            list DAIVlan-list {
                key "daiVlanNum";

                // Added containment: Prefix=daivlan
                // Acquired From Package dhcp
                uses dhcp_DAIVlan-group;
            }
        }

        // DHCP DAI interface,
        // used for representing DAI functionality on
        // the interface
        container daiif-items {
            list DAIIf-list {
                key "id";

                // Added containment: Prefix=daiif
                // Acquired From Package dhcp
                uses dhcp_DAIIf-group;
            }
        }

        // DHCP client-if, used for representing client functionality on
        // the interface
        container clientif-items {
            list ClientIf-list {
                key "id";

                // Added containment: Prefix=clientif
                // Acquired From Package dhcp
                uses dhcp_ClientIf-group;
            }
        }

        // DHCP relay-if, used for representing relay functionality on
        // the interface
        container relayif-items {
            list RelayIf-list {
                key "id";

                // Added containment: Prefix=relayif
                // Acquired From Package dhcp
                uses dhcp_RelayIf-group;
            }
        }

        // DHCP server if, not supported; defined for completeness
        container serverif-items {
            list ServerIf-list {
                key "id";

                // Added containment: Prefix=serverif
                // Acquired From Package dhcp
                uses dhcp_ServerIf-group;
            }
        }

        // Global Ipv4 Source Interface Config
        container srcif-items {

            // Added containment as a singleton: Prefix=srcif
            // Acquired From Package dhcp
            uses dhcp_SourceIf-group;
        }

        // Global Ipv6 Source Interface Config
        container v6srcif-items {

            // Added containment as a singleton: Prefix=v6srcif
            // Acquired From Package dhcp
            uses dhcp_V6SourceIf-group;
        }

        // DHCP IP source binding,
        // (ip source binding <ip> <mac> vlan <vlanid> interface <l2-intf)
        container ipsrcbindip-items {
            list IpSrcBind-list {
                key "bindIp bindVlan bindMac bindIntf";

                // Added containment: Prefix=ipsrcbindip
                // Acquired From Package dhcp
                uses dhcp_IpSrcBind-group;
            }
        }

        // DHCP ipsgif, used for representing ipsg functionality on
        // the interface (ip verify source dhcp-snooping-vlan)
        container ipsgif-items {
            list IpsgIf-list {
                key "id";

                // Added containment: Prefix=ipsgif
                // Acquired From Package dhcp
                uses dhcp_IpsgIf-group;
            }
        }

        // DHCP IPSG Exclude Vlan, used forexcluding vlan from IPSG
        container ipsgexvlan-items {
            list IpsgExVlan-list {
                key "ipsgExVlanNum";

                // Added containment: Prefix=ipsgexvlan
                // Acquired From Package dhcp
                uses dhcp_IpsgExVlan-group;
            }
        }

        // DHCP snoop-vlan, used for representing snooping functionality on
        // the vlan
        container snoopvlan-items {
            list SnoopVlan-list {
                key "snoopVlanNum";

                // Added containment: Prefix=snoopvlan
                // Acquired From Package dhcp
                uses dhcp_SnoopVlan-group;
            }
        }

        // DHCP snoop-if, used for representing snoop functionality on
        // the interface
        container snoopif-items {
            list SnoopIf-list {
                key "id";

                // Added containment: Prefix=snoopif
                // Acquired From Package dhcp
                uses dhcp_SnoopIf-group;
            }
        }
    }

    grouping dhcp_DAIVlan-group {
        leaf daiVlanNum {
            type uint16;
        }

        // Log All/Permit/None DAI on Vlan matching DHCP Bindings
        // Type is an MO-Defined-Type
        leaf daiLogTypeOnVlan {
            description "Log All/Permit/None DAI on Vlan matching DHCP Bindings";

            // Type is an MO-Defined-Type
            type dhcp_DAILogType;
        }
    }

    grouping dhcp_DAIIf-group {
        leaf daiEnabled {
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        container rtvrfMbr-items {

            // Added containment as a singleton: Prefix=rtvrfMbr
            // Acquired From Package l3
            uses l3_RtVrfMbr_target-group;
        }

        // Rel-def target from pathToIf
        // Inherited From dhcp:DAIIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcptlvpol_Complex-group {

        // TLV Code. Code is a Uint16. Its set by the application & is not captured in the model.
        // Inherited From tlv:TLV
        // Type is an MO-Defined-Type
        leaf code {
            config "false";
            description "TBD";

            // Type is an MO-Defined-Type
            type tlv_Code;
        }
        leaf id {
            config "false";
            type uint32;
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Represents a text TLV
        container text-items {
            list Text-list {
                config "false";
                key "code";

                // Added containment: Prefix=text
                // Acquired From Package dhcptlvpol
                uses dhcptlvpol_Text-group;
            }
        }
    }

    grouping dhcptlvpol_Ip-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Ip;
        }
    }

    grouping dhcptlvpol_Mac-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Mac;
        }
    }

    grouping dhcptlvpol_UInt64-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint64;
        }
    }

    grouping dhcptlvpol_UInt32-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint32;
        }
    }

    grouping dhcptlvpol_UInt16-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint16;
        }
    }

    grouping dhcptlvpol_UByte-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint8;
        }
    }

    grouping dhcptlvpol_Text-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type string;
        }
    }

    grouping dhcp_ClientIf-group {

        // Mode
        // Type is an MO-Defined-Type
        leaf mode {
            description "Mode";

            // Type is an MO-Defined-Type
            type dhcp_Mode;
        }

        // These are the options that were set by the PE to be
        // sent across in the dhcp request    Vendor Id (option code 60)
        // Type is an MO-Defined-Type
        leaf vendorId {
            description "Vendor ID";

            // Type is an MO-Defined-Type
            type dhcp_VendorId;
        }

        // Client Id (option code 61)
        // Type is an MO-Defined-Type
        leaf clientId {
            description "Client ID";

            // Type is an MO-Defined-Type
            type dhcp_ClientId;
        }
        leaf reqAddr {
            type address_Ip;
        }

        // Host name (option code 12)
        // Type is an MO-Defined-Type
        leaf hostName {
            description "Host Name";

            // Type is an MO-Defined-Type
            type dhcp_HostName;
        }

        // Operational state
        // Type is an MO-Defined-Type
        leaf operSt {
            config "false";
            description "Operational State";

            // Type is an MO-Defined-Type
            type dhcp_ClIfOperSt;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // DHCP address received (for client)
        container addr-items {
            list ClientAddr-list {
                config "false";
                key "address";

                // Added containment: Prefix=addr
                // Acquired From Package dhcp
                uses dhcp_ClientAddr-group;
            }
        }

        // DHCPv6 address received (for client)
        container addrv6-items {
            list Clientv6Addr-list {
                config "false";
                key "address";

                // Added containment: Prefix=addrv6
                // Acquired From Package dhcp
                uses dhcp_Clientv6Addr-group;
            }
        }

        // Psuedo Interface definition
        container pseudoIf-items {
            list PseudoIf-list {
                key "id";

                // Added containment: Prefix=pseudoIf
                // Acquired From Package dhcp
                uses dhcp_PseudoIf-group;
            }
        }

        // DHCP client response
        container resp-items {

            // Added containment as a singleton: Prefix=resp
            // Acquired From Package dhcp
            uses dhcp_ClientResp-group;
        }

        // DHCP message statistics
        container msgstats-items {
            list MsgStats-list {
                config "false";
                key "type";

                // Added containment: Prefix=msgstats
                // Acquired From Package dhcp
                uses dhcp_MsgStats-group;
            }
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def from pseudoIf
        container rspseudoIf-items {

            // Abstract containment of rspseudoIf derived from dhcp:ClientIf
            list RsPseudoIf-list {
                key "tDn";

                // Added containment: Prefix=rspseudoIf
                // Acquired From Package dhcp
                uses dhcp_RsPseudoIf_source-group;
            }
        }

        // Rel-def target from vrfMbr
        // Inherited From dhcp:DAIIf
        // Inherited From dhcp:ClientIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcp_ClientAddr-group {
        leaf address {
            config "false";
            type address_Ip;
        }
    }

    grouping dhcp_Clientv6Addr-group {
        leaf address {
            config "false";
            type address_Ip;
        }
    }

    grouping dhcp_PseudoIf-group {

        // Broadcast domain for the dhcp packets
        // Type is an MO-Defined-Type
        leaf domId {
            description "Domain ID";

            // Type is an MO-Defined-Type
            type l2_DomId;
        }

        // Type of interface
        // Type is an MO-Defined-Type
        leaf ifT {
            description "Interface Type";

            // Type is an MO-Defined-Type
            type l1_Layer;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        // Inherited From dhcp:ClientIf
        // Inherited From dhcp:RelayIf
        // Inherited From dhcp:PseudoIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcp_ClientResp-group {
        leaf chAddr {
            config "false";
            type address_Mac;
        }
        leaf yiAddr {
            config "false";
            type address_Ip;
        }
        leaf siAddr {
            config "false";
            type address_Ip;
        }

        // File, location of the boot script file given by the
        // server
        // Type is an MO-Defined-Type
        leaf file {
            config "false";
            description "File";

            // Type is an MO-Defined-Type
            type dhcp_File;
        }

        // Message type (option code 53)
        // Type is an MO-Defined-Type
        leaf msgT {
            config "false";
            description "Message Type";

            // Type is an MO-Defined-Type
            type dhcp_MsgT;
        }
        leaf serverId {
            config "false";
            type address_Ip;
        }
        leaf subnetMask {
            config "false";
            type address_Ip;
        }

        // Lease time (option code 51)
        // Type is an MO-Defined-Type
        leaf leaseTime {
            config "false";
            description "Lease Time";

            // Type is an MO-Defined-Type
            type dhcp_LeaseTime;
        }

        // Host name (option code 12)
        // Type is an MO-Defined-Type
        leaf hostName {
            config "false";
            description "Host Name";

            // Type is an MO-Defined-Type
            type dhcp_HostName;
        }

        // In case of proxy interface, ifindex of the l3 interface on
        // which the resp received
        // Type is an MO-Defined-Type
        leaf ifId {
            config "false";
            description "Interface ID";

            // Type is an MO-Defined-Type
            type nw_IfId;
        }

        // Represents an IP TLV
        container ip-items {
            list Ip-list {
                config "false";
                key "code value";

                // Added containment: Prefix=ip
                // Acquired From Package dhcptlv
                uses dhcptlv_Ip-group;
            }
        }

        // Represents a Mac TLV
        container mac-items {
            list Mac-list {
                config "false";
                key "code value";

                // Added containment: Prefix=mac
                // Acquired From Package dhcptlv
                uses dhcptlv_Mac-group;
            }
        }

        // Represents a UInt64 TLV
        container uint64-items {
            list UInt64-list {
                config "false";
                key "code value";

                // Added containment: Prefix=uint64
                // Acquired From Package dhcptlv
                uses dhcptlv_UInt64-group;
            }
        }

        // Represents a UInt32 TLV
        container uint32-items {
            list UInt32-list {
                config "false";
                key "code value";

                // Added containment: Prefix=uint32
                // Acquired From Package dhcptlv
                uses dhcptlv_UInt32-group;
            }
        }

        // Represents a UInt16 TLV
        container uint16-items {
            list UInt16-list {
                config "false";
                key "code value";

                // Added containment: Prefix=uint16
                // Acquired From Package dhcptlv
                uses dhcptlv_UInt16-group;
            }
        }

        // Represents a UByte TLV
        container ubyte-items {
            list UByte-list {
                config "false";
                key "code value";

                // Added containment: Prefix=ubyte
                // Acquired From Package dhcptlv
                uses dhcptlv_UByte-group;
            }
        }

        // Represents a text TLV
        container text-items {
            list Text-list {
                config "false";
                key "code";

                // Added containment: Prefix=text
                // Acquired From Package dhcptlv
                uses dhcptlv_Text-group;
            }
        }

        // Represents a Complex TLV.
        // Complex TLV contains Basic TLVs
        container complex-items {
            list Complex-list {
                config "false";
                key "code id";

                // Added containment: Prefix=complex
                // Acquired From Package dhcptlv
                uses dhcptlv_Complex-group;
            }
        }
    }

    grouping dhcptlv_Ip-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Ip;
        }
    }

    grouping dhcptlv_Mac-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Mac;
        }
    }

    grouping dhcptlv_UInt64-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint64;
        }
    }

    grouping dhcptlv_UInt32-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint32;
        }
    }

    grouping dhcptlv_UInt16-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint16;
        }
    }

    grouping dhcptlv_UByte-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint8;
        }
    }

    grouping dhcptlv_Text-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type string;
        }
    }

    grouping dhcptlv_Complex-group {

        // TLV Code. Code is a Uint16. Its set by the application & is not captured in the model.
        // Inherited From tlv:TLV
        // Type is an MO-Defined-Type
        leaf code {
            config "false";
            description "TBD";

            // Type is an MO-Defined-Type
            type tlv_Code;
        }
        leaf id {
            config "false";
            type uint32;
        }

        // Represents an IP TLV
        container ip-items {
            list Ip-list {
                config "false";
                key "code value";

                // Added containment: Prefix=ip
                // Acquired From Package dhcptlv
                uses dhcptlv_Ip-group;
            }
        }

        // Represents a Mac TLV
        container mac-items {
            list Mac-list {
                config "false";
                key "code value";

                // Added containment: Prefix=mac
                // Acquired From Package dhcptlv
                uses dhcptlv_Mac-group;
            }
        }

        // Represents a UInt64 TLV
        container uint64-items {
            list UInt64-list {
                config "false";
                key "code value";

                // Added containment: Prefix=uint64
                // Acquired From Package dhcptlv
                uses dhcptlv_UInt64-group;
            }
        }

        // Represents a UInt32 TLV
        container uint32-items {
            list UInt32-list {
                config "false";
                key "code value";

                // Added containment: Prefix=uint32
                // Acquired From Package dhcptlv
                uses dhcptlv_UInt32-group;
            }
        }

        // Represents a UInt16 TLV
        container uint16-items {
            list UInt16-list {
                config "false";
                key "code value";

                // Added containment: Prefix=uint16
                // Acquired From Package dhcptlv
                uses dhcptlv_UInt16-group;
            }
        }

        // Represents a UByte TLV
        container ubyte-items {
            list UByte-list {
                config "false";
                key "code value";

                // Added containment: Prefix=ubyte
                // Acquired From Package dhcptlv
                uses dhcptlv_UByte-group;
            }
        }

        // Represents a text TLV
        container text-items {
            list Text-list {
                config "false";
                key "code";

                // Added containment: Prefix=text
                // Acquired From Package dhcptlv
                uses dhcptlv_Text-group;
            }
        }
    }

    grouping dhcp_MsgStats-group {

        // Type of dhcp message
        // Type is an MO-Defined-Type
        leaf type {
            config "false";
            description "Message Type";

            // Type is an MO-Defined-Type
            type dhcp_MsgT;
        }

        // Number of dhcp packets received
        // Type is an MO-Defined-Type
        leaf pktRcvd {
            config "false";
            description "Packets Received";

            // Type is an MO-Defined-Type
            type nw_Counter32;
        }

        // Number of dhcp packets sent
        // Type is an MO-Defined-Type
        leaf pktSent {
            config "false";
            description "Packets Sent";

            // Type is an MO-Defined-Type
            type nw_Counter32;
        }

        // Number of dhcp packets dropped
        // Type is an MO-Defined-Type
        leaf pktDrop {
            config "false";
            description "Packets Dropped";

            // Type is an MO-Defined-Type
            type nw_Counter32;
        }
    }

    grouping dhcp_RelayIf-group {

        // DHCP options
        // Type is an MO-Defined-Type
        leaf options {
            description "Options";

            // Type is an MO-Defined-Type
            type dhcp_Options;
        }
        leaf SmartRelayEnabled {
            type boolean;
        }
        leaf SubnetBroadcastEnabled {
            type boolean;
        }
        leaf InformationTrustedEnabled {
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // DHCP OPTION
        container opt-items {
            list OptionDef-list {
                key "name";

                // Added containment: Prefix=opt
                // Acquired From Package dhcp
                uses dhcp_OptionDef-group;
            }
        }

        // DHCP relay address
        container addr-items {
            list RelayAddr-list {
                config "false";
                key "vrf address";

                // Added containment: Prefix=addr
                // Acquired From Package dhcp
                uses dhcp_RelayAddr-group;
            }
        }

        // DHCPv6 relay address
        container addrv6-items {
            list V6RelayAddr-list {
                config "false";
                key "vrf address dstif";

                // Added containment: Prefix=addrv6
                // Acquired From Package dhcp
                uses dhcp_V6RelayAddr-group;
            }
        }

        // Ipv4 dhcp Source interface per i/f
        container srcif-items {

            // Added containment as a singleton: Prefix=srcif
            // Acquired From Package dhcp
            uses dhcp_SrcIf-group;
        }

        // Ipv6 dhcp Source interface per i/f
        container v6srcif-items {

            // Added containment as a singleton: Prefix=v6srcif
            // Acquired From Package dhcp
            uses dhcp_V6SrcIf-group;
        }

        // DHCP message statistics
        container msgstats-items {
            list MsgStats-list {
                config "false";
                key "type";

                // Added containment: Prefix=msgstats
                // Acquired From Package dhcp
                uses dhcp_MsgStats-group;
            }
        }

        // DHCP Relay Interface Statistics
        container stat-items {

            // Added containment as a singleton: Prefix=stat
            // Acquired From Package dhcp
            uses dhcp_RelayIfStats-group;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        // Inherited From dhcp:ClientIf
        // Inherited From dhcp:RelayIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcp_RelayAddr-group {

        // vrf in which the dhcp server is present. Valid only
        // when the client is in a different vrf from the server
        // vrf
        // Type is an MO-Defined-Type
        leaf vrf {
            description "VRF";

            // Type is an MO-Defined-Type
            type l3_VrfName;
        }
        leaf gw {
            type address_Ip;
        }

        // Mode of the DHCP relay. 'visible' leaks route.
        // Type is an MO-Defined-Type
        leaf mode {
            description "Relay mode";

            // Type is an MO-Defined-Type
            type dhcp_RelayVisibility;
        }
        leaf counter {
            type uint16;
        }
        leaf address {
            config "false";
            type address_Ip;
        }

        // Gateway IP address, valid only when we are crossing
        // vrfs. Should always be present when client is crossing
        // vrf to get its ip address
        container gw-items {
            list RelayGw-list {
                config "false";
                key "address";

                // Added containment: Prefix=gw
                // Acquired From Package dhcp
                uses dhcp_RelayGw-group;
            }
        }

        // DHCP Relay Address Stat
        container statistics-items {

            // Added containment as a singleton: Prefix=statistics
            // Acquired From Package dhcp
            uses dhcp_RelayAddrStats-group;
        }
    }

    grouping dhcp_RelayGw-group {
        leaf address {
            config "false";
            type address_Ip;
        }
    }

    grouping dhcp_RelayAddrStats-group {

        // Number of dhcp requesting packets sent to the server
        // address
        // Type is an MO-Defined-Type
        leaf reqPktSent {
            config "false";
            description "Requesting Packet Sent Count";

            // Type is an MO-Defined-Type
            type nw_Counter32;
        }

        // Number of dhcp response packets received from the
        // server address
        // Type is an MO-Defined-Type
        leaf respPktRcvd {
            config "false";
            description "Response Packet Received Count";

            // Type is an MO-Defined-Type
            type nw_Counter32;
        }
    }

    grouping dhcp_V6RelayAddr-group {

        // vrf in which the dhcp server is present. Valid only
        // when the client is in a different vrf from the server
        // vrf
        // Type is an MO-Defined-Type
        leaf vrf {
            description "VRF";

            // Type is an MO-Defined-Type
            type l3_VrfName;
        }

        // Mode of the DHCP relay. 'visible' leaks route.
        // Type is an MO-Defined-Type
        leaf mode {
            description "Relay mode";

            // Type is an MO-Defined-Type
            type dhcp_RelayVisibility;
        }
        leaf counter {
            type uint16;
        }

        // Destination interface for IPv6 relay address
        // Type is an MO-Defined-Type
        leaf dstif {
            description "Destination Interface";

            // Type is an MO-Defined-Type
            type nw_IfId;
        }
        leaf address {
            config "false";
            type address_Ip;
        }

        // Gateway IP address, valid only when we are crossing
        // vrfs. Should always be present when client is crossing
        // vrf to get its ip address
        container gw-items {
            list V6RelayGw-list {
                config "false";
                key "address";

                // Added containment: Prefix=gw
                // Acquired From Package dhcp
                uses dhcp_V6RelayGw-group;
            }
        }
    }

    grouping dhcp_V6RelayGw-group {
        leaf address {
            config "false";
            type address_Ip;
        }
    }

    grouping dhcp_SrcIf-group {

        // Type is an MO-Defined-Type
        leaf sourceInterface {
            description "Source Interface";

            // Type is an MO-Defined-Type
            type nw_IfId;
        }
    }

    grouping dhcp_V6SrcIf-group {

        // Type is an MO-Defined-Type
        leaf v6sourceInterface {
            description "Source Interface";

            // Type is an MO-Defined-Type
            type nw_IfId;
        }
    }

    grouping dhcp_RelayIfStats-group {

        // Number of packets dropped due to invalid dhcp message
        // type
        // Type is an MO-Defined-Type
        leaf invalidMsgTypeDrop {
            config "false";
            description "Invalid Message Type Drop Count";

            // Type is an MO-Defined-Type
            type nw_Counter32;
        }

        // Number of packets dropped due to interface error
        // Type is an MO-Defined-Type
        leaf ifErrDrop {
            config "false";
            description "Interface Error Drop Count";

            // Type is an MO-Defined-Type
            type nw_Counter32;
        }

        // Number of packets dropped due to tx failure towards
        // server
        // Type is an MO-Defined-Type
        leaf sendServerFail {
            config "false";
            description "Send Failure to Server Drop Count";

            // Type is an MO-Defined-Type
            type nw_Counter32;
        }

        // Number of packets dropped due to tx failure towards
        // client
        // Type is an MO-Defined-Type
        leaf sendClientFail {
            config "false";
            description "Send Failure to Client Drop Count";

            // Type is an MO-Defined-Type
            type nw_Counter32;
        }

        // Number of packets dropped due to unknown vrf or interface
        // for server
        // Type is an MO-Defined-Type
        leaf unkServerVrfIntfDrop {
            config "false";
            description "Unknown Server Vrf/Intf Drop Count";

            // Type is an MO-Defined-Type
            type nw_Counter32;
        }

        // Number of packets dropped due to max hop exceeded
        // Type is an MO-Defined-Type
        leaf maxHopExceedDrop {
            config "false";
            description "Max Hop Exceeded Drop Count";

            // Type is an MO-Defined-Type
            type nw_Counter32;
        }

        // Number of packets dropped due to option 82 validation
        // failed
        // Type is an MO-Defined-Type
        leaf opt82FailDrop {
            config "false";
            description "Option 82 Validation Fail Drop Count";

            // Type is an MO-Defined-Type
            type nw_Counter32;
        }

        // Number of packets dropped due to packet malformed
        // Type is an MO-Defined-Type
        leaf malformPktDrop {
            config "false";
            description "Malformed Packet Drop Count";

            // Type is an MO-Defined-Type
            type nw_Counter32;
        }
    }

    grouping dhcp_ServerIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        // Inherited From dhcp:ClientIf
        // Inherited From dhcp:RelayIf
        // Inherited From dhcp:PseudoIf
        // Inherited From dhcp:ServerIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcp_SourceIf-group {

        // Type is an MO-Defined-Type
        leaf sourceInterface {
            description "Global Source Interface";

            // Type is an MO-Defined-Type
            type nw_IfId;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping dhcp_V6SourceIf-group {

        // Type is an MO-Defined-Type
        leaf v6sourceInterface {
            description "Global Source Interface";

            // Type is an MO-Defined-Type
            type nw_IfId;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping dhcp_IpSrcBind-group {
        leaf bindVlan {
            type uint16;
        }
        leaf bindIp {
            type address_Ip;
        }
        leaf bindMac {
            type address_Mac;
        }

        // Interface on which the client was discovered
        // Type is an MO-Defined-Type
        leaf bindIntf {
            description "Interface ID";

            // Type is an MO-Defined-Type
            type nw_IfId;
        }
    }

    grouping dhcp_IpsgIf-group {
        leaf ipsgEnabled {
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dhcp_IpsgExVlan-group {
        leaf ipsgExVlanNum {
            type uint16;
        }
    }

    grouping dhcp_SnoopVlan-group {
        leaf snoopVlanNum {
            type uint16;
        }
    }

    grouping dhcp_SnoopIf-group {
        leaf trustEnabled {
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Represents a Complex TLV,
        // complex TLV contains Basic TLVs
        container complex-items {
            list Complex-list {
                config "false";
                key "code id";

                // Added containment: Prefix=complex
                // Acquired From Package dhcptlvpol
                uses dhcptlvpol_Complex-group;
            }
        }

        // Represents a text TLV
        container text-items {
            list Text-list {
                config "false";
                key "code";

                // Added containment: Prefix=text
                // Acquired From Package dhcptlvpol
                uses dhcptlvpol_Text-group;
            }
        }

        // Represents an IP TLV
        container ip-items {
            list Ip-list {
                config "false";
                key "code value";

                // Added containment: Prefix=ip
                // Acquired From Package dhcptlvpol
                uses dhcptlvpol_Ip-group;
            }
        }

        // Represents a Mac TLV
        container mac-items {
            list Mac-list {
                config "false";
                key "code value";

                // Added containment: Prefix=mac
                // Acquired From Package dhcptlvpol
                uses dhcptlvpol_Mac-group;
            }
        }

        // Represents a UInt64 TLV
        container uint64-items {
            list UInt64-list {
                config "false";
                key "code value";

                // Added containment: Prefix=uint64
                // Acquired From Package dhcptlvpol
                uses dhcptlvpol_UInt64-group;
            }
        }

        // Represents a UInt32 TLV
        container uint32-items {
            list UInt32-list {
                config "false";
                key "code value";

                // Added containment: Prefix=uint32
                // Acquired From Package dhcptlvpol
                uses dhcptlvpol_UInt32-group;
            }
        }

        // Represents a UInt16 TLV
        container uint16-items {
            list UInt16-list {
                config "false";
                key "code value";

                // Added containment: Prefix=uint16
                // Acquired From Package dhcptlvpol
                uses dhcptlvpol_UInt16-group;
            }
        }

        // Represents a UByte TLV
        container ubyte-items {
            list UByte-list {
                config "false";
                key "code value";

                // Added containment: Prefix=ubyte
                // Acquired From Package dhcptlvpol
                uses dhcptlvpol_UByte-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping dns_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per dns instance information
        container prof-items {
            list Prof-list {
                key "name";

                // Added containment: Prefix=prof
                // Acquired From Package dns
                uses dns_Prof-group;
            }
        }
    }

    grouping dns_Prof-group {

        // From Interface naming:Named
        // Inherited From naming:NamedObject
        // Modified by Override: dns:Prof->name
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // DNS Provider
        container prov-items {
            list Provider-list {
                key "addr";

                // Added containment: Prefix=prov
                // Acquired From Package dns
                uses dns_Provider-group;
            }
        }

        // VRF modes to search for additional to current vrf mode
        container vrf-items {
            list Vrf-list {
                key "name";

                // Added containment: Prefix=vrf
                // Acquired From Package dns
                uses dns_Vrf-group;
            }
        }

        // DNS Domain
        container dom-items {

            // Added containment as a singleton: Prefix=dom
            // Acquired From Package dns
            uses dns_Dom-group;
        }

        // Additional DNS Domains to search for
        container domext-items {
            list DomExt-list {
                key "name";

                // Added containment: Prefix=domext
                // Acquired From Package dns
                uses dns_DomExt-group;
            }
        }

        // DNS host entries
        container host-items {
            list Host-list {
                key "name";

                // Added containment: Prefix=host
                // Acquired From Package dns
                uses dns_Host-group;
            }
        }
    }

    grouping dns_Provider-group {

        // From Interface naming:Named
        // Inherited From naming:NamedObject
        // Modified by Override: pol:Obj->name
        // Type is an MO-Defined-Type
        leaf name {
            description "Name";

            // Type is an MO-Defined-Type
            type naming_Name {
                length "0..64";
            }
        }
        leaf addr {
            type address_Ip;
        }
        leaf preferred {
            type boolean;
        }
    }

    grouping dns_Vrf-group {

        // The vrf that this client group belongs to
        // Type is an MO-Defined-Type
        leaf name {
            description "Vrf Name";

            // Type is an MO-Defined-Type
            type l3_VrfName {
            }
        }

        // DNS Provider
        container prov-items {
            list Provider-list {
                key "addr";

                // Added containment: Prefix=prov
                // Acquired From Package dns
                uses dns_Provider-group;
            }
        }

        // DNS Domain
        container dom-items {

            // Added containment as a singleton: Prefix=dom
            // Acquired From Package dns
            uses dns_Dom-group;
        }

        // Additional DNS Domains to search for
        container domext-items {
            list DomExt-list {
                key "name";

                // Added containment: Prefix=domext
                // Acquired From Package dns
                uses dns_DomExt-group;
            }
        }
    }

    grouping dns_Dom-group {

        // From Interface naming:Named
        // Inherited From naming:NamedObject
        // Modified by Override: dns:Dom->name
        // Modified by Override: pol:Obj->name
        // Modified by Override: dns:ADomain->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf isDefault {
            type boolean;
        }
    }

    grouping dns_DomExt-group {

        // From Interface naming:Named
        // Inherited From naming:NamedObject
        // Modified by Override: dns:DomExt->name
        // Modified by Override: pol:Obj->name
        // Modified by Override: dns:ADomain->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf isDefault {
            type boolean;
        }
    }

    grouping dns_Host-group {
        leaf name {
            type string {
            }
        }

        // DNS IPv4 Entries
        container ipv4host-items {

            // Added containment as a singleton: Prefix=ipv4host
            // Acquired From Package dns
            uses dns_Ipv4Host-group;
        }

        // DNS IPv6 Entries
        container ipv6host-items {

            // Added containment as a singleton: Prefix=ipv6host
            // Acquired From Package dns
            uses dns_Ipv6Host-group;
        }
    }

    grouping dns_Ipv4Host-group {
        leaf addr {
            type address_Ipv4;
        }
    }

    grouping dns_Ipv6Host-group {
        leaf addr {
            type address_Ipv6;
        }
    }

    grouping fabric_Decommission-group {

        // Type is an MO-Defined-Type
        leaf nodeDn {
            config "false";
            description "TBD";

            // Type is an MO-Defined-Type
            type reln_Dn;
        }
        leaf wipe {
            config "false";
            type boolean;
        }
        leaf targetId {
            config "false";
            type uint32;
        }

        // Type is an MO-Defined-Type
        leaf tickCount {
            config "false";
            description "TBD";

            // Type is an MO-Defined-Type
            type fabric_TickCount;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
    }

    grouping l2_InbandIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // @@@Relationship to policy providing physical configuration of
        // the ports    @@@rel-def
        // name="IfConf"
        // type="named"
        // from="fv:RsCcepConn"
        // to="fabric:HIfPol"
        // cardinality="1-to-1"
        // owner="management"
        // mod="explicit"
        // >
        // </rel-def   DEp represents a dynamically learned end point on the switch.
        // This object is owned by the end point manager
        container dep-items {
            list DEp-list {
                key "mac encap";

                // Added containment: Prefix=dep
                // Acquired From Package fv
                uses fv_DEp-group;
            }
        }

        // VNode represents an opflex capable vnode that is connected
        // to the fabric.
        container vnode-items {
            list VNode-list {
                config "false";
                key "devId";

                // Added containment: Prefix=vnode
                // Acquired From Package fv
                uses fv_VNode-group;
            }
        }

        // IDEp represents a inband learned end point on the switch.
        // This object is owned by the end point manager
        container idep-items {
            list IDEp-list {
                key "mac encap";

                // Added containment: Prefix=idep
                // Acquired From Package opflex
                uses opflex_IDEp-group;
            }
        }

        // Device represents an opflex capable device that is connected
        // to the fabric.
        // This object is owned by the opflexelem
        container odev-items {
            list ODev-list {
                key "devId";

                // Added containment: Prefix=odev
                // Acquired From Package opflex
                uses opflex_ODev-group;
            }
        }

        // Rel-def from InbandConf
        container rsinbandConf-items {

            // Added containment as a singleton: Prefix=rsinbandConf
            // Acquired From Package l2
            uses l2_RsInbandConf_source-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping fv_VNode-group {
        leaf devId {
            config "false";
            type uint32;
        }

        // type of the device
        // Type is an MO-Defined-Type
        leaf devType {
            config "false";
            description "TBD";

            // Type is an MO-Defined-Type
            type opflex_DeviceType;
        }
        leaf lNodeDn {
            config "false";
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Rel-def target from vNode
        // Inherited From fv:VNode
        container rtfvVNode-items {

            // Abstract containment of rtfvVNode derived from fv:VNode
            list RtFvVNode-list {
                key "tDn";

                // Added containment: Prefix=rtfvVNode
                // Acquired From Package fv
                uses fv_RtFvVNode_target-group;
            }
        }

        // Rel-def from lNode
        container rslNode-items {

            // Abstract containment of rslNode derived from fv:VNode
            list RsLNode-list {
                config "false";
                key "tDn";

                // Added containment: Prefix=rslNode
                // Acquired From Package fv
                uses fv_RsLNode_source-group;
            }
        }
    }

    grouping opflex_ODev-group {
        leaf devId {
            type uint32;
        }

        // type of the device
        // Type is an MO-Defined-Type
        leaf devType {
            description "TBD";

            // Type is an MO-Defined-Type
            type opflex_DeviceType;
        }
        leaf lNodeDn {
            config "false";
            type string;
        }
        leaf ip {
            type address_Ip;
        }
        leaf mac {
            type address_Mac;
        }
        leaf encap {
            type string;
        }
        leaf updateTs {
            config "false";
            type uint64;
        }
        leaf hostName {
            type string;
        }
        leaf ipAddr {
            type string;
        }
        leaf numHB {
            config "false";
            type uint32;
        }
        leaf lastNumHB {
            config "false";
            type uint32;
        }

        // channel failure
        // Type is an MO-Defined-Type
        leaf hbStatus {
            config "false";
            description "TBD";

            // Type is an MO-Defined-Type
            type opflex_HbStatus;
        }

        // Operational State
        // Type is an MO-Defined-Type
        leaf operSt {
            config "false";
            description "Status";

            // Type is an MO-Defined-Type
            type opflex_DevOperState;
        }

        // Device Operational Issues.
        // It captures various device operational issues
        // It is represented as a bitmask to collect all
        // errors and provide feedback to users.
        // Type is an MO-Defined-Type
        leaf devOperIssues {
            description "TBD";

            // Type is an MO-Defined-Type
            type opflex_DevOperIssues;
        }
        leaf maxMissHb {
            config "false";
            type uint32;
        }
        leaf pcIfId {
            type uint32;
        }

        // ep transition status
        // Type is an MO-Defined-Type
        leaf transitionStatus {
            config "false";
            description "TBD";

            // Type is an MO-Defined-Type
            type opflex_EpTransitionStatus;
        }

        // Name of the domain
        // Type is an MO-Defined-Type
        leaf domName {
            description "TBD";

            // Type is an MO-Defined-Type
            type naming_LongDescr;
        }

        // Name of the controller
        // Type is an MO-Defined-Type
        leaf ctrlrName {
            description "TBD";

            // Type is an MO-Defined-Type
            type naming_LongDescr;
        }
        leaf portId {
            type uint32;
        }

        // type of the device
        // Type is an MO-Defined-Type
        leaf state {
            description "TBD";

            // Type is an MO-Defined-Type
            type comp_HostState;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // DeviceCap represents the capabilities of an opflex
        // capable device that is connected to the fabric.
        // This object is owned by the opflexelem
        container odevcap-items {

            // Added containment as a singleton: Prefix=odevcap
            // Acquired From Package opflex
            uses opflex_ODevCap-group;
        }

        // VNode represents an opflex capable vnode that is connected
        // to the fabric.
        container vnode-items {
            list VNode-list {
                config "false";
                key "devId";

                // Added containment: Prefix=vnode
                // Acquired From Package fv
                uses fv_VNode-group;
            }
        }

        // Device represents an opflex capable device that is connected
        // to the fabric.
        // This object is owned by the opflexelem
        container opnic-items {
            list OPNic-list {
                key "mac";

                // Added containment: Prefix=opnic
                // Acquired From Package opflex
                uses opflex_OPNic-group;
            }
        }
    }

    grouping opflex_ODevCap-group {
        leaf version {
            config "false";
            type string;
        }
        leaf devId {
            config "false";
            type uint32;
        }
        leaf lNodeDn {
            config "false";
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }
    }

    grouping opflex_OPNic-group {
        leaf ip {
            type address_Ip;
        }
        leaf mac {
            type address_Mac;
        }

        // type of the device
        // Type is an MO-Defined-Type
        leaf state {
            description "TBD";

            // Type is an MO-Defined-Type
            type comp_NicState;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }
    }

    grouping l2_ExtIf-group {

        // Extension chassis ID
        // Type is an MO-Defined-Type
        leaf extChasId {
            description "Extension Chassis ID";

            // Type is an MO-Defined-Type
            type l2_ExtChasId;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // @@@Relationship to policy providing physical configuration of
        // the ports    @@@rel-def
        // name="IfConf"
        // type="named"
        // from="fv:RsCcepConn"
        // to="fabric:HIfPol"
        // cardinality="1-to-1"
        // owner="management"
        // mod="explicit"
        // >
        // </rel-def   DEp represents a dynamically learned end point on the switch.
        // This object is owned by the end point manager
        container dep-items {
            list DEp-list {
                key "mac encap";

                // Added containment: Prefix=dep
                // Acquired From Package fv
                uses fv_DEp-group;
            }
        }

        // VNode represents an opflex capable vnode that is connected
        // to the fabric.
        container vnode-items {
            list VNode-list {
                config "false";
                key "devId";

                // Added containment: Prefix=vnode
                // Acquired From Package fv
                uses fv_VNode-group;
            }
        }

        // IDEp represents a inband learned end point on the switch.
        // This object is owned by the end point manager
        container idep-items {
            list IDEp-list {
                key "mac encap";

                // Added containment: Prefix=idep
                // Acquired From Package opflex
                uses opflex_IDEp-group;
            }
        }

        // Device represents an opflex capable device that is connected
        // to the fabric.
        // This object is owned by the opflexelem
        container odev-items {
            list ODev-list {
                key "devId";

                // Added containment: Prefix=odev
                // Acquired From Package opflex
                uses opflex_ODev-group;
            }
        }

        // Rel-def from extConf
        container rsextConf-items {

            // Added containment as a singleton: Prefix=rsextConf
            // Acquired From Package l2
            uses l2_RsExtConf_source-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping l2_BrIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // @@@Relationship to policy providing physical configuration of
        // the ports    @@@rel-def
        // name="IfConf"
        // type="named"
        // from="fv:RsCcepConn"
        // to="fabric:HIfPol"
        // cardinality="1-to-1"
        // owner="management"
        // mod="explicit"
        // >
        // </rel-def   DEp represents a dynamically learned end point on the switch.
        // This object is owned by the end point manager
        container dep-items {
            list DEp-list {
                key "mac encap";

                // Added containment: Prefix=dep
                // Acquired From Package fv
                uses fv_DEp-group;
            }
        }

        // VNode represents an opflex capable vnode that is connected
        // to the fabric.
        container vnode-items {
            list VNode-list {
                config "false";
                key "devId";

                // Added containment: Prefix=vnode
                // Acquired From Package fv
                uses fv_VNode-group;
            }
        }

        // IDEp represents a inband learned end point on the switch.
        // This object is owned by the end point manager
        container idep-items {
            list IDEp-list {
                key "mac encap";

                // Added containment: Prefix=idep
                // Acquired From Package opflex
                uses opflex_IDEp-group;
            }
        }

        // Device represents an opflex capable device that is connected
        // to the fabric.
        // This object is owned by the opflexelem
        container odev-items {
            list ODev-list {
                key "devId";

                // Added containment: Prefix=odev
                // Acquired From Package opflex
                uses opflex_ODev-group;
            }
        }

        // Rel-def from brConf
        container rsbrConf-items {

            // Added containment as a singleton: Prefix=rsbrConf
            // Acquired From Package l2
            uses l2_RsBrConf_source-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping cdp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per cdp instance information. There is
        // only one instance of cdp running in the system today
        container inst-items {

            // Added containment as a singleton: Prefix=inst
            // Acquired From Package cdp
            uses cdp_Inst-group;
        }
    }

    grouping cdp_Inst-group {

        // CDP version supported by the device
        // Type is an MO-Defined-Type
        leaf ver {
            description "Version";

            // Type is an MO-Defined-Type
            type cdp_Ver;
        }

        // What to advertise in the device id to the peer?
        // This will be the identifier of the local switch
        // to the remote peer
        // Type is an MO-Defined-Type
        leaf devIdType {
            description "Device ID Type";

            // Type is an MO-Defined-Type
            type cdp_DevIdT;
        }

        // Sets the time that cdp holds onto neighbor
        // information before aging it out
        // Type is an MO-Defined-Type
        leaf holdIntvl {
            description "Hold Interval";

            // Type is an MO-Defined-Type
            type cdp_HoldIntvl;
        }

        // Sets the transmission frequency of cdp
        // advertisements in seconds
        // Type is an MO-Defined-Type
        leaf txFreq {
            description "Transmit Frequency";

            // Type is an MO-Defined-Type
            type cdp_TxFreq;
        }

        // System Name
        // Type is an MO-Defined-Type
        leaf sysName {
            config "false";
            description "System Name";

            // Type is an MO-Defined-Type
            type cdp_SysName;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds cdp information that is operated at a
        // interface level
        container if-items {
            list If-list {
                key "id";

                // Added containment: Prefix=if
                // Acquired From Package cdp
                uses cdp_If-group;
            }
        }
    }

    grouping cdp_If-group {

        // Port description
        // Type is an MO-Defined-Type
        leaf portDesc {
            config "false";
            description "Port Description";

            // Type is an MO-Defined-Type
            type naming_Descr;
        }

        // Type is an MO-Defined-Type
        leaf locDesc {
            config "false";
            description "Location Description";

            // Type is an MO-Defined-Type
            type naming_Descr;
        }

        // Operational state
        // Type is an MO-Defined-Type
        leaf operSt {
            config "false";
            description "Operational State";

            // Type is an MO-Defined-Type
            type cdp_OperSt;
        }

        // Operational state qualifier
        // Type is an MO-Defined-Type
        leaf operStQual {
            config "false";
            description "Operational State Qualifier";

            // Type is an MO-Defined-Type
            type cdp_OperStQual;
        }

        // Native vlan
        // Type is an MO-Defined-Type
        leaf nativeVlan {
            config "false";
            description "Native Vlan";

            // Type is an MO-Defined-Type
            type cdp_VlanId;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds cdp neighbor information
        container adj-items {
            list AdjEp-list {
                config "false";
                key "index";

                // Added containment: Prefix=adj
                // Acquired From Package cdp
                uses cdp_AdjEp-group;
            }
        }

        // This object holds cdp intf statistics operational information.
        // This is a singleton within an intferace
        container ifstats-items {

            // Added containment as a singleton: Prefix=ifstats
            // Acquired From Package cdp
            uses cdp_IfStats-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping cdp_AdjEp-group {

        // A unique value for each device from which CDP
        // messages are being received
        // Type is an MO-Defined-Type
        leaf index {
            config "false";
            description "Index";

            // Type is an MO-Defined-Type
            type cdp_DevIndex;
        }

        // Neighbor state qualifiers
        // Type is an MO-Defined-Type
        leaf stQual {
            config "false";
            description "Operational State Qualifier";

            // Type is an MO-Defined-Type
            type cdp_AdjStQual;
        }

        // Remote version
        // Type is an MO-Defined-Type
        leaf ver {
            config "false";
            description "Version";

            // Type is an MO-Defined-Type
            type cdp_NbrVer;
        }

        // Remote device ID
        // Type is an MO-Defined-Type
        leaf devId {
            config "false";
            description "Device ID";

            // Type is an MO-Defined-Type
            type cdp_DevId;
        }

        // Remote Port ID
        // Type is an MO-Defined-Type
        leaf portId {
            config "false";
            description "Port ID";

            // Type is an MO-Defined-Type
            type cdp_PortId;
        }

        // Remote Platform ID
        // Type is an MO-Defined-Type
        leaf platId {
            config "false";
            description "Platform ID";

            // Type is an MO-Defined-Type
            type cdp_PlatId;
        }

        // Capabilities
        // Type is an MO-Defined-Type
        leaf cap {
            config "false";
            description "Capabilities";

            // Type is an MO-Defined-Type
            type cdp_CapT;
        }

        // Duplex advertised by neighbor
        // Type is an MO-Defined-Type
        leaf duplex {
            config "false";
            description "Duplex";

            // Type is an MO-Defined-Type
            type cdp_Duplex;
        }

        // Native vlan advertised by neighbor
        // Type is an MO-Defined-Type
        leaf nativeVlan {
            config "false";
            description "Native Vlan";

            // Type is an MO-Defined-Type
            type cdp_VlanId;
        }

        // MTU advertised by neighbor
        // Type is an MO-Defined-Type
        leaf mtu {
            config "false";
            description "MTU";

            // Type is an MO-Defined-Type
            type cdp_MTU;
        }

        // System name advertised by neighbor
        // Type is an MO-Defined-Type
        leaf sysName {
            config "false";
            description "System Name";

            // Type is an MO-Defined-Type
            type cdp_SysName;
        }

        // System location advertised by neighbor
        // Type is an MO-Defined-Type
        leaf sysLoc {
            config "false";
            description "System Location";

            // Type is an MO-Defined-Type
            type cdp_SysLoc;
        }

        // System OID Values advertised by neighbor
        // Type is an MO-Defined-Type
        leaf sysObjIdV {
            config "false";
            description "System OID Value";

            // Type is an MO-Defined-Type
            type cdp_SysObjIdV;
        }

        // System OID Length advertised by neighbor
        // Type is an MO-Defined-Type
        leaf sysObjIdL {
            config "false";
            description "System OID Length";

            // Type is an MO-Defined-Type
            type cdp_SysObjIdL;
        }

        // Inherited From nw:Conn
        // Modified by Override: nw:Ep->name
        // Type is an MO-Defined-Type
        leaf name {
            description "Name";

            // Type is an MO-Defined-Type
            type naming_Name {
                length "1..64";
            }
        }

        // Management address received from cdp neighbor
        container mgmt-items {
            list MgmtAddr-list {
                config "false";
                key "addr";

                // Added containment: Prefix=mgmt
                // Acquired From Package cdp
                uses cdp_MgmtAddr-group;
            }
        }

        // Interface address received from cdp neighbor
        container intf-items {
            list IntfAddr-list {
                config "false";
                key "addr";

                // Added containment: Prefix=intf
                // Acquired From Package cdp
                uses cdp_IntfAddr-group;
            }
        }

        // This object holds cdp adj statistics operational information.
        // This is a singleton within an adjacency
        container adjstats-items {

            // Added containment as a singleton: Prefix=adjstats
            // Acquired From Package cdp
            uses cdp_AdjStats-group;
        }
    }

    grouping cdp_MgmtAddr-group {
        leaf addr {
            config "false";
            type address_Ip;
        }
    }

    grouping cdp_IntfAddr-group {
        leaf addr {
            config "false";
            type address_Ip;
        }
    }

    grouping cdp_AdjStats-group {
        leaf adjExpTs {
            config "false";
            type uint64;
        }
    }

    grouping cdp_IfStats-group {

        // CDP Interface Stats    Number of v1 packets sent
        // Type is an MO-Defined-Type
        leaf v1Sent {
            config "false";
            description "Number of V1 Packets Sent";

            // Type is an MO-Defined-Type
            type nw_Counter32;
        }

        // Number of v2 packets sent
        // Type is an MO-Defined-Type
        leaf v2Sent {
            config "false";
            description "Number of V2 Packets Sent";

            // Type is an MO-Defined-Type
            type nw_Counter32;
        }

        // Number of packets failed to send
        // Type is an MO-Defined-Type
        leaf failedSent {
            config "false";
            description "Number of Packets Failed to Send";

            // Type is an MO-Defined-Type
            type nw_Counter32;
        }

        // Number of valid v1 packets received
        // Type is an MO-Defined-Type
        leaf validV1Rcvd {
            config "false";
            description "Number of Valid V1 Packets Received";

            // Type is an MO-Defined-Type
            type nw_Counter32;
        }

        // Number of v2 packets received
        // Type is an MO-Defined-Type
        leaf validV2Rcvd {
            config "false";
            description "Number of Valid V2 Packets Received";

            // Type is an MO-Defined-Type
            type nw_Counter32;
        }

        // Number of unsupported version packets received
        // Type is an MO-Defined-Type
        leaf unSupVerRcvd {
            config "false";
            description "Number of Unsupported Version Packets Received";

            // Type is an MO-Defined-Type
            type nw_Counter32;
        }

        // Number of checksum error packets received
        // Type is an MO-Defined-Type
        leaf cksumErrRcvd {
            config "false";
            description "Number of Checksum Error Packets Received";

            // Type is an MO-Defined-Type
            type nw_Counter32;
        }

        // Number of malformed packets received
        // Type is an MO-Defined-Type
        leaf malformRcvd {
            config "false";
            description "Number of Malform Packets Received";

            // Type is an MO-Defined-Type
            type nw_Counter32;
        }
    }

    grouping lldp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per lldp instance information. There is
        // only one instance of lldp running in the system today
        container inst-items {

            // Added containment as a singleton: Prefix=inst
            // Acquired From Package lldp
            uses lldp_Inst-group;
        }
    }

    grouping lldp_Inst-group {

        // Amount of time in seconds that a receiving device
        // should hold the information sent by your device
        // before discarding it
        // Type is an MO-Defined-Type
        leaf holdTime {
            config "false";
            description "Hold Time";

            // Type is an MO-Defined-Type
            type lldp_HoldTime;
        }

        // Delay time in seconds for lldp to initialize on any
        // interface
        // Type is an MO-Defined-Type
        leaf initDelayTime {
            config "false";
            description "Init Delay Time";

            // Type is an MO-Defined-Type
            type lldp_InitDelayTime;
        }

        // Transmission frequency of lldp updates in seconds
        // Type is an MO-Defined-Type
        leaf txFreq {
            config "false";
            description "Transmission Frequency";

            // Type is an MO-Defined-Type
            type lldp_TxFreq;
        }

        // Some tlvs are optional as per LLDP protocol (802.1AB)
        // specifications. Use these selectors to turn on/off
        // Type is an MO-Defined-Type
        leaf optTlvSel {
            config "false";
            description "Optional TLV Selector";

            // Type is an MO-Defined-Type
            type lldp_OptTlvSel;
        }

        // System description
        // Type is an MO-Defined-Type
        leaf sysDesc {
            config "false";
            description "System Description";

            // Type is an MO-Defined-Type
            type naming_Descr;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Local management address
        container mgmt-items {
            list MgmtAddr-list {
                config "false";
                key "addr";

                // Added containment: Prefix=mgmt
                // Acquired From Package lldp
                uses lldp_MgmtAddr-group;
            }
        }

        // This object holds lldp information that is operated at a
        // interface level
        container if-items {
            list If-list {
                key "id";

                // Added containment: Prefix=if
                // Acquired From Package lldp
                uses lldp_If-group;
            }
        }
        container instsendtask-items {
            list InstSendTask-list {
                config "false";
                key "shard";

                // Added containment: Prefix=instsendtask
                // Acquired From Package lldp
                uses lldp_InstSendTask-group;
            }
        }

        // This object holds lldp inst statistics operational information.
        // This is a singleton within lldp
        container inststats-items {

            // Added containment as a singleton: Prefix=inststats
            // Acquired From Package lldp
            uses lldp_InstStats-group;
        }

        // Represents a Complex TLV,
        // complex TLV contains Basic TLVs
        container polcomplex-items {
            list Complex-list {
                config "false";
                key "code id";

                // Added containment: Prefix=polcomplex
                // Acquired From Package lldptlvpol
                uses lldptlvpol_Complex-group;
            }
        }

        // Represents a text TLV
        container poltext-items {
            list Text-list {
                config "false";
                key "code";

                // Added containment: Prefix=poltext
                // Acquired From Package lldptlvpol
                uses lldptlvpol_Text-group;
            }
        }

        // Represents an IP TLV
        container polip-items {
            list Ip-list {
                config "false";
                key "code value";

                // Added containment: Prefix=polip
                // Acquired From Package lldptlvpol
                uses lldptlvpol_Ip-group;
            }
        }

        // Represents a Mac TLV
        container polmac-items {
            list Mac-list {
                config "false";
                key "code value";

                // Added containment: Prefix=polmac
                // Acquired From Package lldptlvpol
                uses lldptlvpol_Mac-group;
            }
        }

        // Represents a UInt64 TLV
        container poluint64-items {
            list UInt64-list {
                config "false";
                key "code value";

                // Added containment: Prefix=poluint64
                // Acquired From Package lldptlvpol
                uses lldptlvpol_UInt64-group;
            }
        }

        // Represents a UInt32 TLV
        container poluint32-items {
            list UInt32-list {
                config "false";
                key "code value";

                // Added containment: Prefix=poluint32
                // Acquired From Package lldptlvpol
                uses lldptlvpol_UInt32-group;
            }
        }

        // Represents a UInt16 TLV
        container poluint16-items {
            list UInt16-list {
                config "false";
                key "code value";

                // Added containment: Prefix=poluint16
                // Acquired From Package lldptlvpol
                uses lldptlvpol_UInt16-group;
            }
        }

        // Represents a UByte TLV
        container polubyte-items {
            list UByte-list {
                config "false";
                key "code value";

                // Added containment: Prefix=polubyte
                // Acquired From Package lldptlvpol
                uses lldptlvpol_UByte-group;
            }
        }

        // Rel-def from lldpInstPolCons
        container rslldpInstPolCons-items {

            // Added containment as a singleton: Prefix=rslldpInstPolCons
            // Acquired From Package lldp
            uses lldp_RsLldpInstPolCons_source-group;
        }
    }

    grouping lldp_MgmtAddr-group {
        leaf addr {
            config "false";
            type address_Ip;
        }
    }

    grouping lldp_If-group {

        // Receive admin state
        // Type is an MO-Defined-Type
        leaf adminRxSt {
            config "false";
            description "Admin Receive State";

            // Type is an MO-Defined-Type
            type lldp_AdminSt;
        }

        // Transmit admin state
        // Type is an MO-Defined-Type
        leaf adminTxSt {
            config "false";
            description "Admin Transmit State";

            // Type is an MO-Defined-Type
            type lldp_AdminSt;
        }

        // System description
        // Type is an MO-Defined-Type
        leaf sysDesc {
            config "false";
            description "System Description";

            // Type is an MO-Defined-Type
            type naming_Descr;
        }

        // Port description
        // Type is an MO-Defined-Type
        leaf portDesc {
            config "false";
            description "Port Description";

            // Type is an MO-Defined-Type
            type naming_Descr;
        }

        // Operational state of receive enable
        // Type is an MO-Defined-Type
        leaf operRxSt {
            config "false";
            description "Operational Receive State";

            // Type is an MO-Defined-Type
            type lldp_OperSt;
        }

        // Operational state of transmit enable
        // Type is an MO-Defined-Type
        leaf operTxSt {
            config "false";
            description "Operational Transmit State";

            // Type is an MO-Defined-Type
            type lldp_OperSt;
        }
        leaf mac {
            config "false";
            type address_Mac;
        }

        // Port vlan
        // Type is an MO-Defined-Type
        leaf portVlan {
            config "false";
            description "Port Vlan";

            // Type is an MO-Defined-Type
            type lldp_PortVlan;
        }

        // Wiring Issues
        // Type is an MO-Defined-Type
        leaf wiringIssues {
            config "false";
            description "Wiring Issues";

            // Type is an MO-Defined-Type
            type lldp_WiringIssues;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds lldp neighbor information
        container adj-items {
            list AdjEp-list {
                config "false";
                key "id";

                // Added containment: Prefix=adj
                // Acquired From Package lldp
                uses lldp_AdjEp-group;
            }
        }

        // This object holds the information about IFC adj, used by PE to cache
        // Controller adjEP information to handle adj deletes
        container ctrlradj-items {

            // Added containment as a singleton: Prefix=ctrlradj
            // Acquired From Package lldp
            uses lldp_CtrlrAdjEp-group;
        }
        container ifsendtask-items {
            list IfSendTask-list {
                config "false";
                key "shard";

                // Added containment: Prefix=ifsendtask
                // Acquired From Package lldp
                uses lldp_IfSendTask-group;
            }
        }

        // This object holds lldp intf statistics operational information.
        // This is a singleton within an interface
        container ifstats-items {

            // Added containment as a singleton: Prefix=ifstats
            // Acquired From Package lldp
            uses lldp_IfStats-group;
        }

        // Represents a Complex TLV,
        // complex TLV contains Basic TLVs
        container polcomplex-items {
            list Complex-list {
                config "false";
                key "code id";

                // Added containment: Prefix=polcomplex
                // Acquired From Package lldptlvpol
                uses lldptlvpol_Complex-group;
            }
        }

        // Represents a text TLV
        container poltext-items {
            list Text-list {
                config "false";
                key "code";

                // Added containment: Prefix=poltext
                // Acquired From Package lldptlvpol
                uses lldptlvpol_Text-group;
            }
        }

        // Represents an IP TLV
        container polip-items {
            list Ip-list {
                config "false";
                key "code value";

                // Added containment: Prefix=polip
                // Acquired From Package lldptlvpol
                uses lldptlvpol_Ip-group;
            }
        }

        // Represents a Mac TLV
        container polmac-items {
            list Mac-list {
                config "false";
                key "code value";

                // Added containment: Prefix=polmac
                // Acquired From Package lldptlvpol
                uses lldptlvpol_Mac-group;
            }
        }

        // Represents a UInt64 TLV
        container poluint64-items {
            list UInt64-list {
                config "false";
                key "code value";

                // Added containment: Prefix=poluint64
                // Acquired From Package lldptlvpol
                uses lldptlvpol_UInt64-group;
            }
        }

        // Represents a UInt32 TLV
        container poluint32-items {
            list UInt32-list {
                config "false";
                key "code value";

                // Added containment: Prefix=poluint32
                // Acquired From Package lldptlvpol
                uses lldptlvpol_UInt32-group;
            }
        }

        // Represents a UInt16 TLV
        container poluint16-items {
            list UInt16-list {
                config "false";
                key "code value";

                // Added containment: Prefix=poluint16
                // Acquired From Package lldptlvpol
                uses lldptlvpol_UInt16-group;
            }
        }

        // Represents a UByte TLV
        container polubyte-items {
            list UByte-list {
                config "false";
                key "code value";

                // Added containment: Prefix=polubyte
                // Acquired From Package lldptlvpol
                uses lldptlvpol_UByte-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping lldp_AdjEp-group {

        // Neighbor ID
        // Type is an MO-Defined-Type
        leaf id {
            config "false";
            description "ID";

            // Type is an MO-Defined-Type
            type lldp_AdjId;
        }

        // Neighbor state qualifiers
        // Type is an MO-Defined-Type
        leaf stQual {
            config "false";
            description "State Qualifier";

            // Type is an MO-Defined-Type
            type lldp_AdjStQual;
        }

        // Neighbor chassis id type
        // Type is an MO-Defined-Type
        leaf chassisIdT {
            config "false";
            description "Chassis ID Type";

            // Type is an MO-Defined-Type
            type lldp_ChassisIdT;
        }

        // Neighbor chassis id value
        // Type is an MO-Defined-Type
        leaf chassisIdV {
            config "false";
            description "Chassis ID Value";

            // Type is an MO-Defined-Type
            type lldp_ChassisIdV;
        }

        // Neighbor port type
        // Type is an MO-Defined-Type
        leaf portIdT {
            config "false";
            description "Port ID Type";

            // Type is an MO-Defined-Type
            type lldp_PortIdT;
        }

        // Neighbor port value
        // Type is an MO-Defined-Type
        leaf portIdV {
            config "false";
            description "Port ID Value";

            // Type is an MO-Defined-Type
            type lldp_PortIdV;
        }

        // Neighbor TTL
        // Type is an MO-Defined-Type
        leaf ttl {
            config "false";
            description "TTL";

            // Type is an MO-Defined-Type
            type lldp_TTL;
        }

        // Neighbor system name
        // Type is an MO-Defined-Type
        leaf sysName {
            config "false";
            description "System Name";

            // Type is an MO-Defined-Type
            type lldp_SysName;
        }

        // Neighbor system description
        // Type is an MO-Defined-Type
        leaf sysDesc {
            config "false";
            description "System Description";

            // Type is an MO-Defined-Type
            type lldp_NbrSysDesc;
        }

        // Neighbor port description
        // Type is an MO-Defined-Type
        leaf portDesc {
            config "false";
            description "Port Description";

            // Type is an MO-Defined-Type
            type naming_Descr;
        }

        // Neighbor System Capability
        // Type is an MO-Defined-Type
        leaf capability {
            config "false";
            description "Capability";

            // Type is an MO-Defined-Type
            type lldp_Capability;
        }

        // Neighbor Enabled Capability
        // Type is an MO-Defined-Type
        leaf enCap {
            config "false";
            description "Enabled Capability";

            // Type is an MO-Defined-Type
            type lldp_Capability;
        }

        // Neighbor Management Address
        // Type is an MO-Defined-Type
        leaf mgmtIp {
            config "false";
            description "Management Address";

            // Type is an MO-Defined-Type
            type lldp_MgmtIp;
        }

        // Type is an MO-Defined-Type
        leaf mgmtPortMac {
            config "false";
            description "Management Port MAC";

            // Type is an MO-Defined-Type
            type lldp_MgmtPortMac;
        }
        leaf mgmtId {
            config "false";
            type uint32;
        }

        // Org tlv, Neighbor port vlan
        // Type is an MO-Defined-Type
        leaf portVlan {
            config "false";
            description "Port Vlan";

            // Type is an MO-Defined-Type
            type lldp_PortVlan;
        }

        // Inherited From nw:Conn
        // Modified by Override: nw:Ep->name
        // Type is an MO-Defined-Type
        leaf name {
            description "Name";

            // Type is an MO-Defined-Type
            type naming_Name {
                length "1..64";
            }
        }

        // This object holds lldp adj statistics operational information.
        // This is a singleton within an adjacency
        container adjstats-items {

            // Added containment as a singleton: Prefix=adjstats
            // Acquired From Package lldp
            uses lldp_AdjStats-group;
        }

        // Represents an IP TLV
        container ip-items {
            list Ip-list {
                config "false";
                key "code value";

                // Added containment: Prefix=ip
                // Acquired From Package lldptlv
                uses lldptlv_Ip-group;
            }
        }

        // Represents a Mac TLV
        container mac-items {
            list Mac-list {
                config "false";
                key "code value";

                // Added containment: Prefix=mac
                // Acquired From Package lldptlv
                uses lldptlv_Mac-group;
            }
        }

        // Represents a UInt64 TLV
        container uint64-items {
            list UInt64-list {
                config "false";
                key "code value";

                // Added containment: Prefix=uint64
                // Acquired From Package lldptlv
                uses lldptlv_UInt64-group;
            }
        }

        // Represents a UInt32 TLV
        container uint32-items {
            list UInt32-list {
                config "false";
                key "code value";

                // Added containment: Prefix=uint32
                // Acquired From Package lldptlv
                uses lldptlv_UInt32-group;
            }
        }

        // Represents a UInt16 TLV
        container uint16-items {
            list UInt16-list {
                config "false";
                key "code value";

                // Added containment: Prefix=uint16
                // Acquired From Package lldptlv
                uses lldptlv_UInt16-group;
            }
        }

        // Represents a UByte TLV
        container ubyte-items {
            list UByte-list {
                config "false";
                key "code value";

                // Added containment: Prefix=ubyte
                // Acquired From Package lldptlv
                uses lldptlv_UByte-group;
            }
        }

        // Represents a text TLV
        container text-items {
            list Text-list {
                config "false";
                key "code";

                // Added containment: Prefix=text
                // Acquired From Package lldptlv
                uses lldptlv_Text-group;
            }
        }

        // Represents a Complex TLV.
        // Complex TLV contains Basic TLVs
        container complex-items {
            list Complex-list {
                config "false";
                key "code id";

                // Added containment: Prefix=complex
                // Acquired From Package lldptlv
                uses lldptlv_Complex-group;
            }
        }
    }

    grouping lldp_AdjStats-group {
        leaf adjExpTs {
            config "false";
            type uint64;
        }
    }

    grouping lldptlv_Ip-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Ip;
        }
    }

    grouping lldptlv_Mac-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Mac;
        }
    }

    grouping lldptlv_UInt64-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint64;
        }
    }

    grouping lldptlv_UInt32-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint32;
        }
    }

    grouping lldptlv_UInt16-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint16;
        }
    }

    grouping lldptlv_UByte-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint8;
        }
    }

    grouping lldptlv_Text-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type string;
        }
    }

    grouping lldptlv_Complex-group {

        // TLV Code. Code is a Uint16. Its set by the application & is not captured in the model.
        // Inherited From tlv:TLV
        // Type is an MO-Defined-Type
        leaf code {
            config "false";
            description "TBD";

            // Type is an MO-Defined-Type
            type tlv_Code;
        }
        leaf id {
            config "false";
            type uint32;
        }

        // Represents an IP TLV
        container ip-items {
            list Ip-list {
                config "false";
                key "code value";

                // Added containment: Prefix=ip
                // Acquired From Package lldptlv
                uses lldptlv_Ip-group;
            }
        }

        // Represents a Mac TLV
        container mac-items {
            list Mac-list {
                config "false";
                key "code value";

                // Added containment: Prefix=mac
                // Acquired From Package lldptlv
                uses lldptlv_Mac-group;
            }
        }

        // Represents a UInt64 TLV
        container uint64-items {
            list UInt64-list {
                config "false";
                key "code value";

                // Added containment: Prefix=uint64
                // Acquired From Package lldptlv
                uses lldptlv_UInt64-group;
            }
        }

        // Represents a UInt32 TLV
        container uint32-items {
            list UInt32-list {
                config "false";
                key "code value";

                // Added containment: Prefix=uint32
                // Acquired From Package lldptlv
                uses lldptlv_UInt32-group;
            }
        }

        // Represents a UInt16 TLV
        container uint16-items {
            list UInt16-list {
                config "false";
                key "code value";

                // Added containment: Prefix=uint16
                // Acquired From Package lldptlv
                uses lldptlv_UInt16-group;
            }
        }

        // Represents a UByte TLV
        container ubyte-items {
            list UByte-list {
                config "false";
                key "code value";

                // Added containment: Prefix=ubyte
                // Acquired From Package lldptlv
                uses lldptlv_UByte-group;
            }
        }

        // Represents a text TLV
        container text-items {
            list Text-list {
                config "false";
                key "code";

                // Added containment: Prefix=text
                // Acquired From Package lldptlv
                uses lldptlv_Text-group;
            }
        }
    }

    grouping lldp_CtrlrAdjEp-group {

        // Fabric node ID of the Controller
        // Type is an MO-Defined-Type
        leaf id {
            config "false";
            description "Controller ID";

            // Type is an MO-Defined-Type
            type fabric_NodeId;
        }
        leaf ip {
            config "false";
            type address_Ip;
        }

        // Infra VLAN
        // Type is an MO-Defined-Type
        leaf infraVlan {
            config "false";
            description "Access Vlan";

            // Type is an MO-Defined-Type
            type lldp_InfraVlan;
        }

        // Port role
        // Type is an MO-Defined-Type
        leaf portRole {
            config "false";
            description "Port Role";

            // Type is an MO-Defined-Type
            type lldptlv_PortRole;
        }
        leaf mac {
            config "false";
            type address_Mac;
        }

        // Rel-def from CtrlrAdjEpToStAdjEp
        container rsctrlrAdjEpToStAdjEp-items {

            // Added containment as a singleton: Prefix=rsctrlrAdjEpToStAdjEp
            // Acquired From Package lldp
            uses lldp_RsCtrlrAdjEpToStAdjEp_source-group;
        }
    }

    grouping lldp_IfSendTask-group {

        // Type is an MO-Defined-Type
        leaf shard {
            config "false";
            description "TBD";

            // Type is an MO-Defined-Type
            type ident_ShardId;
        }
    }

    grouping lldp_IfStats-group {

        // LLDP Interface Stats    Number of packets sent
        // Type is an MO-Defined-Type
        leaf pktSent {
            config "false";
            description "Number of Packets Sent";

            // Type is an MO-Defined-Type
            type nw_Counter64;
        }

        // Number of packets received
        // Type is an MO-Defined-Type
        leaf pktRcvd {
            config "false";
            description "Number of Packets Received";

            // Type is an MO-Defined-Type
            type nw_Counter64;
        }

        // Number of entries aged
        // Type is an MO-Defined-Type
        leaf entriesAged {
            config "false";
            description "Number of Entries Aged";

            // Type is an MO-Defined-Type
            type nw_Counter64;
        }

        // Number of packets received in error
        // Type is an MO-Defined-Type
        leaf errPktRcvd {
            config "false";
            description "Number of Packets Received in Error";

            // Type is an MO-Defined-Type
            type nw_Counter64;
        }

        // Number of packets discarded
        // Type is an MO-Defined-Type
        leaf pktDiscarded {
            config "false";
            description "Number of Packets Discarded";

            // Type is an MO-Defined-Type
            type nw_Counter64;
        }

        // Number of unrecognized TLVs
        // Type is an MO-Defined-Type
        leaf unrecogTLV {
            config "false";
            description "Number of Unrecognized TLVs";

            // Type is an MO-Defined-Type
            type nw_Counter64;
        }
    }

    grouping lldptlvpol_Complex-group {

        // TLV Code. Code is a Uint16. Its set by the application & is not captured in the model.
        // Inherited From tlv:TLV
        // Type is an MO-Defined-Type
        leaf code {
            config "false";
            description "TBD";

            // Type is an MO-Defined-Type
            type tlv_Code;
        }
        leaf id {
            config "false";
            type uint32;
        }

        // Represents an IP TLV
        container polip-items {
            list Ip-list {
                config "false";
                key "code value";

                // Added containment: Prefix=polip
                // Acquired From Package lldptlvpol
                uses lldptlvpol_Ip-group;
            }
        }

        // Represents a Mac TLV
        container polmac-items {
            list Mac-list {
                config "false";
                key "code value";

                // Added containment: Prefix=polmac
                // Acquired From Package lldptlvpol
                uses lldptlvpol_Mac-group;
            }
        }

        // Represents a UInt64 TLV
        container poluint64-items {
            list UInt64-list {
                config "false";
                key "code value";

                // Added containment: Prefix=poluint64
                // Acquired From Package lldptlvpol
                uses lldptlvpol_UInt64-group;
            }
        }

        // Represents a UInt32 TLV
        container poluint32-items {
            list UInt32-list {
                config "false";
                key "code value";

                // Added containment: Prefix=poluint32
                // Acquired From Package lldptlvpol
                uses lldptlvpol_UInt32-group;
            }
        }

        // Represents a UInt16 TLV
        container poluint16-items {
            list UInt16-list {
                config "false";
                key "code value";

                // Added containment: Prefix=poluint16
                // Acquired From Package lldptlvpol
                uses lldptlvpol_UInt16-group;
            }
        }

        // Represents a UByte TLV
        container polubyte-items {
            list UByte-list {
                config "false";
                key "code value";

                // Added containment: Prefix=polubyte
                // Acquired From Package lldptlvpol
                uses lldptlvpol_UByte-group;
            }
        }

        // Represents a text TLV
        container poltext-items {
            list Text-list {
                config "false";
                key "code";

                // Added containment: Prefix=poltext
                // Acquired From Package lldptlvpol
                uses lldptlvpol_Text-group;
            }
        }
    }

    grouping lldptlvpol_Ip-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Ip;
        }
    }

    grouping lldptlvpol_Mac-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type address_Mac;
        }
    }

    grouping lldptlvpol_UInt64-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint64;
        }
    }

    grouping lldptlvpol_UInt32-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint32;
        }
    }

    grouping lldptlvpol_UInt16-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint16;
        }
    }

    grouping lldptlvpol_UByte-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type uint8;
        }
    }

    grouping lldptlvpol_Text-group {

        // TLV Code. Code is a Uint16. Its set by the application & is not captured in the model.
        // Inherited From tlv:TLV
        // Type is an MO-Defined-Type
        leaf code {
            config "false";
            description "TBD";

            // Type is an MO-Defined-Type
            type tlv_Code;
        }
        leaf value {
            config "false";
            type string;
        }
    }

    grouping lldp_InstSendTask-group {

        // Type is an MO-Defined-Type
        leaf shard {
            config "false";
            description "TBD";

            // Type is an MO-Defined-Type
            type ident_ShardId;
        }
    }

    grouping lldp_InstStats-group {

        // LLDP Inst Stats    Number of packets sent
        // Type is an MO-Defined-Type
        leaf pktSent {
            config "false";
            description "Number of Packets Sent";

            // Type is an MO-Defined-Type
            type nw_Counter64;
        }

        // Number of packets received
        // Type is an MO-Defined-Type
        leaf pktRcvd {
            config "false";
            description "Number of Packets Received";

            // Type is an MO-Defined-Type
            type nw_Counter64;
        }

        // Number of entries aged
        // Type is an MO-Defined-Type
        leaf entriesAged {
            config "false";
            description "Number of Entries Aged";

            // Type is an MO-Defined-Type
            type nw_Counter64;
        }

        // Number of packets received in error
        // Type is an MO-Defined-Type
        leaf errPktRcvd {
            config "false";
            description "Number of Packets Received in Error";

            // Type is an MO-Defined-Type
            type nw_Counter64;
        }

        // Number of packets discarded
        // Type is an MO-Defined-Type
        leaf pktDiscarded {
            config "false";
            description "Number of Packets Discarded";

            // Type is an MO-Defined-Type
            type nw_Counter64;
        }

        // Number of unrecognized TLVs
        // Type is an MO-Defined-Type
        leaf unrecogTLV {
            config "false";
            description "Number of Unrecognized TLVs";

            // Type is an MO-Defined-Type
            type nw_Counter64;
        }

        // Number of adjacency added
        // Type is an MO-Defined-Type
        leaf numAdjAdded {
            config "false";
            description "Number of Adjacencies Added";

            // Type is an MO-Defined-Type
            type nw_Counter32;
        }

        // Number of adjacency removed
        // Type is an MO-Defined-Type
        leaf numAdjRemoved {
            config "false";
            description "Number of Adjacencies Removed";

            // Type is an MO-Defined-Type
            type nw_Counter32;
        }
        leaf lastAdjChgTs {
            config "false";
            type uint64;
        }
    }

    grouping mcp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per MCP instance information. There is only
        // one instance of MCP running in the system today
        container inst-items {

            // Added containment as a singleton: Prefix=inst
            // Acquired From Package mcp
            uses mcp_Inst-group;
        }
    }

    grouping mcp_Inst-group {

        // Transmission frequency of MCP packets on each L2
        // interface in seconds
        // Type is an MO-Defined-Type
        leaf txFreq {
            config "false";
            description "Transmission Frequency";

            // Type is an MO-Defined-Type
            type mcp_TxFreq;
        }

        // Loop detection multiplier i.e. number of MCP packets,
        // when received consecutively from same {leaf, port},
        // treated as loop condition
        // Type is an MO-Defined-Type
        leaf loopDetectMult {
            config "false";
            description "TBD";

            // Type is an MO-Defined-Type
            type mcp_LoopDetectMult;
        }
        leaf key {
            config "false";
            type string;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds mcp information that is operated at a
        // interface level
        container if-items {
            list If-list {
                key "id";

                // Added containment: Prefix=if
                // Acquired From Package mcp
                uses mcp_If-group;
            }
        }
    }

    grouping mcp_If-group {

        // Operational state
        // Type is an MO-Defined-Type
        leaf operSt {
            config "false";
            description "TBD";

            // Type is an MO-Defined-Type
            type mcp_OperSt;
        }

        // Block state qualifier
        // Type is an MO-Defined-Type
        leaf operStQual {
            config "false";
            description "TBD";

            // Type is an MO-Defined-Type
            type mcp_OperStQual;
        }
        leaf lastLoopDetTs {
            config "false";
            type uint64;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping vpc_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per vpc instance information. There is only
        // one instance of vpcm running in the system today
        container inst-items {

            // Added containment as a singleton: Prefix=inst
            // Acquired From Package vpc
            uses vpc_Inst-group;
        }
    }

    grouping vpc_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // configure orphan ports to be brought down on Secondary peerlink failure
        container orphan-items {
            list OrphanPort-list {
                key "id";

                // Added containment: Prefix=orphan
                // Acquired From Package vpc
                uses vpc_OrphanPort-group;
            }
        }

        // This objects hold per vpc domain information. There is only
        // one vpc domain that is configurable in the system
        container dom-items {

            // Added containment as a singleton: Prefix=dom
            // Acquired From Package vpc
            uses vpc_Dom-group;
        }
    }

    grouping vpc_OrphanPort-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping vpc_Dom-group {

        // Domain id    @@@ This property is internally set by PE
        // Type is an MO-Defined-Type
        leaf id {
            description "Domain ID";

            // Type is an MO-Defined-Type
            type vpc_DomId;
        }
        leaf peerIp {
            config "false";
            type address_Ip;
        }
        leaf virtualIp {
            config "false";
            type address_Ip;
        }

        // vpc virtual IP address announcement delay
        // Type is an MO-Defined-Type
        leaf vIpAnnounceDelay {
            config "false";
            description "Virtual IP Announcement Delay";

            // Type is an MO-Defined-Type
            type vpc_VIpAnnounceDelay;
        }

        // system priority   @@@ This comes from the lacp policy
        // Type is an MO-Defined-Type
        leaf sysPrio {
            description "System Priority";

            // Type is an MO-Defined-Type
            type vpc_SysPrio;
        }
        leaf sysMac {
            type address_Mac;
        }

        // role priority    @@@ This comes from the vpc policy
        // Type is an MO-Defined-Type
        leaf rolePrio {
            description "Role Priority";

            // Type is an MO-Defined-Type
            type vpc_RolePrio;
        }

        // Peer dead interval    @@@ This comes from the vpc policy
        // Type is an MO-Defined-Type
        leaf deadIntvl {
            config "false";
            description "Dead Interval";

            // Type is an MO-Defined-Type
            type vpc_DeadIntvl;
        }

        // Orphan port config. This is the list of orphan ports to be
        // brought down when all uplinks are lost.
        // Type is an MO-Defined-Type
        leaf orphanPortList {
            config "false";
            description "Orphan Port List";

            // Type is an MO-Defined-Type
            type vpc_OrphanPortList;
        }

        // Enable L3 forwarding for packets destined to peer's gateway
        // mac-address.
        // Type is an MO-Defined-Type
        leaf peerGw {
            description "Peer Gateway";

            // Type is an MO-Defined-Type
            type nw_AdminSt;
        }

        // Enable graceful type-1 consistency check
        // Type is an MO-Defined-Type
        leaf grcflCnstncyChck {
            description "Graceful Type-1 Consistency Check";

            // Type is an MO-Defined-Type
            type nw_AdminSt;
        }

        // Tracking object to suspend vPC if object goes down
        // Type is an MO-Defined-Type
        leaf track {
            description "Tracking object";

            // Type is an MO-Defined-Type
            type vpc_Track;
        }

        // Enable auto recovery if peer is presumed non-operational
        // Type is an MO-Defined-Type
        leaf autoRecovery {
            description "Auto Recovery";

            // Type is an MO-Defined-Type
            type nw_AdminSt;
        }

        // Duration to wait before assuming peer dead and restoring vpcs
        // Type is an MO-Defined-Type
        leaf autoRecoveryIntvl {
            description "Auto Recovery";

            // Type is an MO-Defined-Type
            type vpc_AutoRecoveryIntvl;
        }

        // IPv4 CFS synchronize
        // Type is an MO-Defined-Type
        leaf ipv4CfsSync {
            description "IPv4 CFS synchronize";

            // Type is an MO-Defined-Type
            type nw_AdminSt;
        }

        // IPv6 CFS synchronize
        // Type is an MO-Defined-Type
        leaf ipv6CfsSync {
            description "IPv6 CFS synchronize";

            // Type is an MO-Defined-Type
            type nw_AdminSt;
        }

        // Enable peer switch on vPC pair switches
        // Type is an MO-Defined-Type
        leaf peerSwitch {
            config "false";
            description "vPC pair switches";

            // Type is an MO-Defined-Type
            type nw_AdminSt;
        }

        // Delay in bringing up the vPC links
        // Type is an MO-Defined-Type
        leaf delayRestoreVPC {
            description "Delay restore for vPC links";

            // Type is an MO-Defined-Type
            type vpc_DelayRestoreVPC;
        }

        // Delay in bringing-up interface-vlan
        // Type is an MO-Defined-Type
        leaf delayRestoreSVI {
            description "Delay restore for SVI";

            // Type is an MO-Defined-Type
            type vpc_DelayRestoreSVI;
        }

        // Delay in bringing-up the peer-link
        // Type is an MO-Defined-Type
        leaf delayPeerLinkBringup {
            description "Peer link delay timer";

            // Type is an MO-Defined-Type
            type vpc_DelayPeerLinkBringup;
        }

        // Interface vlans to exclude from suspension when dual-active
        // Type is an MO-Defined-Type
        leaf excludeSVI {
            description "Exclude SVI List";

            // Type is an MO-Defined-Type
            type vpc_ExcludeSVI;
        }

        // Suspend vPC locally
        // Type is an MO-Defined-Type
        leaf adminSt {
            description "vPC suspend locally";

            // Type is an MO-Defined-Type
            type nw_AdminSt;
        }

        // role
        // Type is an MO-Defined-Type
        leaf operRole {
            config "false";
            description "Operational Role";

            // Type is an MO-Defined-Type
            type vpc_Role;
        }

        // old role
        // Type is an MO-Defined-Type
        leaf oldRole {
            config "false";
            description "Old Role";

            // Type is an MO-Defined-Type
            type vpc_Role;
        }

        // lacp role
        // Type is an MO-Defined-Type
        leaf lacpRole {
            config "false";
            description "Lacp Role";

            // Type is an MO-Defined-Type
            type vpc_Role;
        }

        // summarized role
        // Type is an MO-Defined-Type
        leaf summOperRole {
            config "false";
            description "Summarized Oper Role";

            // Type is an MO-Defined-Type
            type vpc_SummRole;
        }

        // local system priority
        // Type is an MO-Defined-Type
        leaf localPrio {
            config "false";
            description "Local System Priority";

            // Type is an MO-Defined-Type
            type vpc_SysPrio;
        }

        // peer system priority
        // Type is an MO-Defined-Type
        leaf peerPrio {
            config "false";
            description "Peer System Priority";

            // Type is an MO-Defined-Type
            type vpc_SysPrio;
        }

        // vpc system priority
        // Type is an MO-Defined-Type
        leaf vpcPrio {
            config "false";
            description "Vpc System Priority";

            // Type is an MO-Defined-Type
            type vpc_SysPrio;
        }
        leaf localMAC {
            config "false";
            type address_Mac;
        }
        leaf peerMAC {
            config "false";
            type address_Mac;
        }
        leaf vpcMAC {
            config "false";
            type address_Mac;
        }

        // various operational state
        // Type is an MO-Defined-Type
        leaf operSt {
            config "false";
            description "Operational State";

            // Type is an MO-Defined-Type
            type vpc_DomOperSt;
        }

        // peer version
        // Type is an MO-Defined-Type
        leaf peerVersion {
            config "false";
            description "Peer Version";

            // Type is an MO-Defined-Type
            type vpc_PeerVersion;
        }

        // batched vpc inventory
        // Type is an MO-Defined-Type
        leaf batchedVpcInv {
            config "false";
            description "Batched Vpc Inventory";

            // Type is an MO-Defined-Type
            type vpc_BatchedVpcInv;
        }
        leaf issuFromVer {
            config "false";
            type string;
        }
        leaf issuToVer {
            config "false";
            type string;
        }

        // Peer state
        // Type is an MO-Defined-Type
        leaf peerSt {
            config "false";
            description "Peer State";

            // Type is an MO-Defined-Type
            type vpc_PeerSt;
        }

        // Peer status reason code
        // Type is an MO-Defined-Type
        leaf peerStQual {
            config "false";
            description "Peer Status Qualifier";

            // Type is an MO-Defined-Type
            type vpc_PeerStQual;
        }

        // Dual active status
        // Type is an MO-Defined-Type
        leaf dualActiveSt {
            config "false";
            description "Dual Active Status";

            // Type is an MO-Defined-Type
            type vpc_DualActiveSt;
        }

        // Compatibility status
        // Type is an MO-Defined-Type
        leaf compatSt {
            config "false";
            description "Compatibility Status";

            // Type is an MO-Defined-Type
            type vpc_CompatSt;
        }

        // Compatibility reason code
        // Type is an MO-Defined-Type
        leaf compatQual {
            config "false";
            description "Compatibility Qualifier";

            // Type is an MO-Defined-Type
            type vpc_CompatQual;
        }
        leaf compatQualStr {
            config "false";
            type string;
        }

        // Type-2 compatibility status
        // Type is an MO-Defined-Type
        leaf type2CompatSt {
            config "false";
            description "Type-2 Compatibility Status";

            // Type is an MO-Defined-Type
            type vpc_CompatSt;
        }

        // Type-2 compatibility reason code
        // Type is an MO-Defined-Type
        leaf type2CompatQual {
            config "false";
            description "Type-2 Compatibility Qualifier";

            // Type is an MO-Defined-Type
            type vpc_CompatQual;
        }
        leaf type2CompatQualStr {
            config "false";
            type string;
        }

        // Inherited From nw:Conn
        // Modified by Override: nw:CpDom->name
        // Type is an MO-Defined-Type
        leaf name {
            description "Name";

            // Type is an MO-Defined-Type
            type naming_Name {
                length "1..64";
            }
        }
        container if-items {
            list If-list {
                key "id";

                // Added containment: Prefix=if
                // Acquired From Package vpc
                uses vpc_If-group;
            }
        }

        // vpc keepalive definitions
        container keepalive-items {

            // Added containment as a singleton: Prefix=keepalive
            // Acquired From Package vpc
            uses vpc_Keepalive-group;
        }

        // This object holds parameters information for an app.
        container params-items {
            list AppParams-list {
                config "false";
                key "appId";

                // Added containment: Prefix=params
                // Acquired From Package vpc
                uses vpc_AppParams-group;
            }
        }

        // Rel-def from vpcInstPolCons
        container rsvpcInstPolCons-items {

            // Added containment as a singleton: Prefix=rsvpcInstPolCons
            // Acquired From Package vpc
            uses vpc_RsVpcInstPolCons_source-group;
        }
    }

    grouping vpc_If-group {

        // vpc id
        // Type is an MO-Defined-Type
        leaf id {
            description "VPC ID";

            // Type is an MO-Defined-Type
            type vpc_Id;
        }

        // local operational status
        // Type is an MO-Defined-Type
        leaf localOperSt {
            config "false";
            description "Local Operational State";

            // Type is an MO-Defined-Type
            type vpc_OperSt;
        }

        // remote operational status
        // Type is an MO-Defined-Type
        leaf remoteOperSt {
            config "false";
            description "Remote Operational State";

            // Type is an MO-Defined-Type
            type vpc_OperSt;
        }

        // Compatibility status
        // Type is an MO-Defined-Type
        leaf compatSt {
            config "false";
            description "Compatibility Status";

            // Type is an MO-Defined-Type
            type vpc_CompatSt;
        }

        // Compatibility reason code
        // Type is an MO-Defined-Type
        leaf compatQual {
            config "false";
            description "Compatibility Qualifier";

            // Type is an MO-Defined-Type
            type vpc_CompatQual;
        }
        leaf compatQualStr {
            config "false";
            type string;
        }

        // Configured vlans
        // Type is an MO-Defined-Type
        leaf cfgdVlans {
            config "false";
            description "Configured Vlans";

            // Type is an MO-Defined-Type
            type l2_VlanBitmap;
        }

        // Configured trunk vlans
        // Type is an MO-Defined-Type
        leaf cfgdTrunkVlans {
            config "false";
            description "Configured Trunk Vlans";

            // Type is an MO-Defined-Type
            type l2_VlanBitmap;
        }
        leaf cfgdAccessVlan {
            config "false";
            type string;
        }

        // Up vlans
        // Type is an MO-Defined-Type
        leaf upVlans {
            config "false";
            description "Up Vlans";

            // Type is an MO-Defined-Type
            type l2_VlanBitmap;
        }

        // Suspended vlans
        // Type is an MO-Defined-Type
        leaf suspVlans {
            config "false";
            description "Suspended Vlans";

            // Type is an MO-Defined-Type
            type l2_VlanBitmap;
        }

        // Configured vlans on peer
        // Type is an MO-Defined-Type
        leaf peerCfgdVlans {
            config "false";
            description "Peer Configured Vlans";

            // Type is an MO-Defined-Type
            type l2_VlanBitmap;
        }

        // Up vlans on peer
        // Type is an MO-Defined-Type
        leaf peerUpVlans {
            config "false";
            description "Peer Up Vlans";

            // Type is an MO-Defined-Type
            type l2_VlanBitmap;
        }

        // This object holds parameters information for an app.
        container params-items {
            list AppParams-list {
                config "false";
                key "appId";

                // Added containment: Prefix=params
                // Acquired From Package vpc
                uses vpc_AppParams-group;
            }
        }

        // Rel-def from vpcConf
        container rsvpcConf-items {

            // Added containment as a singleton: Prefix=rsvpcConf
            // Acquired From Package vpc
            uses vpc_RsVpcConf_source-group;
        }
    }

    grouping vpc_AppParams-group {

        // Application Sap Id
        // Type is an MO-Defined-Type
        leaf appId {
            config "false";
            description "Application SAP ID";

            // Type is an MO-Defined-Type
            type vpc_AppId;
        }

        // Local Reason Code
        // Type is an MO-Defined-Type
        leaf locRsnCode {
            config "false";
            description "Local Reason Code";

            // Type is an MO-Defined-Type
            type vpc_CompatQual;
        }

        // Local Param Length
        // Type is an MO-Defined-Type
        leaf locParamLen {
            config "false";
            description "Local Param Length";

            // Type is an MO-Defined-Type
            type vpc_ParamLen;
        }

        // Local Param Value
        // Type is an MO-Defined-Type
        leaf locParamVal {
            config "false";
            description "Local Param Value";

            // Type is an MO-Defined-Type
            type vpc_ParamVal;
        }

        // Remote Reason Code
        // Type is an MO-Defined-Type
        leaf remRsnCode {
            config "false";
            description "Remoe Reason Code";

            // Type is an MO-Defined-Type
            type vpc_CompatQual;
        }

        // Remote Param Length
        // Type is an MO-Defined-Type
        leaf remParamLen {
            config "false";
            description "Remote Param Length";

            // Type is an MO-Defined-Type
            type vpc_ParamLen;
        }

        // Remote Param Value
        // Type is an MO-Defined-Type
        leaf remParamVal {
            config "false";
            description "Remote Param Value";

            // Type is an MO-Defined-Type
            type vpc_ParamVal;
        }

        // This object holds per app per param information .
        container param-items {
            list AppParamInfo-list {
                config "false";
                key "paramName";

                // Added containment: Prefix=param
                // Acquired From Package vpc
                uses vpc_AppParamInfo-group;
            }
        }
    }

    grouping vpc_AppParamInfo-group {
        leaf paramName {
            config "false";
            type string;
        }

        // Param Type
        // Type is an MO-Defined-Type
        leaf paramType {
            config "false";
            description "Parameter Type";

            // Type is an MO-Defined-Type
            type vpc_ParamType;
        }
        leaf locParamVal {
            config "false";
            type string;
        }
        leaf remParamVal {
            config "false";
            type string;
        }
    }

    grouping vpc_Keepalive-group {

        // vrf name
        // Type is an MO-Defined-Type
        leaf vrf {
            description "VRF";

            // Type is an MO-Defined-Type
            type l3_VrfName;
        }
        leaf srcIp {
            type address_Ip;
        }
        leaf srcIpCli {
            config "false";
            type boolean;
            default "true";
        }
        leaf destIp {
            type address_Ip;
        }

        // port number
        // Type is an MO-Defined-Type
        leaf udpPort {
            description "UDP Port";

            // Type is an MO-Defined-Type
            type comm_Port;
        }

        // interval
        // Type is an MO-Defined-Type
        leaf interval {
            description "Interval";

            // Type is an MO-Defined-Type
            type vpc_KeepaliveInterval;
        }

        // timeout
        // Type is an MO-Defined-Type
        leaf timeout {
            description "Timeout";

            // Type is an MO-Defined-Type
            type vpc_KeepaliveTout;
        }

        // tos config type
        // Type is an MO-Defined-Type
        leaf tosCfgType {
            description "TOS Type";

            // Type is an MO-Defined-Type
            type vpc_TosCfgType;
        }

        // tos byte
        // Type is an MO-Defined-Type
        leaf tosByte {
            description "TOS Byte";

            // Type is an MO-Defined-Type
            type vpc_TosByte;
        }

        // tos value
        // Type is an MO-Defined-Type
        leaf tosValue {
            description "TOS Value";

            // Type is an MO-Defined-Type
            type vpc_TosValue;
        }

        // tos type
        // Type is an MO-Defined-Type
        leaf tosType {
            description "TOS Type";

            // Type is an MO-Defined-Type
            type vpc_TosType;
        }

        // precedence value
        // Type is an MO-Defined-Type
        leaf precValue {
            description "Precedence Value";

            // Type is an MO-Defined-Type
            type vpc_PrecValue;
        }

        // precedence type
        // Type is an MO-Defined-Type
        leaf precType {
            description "Precedence Type";

            // Type is an MO-Defined-Type
            type vpc_PrecType;
        }

        // flush timeout
        // Type is an MO-Defined-Type
        leaf flushTout {
            description "Flush Timeout";

            // Type is an MO-Defined-Type
            type vpc_FlushTout;
        }

        // operational state
        // Type is an MO-Defined-Type
        leaf operSt {
            config "false";
            description "Operational State";

            // Type is an MO-Defined-Type
            type vpc_KeepaliveOperSt;
        }

        // send interface
        // Type is an MO-Defined-Type
        leaf sendIf {
            config "false";
            description "Send Interface";

            // Type is an MO-Defined-Type
            type nw_IfId;
        }

        // recv interface
        // Type is an MO-Defined-Type
        leaf recvIf {
            config "false";
            description "Received Interface";

            // Type is an MO-Defined-Type
            type nw_IfId;
        }

        // last send time
        // Type is an MO-Defined-Type
        leaf sendTime {
            config "false";
            description "Last Send Time";

            // Type is an MO-Defined-Type
            type vpc_Time;
        }

        // last recv time
        // Type is an MO-Defined-Type
        leaf recvTime {
            config "false";
            description "Last Received Time";

            // Type is an MO-Defined-Type
            type vpc_Time;
        }

        // first recv time
        // Type is an MO-Defined-Type
        leaf firstRecvTime {
            config "false";
            description "First Received Time";

            // Type is an MO-Defined-Type
            type vpc_Time;
        }

        // number of packets sent
        // Type is an MO-Defined-Type
        leaf sentPkts {
            config "false";
            description "Sent Packets";

            // Type is an MO-Defined-Type
            type vpc_Counter;
        }

        // number of packets received
        // Type is an MO-Defined-Type
        leaf rcvdPkts {
            config "false";
            description "Received Packets";

            // Type is an MO-Defined-Type
            type vpc_Counter;
        }
        leaf avgRecvInterval {
            config "false";
            type uint32;
        }
        leaf peerStateChanges {
            config "false";
            type uint32;
        }

        // From Interface naming:Named
        // Inherited From naming:NamedObject
        // Type is an MO-Defined-Type
        leaf name {
            description "Name";

            // Type is an MO-Defined-Type
            type naming_Name;
        }

        // Specify link used for peer communication
        container peerlink-items {

            // Added containment as a singleton: Prefix=peerlink
            // Acquired From Package vpc
            uses vpc_PeerLink-group;
        }
    }

    grouping vpc_PeerLink-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping fv_EpNs-group {

        // Represents the number of EPs currently
        // discovered
        // Type is an MO-Defined-Type
        leaf epCount {
            config "false";
            description "TBD";

            // Type is an MO-Defined-Type
            type fv_EpCount;
        }
    }

    grouping igmp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per igmp instance information. There is only
        // one instance of igmp running in the system today
        container inst-items {

            // Added containment as a singleton: Prefix=inst
            // Acquired From Package igmp
            uses igmp_Inst-group;
        }
    }

    grouping igmp_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Control
        // Inherited From ipmc:AInst
        // Type is an MO-Defined-Type
        leaf instCtrl {
            config "false";
            description "Inst Controls";

            // Type is an MO-Defined-Type
            type ipmc_InstCtrl;
        }

        // Bootup route add delay to RIB
        // Inherited From ipmc:AInst
        // Type is an MO-Defined-Type
        leaf bootupDelay {
            config "false";
            description "Bootup Route Add Delay";

            // Type is an MO-Defined-Type
            type ipmc_BootupDelay;
        }
        leaf flushRoute {
            config "false";
            type boolean;
        }
        leaf rtrAlert {
            config "false";
            type boolean;
        }
        leaf anyQueryDest {
            config "false";
            type boolean;
        }

        // This objects hold per igmp external domain information
        container extdom-items {
            list ExtDom-list {
                config "false";
                key "id";

                // Added containment: Prefix=extdom
                // Acquired From Package igmp
                uses igmp_ExtDom-group;
            }
        }

        // This objects hold per igmp domain information
        container dom-items {
            list Dom-list {
                key "name";

                // Added containment: Prefix=dom
                // Acquired From Package igmp
                uses igmp_Dom-group;
            }
        }
    }

    grouping igmp_ExtDom-group {

        // Id for this domain    @@@ This comes from the Network id assigned by the
        // PE for the external domain
        // Type is an MO-Defined-Type
        leaf id {
            config "false";
            description "ID";

            // Type is an MO-Defined-Type
            type top_RemoteNetworkId;
        }

        // Igmp Version
        // Type is an MO-Defined-Type
        leaf ver {
            config "false";
            description "Version";

            // Type is an MO-Defined-Type
            type mcast_Ver;
        }

        // Inherited From nw:Conn
        // Modified by Override: nw:CpDom->name
        // Type is an MO-Defined-Type
        leaf name {
            description "Name";

            // Type is an MO-Defined-Type
            type naming_Name {
                length "1..64";
            }
        }

        // This objects hold per igmp external interface information
        container extif-items {
            list ExtIf-list {
                key "id";

                // Added containment: Prefix=extif
                // Acquired From Package igmp
                uses igmp_ExtIf-group;
            }
        }
    }

    grouping igmp_ExtIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping igmp_Dom-group {

        // Inherited From nw:Conn
        // Modified by Override: nw:CpDom->name
        // Type is an MO-Defined-Type
        leaf name {
            description "Name";

            // Type is an MO-Defined-Type
            type naming_Name {
                length "1..64";
            }
        }

        // IGMP databases
        container db-items {
            list Db-list {
                config "false";
                key "type";

                // Added containment: Prefix=db
                // Acquired From Package igmp
                uses igmp_Db-group;
            }
        }

        // This objects hold per igmp interface information
        container if-items {
            list If-list {
                key "id";

                // Added containment: Prefix=if
                // Acquired From Package igmp
                uses igmp_If-group;
            }
        }

        // This objects hold per igmp domain information
        container ssmxlate-items {
            list SSMXlate-list {
                config "false";
                key "srcAddr grpPfx";

                // Added containment: Prefix=ssmxlate
                // Acquired From Package igmp
                uses igmp_SSMXlate-group;
            }
        }
    }

    grouping igmp_Db-group {

        // Type of the repository
        // Type is an MO-Defined-Type
        leaf type {
            config "false";
            description "Type";

            // Type is an MO-Defined-Type
            type igmp_DbT;
        }

        // Inherited From nw:Conn
        // Modified by Override: nw:Db->name
        // Type is an MO-Defined-Type
        leaf name {
            description "Name";

            // Type is an MO-Defined-Type
            type naming_Name {
                length "1..64";
            }
        }

        // IGMP Group/Src MOs
        container src-items {
            list Route-list {
                config "false";
                key "src grp";

                // Added containment: Prefix=src
                // Acquired From Package igmp
                uses igmp_Route-group;
            }
        }
    }

    grouping igmp_Route-group {
        leaf src {
            config "false";
            type address_Ip;
        }
        leaf grp {
            config "false";
            type address_Ip;
        }

        // IGMP Oif MOs. We create one object per interface in the oif list
        container oif-items {
            list Oif-list {
                config "false";
                key "oif";

                // Added containment: Prefix=oif
                // Acquired From Package igmp
                uses igmp_Oif-group;
            }
        }
    }

    grouping igmp_Oif-group {

        // Inherited From ipmc:Oif
        // Type is an MO-Defined-Type
        leaf oif {
            config "false";
            description "Outgoing interface";

            // Type is an MO-Defined-Type
            type nw_IfId;
        }
        leaf expiryTs {
            config "false";
            type uint64;
        }
        leaf createTs {
            config "false";
            type uint64;
        }
        leaf lastRep {
            config "false";
            type address_Ip;
        }

        // Inherited From ipmc:Oif
        // Type is an MO-Defined-Type
        leaf type {
            config "false";
            description "Join type";

            // Type is an MO-Defined-Type
            type ipmc_RouteFlags;
        }
    }

    grouping igmp_If-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface Control
        // Inherited From ipmc:AIf
        // Type is an MO-Defined-Type
        leaf ifCtrl {
            config "false";
            description "Controls";

            // Type is an MO-Defined-Type
            type ipmc_IfCtrl;
        }

        // Interface version
        // Inherited From ipmc:AIf
        // Modified by Override: igmp:If->ver
        // Type is an MO-Defined-Type
        leaf ver {
            config "false";
            description "Version";

            // Type is an MO-Defined-Type
            type mcast_Ver;
        }

        // Group Timeout
        // Inherited From ipmc:AIf
        // Type is an MO-Defined-Type
        leaf grpTimeout {
            config "false";
            description "Group Membership Timeout";

            // Type is an MO-Defined-Type
            type ipmc_GrpTimeout;
        }
        leaf actQuer {
            config "false";
            type address_Ip;
        }
        leaf nextQuerTime {
            config "false";
            type uint64;
        }

        // Flags
        // Inherited From ipmc:AIf
        // Type is an MO-Defined-Type
        leaf flags {
            config "false";
            description "Flags";

            // Type is an MO-Defined-Type
            type ipmc_IfFlags;
        }
        leaf entryCount {
            config "false";
            type uint32;
        }
        leaf stEntryCount {
            config "false";
            type uint32;
        }
        leaf querExpiry {
            config "false";
            type uint64;
        }
        leaf reportLl {
            config "false";
            type boolean;
        }
        leaf immediateLeave {
            config "false";
            type boolean;
        }
        leaf allowv3Asm {
            config "false";
            type boolean;
        }

        // IGMP Interface Stats Oper MO
        container IfStats-items {

            // Added containment as a singleton: Prefix=IfStats
            // Acquired From Package igmp
            uses igmp_IfStats-group;
        }

        // This objects hold IP Multicast Group JoinType information
        container jointype-items {
            list JoinType-list {
                config "false";
                key "type";

                // Added containment: Prefix=jointype
                // Acquired From Package igmp
                uses igmp_JoinType-group;
            }
        }

        // This object holds resource (router state) limit policy
        // to limit amount of multicast routing state on the router
        container limit-items {

            // Added containment as a singleton: Prefix=limit
            // Acquired From Package igmp
            uses igmp_ResP-group;
        }

        // This object holds igmp reports policy state per Interface
        container reppol-items {

            // Added containment as a singleton: Prefix=reppol
            // Acquired From Package igmp
            uses igmp_RepP-group;
        }

        // This object holds static igmp reports policy state per Interface
        container streppol-items {
            list StRepP-list {
                config "false";
                key "joinType";

                // Added containment: Prefix=streppol
                // Acquired From Package igmp
                uses igmp_StRepP-group;
            }
        }

        // This object holds querier information per interface
        container querierp-items {

            // Added containment as a singleton: Prefix=querierp
            // Acquired From Package igmp
            uses igmp_QuerierP-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping igmp_IfStats-group {
        leaf v2querSent {
            config "false";
            type uint32;
        }
        leaf v2querRcvd {
            config "false";
            type uint32;
        }
        leaf v3querSent {
            config "false";
            type uint32;
        }
        leaf v3querRcvd {
            config "false";
            type uint32;
        }
        leaf v2rprtSent {
            config "false";
            type uint32;
        }
        leaf v2rprtRcvd {
            config "false";
            type uint32;
        }
        leaf v3rprtSent {
            config "false";
            type uint32;
        }
        leaf v3rprtRcvd {
            config "false";
            type uint32;
        }
        leaf v2leaveSent {
            config "false";
            type uint32;
        }
        leaf v2leaveRcvd {
            config "false";
            type uint32;
        }
    }

    grouping igmp_JoinType-group {

        // Join Type of the groups
        // Type is an MO-Defined-Type
        leaf type {
            config "false";
            description "Join Type of Groups";

            // Type is an MO-Defined-Type
            type ipmc_JoinType;
        }

        // This objects hold IP Multicast Group version information
        container ver-items {
            list Version-list {
                config "false";
                key "version";

                // Added containment: Prefix=ver
                // Acquired From Package igmp
                uses igmp_Version-group;
            }
        }
    }

    grouping igmp_Version-group {

        // IGMP version
        // Type is an MO-Defined-Type
        leaf version {
            config "false";
            description "Group Version";

            // Type is an MO-Defined-Type
            type ipmc_Ver;
        }

        // This object holds igmp group configuration per Interface
        container group-items {
            list Group-list {
                config "false";
                key "grp";

                // Added containment: Prefix=group
                // Acquired From Package igmp
                uses igmp_Group-group;
            }
        }
    }

    grouping igmp_Group-group {
        leaf grp {
            config "false";
            type address_Ip;
        }

        // This object holds static igmp source per group
        container source-items {
            list Source-list {
                config "false";
                key "src";

                // Added containment: Prefix=source
                // Acquired From Package igmp
                uses igmp_Source-group;
            }
        }
    }

    grouping igmp_Source-group {
        leaf src {
            config "false";
            type address_Ip;
        }
    }

    grouping igmp_ResP-group {

        // Reserved entry Limit Status
        // Type is an MO-Defined-Type
        leaf rsvdEntries {
            config "false";
            description "Reserved entries availability status";

            // Type is an MO-Defined-Type
            type igmp_LimitSt;
        }

        // Regular entry Limit Status
        // Type is an MO-Defined-Type
        leaf regEntries {
            config "false";
            description "Regular entries availability status";

            // Type is an MO-Defined-Type
            type igmp_LimitSt;
        }
        leaf availRsvdEntries {
            config "false";
            type uint32;
        }
        leaf availRegEntries {
            config "false";
            type uint32;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Maximum Multicast Entries
        // Inherited From mcast:AResP
        // Type is an MO-Defined-Type
        leaf max {
            description "Maximum Multicast Entries";

            // Type is an MO-Defined-Type
            type mcast_NumEntries;
        }

        // Reserved Multicast Entries
        // Inherited From mcast:AResP
        // Type is an MO-Defined-Type
        leaf rsvd {
            description "Reserved Multicast Entries";

            // Type is an MO-Defined-Type
            type mcast_NumEntries;
        }
        leaf rtMap {
            type string;
        }
    }

    grouping igmp_RepP-group {
        leaf rtMap {
            config "false";
            type string;
        }
        leaf pfxList {
            config "false";
            type string;
        }
    }

    grouping igmp_StRepP-group {
        leaf rtMap {
            config "false";
            type string;
        }
        leaf pfxList {
            config "false";
            type string;
        }

        // Join Type of the groups
        // Inherited From ipmc:AStRepP
        // Type is an MO-Defined-Type
        leaf joinType {
            config "false";
            description "Join Type of Groups";

            // Type is an MO-Defined-Type
            type ipmc_JoinType;
        }
    }

    grouping igmp_QuerierP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Querier version
        // Inherited From mcast:AQuerier
        // Type is an MO-Defined-Type
        leaf ver {
            description "Version";

            // Type is an MO-Defined-Type
            type mcast_Ver;
        }

        // Querier IP address
        // Inherited From mcast:AQuerier
        // Type is an MO-Defined-Type
        leaf addr {
            description "Address";

            // Type is an MO-Defined-Type
            type mcast_QuerierIp;
        }

        // Query interval
        // Inherited From mcast:AQuerier
        // Type is an MO-Defined-Type
        leaf queryIntvl {
            description "Query Interval";

            // Type is an MO-Defined-Type
            type mcast_QueryIntvl;
        }

        // Query response interval
        // Inherited From mcast:AQuerier
        // Type is an MO-Defined-Type
        leaf rspIntvl {
            description "Response Interval";

            // Type is an MO-Defined-Type
            type mcast_QueryRspIntvl;
        }

        // Robustness factor
        // Inherited From mcast:AQuerier
        // Type is an MO-Defined-Type
        leaf robustFac {
            description "Robustness Factor";

            // Type is an MO-Defined-Type
            type mcast_RobustFactor;
        }

        // Startup query interval
        // Inherited From mcast:AQuerier
        // Type is an MO-Defined-Type
        leaf startQueryIntvl {
            description "Startup Query Interval";

            // Type is an MO-Defined-Type
            type mcast_StartQueryIntvl;
        }

        // Startup query count
        // Inherited From mcast:AQuerier
        // Type is an MO-Defined-Type
        leaf startQueryCnt {
            description "Startup Query Count";

            // Type is an MO-Defined-Type
            type mcast_QueryCnt;
        }

        // Querier timeout
        // Inherited From ipmc:QuerierP
        // Type is an MO-Defined-Type
        leaf querierTimeout {
            config "false";
            description "Querier Timeout";

            // Type is an MO-Defined-Type
            type mcast_QuerierTimeout;
        }

        // Last member query count
        // Inherited From ipmc:QuerierP
        // Type is an MO-Defined-Type
        leaf lastMbrCnt {
            config "false";
            description "Last Member Query Count";

            // Type is an MO-Defined-Type
            type mcast_LastMbrQueryCnt;
        }

        // Last member response time
        // Inherited From ipmc:QuerierP
        // Type is an MO-Defined-Type
        leaf lastMbrRespTime {
            config "false";
            description "Last Member Response Time";

            // Type is an MO-Defined-Type
            type mcast_LastMbrRespTime;
        }
    }

    grouping igmp_SSMXlate-group {

        // Group IP Prefix address
        // Inherited From ipmc:ASSMXlate
        // Type is an MO-Defined-Type
        leaf grpPfx {
            config "false";
            description "Address";

            // Type is an MO-Defined-Type
            type mcast_GrpIp;
        }
        leaf srcAddr {
            config "false";
            type address_Ip;
        }
    }

    grouping firmware_CtrlrFwStatusCont-group {

        // Information about firmware running on a controller.
        container ctrlrrunning-items {

            // Added containment as a singleton: Prefix=ctrlrrunning
            // Acquired From Package firmware
            uses firmware_CtrlrRunning-group;
        }

        // Specification for maintenance policy enforcement status on a node.
        // This object exists on every node where the policy is enforced.
        container upgjob-items {

            // Added containment as a singleton: Prefix=upgjob
            // Acquired From Package maint
            uses maint_UpgJob-group;
        }
    }

    grouping firmware_CtrlrRunning-group {
        leaf tpmInUse {
            type boolean;
        }

        // Running firmware version.
        // Inherited From firmware:ARunning
        // Type is an MO-Defined-Type
        leaf version {
            config "false";
            description "Version";

            // Type is an MO-Defined-Type
            type cap_Version;
        }
        leaf internalLabel {
            type string;
        }

        // Running firmware type.
        // Inherited From firmware:ARunning
        // Type is an MO-Defined-Type
        leaf type {
            config "false";
            description "Type";

            // Type is an MO-Defined-Type
            type firmware_Type;
        }

        // Running firmware mode.
        // Inherited From firmware:ARunning
        // Type is an MO-Defined-Type
        leaf mode {
            config "false";
            description "Mode";

            // Type is an MO-Defined-Type
            type firmware_RunningMode;
        }
        leaf ts {
            config "false";
            type uint64;
        }

        // From Interface naming:Described
        // Inherited From firmware:ARunning
        // Type is an MO-Defined-Type
        leaf descr {
            description "Description";

            // Type is an MO-Defined-Type
            type naming_Descr;
        }
    }

    grouping maint_UpgJob-group {
        leaf grpPriKey {
            config "false";
            type string;
        }

        // Upgrade status of a node where a maintenance policy is being
        // enforced.
        // Type is an MO-Defined-Type
        leaf upgradeStatus {
            description "Upgrade Status";

            // Type is an MO-Defined-Type
            type maint_NodeUpgradeStatus;
        }

        // Installation stage.
        // Type is an MO-Defined-Type
        leaf installStage {
            description "Install Stage";

            // Type is an MO-Defined-Type
            type maint_InstallStage;
        }
        leaf creationDate {
            config "false";
            type uint64;
        }
        leaf startDate {
            config "false";
            type uint64;
        }
        leaf endDate {
            config "false";
            type uint64;
        }
        leaf internalLabel {
            type string;
        }
        leaf installId {
            type string;
        }

        // Internal URL of firmware used for upgrade.
        // Type is an MO-Defined-Type
        leaf iUrl {
            description "Internal URL";

            // Type is an MO-Defined-Type
            type reference_URI;
        }
        leaf numAttempts {
            type uint32;
        }

        // Name of the associated policy.
        // Type is an MO-Defined-Type
        leaf polName {
            description "Maintenance Policy Name";

            // Type is an MO-Defined-Type
            type naming_Name;
        }

        // Name of the associated firmware policy.
        // Type is an MO-Defined-Type
        leaf fwPolName {
            description "Firmware Policy Name";

            // Type is an MO-Defined-Type
            type naming_Name;
        }

        // Name of the associated scheduler policy.
        // Type is an MO-Defined-Type
        leaf scheduler {
            description "Scheduler Policy Name";

            // Type is an MO-Defined-Type
            type naming_Name;
        }

        // Name of the associated maintenance group.
        // Type is an MO-Defined-Type
        leaf maintGrp {
            description "Maintenance Group Name";

            // Type is an MO-Defined-Type
            type naming_Name;
        }

        // Name of the associated firmware group.
        // Type is an MO-Defined-Type
        leaf fwGrp {
            description "Firmware Group Name";

            // Type is an MO-Defined-Type
            type naming_Name;
        }

        // Desired version.
        // Type is an MO-Defined-Type
        leaf desiredVersion {
            description "Desired Version";

            // Type is an MO-Defined-Type
            type cap_Version;
        }
        leaf upgradeStatusStr {
            type string;
        }

        // Installation progress in percent.
        // Type is an MO-Defined-Type
        leaf instlProgPct {
            description "Install Stage";

            // Type is an MO-Defined-Type
            type maint_InstallProgPercent;
        }

        // A scheduler keeps a list consisting only of nodes with upgrade
        // in progress. This object is used by scheduler to keep track of nodes in installation.
        // This object exists only on Controller.
        container node-items {
            list NodeInMaint-list {
                key "nodeId";

                // Added containment: Prefix=node
                // Acquired From Package maint
                uses maint_NodeInMaint-group;
            }
        }

        container upgjobfault-items {

            // Added containment as a singleton: Prefix=upgjobfault
            // Acquired From Package maint
            uses maint_UpgJobFault-group;
        }
    }

    grouping maint_UpgJobFault-group {

        // Upgrade status of a node where a maintenance policy is being
        // enforced.
        // Type is an MO-Defined-Type
        leaf upgradeStatus {
            description "Upgrade Status";

            // Type is an MO-Defined-Type
            type maint_NodeUpgradeStatus;
        }
        leaf faultDelegateKey {
            config "false";
            type string;
        }
    }

    grouping firmware_FwStatusCont-group {

        // Information about switch firmware running on a node
        container running-items {

            // Added containment as a singleton: Prefix=running
            // Acquired From Package firmware
            uses firmware_Running-group;
        }

        // Specification for maintenance policy enforcement status on a node.
        // This object exists on every node where the policy is enforced.
        container upgjob-items {

            // Added containment as a singleton: Prefix=upgjob
            // Acquired From Package maint
            uses maint_UpgJob-group;
        }
    }

    grouping firmware_Running-group {

        // PE version
        // Type is an MO-Defined-Type
        leaf peVer {
            config "false";
            description "Policy Element Version";

            // Type is an MO-Defined-Type
            type cap_Version;
        }

        // Bios version
        // Type is an MO-Defined-Type
        leaf biosVer {
            config "false";
            description "BIOS Version";

            // Type is an MO-Defined-Type
            type cap_Version;
        }
        leaf biosTs {
            config "false";
            type uint64;
        }

        // Kickstart image file name
        // Type is an MO-Defined-Type
        leaf ksFile {
            config "false";
            description "Kickstart File Name";

            // Type is an MO-Defined-Type
            type firmware_Name;
        }

        // System image file name
        // Type is an MO-Defined-Type
        leaf sysFile {
            config "false";
            description "System File Name";

            // Type is an MO-Defined-Type
            type firmware_Name;
        }

        // Running firmware version.
        // Inherited From firmware:ARunning
        // Type is an MO-Defined-Type
        leaf version {
            config "false";
            description "Version";

            // Type is an MO-Defined-Type
            type cap_Version;
        }
        leaf internalLabel {
            type string;
        }

        // Running firmware type.
        // Inherited From firmware:ARunning
        // Type is an MO-Defined-Type
        leaf type {
            config "false";
            description "Type";

            // Type is an MO-Defined-Type
            type firmware_Type;
        }

        // Running firmware mode.
        // Inherited From firmware:ARunning
        // Type is an MO-Defined-Type
        leaf mode {
            config "false";
            description "Mode";

            // Type is an MO-Defined-Type
            type firmware_RunningMode;
        }
        leaf ts {
            config "false";
            type uint64;
        }

        // From Interface naming:Described
        // Inherited From firmware:ARunning
        // Type is an MO-Defined-Type
        leaf descr {
            description "Description";

            // Type is an MO-Defined-Type
            type naming_Descr;
        }
    }

    grouping firmware_CatFwStatusCont-group {

        // Specification for catalog policy enforcement status.
        // This object exists on every node where the policy is enforced.
        container catupgjob-items {

            // Added containment as a singleton: Prefix=catupgjob
            // Acquired From Package maint
            uses maint_CatUpgJob-group;
        }
    }

    grouping maint_CatUpgJob-group {

        // Upgrade status of a node where a maintenance policy is being
        // enforced.
        // Type is an MO-Defined-Type
        leaf upgradeStatus {
            description "Upgrade Status";

            // Type is an MO-Defined-Type
            type maint_CatUpgradeStatus;
        }
        leaf creationDate {
            config "false";
            type uint64;
        }
        leaf startDate {
            config "false";
            type uint64;
        }
        leaf endDate {
            config "false";
            type uint64;
        }

        // Internal URL of firmware used for upgrade.
        // Type is an MO-Defined-Type
        leaf iUrl {
            description "Internal URL";

            // Type is an MO-Defined-Type
            type reference_URI;
        }

        // Name of the associated scheduler policy.
        // Type is an MO-Defined-Type
        leaf scheduler {
            description "Scheduler Policy Name";

            // Type is an MO-Defined-Type
            type naming_Name;
        }

        // Desired version.
        // Type is an MO-Defined-Type
        leaf desiredVersion {
            description "Desired Version";

            // Type is an MO-Defined-Type
            type cap_Version;
        }
    }

    grouping isis_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per isis instance information.
        container inst-items {
            list Inst-list {
                key "name";

                // Added containment: Prefix=inst
                // Acquired From Package isis
                uses isis_Inst-group;
            }
        }
    }

    grouping isis_Inst-group {

        // Operational state
        // Type is an MO-Defined-Type
        leaf operSt {
            config "false";
            description "Operational State";

            // Type is an MO-Defined-Type
            type isis_OperSt;
        }
        leaf processTag {
            config "false";
            type string;
        }
        leaf processSap {
            config "false";
            type uint32;
        }
        leaf processQueue {
            config "false";
            type uint32;
        }

        // Memory alert level
        // Type is an MO-Defined-Type
        leaf memAlert {
            config "false";
            description "Memory Alert Level";

            // Type is an MO-Defined-Type
            type nw_MemAlertLevel;
        }
        leaf protoErr {
            config "false";
            type boolean;
        }
        leaf pssErr {
            config "false";
            type boolean;
        }
        leaf mtsErr {
            config "false";
            type boolean;
        }
        leaf dupSysIdErr {
            config "false";
            type boolean;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Modified by Override: isis:Inst->operErr
        // Type is an MO-Defined-Type
        leaf operErr {
            config "false";
            description "Operational Errors Qualifier";

            // Type is a Local-MO-Defined-Type
            type nw_OperErrQual_Inst_operErr;
        }

        // This objects hold per isis domain (vrf) information
        container dom-items {
            list Dom-list {
                key "name";

                // Added containment: Prefix=dom
                // Acquired From Package isis
                uses isis_Dom-group;
            }
        }
    }

    grouping isis_Dom-group {

        // Mode
        // Type is an MO-Defined-Type
        leaf mode {
            config "false";
            description "Mode";

            // Type is an MO-Defined-Type
            type isis_Mode;
        }

        // Area id
        // Type is an MO-Defined-Type
        leaf areaId {
            config "false";
            description "Area ID";

            // Type is an MO-Defined-Type
            type isis_AreaId;
        }

        // System id
        // Type is an MO-Defined-Type
        leaf sysId {
            config "false";
            description "System ID";

            // Type is an MO-Defined-Type
            type isis_SysId;
        }

        // Network selector
        // Type is an MO-Defined-Type
        leaf nSel {
            config "false";
            description "Network Selector";

            // Type is an MO-Defined-Type
            type isis_NSEL;
        }

        // LSP MTU
        // Type is an MO-Defined-Type
        leaf mtu {
            config "false";
            description "Maximum Transmission Unit";

            // Type is an MO-Defined-Type
            type isis_Mtu;
        }

        // MAX ECMP
        // Type is an MO-Defined-Type
        leaf maxEcmp {
            config "false";
            description "Max ECMP";

            // Type is an MO-Defined-Type
            type isis_Ecmp;
        }

        // Bandwidth Reference
        // Type is an MO-Defined-Type
        leaf bwRef {
            config "false";
            description "Bandwidth Reference";

            // Type is an MO-Defined-Type
            type isis_BwRef;
        }

        // Narrow/Wide Metric Style
        // Type is an MO-Defined-Type
        leaf metricStyle {
            config "false";
            description "Metric Style";

            // Type is an MO-Defined-Type
            type isis_MetricStyle;
        }

        // Operational state
        // Type is an MO-Defined-Type
        leaf operSt {
            config "false";
            description "Operational State";

            // Type is an MO-Defined-Type
            type isis_OperSt;
        }
        leaf contextId {
            config "false";
            type uint32;
        }
        leaf fastLsps {
            config "false";
            type uint32;
        }
        leaf fastCsnps {
            config "false";
            type uint32;
        }
        leaf spfCalculated {
            config "false";
            type uint32;
        }
        leaf lspSourced {
            config "false";
            type uint32;
        }
        leaf lspRefreshed {
            config "false";
            type uint32;
        }
        leaf lspPurged {
            config "false";
            type uint32;
        }
        leaf seqWrapError {
            config "false";
            type boolean;
        }
        leaf uribError {
            config "false";
            type boolean;
        }
        leaf mtsError {
            config "false";
            type boolean;
        }

        // Inherited From nw:Conn
        // Modified by Override: nw:CpDom->name
        // Type is an MO-Defined-Type
        leaf name {
            description "Name";

            // Type is an MO-Defined-Type
            type naming_Name {
                length "1..64";
            }
        }

        // ISIS databases
        container db-items {
            list Db-list {
                config "false";
                key "type";

                // Added containment: Prefix=db
                // Acquired From Package isis
                uses isis_Db-group;
            }
        }

        // This object holds overload information
        container overload-items {

            // Added containment as a singleton: Prefix=overload
            // Acquired From Package isis
            uses isis_Overload-group;
        }

        // This object holds per level isis vrf information
        container lvl-items {
            list DomLvl-list {
                config "false";
                key "type";

                // Added containment: Prefix=lvl
                // Acquired From Package isis
                uses isis_DomLvl-group;
            }
        }

        // This object holds per address family isis vrf information
        container af-items {
            list DomAf-list {
                config "false";
                key "type";

                // Added containment: Prefix=af
                // Acquired From Package isis
                uses isis_DomAf-group;
            }
        }

        // Fabric multicast (ftag) tree element
        container fmtree-items {
            list FmcastTree-list {
                config "false";
                key "id";

                // Added containment: Prefix=fmtree
                // Acquired From Package isis
                uses isis_FmcastTree-group;
            }
        }

        // This objects hold per graceful restart information
        container gr-items {

            // Added containment as a singleton: Prefix=gr
            // Acquired From Package isis
            uses isis_Gr-group;
        }

        // This object holds isis information that is operated at a
        // interface level
        container if-items {
            list If-list {
                key "id";

                // Added containment: Prefix=if
                // Acquired From Package isis
                uses isis_If-group;
            }
        }

        // This objects holds default route leak policy
        container defrtleak-items {

            // Added containment as a singleton: Prefix=defrtleak
            // Acquired From Package isis
            uses isis_DefRtLeakP-group;
        }

        // Intra protocol leak policy. This defines distribution of
        // routes from one level to another level
        container intraleak-items {

            // Added containment as a singleton: Prefix=intraleak
            // Acquired From Package isis
            uses isis_IntraLeakP-group;
        }

        // Inter protocol route leak policy. This defines distribution
        // of routes from other protocols to isis
        container interleak-items {
            list InterLeakP-list {
                key "proto inst asn";

                // Added containment: Prefix=interleak
                // Acquired From Package isis
                uses isis_InterLeakP-group;
            }
        }

        // Leak controls related to the number of routes leaked
        container leakctrl-items {

            // Added containment as a singleton: Prefix=leakctrl
            // Acquired From Package isis
            uses isis_LeakCtrlP-group;
        }
    }

    grouping isis_Db-group {

        // Type of the repository
        // Type is an MO-Defined-Type
        leaf type {
            config "false";
            description "Type";

            // Type is an MO-Defined-Type
            type isis_DbT;
        }

        // Inherited From nw:Conn
        // Modified by Override: nw:Db->name
        // Type is an MO-Defined-Type
        leaf name {
            description "Name";

            // Type is an MO-Defined-Type
            type naming_Name {
                length "1..64";
            }
        }

        // Database of fabric multicast group elements
        container grp-items {
            list GrpRec-list {
                config "false";
                key "addr";

                // Added containment: Prefix=grp
                // Acquired From Package isis
                uses isis_GrpRec-group;
            }
        }

        // Node records
        container node-items {
            list NodeRec-list {
                config "false";
                key "sysId";

                // Added containment: Prefix=node
                // Acquired From Package isis
                uses isis_NodeRec-group;
            }
        }

        // LSP records
        container lsp-items {
            list LspRec-list {
                config "false";
                key "sysId lanId frag";

                // Added containment: Prefix=lsp
                // Acquired From Package isis
                uses isis_LspRec-group;
            }
        }

        // This object holds the isis nexthop information
        container nh-items {
            list Nexthop-list {
                config "false";
                key "nhIf addr";

                // Added containment: Prefix=nh
                // Acquired From Package isis
                uses isis_Nexthop-group;
            }
        }

        // This object holds the isis route information
        container rt-items {
            list Route-list {
                config "false";
                key "pfx";

                // Added containment: Prefix=rt
                // Acquired From Package isis
                uses isis_Route-group;
            }
        }

        // Tunnel endpoints discovered through isis
        container dtep-items {
            list DTEp-list {
                config "false";
                key "id";

                // Added containment: Prefix=dtep
                // Acquired From Package isis
                uses isis_DTEp-group;
            }
        }
    }

    grouping isis_GrpRec-group {

        // Group address
        // Type is an MO-Defined-Type
        leaf addr {
            config "false";
            description "Address";

            // Type is an MO-Defined-Type
            type mcast_GrpIp;
        }

        // Origin of this multicast group element
        // Type is an MO-Defined-Type
        leaf origin {
            config "false";
            description "Origin";

            // Type is an MO-Defined-Type
            type fmcast_Origin;
        }

        // Inherited From nw:Conn
        // Modified by Override: nw:DbRec->name
        // Type is an MO-Defined-Type
        leaf name {
            description "Name";

            // Type is an MO-Defined-Type
            type naming_Name {
                length "1..64";
            }
        }

        // Per FTAG OIF List Record
        container ftagoif-items {
            list FtagOifRec-list {
                config "false";
                key "id";

                // Added containment: Prefix=ftagoif
                // Acquired From Package isis
                uses isis_FtagOifRec-group;
            }
        }

        // BD records active for this multicast group element
        container bd-items {
            list BdIdRec-list {
                config "false";
                key "encap";

                // Added containment: Prefix=bd
                // Acquired From Package isis
                uses isis_BdIdRec-group;
            }
        }

        // Fabric nodes active for this multicast group element
        container node-items {
            list NodeIdRec-list {
                config "false";
                key "addr";

                // Added containment: Prefix=node
                // Acquired From Package isis
                uses isis_NodeIdRec-group;
            }
        }

        // Outgoing interface List on Leaf
        container oifleaf-items {
            list OifListLeaf-list {
                config "false";
                key "idx";

                // Added containment: Prefix=oifleaf
                // Acquired From Package isis
                uses isis_OifListLeaf-group;
            }
        }

        // Outgoing interface List on Spine
        container oifspine-items {
            list OifListSpine-list {
                config "false";
                key "idx";

                // Added containment: Prefix=oifspine
                // Acquired From Package isis
                uses isis_OifListSpine-group;
            }
        }
    }

    grouping isis_FtagOifRec-group {

        // Ftag ID
        // Type is an MO-Defined-Type
        leaf id {
            config "false";
            description "Ftag ID";

            // Type is an MO-Defined-Type
            type fmcast_Id;
        }

        // Inherited From nw:Conn
        // Modified by Override: nw:DbRec->name
        // Type is an MO-Defined-Type
        leaf name {
            description "Name";

            // Type is an MO-Defined-Type
            type naming_Name {
                length "1..64";
            }
        }

        // Outgoing interface List on Leaf
        container oifleaf-items {
            list OifListLeaf-list {
                config "false";
                key "idx";

                // Added containment: Prefix=oifleaf
                // Acquired From Package isis
                uses isis_OifListLeaf-group;
            }
        }

        // Outgoing interface List on Spine
        container oifspine-items {
            list OifListSpine-list {
                config "false";
                key "idx";

                // Added containment: Prefix=oifspine
                // Acquired From Package isis
                uses isis_OifListSpine-group;
            }
        }
    }

    grouping isis_OifListLeaf-group {

        // Index
        // Type is an MO-Defined-Type
        leaf idx {
            config "false";
            description "Index";

            // Type is an MO-Defined-Type
            type fmcast_Id;
        }

        // Type is an MO-Defined-Type
        leaf oifList {
            config "false";
            description "Interface List";

            // Type is an MO-Defined-Type
            type fmcast_OIFList16;
        }

        // Inherited From nw:Conn
        // Modified by Override: nw:Tree->name
        // Type is an MO-Defined-Type
        leaf name {
            description "Name";

            // Type is an MO-Defined-Type
            type naming_Name {
                length "1..64";
            }
        }
    }

    grouping isis_OifListSpine-group {

        // Index
        // Type is an MO-Defined-Type
        leaf idx {
            config "false";
            description "Index";

            // Type is an MO-Defined-Type
            type fmcast_Id;
        }

        // Type is an MO-Defined-Type
        leaf oifList {
            config "false";
            description "Interface List";

            // Type is an MO-Defined-Type
            type fmcast_OIFList128;
        }

        // Inherited From nw:Conn
        // Modified by Override: nw:Tree->name
        // Type is an MO-Defined-Type
        leaf name {
            description "Name";

            // Type is an MO-Defined-Type
            type naming_Name {
                length "1..64";
            }
        }
    }

    grouping isis_BdIdRec-group {
        leaf encap {
            config "false";
            type string;
        }

        // Inherited From nw:Conn
        // Modified by Override: nw:DbRec->name
        // Type is an MO-Defined-Type
        leaf name {
            description "Name";

            // Type is an MO-Defined-Type
            type naming_Name {
                length "1..64";
            }
        }
    }

    grouping isis_NodeIdRec-group {
        leaf addr {
            config "false";
            type address_Ip;
        }

        // Inherited From nw:Conn
        // Modified by Override: nw:DbRec->name
        // Type is an MO-Defined-Type
        leaf name {
            description "Name";

            // Type is an MO-Defined-Type
            type naming_Name {
                length "1..64";
            }
        }
    }

    grouping isis_NodeRec-group {
        leaf addr {
            config "false";
            type address_Ip;
        }
        leaf sysId {
            config "false";
            type address_Mac;
        }

        // Outgoing port to this fabric node on each ftag tree
        // Type is an MO-Defined-Type
        leaf ftagRt {
            config "false";
            description "FTAG Route";

            // Type is an MO-Defined-Type
            type fmcast_OIFList16;
        }

        // Inherited From nw:Conn
        // Modified by Override: nw:DbRec->name
        // Type is an MO-Defined-Type
        leaf name {
            description "Name";

            // Type is an MO-Defined-Type
            type naming_Name {
                length "1..64";
            }
        }

        // Multicast groups identifier record
        container grp-items {
            list GrpIdRec-list {
                config "false";
                key "addr";

                // Added containment: Prefix=grp
                // Acquired From Package isis
                uses isis_GrpIdRec-group;
            }
        }
    }

    grouping isis_GrpIdRec-group {

        // Group address
        // Type is an MO-Defined-Type
        leaf addr {
            config "false";
            description "Address";

            // Type is an MO-Defined-Type
            type mcast_GrpIp;
        }

        // Inherited From nw:Conn
        // Modified by Override: nw:DbRec->name
        // Type is an MO-Defined-Type
        leaf name {
            description "Name";

            // Type is an MO-Defined-Type
            type naming_Name {
                length "1..64";
            }
        }
    }

    grouping isis_LspRec-group {
        leaf sysId {
            config "false";
            type address_Mac;
        }

        // LAN id
        // Type is an MO-Defined-Type
        leaf lanId {
            config "false";
            description "LAN ID";

            // Type is an MO-Defined-Type
            type isis_LanId;
        }

        // Fragment number
        // Type is an MO-Defined-Type
        leaf frag {
            config "false";
            description "Fragment Number";

            // Type is an MO-Defined-Type
            type isis_FragNum;
        }

        // Sequence Number
        // Type is an MO-Defined-Type
        leaf seqNum {
            config "false";
            description "Sequence Number";

            // Type is an MO-Defined-Type
            type isis_SeqNum;
        }

        // Remaining lifetime
        // Type is an MO-Defined-Type
        leaf lifeTime {
            config "false";
            description "Remaining Lifetime";

            // Type is an MO-Defined-Type
            type isis_LifeTime;
        }

        // LSP Timer Type
        // Type is an MO-Defined-Type
        leaf timerType {
            config "false";
            description "Timer Type";

            // Type is an MO-Defined-Type
            type isis_TimerType;
        }
        leaf timerExpiryTS {
            config "false";
            type uint64;
        }

        // Checksum
        // Type is an MO-Defined-Type
        leaf ckSum {
            config "false";
            description "Checksum";

            // Type is an MO-Defined-Type
            type isis_Cksum;
        }

        // Attached flag
        // Type is an MO-Defined-Type
        leaf attached {
            config "false";
            description "Attached";

            // Type is an MO-Defined-Type
            type isis_Attached;
        }

        // Partition flag
        // Type is an MO-Defined-Type
        leaf partition {
            config "false";
            description "Partition";

            // Type is an MO-Defined-Type
            type isis_Partition;
        }

        // Overload flag
        // Type is an MO-Defined-Type
        leaf overload {
            config "false";
            description "Overload";

            // Type is an MO-Defined-Type
            type isis_Overload;
        }

        // Level type
        // Type is an MO-Defined-Type
        leaf type {
            config "false";
            description "Level Type";

            // Type is an MO-Defined-Type
            type isis_LvlT;
        }
        leaf areaAddr {
            config "false";
            type string;
        }
        leaf nlpId {
            config "false";
            type address_Ip;
        }
        leaf routerId {
            config "false";
            type string;
        }
        leaf hostName {
            config "false";
            type string;
        }
        leaf srmBitMaps {
            config "false";
            type string;
        }
        leaf rrmBitMaps {
            config "false";
            type string;
        }
        leaf ssnBitMaps {
            config "false";
            type string;
        }

        // Inherited From nw:Conn
        // Modified by Override: nw:DbRec->name
        // Type is an MO-Defined-Type
        leaf name {
            description "Name";

            // Type is an MO-Defined-Type
            type naming_Name {
                length "1..64";
            }
        }

        // Extended IS Record
        container extisrec-items {
            list ExtIsRec-list {
                key "name";

                // Added containment: Prefix=extisrec
                // Acquired From Package isis
                uses isis_ExtIsRec-group;
            }
        }

        // Generic TLV Record
        container tlvRec-items {
            list TlvRec-list {
                config "false";
                key "type";

                // Added containment: Prefix=tlvRec
                // Acquired From Package isis
                uses isis_TlvRec-group;
            }
        }

        // IP Prefix record
        container iprec-items {
            list IpRec-list {
                config "false";
                key "pfx";

                // Added containment: Prefix=iprec
                // Acquired From Package isis
                uses isis_IpRec-group;
            }
        }
    }

    grouping isis_ExtIsRec-group {

        // IS Metric
        // Type is an MO-Defined-Type
        leaf metric {
            config "false";
            description "Metric";

            // Type is an MO-Defined-Type
            type isis_Metric;
        }

        // Inherited From nw:Conn
        // Modified by Override: nw:DbRec->name
        // Type is an MO-Defined-Type
        leaf name {
            description "Name";

            // Type is an MO-Defined-Type
            type naming_Name {
                length "1..64";
            }
        }
    }

    grouping isis_TlvRec-group {

        // TLV Type
        // Type is an MO-Defined-Type
        leaf type {
            config "false";
            description "TLV";

            // Type is an MO-Defined-Type
            type isis_TlvType;
        }

        // TLV Len
        // Type is an MO-Defined-Type
        leaf len {
            config "false";
            description "Length";

            // Type is an MO-Defined-Type
            type isis_TlvLen;
        }

        // TLV Value
        // Type is an MO-Defined-Type
        leaf value {
            config "false";
            description "Value";

            // Type is an MO-Defined-Type
            type isis_TlvVal;
        }

        // Inherited From nw:Conn
        // Modified by Override: nw:DbRec->name
        // Type is an MO-Defined-Type
        leaf name {
            description "Name";

            // Type is an MO-Defined-Type
            type naming_Name {
                length "1..64";
            }
        }
    }

    grouping isis_IpRec-group {
        leaf pfx {
            config "false";
            type address_Ip;
        }

        // Metric
        // Type is an MO-Defined-Type
        leaf metric {
            config "false";
            description "Metric";

            // Type is an MO-Defined-Type
            type isis_Metric;
        }

        // Up/down bit
        // Type is an MO-Defined-Type
        leaf udBit {
            config "false";
            description "Up/down Bit";

            // Type is an MO-Defined-Type
            type isis_UdBit;
        }

        // Inherited From nw:Conn
        // Modified by Override: nw:DbRec->name
        // Type is an MO-Defined-Type
        leaf name {
            description "Name";

            // Type is an MO-Defined-Type
            type naming_Name {
                length "1..64";
            }
        }
    }

    grouping isis_Nexthop-group {

        // Nexhop interface [Deprecated]
        // Type is an MO-Defined-Type
        leaf if {
            config "false";
            description "Interface (IOD Internal)";

            // Type is an MO-Defined-Type
            type nw_Iod;
        }

        // Nexhop interface
        // Type is an MO-Defined-Type
        leaf nhIf {
            config "false";
            description "Interface";

            // Type is an MO-Defined-Type
            type nw_IfId;
        }
        leaf addr {
            config "false";
            type address_Ip;
        }

        // Inherited From nw:Conn
        // Modified by Override: nw:DbRec->name
        // Type is an MO-Defined-Type
        leaf name {
            description "Name";

            // Type is an MO-Defined-Type
            type naming_Name {
                length "1..64";
            }
        }
    }

    grouping isis_Route-group {
        leaf pfx {
            config "false";
            type address_Ip;
        }
        leaf metric {
            config "false";
            type uint32;
        }
        leaf pref {
            config "false";
            type uint8;
        }

        // Inherited From nw:Conn
        // Modified by Override: nw:DbRec->name
        // Type is an MO-Defined-Type
        leaf name {
            description "Name";

            // Type is an MO-Defined-Type
            type naming_Name {
                length "1..64";
            }
        }

        // Rel-def from NhAtt
        container rsnhAtt-items {

            // Abstract containment of rsnhAtt derived from isis:Route
            list RsNhAtt-list {
                key "tDn";

                // Added containment: Prefix=rsnhAtt
                // Acquired From Package isis
                uses isis_RsNhAtt_source-group;
            }
        }
    }

    grouping isis_DTEp-group {

        // Inherited From nw:Conn
        // Modified by Override: nw:Ep->name
        // Type is an MO-Defined-Type
        leaf name {
            description "Name";

            // Type is an MO-Defined-Type
            type naming_Name {
                length "1..64";
            }
        }

        // Endpoint identifier
        // Inherited From tunnel:Ep
        // Type is an MO-Defined-Type
        leaf id {
            config "false";
            description "ID";

            // Type is an MO-Defined-Type
            type tunnel_EpId;
        }

        // Endpoint encapsulation type
        // Inherited From tunnel:Ep
        // Type is an MO-Defined-Type
        leaf encapt {
            config "false";
            description "Encapsulation Type";

            // Type is an MO-Defined-Type
            type tunnel_EncapT;
        }

        // Endpoint type
        // Inherited From tunnel:Ep
        // Type is an MO-Defined-Type
        leaf type {
            config "false";
            description "Type";

            // Type is an MO-Defined-Type
            type tunnel_EpT;
        }

        // Role of the remote endpoint
        // Inherited From tunnel:Ep
        // Type is an MO-Defined-Type
        leaf role {
            config "false";
            description "Role";

            // Type is an MO-Defined-Type
            type top_NodeRole;
        }
    }

    grouping isis_Overload-group {

        // Adminstrative state
        // Type is an MO-Defined-Type
        leaf adminSt {
            config "false";
            description "Admin State";

            // Type is an MO-Defined-Type
            type isis_OverloadAdminSt;
        }
        leaf startupTime {
            config "false";
            type uint64;
            default "600000";
        }
        leaf bgpAsNum {
            config "false";
            type uint16;
        }
    }

    grouping isis_DomLvl-group {

        // Administrative distance preference
        // Type is an MO-Defined-Type
        leaf dist {
            config "false";
            description "Distance";

            // Type is an MO-Defined-Type
            type isis_Dist;
        }

        // Per level controls
        // Type is an MO-Defined-Type
        leaf ctrl {
            config "false";
            description "Controls";

            // Type is an MO-Defined-Type
            type isis_DomLvlControl;
        }

        // Number of routes summarized
        // Type is an MO-Defined-Type
        leaf numRtSummarized {
            config "false";
            description "Summarized Routes";

            // Type is an MO-Defined-Type
            type nw_Counter32;
        }

        // Total FAST LSP
        // Type is an MO-Defined-Type
        leaf fastLsp {
            config "false";
            description "Total Fast LSP";

            // Type is an MO-Defined-Type
            type nw_Counter32;
        }

        // Total FAST Csnp
        // Type is an MO-Defined-Type
        leaf fastCsnp {
            config "false";
            description "Total Fast Csnp";

            // Type is an MO-Defined-Type
            type nw_Counter32;
        }

        // Total SPF scheduled
        // Type is an MO-Defined-Type
        leaf spfScheduled {
            config "false";
            description "Total SPF Scheduled";

            // Type is an MO-Defined-Type
            type nw_Counter32;
        }

        // Total SPF resynced
        // Type is an MO-Defined-Type
        leaf spfResynced {
            config "false";
            description "Total SPF Resynced";

            // Type is an MO-Defined-Type
            type nw_Counter32;
        }

        // Inherited From nw:Conn
        // Modified by Override: nw:CpDom->name
        // Type is an MO-Defined-Type
        leaf name {
            description "Name";

            // Type is an MO-Defined-Type
            type naming_Name {
                length "1..64";
            }
        }

        // Type
        // Inherited From isis:Lvl
        // Type is an MO-Defined-Type
        leaf type {
            config "false";
            description "Type";

            // Type is an MO-Defined-Type
            type isis_LvlT;
        }

        // ISIS databases
        container db-items {
            list Db-list {
                config "false";
                key "type";

                // Added containment: Prefix=db
                // Acquired From Package isis
                uses isis_Db-group;
            }
        }

        // This object holds lsp generation interval controls
        container lspgen-items {

            // Added containment as a singleton: Prefix=lspgen
            // Acquired From Package isis
            uses isis_LspGen-group;
        }

        // This object holds spf computation frequency controls
        container spfcomp-items {

            // Added containment as a singleton: Prefix=spfcomp
            // Acquired From Package isis
            uses isis_SpfComp-group;
        }

        // This objects hold summarization address. Any address
        // that maps to this prefix will be summarized through
        // this address
        container rtsum-items {
            list RtSum-list {
                key "addr";

                // Added containment: Prefix=rtsum
                // Acquired From Package isis
                uses isis_RtSum-group;
            }
        }
    }

    grouping isis_LspGen-group {

        // Initial wait inerval
        // Type is an MO-Defined-Type
        leaf initIntvl {
            config "false";
            description "Initial Wait Interval";

            // Type is an MO-Defined-Type
            type isis_LspGenInitIntvl;
        }

        // Second wait interval
        // Type is an MO-Defined-Type
        leaf secIntvl {
            config "false";
            description "Second Wait Interval";

            // Type is an MO-Defined-Type
            type isis_LspGenSecIntvl;
        }

        // Maximum wait interval
        // Type is an MO-Defined-Type
        leaf maxIntvl {
            config "false";
            description "Maximum Wait Interval";

            // Type is an MO-Defined-Type
            type isis_LspGenMaxIntvl;
        }
    }

    grouping isis_SpfComp-group {

        // Initial wait inerval
        // Type is an MO-Defined-Type
        leaf initIntvl {
            config "false";
            description "Initial Wait Interval";

            // Type is an MO-Defined-Type
            type isis_SpfCompInitIntvl;
        }

        // Second wait interval
        // Type is an MO-Defined-Type
        leaf secIntvl {
            config "false";
            description "Second Wait Interval";

            // Type is an MO-Defined-Type
            type isis_SpfCompSecIntvl;
        }

        // Maximum wait interval
        // Type is an MO-Defined-Type
        leaf maxIntvl {
            config "false";
            description "Maximum Wait Interval";

            // Type is an MO-Defined-Type
            type isis_SpfCompMaxIntvl;
        }
    }

    grouping isis_RtSum-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf addr {
            type address_Ip;
        }
    }

    grouping isis_DomAf-group {

        // Per address family controls
        // Type is an MO-Defined-Type
        leaf ctrl {
            config "false";
            description "Controls";

            // Type is an MO-Defined-Type
            type isis_DomAfControl;
        }

        // Inherited From nw:Conn
        // Modified by Override: nw:CpDom->name
        // Type is an MO-Defined-Type
        leaf name {
            description "Name";

            // Type is an MO-Defined-Type
            type naming_Name {
                length "1..64";
            }
        }

        // Type
        // Inherited From isis:Af
        // Type is an MO-Defined-Type
        leaf type {
            config "false";
            description "Type";

            // Type is an MO-Defined-Type
            type isis_AfT;
        }
    }

    grouping isis_FmcastTree-group {

        // Id
        // Type is an MO-Defined-Type
        leaf id {
            config "false";
            description "Tree ID";

            // Type is an MO-Defined-Type
            type fmcast_Id;
        }

        // Origin of this ftag element
        // Type is an MO-Defined-Type
        leaf origin {
            config "false";
            description "Origin";

            // Type is an MO-Defined-Type
            type fmcast_Origin;
        }

        // Multicast root address for this tree
        // Type is an MO-Defined-Type
        leaf root {
            config "false";
            description "Root";

            // Type is an MO-Defined-Type
            type mcast_Root;
        }

        // Operational state
        // Type is an MO-Defined-Type
        leaf operSt {
            config "false";
            description "Operational State";

            // Type is an MO-Defined-Type
            type fmcast_OperSt;
        }

        // Tree diameter
        // Type is an MO-Defined-Type
        leaf diameter {
            config "false";
            description "Diameter";

            // Type is an MO-Defined-Type
            type fmcast_Diameter;
        }

        // Tree diameter Alert, set when diameter is large
        // Type is an MO-Defined-Type
        leaf diaAlert {
            config "false";
            description "Diameter Alert";

            // Type is an MO-Defined-Type
            type fmcast_DiameterAlert;
        }
        leaf rootPort {
            config "false";
            type string;
        }

        // Inherited From nw:Conn
        // Modified by Override: nw:Tree->name
        // Type is an MO-Defined-Type
        leaf name {
            description "Name";

            // Type is an MO-Defined-Type
            type naming_Name {
                length "1..64";
            }
        }

        // Fabric nodes active for this multicast group element
        container node-items {
            list NodeIdRec-list {
                config "false";
                key "addr";

                // Added containment: Prefix=node
                // Acquired From Package isis
                uses isis_NodeIdRec-group;
            }
        }

        // Outgoing interface List on Leaf
        container oifleaf-items {
            list OifListLeaf-list {
                config "false";
                key "idx";

                // Added containment: Prefix=oifleaf
                // Acquired From Package isis
                uses isis_OifListLeaf-group;
            }
        }

        // Outgoing interface List on Spine
        container oifspine-items {
            list OifListSpine-list {
                config "false";
                key "idx";

                // Added containment: Prefix=oifspine
                // Acquired From Package isis
                uses isis_OifListSpine-group;
            }
        }
    }

    grouping isis_Gr-group {

        // Graceful Restart
        // Type is an MO-Defined-Type
        leaf adminSt {
            config "false";
            description "Admin State";

            // Type is an MO-Defined-Type
            type nw_AdminSt;
        }

        // T3 timer for graceful restart
        // Type is an MO-Defined-Type
        leaf grT3Intvl {
            config "false";
            description "T3 Interval";

            // Type is an MO-Defined-Type
            type isis_GrT3Intvl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping isis_If-group {

        // Circuit type
        // Type is an MO-Defined-Type
        leaf cktT {
            config "false";
            description "Circuit Type";

            // Type is an MO-Defined-Type
            type isis_IsT;
        }

        // Metric
        // Type is an MO-Defined-Type
        leaf metric {
            config "false";
            description "Metric";

            // Type is an MO-Defined-Type
            type isis_Metric;
        }

        // Interface controls
        // Type is an MO-Defined-Type
        leaf ctrl {
            config "false";
            description "Controls";

            // Type is an MO-Defined-Type
            type isis_IfControl;
        }

        // LSP refresh Interval
        // Type is an MO-Defined-Type
        leaf lspRefreshIntvl {
            config "false";
            description "LSP Refresh Interval";

            // Type is an MO-Defined-Type
            type isis_LspRefreshIntvl;
        }
        leaf iibIdx {
            config "false";
            type uint16;
        }
        leaf localCktId {
            config "false";
            type uint16;
        }
        leaf extdLocalCktId {
            config "false";
            type uint32;
        }
        leaf p2pCktId {
            config "false";
            type string;
        }
        leaf initError {
            config "false";
            type boolean;
        }
        leaf iibUpCtrl {
            config "false";
            type boolean;
        }
        leaf iibState {
            config "false";
            type string;
        }
        leaf nextIIHTs {
            config "false";
            type uint64;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds isis neighbor information
        container adj-items {
            list AdjEp-list {
                config "false";
                key "type sysId";

                // Added containment: Prefix=adj
                // Acquired From Package isis
                uses isis_AdjEp-group;
            }
        }

        // This object holds mesh group information per interface
        container meshgrp-items {
            list MeshGrp-list {
                config "false";
                key "id";

                // Added containment: Prefix=meshgrp
                // Acquired From Package isis
                uses isis_MeshGrp-group;
            }
        }

        // This object holds per level isis interface information
        container lvl-items {
            list IfLvl-list {
                config "false";
                key "type";

                // Added containment: Prefix=lvl
                // Acquired From Package isis
                uses isis_IfLvl-group;
            }
        }

        // This object holds per IF States information
        container traffic-items {

            // Added containment as a singleton: Prefix=traffic
            // Acquired From Package isis
            uses isis_IfTraffic-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping isis_AdjEp-group {

        // Adjacency type
        // Type is an MO-Defined-Type
        leaf type {
            config "false";
            description "Level Type";

            // Type is an MO-Defined-Type
            type isis_LvlT;
        }
        leaf sysId {
            config "false";
            type address_Mac;
        }

        // Operational state of the adjacency
        // Type is an MO-Defined-Type
        leaf operSt {
            config "false";
            description "Operational State";

            // Type is an MO-Defined-Type
            type isis_AdjOperSt;
        }
        leaf holdExpTs {
            config "false";
            type uint64;
        }

        // Local operational circuit type
        // Type is an MO-Defined-Type
        leaf cktType {
            config "false";
            description "Circuit Type";

            // Type is an MO-Defined-Type
            type isis_CktT;
        }

        // Peer Ckt Id
        // Type is an MO-Defined-Type
        leaf peerCktId {
            config "false";
            description "Peer Circuit Type";

            // Type is an MO-Defined-Type
            type isis_CktId;
        }

        // LAN Id
        // Type is an MO-Defined-Type
        leaf lanId {
            config "false";
            description "LAN Circuit ID";

            // Type is an MO-Defined-Type
            type isis_LanId;
        }

        // Peer Ckt Priority
        // Type is an MO-Defined-Type
        leaf peerCktPrio {
            config "false";
            description "Peer Circuit Priority";

            // Type is an MO-Defined-Type
            type isis_CktPrio;
        }

        // Peer graceful restart flags
        // Type is an MO-Defined-Type
        leaf peerGrFlags {
            config "false";
            description "Peer Graceful Restart Flags";

            // Type is an MO-Defined-Type
            type isis_PeerGrFlags;
        }
        leaf numAdjTrans {
            config "false";
            type uint32;
        }
        leaf lastTrans {
            config "false";
            type uint64;
        }

        // Inherited From nw:Conn
        // Modified by Override: nw:Ep->name
        // Type is an MO-Defined-Type
        leaf name {
            description "Name";

            // Type is an MO-Defined-Type
            type naming_Name {
                length "1..64";
            }
        }
        container addr-items {
            list PeerIpAddr-list {
                config "false";
                key "addr";

                // Added containment: Prefix=addr
                // Acquired From Package isis
                uses isis_PeerIpAddr-group;
            }
        }
    }

    grouping isis_PeerIpAddr-group {
        leaf addr {
            config "false";
            type address_Ip;
        }
    }

    grouping isis_MeshGrp-group {

        // Mesh Group Id
        // Type is an MO-Defined-Type
        leaf id {
            config "false";
            description "ID";

            // Type is an MO-Defined-Type
            type isis_MeshGrpId;
        }

        // Mesh group controls
        // Type is an MO-Defined-Type
        leaf ctrl {
            config "false";
            description "Controls";

            // Type is an MO-Defined-Type
            type isis_MeshGrpControl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping isis_IfLvl-group {

        // Priority
        // Type is an MO-Defined-Type
        leaf priority {
            config "false";
            description "Circuit Priority";

            // Type is an MO-Defined-Type
            type isis_CktPrio;
        }

        // Hello Interval
        // Type is an MO-Defined-Type
        leaf helloIntvl {
            config "false";
            description "Hello Interval";

            // Type is an MO-Defined-Type
            type isis_HelloIntvl;
        }

        // Hello Multiplier (3-1000 def: 3)
        // Type is an MO-Defined-Type
        leaf helloMult {
            config "false";
            description "Hello Multiplier";

            // Type is an MO-Defined-Type
            type isis_HelloMult;
        }

        // CSNP Interval
        // Type is an MO-Defined-Type
        leaf csnpIntvl {
            config "false";
            description "CSNP Interval";

            // Type is an MO-Defined-Type
            type isis_CsnpIntvl;
        }
        leaf protoError {
            config "false";
            type boolean;
        }
        leaf nextCsnpTs {
            config "false";
            type uint64;
        }

        // Inherited From nw:Conn
        // Modified by Override: nw:CpDom->name
        // Type is an MO-Defined-Type
        leaf name {
            description "Name";

            // Type is an MO-Defined-Type
            type naming_Name {
                length "1..64";
            }
        }

        // Type
        // Inherited From isis:Lvl
        // Type is an MO-Defined-Type
        leaf type {
            config "false";
            description "Type";

            // Type is an MO-Defined-Type
            type isis_LvlT;
        }
    }

    grouping isis_IfTraffic-group {

        // P2P IIH Packets Tx
        // Type is an MO-Defined-Type
        leaf p2pIIHPktsTx {
            config "false";
            description "P2P IIH Packets Sent";

            // Type is an MO-Defined-Type
            type nw_Counter32;
        }

        // P2P IIH Packets Rx
        // Type is an MO-Defined-Type
        leaf p2pIIHPktsRx {
            config "false";
            description "P2P IIH Packets Recevied";

            // Type is an MO-Defined-Type
            type nw_Counter32;
        }

        // P2P IIH Packets AuthError
        // Type is an MO-Defined-Type
        leaf p2pIIHPktsAuthErr {
            config "false";
            description "P2P IIH Packets with Authentication Error";

            // Type is an MO-Defined-Type
            type nw_Counter32;
        }

        // P2P IIH Packets Misc Error
        // Type is an MO-Defined-Type
        leaf p2pIIHPktsMiscErr {
            config "false";
            description "P2P IIH Packets with Miscellaneous Error";

            // Type is an MO-Defined-Type
            type nw_Counter32;
        }

        // LAN IIH Packets Tx
        // Type is an MO-Defined-Type
        leaf lanIIHPktsTx {
            config "false";
            description "LAN IIH Packets Sent";

            // Type is an MO-Defined-Type
            type nw_Counter32;
        }

        // LAN IIH Packets Rx
        // Type is an MO-Defined-Type
        leaf lanIIHPktsRx {
            config "false";
            description "LAN IIH Packets Recevied";

            // Type is an MO-Defined-Type
            type nw_Counter32;
        }

        // LAN IIH Packets AuthError
        // Type is an MO-Defined-Type
        leaf lanIIHPktsAuthErr {
            config "false";
            description "LAN IIH Packets with Authentication Error";

            // Type is an MO-Defined-Type
            type nw_Counter32;
        }

        // LAN IIH Packets Misc Error
        // Type is an MO-Defined-Type
        leaf lanIIHPktsMiscErr {
            config "false";
            description "LAN IIH Packets with Miscellaneous Error";

            // Type is an MO-Defined-Type
            type nw_Counter32;
        }

        // CSNP  Packets Tx
        // Type is an MO-Defined-Type
        leaf csnpPktsTx {
            config "false";
            description "CSNP Packets Sent";

            // Type is an MO-Defined-Type
            type nw_Counter32;
        }

        // CSNP  Packets Rx
        // Type is an MO-Defined-Type
        leaf csnpPktsRx {
            config "false";
            description "CSNP Packets Recevied";

            // Type is an MO-Defined-Type
            type nw_Counter32;
        }

        // Fast CSNP  Packets Rx
        // Type is an MO-Defined-Type
        leaf fastCsnpPktsRx {
            config "false";
            description "Fast CSNP Packets Recevied";

            // Type is an MO-Defined-Type
            type nw_Counter32;
        }

        // CSNP  Packets AuthError
        // Type is an MO-Defined-Type
        leaf csnpPktsAuthErr {
            config "false";
            description "CSNP Packets with Authentication Error";

            // Type is an MO-Defined-Type
            type nw_Counter32;
        }

        // CSNP  Packets Misc Error
        // Type is an MO-Defined-Type
        leaf csnpPktsMiscErr {
            config "false";
            description "CSNP Packets with Miscelcsnpeous Error";

            // Type is an MO-Defined-Type
            type nw_Counter32;
        }

        // PSNP  Packets Tx
        // Type is an MO-Defined-Type
        leaf psnpPktsTx {
            config "false";
            description "PSNP Packets Sent";

            // Type is an MO-Defined-Type
            type nw_Counter32;
        }

        // PSNP  Packets Rx
        // Type is an MO-Defined-Type
        leaf psnpPktsRx {
            config "false";
            description "PSNP Packets Recevied";

            // Type is an MO-Defined-Type
            type nw_Counter32;
        }

        // PSNP  Packets AuthError
        // Type is an MO-Defined-Type
        leaf psnpPktsAuthErr {
            config "false";
            description "PSNP Packets with Authentication Error";

            // Type is an MO-Defined-Type
            type nw_Counter32;
        }

        // PSNP  Packets Misc Error
        // Type is an MO-Defined-Type
        leaf psnpPktsMiscErr {
            config "false";
            description "PSNP Packets with Miscelcsnpeous Error";

            // Type is an MO-Defined-Type
            type nw_Counter32;
        }

        // LSP  Packets Tx
        // Type is an MO-Defined-Type
        leaf lspPktsTx {
            config "false";
            description "LSP Packets Sent";

            // Type is an MO-Defined-Type
            type nw_Counter32;
        }

        // LSP  Packets ReTx
        // Type is an MO-Defined-Type
        leaf lspPktsRetx {
            config "false";
            description "LSP Packets Retransmitted";

            // Type is an MO-Defined-Type
            type nw_Counter32;
        }

        // LSP  Packets Rx
        // Type is an MO-Defined-Type
        leaf lspPktsRx {
            config "false";
            description "LSP  Packets Recevied";

            // Type is an MO-Defined-Type
            type nw_Counter32;
        }

        // FAST LSP  Packets Rx
        // Type is an MO-Defined-Type
        leaf fastLspPktsRx {
            config "false";
            description "Fast LSP Packets Recevied";

            // Type is an MO-Defined-Type
            type nw_Counter32;
        }

        // LSP  Packets AuthError
        // Type is an MO-Defined-Type
        leaf lspPktsAuthErr {
            config "false";
            description "LSP Packets with Authentication Error";

            // Type is an MO-Defined-Type
            type nw_Counter32;
        }

        // LSP  Packets Misc Error
        // Type is an MO-Defined-Type
        leaf lspPktsMiscErr {
            config "false";
            description "LSP Packets with Miscelcsnpeous Error";

            // Type is an MO-Defined-Type
            type nw_Counter32;
        }
    }

    grouping isis_DefRtLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:DefRtLeakP->scope
        // Type is an MO-Defined-Type
        leaf scope {
            description "Scope";

            // Type is an MO-Defined-Type
            type rtleak_Scope;
        }
        leaf rtMap {
            type string;
        }
    }

    grouping isis_IntraLeakP-group {

        // Source domain, level from which the routes are leaked
        // Type is an MO-Defined-Type
        leaf source {
            config "false";
            description "Source Domain";

            // Type is an MO-Defined-Type
            type isis_LvlT;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:IntraLeakP->scope
        // Type is an MO-Defined-Type
        leaf scope {
            description "Scope";

            // Type is an MO-Defined-Type
            type rtleak_Scope;
        }
        leaf rtMap {
            type string;
        }
    }

    grouping isis_InterLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:InterLeakP->scope
        // Type is an MO-Defined-Type
        leaf scope {
            description "Scope";

            // Type is an MO-Defined-Type
            type rtleak_Scope;
        }
        leaf rtMap {
            type string;
        }

        // Protocol from where the routes are leaked
        // Inherited From rtleak:InterLeakP
        // Type is an MO-Defined-Type
        leaf proto {
            description "Protocol";

            // Type is an MO-Defined-Type
            type rtleak_Proto;
        }

        // Routing protocol instance, the routing instance of the
        // protocol from where the routes are being leaked
        // Inherited From rtleak:InterLeakP
        // Type is an MO-Defined-Type
        leaf inst {
            description "Instance";

            // Type is an MO-Defined-Type
            type rtleak_Inst;
        }

        // Leak BGP routes from this Autonomous System (AS)    <1-4294967295>|<1-65535>[.<0-65535>]  Autonomous system number
        // Inherited From rtleak:InterLeakP
        // Type is an MO-Defined-Type
        leaf asn {
            description "Autonomous System Number";

            // Type is an MO-Defined-Type
            type rtleak_Asn {
            }
        }
    }

    grouping isis_LeakCtrlP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Controls on what to do when the number of routes cross
        // the maximum route/prefix limit
        // Inherited From rtleak:LeakCtrlP
        // Type is an MO-Defined-Type
        leaf ctrl {
            description "Controls";

            // Type is an MO-Defined-Type
            type rtleak_Ctrl;
        }

        // Maximum limit on routes leaked
        // Inherited From rtleak:LeakCtrlP
        // Type is an MO-Defined-Type
        leaf max {
            description "Maximum Limit";

            // Type is an MO-Defined-Type
            type rtleak_MaxPfx;
        }

        // Threshold at which warning is issued when number of
        // routes crosses the threshold
        // Inherited From rtleak:LeakCtrlP
        // Type is an MO-Defined-Type
        leaf thresh {
            description "Threshold";

            // Type is an MO-Defined-Type
            type rtleak_Thresh;
        }

        // Maximum number of retries to retrieve the leaked routes,
        // this is applicable only when the routes are withdrawn
        // Inherited From rtleak:LeakCtrlP
        // Type is an MO-Defined-Type
        leaf retries {
            description "Retries";

            // Type is an MO-Defined-Type
            type rtleak_Retries;
        }

        // Duration between the retries
        // Inherited From rtleak:LeakCtrlP
        // Type is an MO-Defined-Type
        leaf duration {
            description "Duration";

            // Type is an MO-Defined-Type
            type rtleak_Duration;
        }
    }

    grouping lacp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per lacp instance information. There is only
        // one instance of lacp running in the system today
        container inst-items {

            // Added containment as a singleton: Prefix=inst
            // Acquired From Package lacp
            uses lacp_Inst-group;
        }
    }

    grouping lacp_Inst-group {

        // Administrative system priority
        // Type is an MO-Defined-Type
        leaf adminPrio {
            description "Adminstrative Priority";

            // Type is an MO-Defined-Type
            type lacp_SysPrio;
        }

        // Instance Control Fields
        // Type is an MO-Defined-Type
        leaf lacpctrl {
            description "Instance Control";

            // Type is an MO-Defined-Type
            type lacp_LACPInstCtrl;
        }

        // Operational system priority
        // Type is an MO-Defined-Type
        leaf operPrio {
            config "false";
            description "Operational Priority";

            // Type is an MO-Defined-Type
            type lacp_SysPrio;
        }

        // System mac
        // Type is an MO-Defined-Type
        leaf sysMac {
            config "false";
            description "System MAC";

            // Type is an MO-Defined-Type
            type lacp_SysMac;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds lacp information that is operated at a
        // interface (member port of the port channel) level
        container if-items {
            list If-list {
                key "id";

                // Added containment: Prefix=if
                // Acquired From Package lacp
                uses lacp_If-group;
            }
        }
    }

    grouping lacp_If-group {

        // Port priority - LACP uses the port priority to decide
        // which ports should be put in standby mode when there
        // is a limitation that prevents all compatible ports
        // from aggregating and which ports should be put into
        // active mode. A higher port priority value means a
        // lower priority for LACP
        // Type is an MO-Defined-Type
        leaf prio {
            description "Priority";

            // Type is an MO-Defined-Type
            type lacp_PortPrio;
        }

        // Transmit rate, the rate at which the packets are
        // transmitted
        // Type is an MO-Defined-Type
        leaf txRate {
            description "Transmit Rate";

            // Type is an MO-Defined-Type
            type lacp_TxRate;
        }

        // Activity flags
        // Type is an MO-Defined-Type
        leaf activityFlags {
            config "false";
            description "Activity Flags";

            // Type is an MO-Defined-Type
            type lacp_ActivityFlags;
        }
        leaf lastActive {
            config "false";
            type uint64;
        }

        // Local port num
        // Type is an MO-Defined-Type
        leaf port {
            config "false";
            description "Port";

            // Type is an MO-Defined-Type
            type lacp_PortNum;
        }

        // Operational port priority
        // Type is an MO-Defined-Type
        leaf operPrio {
            config "false";
            description "Operational Priority";

            // Type is an MO-Defined-Type
            type lacp_PortPrio;
        }

        // Operational key
        // Type is an MO-Defined-Type
        leaf key {
            config "false";
            description "Operational Key";

            // Type is an MO-Defined-Type
            type lacp_Key;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds lacp neighbor information
        container adj-items {

            // Added containment as a singleton: Prefix=adj
            // Acquired From Package lacp
            uses lacp_AdjEp-group;
        }

        // This object holds lacp intf statistics operational information.
        // This is a singleton within an intferace
        container ifstats-items {

            // Added containment as a singleton: Prefix=ifstats
            // Acquired From Package lacp
            uses lacp_IfStats-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping lacp_AdjEp-group {

        // Neighbor system priority
        // Type is an MO-Defined-Type
        leaf sysPrio {
            config "false";
            description "System Priority";

            // Type is an MO-Defined-Type
            type lacp_SysPrio;
        }

        // Neighbor system id
        // Type is an MO-Defined-Type
        leaf sysId {
            config "false";
            description "System ID";

            // Type is an MO-Defined-Type
            type lacp_SysMac;
        }

        // Neighbor Port number
        // Type is an MO-Defined-Type
        leaf port {
            config "false";
            description "Port Number";

            // Type is an MO-Defined-Type
            type lacp_PortNum;
        }

        // Neighbor port priority
        // Type is an MO-Defined-Type
        leaf portPrio {
            config "false";
            description "Port Priority";

            // Type is an MO-Defined-Type
            type lacp_PortPrio;
        }

        // Neighbor activity flags
        // Type is an MO-Defined-Type
        leaf activityFlags {
            config "false";
            description "Activity Flags";

            // Type is an MO-Defined-Type
            type lacp_ActivityFlags;
        }

        // Neighbor oper key
        // Type is an MO-Defined-Type
        leaf key {
            config "false";
            description "Operational Key";

            // Type is an MO-Defined-Type
            type lacp_Key;
        }

        // Inherited From nw:Conn
        // Modified by Override: nw:Ep->name
        // Type is an MO-Defined-Type
        leaf name {
            description "Name";

            // Type is an MO-Defined-Type
            type naming_Name {
                length "1..64";
            }
        }
    }

    grouping lacp_IfStats-group {

        // LACP Interface Stats    Number of LACP pdus sent
        // Type is an MO-Defined-Type
        leaf pduSent {
            config "false";
            description "Number of PDUs Sent";

            // Type is an MO-Defined-Type
            type nw_Counter64;
        }

        // Number of LACP pdus received
        // Type is an MO-Defined-Type
        leaf pduRcvd {
            config "false";
            description "Number of PDUs Received";

            // Type is an MO-Defined-Type
            type nw_Counter64;
        }

        // Number of marker sent
        // Type is an MO-Defined-Type
        leaf markerSent {
            config "false";
            description "Number of Markers Sent";

            // Type is an MO-Defined-Type
            type nw_Counter64;
        }

        // Number of marker received
        // Type is an MO-Defined-Type
        leaf markerRcvd {
            config "false";
            description "Number of Markers Received";

            // Type is an MO-Defined-Type
            type nw_Counter64;
        }

        // Number of marker response sent
        // Type is an MO-Defined-Type
        leaf markerRspSent {
            config "false";
            description "Number of Marker Responses Sent";

            // Type is an MO-Defined-Type
            type nw_Counter64;
        }

        // Number of marker reponse received
        // Type is an MO-Defined-Type
        leaf markerRspRcvd {
            config "false";
            description "Number of Marker Responses Received";

            // Type is an MO-Defined-Type
            type nw_Counter64;
        }

        // Number of error packets received
        // Type is an MO-Defined-Type
        leaf errPktRcvd {
            config "false";
            description "Number of Error Packets Received";

            // Type is an MO-Defined-Type
            type nw_Counter64;
        }
    }

    grouping mgmt_MgmtIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Type is an MO-Defined-Type
        leaf adminSt {
            description "Administrative State";

            // Type is an MO-Defined-Type
            type l1_AdminSt;
        }

        // Administrative port speed    @@@ This comes from the host interface
        // @@@ configuration policy
        // Inherited From l1:If
        // Modified by Override: mgmt:MgmtIf->speed
        // Type is an MO-Defined-Type
        leaf speed {
            config "false";
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Mgmt interface
        container mgmt-items {

            // Added containment as a singleton: Prefix=mgmt
            // Acquired From Package im
            uses im_MgmtIf-group;
        }

        // Mgmt0 interface capabilities
        container portcap-items {

            // Added containment as a singleton: Prefix=portcap
            // Acquired From Package im
            uses im_PortCap-group;
        }

        // Rel-def target from rtdMgmtConf
        // Inherited From mgmt:MgmtIf
        container rtrtdMgmtConf-items {

            // Added containment as a singleton: Prefix=rtrtdMgmtConf
            // Acquired From Package mgmt
            uses mgmt_RtRtdMgmtConf_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        container dbgIfIn-items {

            // Added containment as a singleton: Prefix=dbgIfIn
            // Acquired From Package rmon
            uses rmon_IfIn-group;
        }

        container dbgIfOut-items {

            // Added containment as a singleton: Prefix=dbgIfOut
            // Acquired From Package rmon
            uses rmon_IfOut-group;
        }

        container dbgIpIn-items {

            // Added containment as a singleton: Prefix=dbgIpIn
            // Acquired From Package rmon
            uses rmon_IpIn-group;
        }

        container dbgDot1d-items {

            // Added containment as a singleton: Prefix=dbgDot1d
            // Acquired From Package rmon
            uses rmon_Dot1d-group;
        }

        container dbgEtherStats-items {

            // Added containment as a singleton: Prefix=dbgEtherStats
            // Acquired From Package rmon
            uses rmon_EtherStats-group;
        }

        container dbgDot3Stats-items {

            // Added containment as a singleton: Prefix=dbgDot3Stats
            // Acquired From Package rmon
            uses rmon_Dot3Stats-group;
        }

        container dbgIfHCIn-items {

            // Added containment as a singleton: Prefix=dbgIfHCIn
            // Acquired From Package rmon
            uses rmon_IfHCIn-group;
        }

        container dbgIfHCOut-items {

            // Added containment as a singleton: Prefix=dbgIfHCOut
            // Acquired From Package rmon
            uses rmon_IfHCOut-group;
        }

        container dbgIpv6IfStats-items {

            // Added containment as a singleton: Prefix=dbgIpv6IfStats
            // Acquired From Package rmon
            uses rmon_Ipv6IfStats-group;
        }

        container dbgIfStorm-items {

            // Added containment as a singleton: Prefix=dbgIfStorm
            // Acquired From Package rmon
            uses rmon_IfStorm-group;
        }
    }

    grouping im_MgmtIf-group {

        // Operational state summary
        // Type is an MO-Defined-Type
        leaf osSum {
            config "false";
            description "Operational State Summary";

            // Type is an MO-Defined-Type
            type nw_OSSum;
        }

        // Operational port state
        // Type is an MO-Defined-Type
        leaf operSt {
            config "false";
            description "Operational Port State";

            // Type is an MO-Defined-Type
            type l1_OperSt;
        }

        // Operational port status reason
        // Type is an MO-Defined-Type
        leaf operStQual {
            config "false";
            description "Operational Port Status Reason";

            // Type is an MO-Defined-Type
            type l1_OperStQual;
        }

        // Operational port speed
        // Type is an MO-Defined-Type
        leaf operSpeed {
            config "false";
            description "Operational Port Speed";

            // Type is an MO-Defined-Type
            type l1_Speed;
        }

        // Operational duplex
        // Type is an MO-Defined-Type
        leaf operDuplex {
            config "false";
            description "Operational Duplex";

            // Type is an MO-Defined-Type
            type l1_Duplex;
        }

        // Operational physical port layer
        // Type is an MO-Defined-Type
        leaf operPhyLayer {
            config "false";
            description "Operational Physical Port Layer";

            // Type is an MO-Defined-Type
            type l1_PhyLayer;
        }
        leaf backplaneMac {
            config "false";
            type address_Mac;
        }
        leaf operRouterMac {
            config "false";
            type address_Mac;
        }
        leaf portInitEvalFlag {
            config "false";
            type uint8;
        }

        // Operational Mtu
        // Type is an MO-Defined-Type
        leaf operMtu {
            config "false";
            description "Operational Mtu";

            // Type is an MO-Defined-Type
            type l1_Mtu;
        }
        leaf iod {
            config "false";
            type uint64;
        }

        // Vdc id
        // Type is an MO-Defined-Type
        leaf vdcId {
            config "false";
            description "Vdc Id";

            // Type is an MO-Defined-Type
            type l2_VdcId;
        }
        leaf createSig {
            config "false";
            type uint32;
        }
        leaf lastLinkStChg {
            config "false";
            type uint64;
        }
    }

    grouping im_PortCap-group {
        leaf portCap {
            config "false";
            type uint32;
        }
    }

    grouping mit_MitOperRoot-group {

        container commitMit-items {

            // Added containment as a singleton: Prefix=commitMit
            // Acquired From Package mit
            uses mit_CommitMit-group;
        }

        container copyMit-items {

            // Added containment as a singleton: Prefix=copyMit
            // Acquired From Package mit
            uses mit_CopyMit-group;
        }
        container mitLock-items {
            list MitLock-list {
                key "treeId";

                // Added containment: Prefix=mitLock
                // Acquired From Package mit
                uses mit_MitLock-group;
            }
        }
        container sessionLock-items {
            list SessionLock-list {
                key "name";

                // Added containment: Prefix=sessionLock
                // Acquired From Package mit
                uses mit_SessionLock-group;
            }
        }
    }

    grouping mit_CommitMit-group {
        leaf srcTreeId {
            type uint32;
        }

        // Type is an MO-Defined-Type
        leaf commitOperType {
            description "commit operation type";

            // Type is an MO-Defined-Type
            type mit_OperType;
        }
        leaf timeout {
            type uint32;
        }
        leaf txnId {
            type string;
        }
    }

    grouping mit_CopyMit-group {

        // Type is an MO-Defined-Type
        leaf srcTreeId {
            description "source id of mit";

            // Type is an MO-Defined-Type
            type mit_TreeType;
        }

        // Type is an MO-Defined-Type
        leaf dstTreeId {
            description "destination id of mit";

            // Type is an MO-Defined-Type
            type mit_TreeType;
        }
    }

    grouping mit_MitLock-group {
        leaf treeId {
            type uint32;
        }

        // Type is an MO-Defined-Type
        leaf lockStatus {
            description "current lock status of a mit";

            // Type is an MO-Defined-Type
            type mit_LockStatus;
        }
        leaf pid {
            type uint32;
        }
        leaf isForceUnlock {
            type boolean;
            default "true";
        }
    }

    grouping mit_SessionLock-group {
        leaf treeId {
            type uint32;
        }

        // Type is an MO-Defined-Type
        leaf lockStatus {
            description "current lock status of a session";

            // Type is an MO-Defined-Type
            type mit_LockStatus;
        }
        leaf pid {
            type uint32;
        }
        leaf name {
            type string;
        }
    }

    grouping snmp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per snmp instance information
        container inst-items {

            // Added containment as a singleton: Prefix=inst
            // Acquired From Package snmp
            uses snmp_Inst-group;
        }
    }

    grouping snmp_Inst-group {
        leaf lastInitTs {
            config "false";
            type uint64;
        }

        // Engine Id
        // Type is an MO-Defined-Type
        leaf engId {
            description "Engine Id";

            // Type is an MO-Defined-Type
            type snmp_EngId;
        }

        // Type is an MO-Defined-Type
        leaf defaultEngId {
            config "false";
            description "Default Engine ID";

            // Type is an MO-Defined-Type
            type snmp_EngId;
        }

        // Type is an MO-Defined-Type
        leaf hiddenEngId {
            config "false";
            description "Default Engine ID";

            // Type is an MO-Defined-Type
            type snmp_EngId;
        }

        // Type is an MO-Defined-Type
        leaf eventSet {
            config "false";
            description "Indicates the event MO thats needs to be created";

            // Type is an MO-Defined-Type
            type snmp_EventSetBitT;
        }

        // Type is an MO-Defined-Type
        leaf defaultTrapsEnableBit {
            config "false";
            description "Indicates the event MO thats needs to be created";

            // Type is an MO-Defined-Type
            type snmp_EnableTrapBit;
        }

        // Type is an MO-Defined-Type
        leaf defaultTrapsDisablebit {
            config "false";
            description "Indicates the event MO thats needs to be created";

            // Type is an MO-Defined-Type
            type snmp_EnableTrapBit;
        }

        // Type is an MO-Defined-Type
        leaf runConfTrapsEnableBit {
            config "false";
            description "Indicates the event MO thats needs to be created";

            // Type is an MO-Defined-Type
            type snmp_EnableTrapBit;
        }

        // From Interface naming:Named
        // Inherited From naming:NamedObject
        // Modified by Override: pol:Obj->name
        // Modified by Override: snmp:APol->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From snmp:APol
        // Type is an MO-Defined-Type
        leaf adminSt {
            description "Admin State";

            // Type is an MO-Defined-Type
            type nw_AdminSt;
        }

        // Inherited From snmp:APol
        // Type is an MO-Defined-Type
        leaf contact {
            description "Contact";

            // Type is an MO-Defined-Type
            type snmp_Contact;
        }

        // Inherited From snmp:APol
        // Type is an MO-Defined-Type
        leaf loc {
            description "Location";

            // Type is an MO-Defined-Type
            type snmp_Location;
        }

        // Access control based on ip addresses and communities.
        // This is valid only with v1/v2c security    Client group
        container clgrp-items {
            list ClientGrp-list {
                key "name";

                // Added containment: Prefix=clgrp
                // Acquired From Package snmp
                uses snmp_ClientGrp-group;
            }
        }

        container globals-items {

            // Added containment as a singleton: Prefix=globals
            // Acquired From Package snmp
            uses snmp_Globals-group;
        }
        container host-items {
            list Host-list {
                key "hostName udpPortID";

                // Added containment: Prefix=host
                // Acquired From Package snmp
                uses snmp_Host-group;
            }
        }

        container rmon-items {

            // Added containment as a singleton: Prefix=rmon
            // Acquired From Package snmp
            uses snmp_Rmon-group;
        }

        // Security policy using communities. Uses a community
        // string match for authentication
        container community-items {
            list CommSecP-list {
                key "name";

                // Added containment: Prefix=community
                // Acquired From Package snmp
                uses snmp_CommSecP-group;
            }
        }

        // Authentication policy using user names
        container user-items {
            list UserSecP-list {
                key "name";

                // Added containment: Prefix=user
                // Acquired From Package snmp
                uses snmp_UserSecP-group;
            }
        }

        // This objects holds snmp context information
        container ctx-items {
            list Ctx-list {
                key "name";

                // Added containment: Prefix=ctx
                // Acquired From Package snmp
                uses snmp_Ctx-group;
            }
        }

        container sysinfo-items {

            // Added containment as a singleton: Prefix=sysinfo
            // Acquired From Package snmp
            uses snmp_SysInfo-group;
        }

        container traps-items {

            // Added containment as a singleton: Prefix=traps
            // Acquired From Package snmp
            uses snmp_Traps-group;
        }
        container rmtUser-items {
            list RemoteUser-list {
                key "userName usrengineId";

                // Added containment: Prefix=rmtUser
                // Acquired From Package snmp
                uses snmp_RemoteUser-group;
            }
        }
        container lclUser-items {
            list LocalUser-list {
                key "userName";

                // Added containment: Prefix=lclUser
                // Acquired From Package snmp
                uses snmp_LocalUser-group;
            }
        }
    }

    grouping snmp_ClientGrp-group {

        // The vrf that this client group belongs to
        // Type is an MO-Defined-Type
        leaf vrf {
            config "false";
            description "VRF";

            // Type is an MO-Defined-Type
            type l3_VrfName;
        }

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf epgDn {
            config "false";
            type string;
        }
        container client-items {
            list Client-list {
                key "addr";

                // Added containment: Prefix=client
                // Acquired From Package snmp
                uses snmp_Client-group;
            }
        }

        // Rel-def from CommSecPClientGrpAtt
        container rscommSecPClientGrpAtt-items {

            // Abstract containment of rscommSecPClientGrpAtt derived from snmp:ClientGrp
            list RsCommSecPClientGrpAtt-list {
                config "false";
                key "tDn";

                // Added containment: Prefix=rscommSecPClientGrpAtt
                // Acquired From Package snmp
                uses snmp_RsCommSecPClientGrpAtt_source-group;
            }
        }
    }

    grouping snmp_Client-group {

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }

        // From Interface naming:Named
        // Inherited From naming:NamedObject
        // Modified by Override: pol:Obj->name
        // Type is an MO-Defined-Type
        leaf name {
            description "Name";

            // Type is an MO-Defined-Type
            type naming_Name {
                length "0..64";
            }
        }
        leaf addr {
            type address_Ip;
        }
    }

    grouping snmp_Globals-group {

        // Type is an MO-Defined-Type
        leaf aaaUserCacheTimeout {
            description "Timeout for AAA Cache";

            // Type is an MO-Defined-Type
            type snmp_AaaUserCacheTimeout;
        }

        // Type is an MO-Defined-Type
        leaf protocolEnable {
            description "Enable/Disable snmp protocol operations";

            // Type is an MO-Defined-Type
            type snmp_Boolean;
        }

        // Type is an MO-Defined-Type
        leaf counterCacheEnable {
            description "Enable port stats cache";

            // Type is an MO-Defined-Type
            type snmp_Boolean;
        }

        // Type is an MO-Defined-Type
        leaf counterCacheTimeout {
            description "Timeout for port stats cache";

            // Type is an MO-Defined-Type
            type snmp_CounterCacheTimeout;
        }

        // SNMP SERVER Packet Size
        // Type is an MO-Defined-Type
        leaf pktSize {
            description "Packet size config";

            // Type is an MO-Defined-Type
            type snmp_PktSizeT;
        }

        // tcp-session auth config
        // Type is an MO-Defined-Type
        leaf tcpSessionAuth {
            description "tcp-session auth config";

            // Type is an MO-Defined-Type
            type snmp_tcpSessionAuthT;
        }

        container srcInterfaceTraps-items {

            // Added containment as a singleton: Prefix=srcInterfaceTraps
            // Acquired From Package snmp
            uses snmp_SourceInterfaceTraps-group;
        }

        container srcInterfaceInforms-items {

            // Added containment as a singleton: Prefix=srcInterfaceInforms
            // Acquired From Package snmp
            uses snmp_SourceInterfaceInforms-group;
        }
    }

    grouping snmp_SourceInterfaceTraps-group {

        // Type is an MO-Defined-Type
        leaf ifname {
            description "Source interface name for Traps";

            // Type is an MO-Defined-Type
            type nw_IfId;
        }
    }

    grouping snmp_SourceInterfaceInforms-group {

        // Type is an MO-Defined-Type
        leaf ifname {
            description "Source interface name for informs";

            // Type is an MO-Defined-Type
            type nw_IfId;
        }
    }

    grouping snmp_Host-group {

        // Host name
        // Type is an MO-Defined-Type
        leaf hostName {
            description "snmp-server host name";

            // Type is an MO-Defined-Type
            type snmp_hostNameT;
        }

        // IP address in string
        // Type is an MO-Defined-Type
        leaf ipAddr {
            config "false";
            description "Ip address corresponding to the host";

            // Type is an MO-Defined-Type
            type snmp_hostNameT;
        }

        // Community name
        // Type is an MO-Defined-Type
        leaf commName {
            description "community to be associated to the host";

            // Type is an MO-Defined-Type
            type snmp_commNameT;
        }

        // Ctrl bits to decide Traps / Informs
        // Type is an MO-Defined-Type
        leaf notifType {
            description "Ctrl bits indicating traps/informs config";

            // Type is an MO-Defined-Type
            type snmp_NotificationType;
        }

        // Ctrl bits to decide version
        // Type is an MO-Defined-Type
        leaf version {
            description "Ctrl bits indicating version";

            // Type is an MO-Defined-Type
            type snmp_Version;
        }

        // Control bitmask for deciding auth/ priv/ noauth for v3
        // Type is an MO-Defined-Type
        leaf secLevel {
            description "Ctrl bits indicating  auth/ priv/ noauth for v3";

            // Type is an MO-Defined-Type
            type snmp_V3SecLvl;
        }

        // udp-port ID
        // Type is an MO-Defined-Type
        leaf udpPortID {
            description "snmp-server host udp-port";

            // Type is an MO-Defined-Type
            type snmp_PortIdT;
        }
        leaf isDuplicate {
            config "false";
            type boolean;
        }

        // Type is an MO-Defined-Type
        leaf duplicateHostName {
            config "false";
            description "The name of the actual MO to be updated";

            // Type is an MO-Defined-Type
            type snmp_hostNameT;
        }

        // Type is an MO-Defined-Type
        leaf configState {
            config "false";
            description "True/False depending on whether config is successful or failed";

            // Type is an MO-Defined-Type
            type snmp_hostConfigErrorType;
        }
        container usevrf-items {
            list UseVrf-list {
                key "vrfname";

                // Added containment: Prefix=usevrf
                // Acquired From Package snmp
                uses snmp_UseVrf-group;
            }
        }
    }

    grouping snmp_UseVrf-group {
        leaf vrfname {
            type string {
            }
        }
    }

    grouping snmp_Rmon-group {
        container event-items {
            list Event-list {
                key "num";

                // Added containment: Prefix=event
                // Acquired From Package snmp
                uses snmp_Event-group;
            }
        }
        container alarm-items {
            list Alarm-list {
                key "num";

                // Added containment: Prefix=alarm
                // Acquired From Package snmp
                uses snmp_Alarm-group;
            }
        }
    }

    grouping snmp_Event-group {

        // Event Number
        // Type is an MO-Defined-Type
        leaf num {
            description "rmon event number";

            // Type is an MO-Defined-Type
            type snmp_EventNum;
        }

        // To generate / not log when alarm event is fired
        // Type is an MO-Defined-Type
        leaf log {
            description "Whether to generate / not log when alarm event is fired";

            // Type is an MO-Defined-Type
            type snmp_LogEnableType;
        }

        // Type is an MO-Defined-Type
        leaf owner {
            description "rmon event owner";

            // Type is an MO-Defined-Type
            type snmp_OwnerType;
        }

        // Type is an MO-Defined-Type
        leaf description {
            description "rmon event description";

            // Type is an MO-Defined-Type
            type snmp_DescType;
        }

        // Type is an MO-Defined-Type
        leaf trap {
            description "rmon event description";

            // Type is an MO-Defined-Type
            type snmp_TrapCommType;
        }
    }

    grouping snmp_Alarm-group {

        // Alarm Number
        // Type is an MO-Defined-Type
        leaf num {
            description "rmon alarm number";

            // Type is an MO-Defined-Type
            type snmp_EventNum;
        }
        leaf oid {
            type string;
        }

        // Sample Interval
        // Type is an MO-Defined-Type
        leaf sampleInterval {
            description "rmon alarm sample interval";

            // Type is an MO-Defined-Type
            type snmp_smplIntvl;
        }

        // Sample Type
        // Type is an MO-Defined-Type
        leaf sampleType {
            description "rmon alarm sample interval type";

            // Type is an MO-Defined-Type
            type snmp_smplType;
        }

        // Rising Threshold
        // Type is an MO-Defined-Type
        leaf risingThr {
            description "rmon alarm rising threshold";

            // Type is an MO-Defined-Type
            type snmp_thrshld;
        }

        // Rising Threshold Event Index
        // Type is an MO-Defined-Type
        leaf risingEvntIndx {
            description "rmon alarm rising threshold event index";

            // Type is an MO-Defined-Type
            type snmp_EventIndx;
        }

        // Falling Threshold
        // Type is an MO-Defined-Type
        leaf fallingThr {
            description "rmon alarm falling threshold";

            // Type is an MO-Defined-Type
            type snmp_thrshld;
        }

        // Falling Threshold Event Index
        // Type is an MO-Defined-Type
        leaf fallingEvntIndx {
            description "rmon alarm falling threshold event index";

            // Type is an MO-Defined-Type
            type snmp_EventIndx;
        }

        // Owner Name
        // Type is an MO-Defined-Type
        leaf owner {
            description "rmon alarm owner";

            // Type is an MO-Defined-Type
            type snmp_OwnerType;
        }

        // Alarm Rmon config state
        // Type is an MO-Defined-Type
        leaf alarmConfigError {
            config "false";
            description "Rmon Alarm configurations state";

            // Type is an MO-Defined-Type
            type snmp_alarmConfigErrorType;
        }
    }

    grouping snmp_CommSecP-group {

        // Group to which community belongs to
        // Type is an MO-Defined-Type
        leaf grpName {
            description "SNMP community group";

            // Type is an MO-Defined-Type
            type snmp_GrpNameT;
        }

        // Community Access
        // Type is an MO-Defined-Type
        leaf commAcess {
            description "SNMP community group";

            // Type is an MO-Defined-Type
            type snmp_CommAcessT;
        }

        // Memory alert level
        // Type is an MO-Defined-Type
        leaf memAlert {
            config "false";
            description "Memory Alert Level";

            // Type is an MO-Defined-Type
            type nw_MemAlertLevel;
        }

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }

        // From Interface naming:Named
        // Inherited From naming:NamedObject
        // Modified by Override: snmp:CommSecP->name
        // Modified by Override: pol:Obj->name
        // Modified by Override: snmp:ACommunityP->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // This object hold the ACl informations
        container acl-items {

            // Added containment as a singleton: Prefix=acl
            // Acquired From Package snmp
            uses snmp_Acl-group;
        }

        // Rel-def from CommToCtxAtt
        container rscommToCtxAtt-items {

            // Added containment as a singleton: Prefix=rscommToCtxAtt
            // Acquired From Package snmp
            uses snmp_RsCommToCtxAtt_source-group;
        }
    }

    grouping snmp_Acl-group {

        // SNMP ACL name
        // Type is an MO-Defined-Type
        leaf useAclName {
            description "SNMP community acl name";

            // Type is an MO-Defined-Type
            type snmp_AclNameT;
        }

        // SNMP ACL name
        // Type is an MO-Defined-Type
        leaf useIpv4AclName {
            description "SNMP community acl name";

            // Type is an MO-Defined-Type
            type snmp_AclNameT;
        }

        // SNMP ACL name
        // Type is an MO-Defined-Type
        leaf useIpv6AclName {
            description "SNMP community acl name";

            // Type is an MO-Defined-Type
            type snmp_AclNameT;
        }

        // Use-ACL config state
        // Type is an MO-Defined-Type
        leaf configStatus {
            config "false";
            description "Configurations status";

            // Type is an MO-Defined-Type
            type snmp_cfgStatus;
        }
    }

    grouping snmp_UserSecP-group {

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }

        // From Interface naming:Named
        // Inherited From naming:NamedObject
        // Modified by Override: pol:Obj->name
        // Modified by Override: snmp:AUserP->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Authentication type
        // Inherited From snmp:AUserP
        // Type is an MO-Defined-Type
        leaf authType {
            description "Authentication Type";

            // Type is an MO-Defined-Type
            type snmp_AuthType;
        }

        // Authentication key
        // Inherited From snmp:AUserP
        // Type is an MO-Defined-Type
        leaf authKey {
            description "Authentication Key";

            // Type is an MO-Defined-Type
            type snmp_AuthKey;
        }

        // Privacy (encryption) type
        // Inherited From snmp:AUserP
        // Type is an MO-Defined-Type
        leaf privType {
            description "Privacy";

            // Type is an MO-Defined-Type
            type snmp_PrivType;
        }

        // Privacy key
        // Inherited From snmp:AUserP
        // Type is an MO-Defined-Type
        leaf privKey {
            description "Privacy Key";

            // Type is an MO-Defined-Type
            type snmp_PrivKey;
        }
    }

    grouping snmp_Ctx-group {

        // The vrf that this client group belongs to
        // Type is an MO-Defined-Type
        leaf vrf {
            config "false";
            description "VRF";

            // Type is an MO-Defined-Type
            type l3_VrfName;
        }

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping snmp_SysInfo-group {

        // Type is an MO-Defined-Type
        leaf sysLocation {
            description "System Location";

            // Type is an MO-Defined-Type
            type snmp_SnmpSysLoc;
        }

        // Type is an MO-Defined-Type
        leaf sysContact {
            description "System Contact";

            // Type is an MO-Defined-Type
            type snmp_SnmpSysContact;
        }

        // Type is an MO-Defined-Type
        leaf sysDescription {
            description "System Description";

            // Type is an MO-Defined-Type
            type snmp_SnmpSysDescr;
        }
    }

    grouping snmp_Traps-group {
        leaf enableAllTriggerCount {
            config "false";
            type uint16;
        }
        leaf enableAllViaCLI {
            config "false";
            type boolean;
        }

        // Default traps List Starts From Here    StormControl trap
        container stormcontrol-items {

            // Added containment as a singleton: Prefix=stormcontrol
            // Acquired From Package snmp
            uses snmp_TstormControl-group;
        }

        // Default traps List Starts From Here    AAA trap
        container aaa-items {

            // Added containment as a singleton: Prefix=aaa
            // Acquired From Package snmp
            uses snmp_Taaa-group;
        }

        // Bfd trap
        container bfd-items {

            // Added containment as a singleton: Prefix=bfd
            // Acquired From Package snmp
            uses snmp_Tbfd-group;
        }

        // Bridge trap
        container bridge-items {

            // Added containment as a singleton: Prefix=bridge
            // Acquired From Package snmp
            uses snmp_Tbridge-group;
        }

        // Callhome trap
        container callhome-items {

            // Added containment as a singleton: Prefix=callhome
            // Acquired From Package snmp
            uses snmp_Tcallhome-group;
        }

        // CFS trap
        container cfs-items {

            // Added containment as a singleton: Prefix=cfs
            // Acquired From Package snmp
            uses snmp_Tcfs-group;
        }

        // Config trap
        container config-items {

            // Added containment as a singleton: Prefix=config
            // Acquired From Package snmp
            uses snmp_Tconfig-group;
        }

        // Entity trap
        container entity-items {

            // Added containment as a singleton: Prefix=entity
            // Acquired From Package snmp
            uses snmp_Tentity-group;
        }

        // Feature-control trap
        container featurecontrol-items {

            // Added containment as a singleton: Prefix=featurecontrol
            // Acquired From Package snmp
            uses snmp_Tfeaturecontrol-group;
        }

        // hsrp trap
        container hsrp-items {

            // Added containment as a singleton: Prefix=hsrp
            // Acquired From Package snmp
            uses snmp_Thsrp-group;
        }

        // generic trap
        container generic-items {

            // Added containment as a singleton: Prefix=generic
            // Acquired From Package snmp
            uses snmp_Tgeneric-group;
        }

        // ip trap
        container ip-items {

            // Added containment as a singleton: Prefix=ip
            // Acquired From Package snmp
            uses snmp_Tip-group;
        }

        // license trap
        container license-items {

            // Added containment as a singleton: Prefix=license
            // Acquired From Package snmp
            uses snmp_Tlicense-group;
        }

        // link trap
        container link-items {

            // Added containment as a singleton: Prefix=link
            // Acquired From Package snmp
            uses snmp_Tlink-group;
        }

        // lldp trap
        container lldp-items {

            // Added containment as a singleton: Prefix=lldp
            // Acquired From Package snmp
            uses snmp_Tlldp-group;
        }

        // msdp trap
        container msdp-items {

            // Added containment as a singleton: Prefix=msdp
            // Acquired From Package snmp
            uses snmp_Tmsdp-group;
        }

        // mmode trap
        container mmode-items {

            // Added containment as a singleton: Prefix=mmode
            // Acquired From Package snmp
            uses snmp_Tmmode-group;
        }

        // pim trap
        container pim-items {

            // Added containment as a singleton: Prefix=pim
            // Acquired From Package snmp
            uses snmp_Tpim-group;
        }

        // rf trap
        container rf-items {

            // Added containment as a singleton: Prefix=rf
            // Acquired From Package snmp
            uses snmp_Trf-group;
        }

        // rmon trap
        container rmon-items {

            // Added containment as a singleton: Prefix=rmon
            // Acquired From Package snmp
            uses snmp_Trmon-group;
        }

        // snmp trap
        container snmp-items {

            // Added containment as a singleton: Prefix=snmp
            // Acquired From Package snmp
            uses snmp_Tsnmp-group;
        }

        // stpx trap
        container stpx-items {

            // Added containment as a singleton: Prefix=stpx
            // Acquired From Package snmp
            uses snmp_Tstpx-group;
        }

        // sysmgr trap
        container sysmgr-items {

            // Added containment as a singleton: Prefix=sysmgr
            // Acquired From Package snmp
            uses snmp_Tsysmgr-group;
        }

        // system trap
        container system-items {

            // Added containment as a singleton: Prefix=system
            // Acquired From Package snmp
            uses snmp_Tsystem-group;
        }

        // upgrade trap
        container upgrade-items {

            // Added containment as a singleton: Prefix=upgrade
            // Acquired From Package snmp
            uses snmp_Tupgrade-group;
        }

        // vsan trap
        container vsan-items {

            // Added containment as a singleton: Prefix=vsan
            // Acquired From Package snmp
            uses snmp_Tvsan-group;
        }

        // vtp trap
        container vtp-items {

            // Added containment as a singleton: Prefix=vtp
            // Acquired From Package snmp
            uses snmp_Tvtp-group;
        }

        // port-security trap
        container portsecurity-items {

            // Added containment as a singleton: Prefix=portsecurity
            // Acquired From Package snmp
            uses snmp_Tportsecurity-group;
        }
    }

    grouping snmp_TstormControl-group {

        // SNMP trap-rate
        // Type is an MO-Defined-Type
        leaf traprate {
            description "Number of traps per minute";

            // Type is an MO-Defined-Type
            type snmp_TrapRateT;
        }

        // snmp authentication trap
        container cpscEventRev1-items {

            // Added containment as a singleton: Prefix=cpscEventRev1
            // Acquired From Package snmp
            uses snmp_CpscEventRev1-group;
        }
    }

    grouping snmp_CpscEventRev1-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Taaa-group {
        leaf enableViaCLI {
            config "false";
            type boolean;
        }

        // AAA server-state-change trap
        container serverstatechange-items {

            // Added containment as a singleton: Prefix=serverstatechange
            // Acquired From Package snmp
            uses snmp_ServerStateChange-group;
        }
    }

    grouping snmp_ServerStateChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tbfd-group {

        // Bfd session-down trap
        container sessiondown-items {

            // Added containment as a singleton: Prefix=sessiondown
            // Acquired From Package snmp
            uses snmp_SessionDown-group;
        }

        // Bfd session-up trap
        container sessionup-items {

            // Added containment as a singleton: Prefix=sessionup
            // Acquired From Package snmp
            uses snmp_SessionUp-group;
        }
    }

    grouping snmp_SessionDown-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_SessionUp-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tbridge-group {

        // Bridge newroot trap
        container newroot-items {

            // Added containment as a singleton: Prefix=newroot
            // Acquired From Package snmp
            uses snmp_NewRoot-group;
        }

        // Bridge topologychange trap
        container topologychange-items {

            // Added containment as a singleton: Prefix=topologychange
            // Acquired From Package snmp
            uses snmp_TopologyChange-group;
        }
    }

    grouping snmp_NewRoot-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_TopologyChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tcallhome-group {

        // callhome event-notify trap
        container eventnotify-items {

            // Added containment as a singleton: Prefix=eventnotify
            // Acquired From Package snmp
            uses snmp_EventNotify-group;
        }

        // callhome smtp-send-fail trap
        container smtpsendfail-items {

            // Added containment as a singleton: Prefix=smtpsendfail
            // Acquired From Package snmp
            uses snmp_SmtpSendFail-group;
        }
    }

    grouping snmp_EventNotify-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_SmtpSendFail-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tcfs-group {

        // cfs state-change-notif trap
        container statechangenotif-items {

            // Added containment as a singleton: Prefix=statechangenotif
            // Acquired From Package snmp
            uses snmp_StateChangeNotif-group;
        }

        // cfs merge-failure trap
        container mergefailure-items {

            // Added containment as a singleton: Prefix=mergefailure
            // Acquired From Package snmp
            uses snmp_MergeFailure-group;
        }
    }

    grouping snmp_StateChangeNotif-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_MergeFailure-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tconfig-group {

        // config CLIRunningConfigChange trap
        container ccmCLIRunningConfigChanged-items {

            // Added containment as a singleton: Prefix=ccmCLIRunningConfigChanged
            // Acquired From Package snmp
            uses snmp_CLIRunningConfigChange-group;
        }
    }

    grouping snmp_CLIRunningConfigChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tentity-group {

        // entity entitymibchange trap
        container entitymibchange-items {

            // Added containment as a singleton: Prefix=entitymibchange
            // Acquired From Package snmp
            uses snmp_EntityMIBChange-group;
        }

        // entity entitymodulestatuschange trap
        container entitymodulestatuschange-items {

            // Added containment as a singleton: Prefix=entitymodulestatuschange
            // Acquired From Package snmp
            uses snmp_EntityModuleStatusChange-group;
        }

        // entity entitypowerstatuschange trap
        container entitypowerstatuschange-items {

            // Added containment as a singleton: Prefix=entitypowerstatuschange
            // Acquired From Package snmp
            uses snmp_EntityPowerStatusChange-group;
        }

        // entity entitymoduleinserted trap
        container entitymoduleinserted-items {

            // Added containment as a singleton: Prefix=entitymoduleinserted
            // Acquired From Package snmp
            uses snmp_EntityModuleInserted-group;
        }

        // entity entitymoduleremoved trap
        container entitymoduleremoved-items {

            // Added containment as a singleton: Prefix=entitymoduleremoved
            // Acquired From Package snmp
            uses snmp_EntityModuleRemoved-group;
        }

        // entity entityunrecognisedmodule trap
        container entityunrecognisedmodule-items {

            // Added containment as a singleton: Prefix=entityunrecognisedmodule
            // Acquired From Package snmp
            uses snmp_EntityUnrecognisedModule-group;
        }

        // entity entityfanstatuschange trap
        container entityfanstatuschange-items {

            // Added containment as a singleton: Prefix=entityfanstatuschange
            // Acquired From Package snmp
            uses snmp_EntityFanStatusChange-group;
        }

        // entity entitypoweroutchange trap
        container entitypoweroutchange-items {

            // Added containment as a singleton: Prefix=entitypoweroutchange
            // Acquired From Package snmp
            uses snmp_EntityPowerOutChange-group;
        }

        // entity entitysensor trap
        container entitysensor-items {

            // Added containment as a singleton: Prefix=entitysensor
            // Acquired From Package snmp
            uses snmp_EntitySensor-group;
        }

        // entity entitymibenablestatusnotification trap
        container cefcMIBEnableStatusNotification-items {

            // Added containment as a singleton: Prefix=cefcMIBEnableStatusNotification
            // Acquired From Package snmp
            uses snmp_EntityMIBEnableStatusNotification-group;
        }
    }

    grouping snmp_EntityMIBChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityModuleStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityPowerStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityModuleInserted-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityModuleRemoved-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityUnrecognisedModule-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityFanStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityPowerOutChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntitySensor-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_EntityMIBEnableStatusNotification-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tfeaturecontrol-group {

        // feature-control FeatureOpStatusChange trap
        container FeatureOpStatusChange-items {

            // Added containment as a singleton: Prefix=FeatureOpStatusChange
            // Acquired From Package snmp
            uses snmp_FeatureOpStatusChange-group;
        }

        // feature-control CiscoFeatOpStatusChange trap
        container ciscoFeatOpStatusChange-items {

            // Added containment as a singleton: Prefix=ciscoFeatOpStatusChange
            // Acquired From Package snmp
            uses snmp_CiscoFeatOpStatusChange-group;
        }
    }

    grouping snmp_FeatureOpStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_CiscoFeatOpStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Thsrp-group {

        // hsrp statechange trap
        container statechange-items {

            // Added containment as a singleton: Prefix=statechange
            // Acquired From Package snmp
            uses snmp_StateChange-group;
        }
    }

    grouping snmp_StateChange-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tgeneric-group {

        // generic coldstart trap
        container coldStart-items {

            // Added containment as a singleton: Prefix=coldStart
            // Acquired From Package snmp
            uses snmp_ColdStart-group;
        }

        // generic warmstart trap
        container warmStart-items {

            // Added containment as a singleton: Prefix=warmStart
            // Acquired From Package snmp
            uses snmp_WarmStart-group;
        }
    }

    grouping snmp_ColdStart-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_WarmStart-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tip-group {

        // ip sla trap
        container sla-items {

            // Added containment as a singleton: Prefix=sla
            // Acquired From Package snmp
            uses snmp_Sla-group;
        }
    }

    grouping snmp_Sla-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tlicense-group {

        // license Notify licenseexpiry trap
        container notifylicenseexpiry-items {

            // Added containment as a singleton: Prefix=notifylicenseexpiry
            // Acquired From Package snmp
            uses snmp_NotifyLicenseExpiry-group;
        }

        // license Notify LicenseExpiryWarning trap
        container notifylicenseexpirywarning-items {

            // Added containment as a singleton: Prefix=notifylicenseexpirywarning
            // Acquired From Package snmp
            uses snmp_NotifyLicenseExpiryWarning-group;
        }

        // license Notify licensefilemissing trap
        container notifylicensefilemissing-items {

            // Added containment as a singleton: Prefix=notifylicensefilemissing
            // Acquired From Package snmp
            uses snmp_NotifyLicenseFileMissing-group;
        }

        // license Notifynolicenceforfeature trap
        container notifynolicenseforfeature-items {

            // Added containment as a singleton: Prefix=notifynolicenseforfeature
            // Acquired From Package snmp
            uses snmp_NotifyNoLicenceForFeature-group;
        }
    }

    grouping snmp_NotifyLicenseExpiry-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_NotifyLicenseExpiryWarning-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_NotifyLicenseFileMissing-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_NotifyNoLicenceForFeature-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tlink-group {

        // link Ciscoxcvrmonstatuschange trap
        container ciscoxcvrmonstatuschg-items {

            // Added containment as a singleton: Prefix=ciscoxcvrmonstatuschg
            // Acquired From Package snmp
            uses snmp_CiscoXcvrMonStatusChange-group;
        }

        // link linkdown trap
        container linkDown-items {

            // Added containment as a singleton: Prefix=linkDown
            // Acquired From Package snmp
            uses snmp_LinkDown-group;
        }

        // link linkup trap
        container linkUp-items {

            // Added containment as a singleton: Prefix=linkUp
            // Acquired From Package snmp
            uses snmp_LinkUp-group;
        }

        // link extended linkdown trap
        container extendedlinkDown-items {

            // Added containment as a singleton: Prefix=extendedlinkDown
            // Acquired From Package snmp
            uses snmp_ExtendedLinkDown-group;
        }

        // link extended linkup trap
        container extendedlinkUp-items {

            // Added containment as a singleton: Prefix=extendedlinkUp
            // Acquired From Package snmp
            uses snmp_ExtendedLinkUp-group;
        }

        // link cielinkdown trap
        container cieLinkDown-items {

            // Added containment as a singleton: Prefix=cieLinkDown
            // Acquired From Package snmp
            uses snmp_CieLinkDown-group;
        }

        // link Cie linkup trap
        container cieLinkUp-items {

            // Added containment as a singleton: Prefix=cieLinkUp
            // Acquired From Package snmp
            uses snmp_CieLinkUp-group;
        }

        // link delayedlinkstatechange trap
        container delayedlinkstatechange-items {

            // Added containment as a singleton: Prefix=delayedlinkstatechange
            // Acquired From Package snmp
            uses snmp_DelayedLinkStateChange-group;
        }
    }

    grouping snmp_CiscoXcvrMonStatusChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_LinkDown-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_LinkUp-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_ExtendedLinkDown-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_ExtendedLinkUp-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_CieLinkDown-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_CieLinkUp-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_DelayedLinkStateChange-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tlldp-group {

        // lldp RemTablesChange trap
        container lldpRemTablesChange-items {

            // Added containment as a singleton: Prefix=lldpRemTablesChange
            // Acquired From Package snmp
            uses snmp_LldpRemTablesChange-group;
        }
    }

    grouping snmp_LldpRemTablesChange-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tmsdp-group {

        // msdp BackwardTransition trap
        container msdpBackwardTransition-items {

            // Added containment as a singleton: Prefix=msdpBackwardTransition
            // Acquired From Package snmp
            uses snmp_MsdpBackwardTransition-group;
        }
    }

    grouping snmp_MsdpBackwardTransition-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tmmode-group {

        // mmode CseMaintModeChangeNotify trap
        container cseMaintModeChangeNotify-items {

            // Added containment as a singleton: Prefix=cseMaintModeChangeNotify
            // Acquired From Package snmp
            uses snmp_CseMaintModeChangeNotify-group;
        }

        // mmode CseNormalModeChangeNotify trap
        container cseNormalModeChangeNotify-items {

            // Added containment as a singleton: Prefix=cseNormalModeChangeNotify
            // Acquired From Package snmp
            uses snmp_CseNormalModeChangeNotify-group;
        }
    }

    grouping snmp_CseMaintModeChangeNotify-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_CseNormalModeChangeNotify-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tpim-group {

        // pim PimNeighborloss trap
        container pimNeighborLoss-items {

            // Added containment as a singleton: Prefix=pimNeighborLoss
            // Acquired From Package snmp
            uses snmp_PimNeighborLoss-group;
        }
    }

    grouping snmp_PimNeighborLoss-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Trf-group {

        // rf redundancyframework trap
        container redundancyframework-items {

            // Added containment as a singleton: Prefix=redundancyframework
            // Acquired From Package snmp
            uses snmp_RedundancyFramework-group;
        }
    }

    grouping snmp_RedundancyFramework-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Trmon-group {

        // rmon RisingAlarm trap
        container risingAlarm-items {

            // Added containment as a singleton: Prefix=risingAlarm
            // Acquired From Package snmp
            uses snmp_RisingAlarm-group;
        }

        // rmon FallingAlarm trap
        container fallingAlarm-items {

            // Added containment as a singleton: Prefix=fallingAlarm
            // Acquired From Package snmp
            uses snmp_FallingAlarm-group;
        }

        // rmon HcRisingAlarm trap
        container hcRisingAlarm-items {

            // Added containment as a singleton: Prefix=hcRisingAlarm
            // Acquired From Package snmp
            uses snmp_HcRisingAlarm-group;
        }

        // rmon HcFallingAlarm trap
        container hcFallingAlarm-items {

            // Added containment as a singleton: Prefix=hcFallingAlarm
            // Acquired From Package snmp
            uses snmp_HcFallingAlarm-group;
        }
    }

    grouping snmp_RisingAlarm-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_FallingAlarm-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_HcRisingAlarm-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_HcFallingAlarm-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tsnmp-group {

        // snmp authentication trap
        container authentication-items {

            // Added containment as a singleton: Prefix=authentication
            // Acquired From Package snmp
            uses snmp_Authentication-group;
        }
    }

    grouping snmp_Authentication-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tstpx-group {

        // stpx inconsistency trap
        container inconsistency-items {

            // Added containment as a singleton: Prefix=inconsistency
            // Acquired From Package snmp
            uses snmp_Inconsistency-group;
        }

        // stpx rootinconsistency trap
        container rootinconsistency-items {

            // Added containment as a singleton: Prefix=rootinconsistency
            // Acquired From Package snmp
            uses snmp_RootInconsistency-group;
        }

        // stpx Loopinconsistency trap
        container loopinconsistency-items {

            // Added containment as a singleton: Prefix=loopinconsistency
            // Acquired From Package snmp
            uses snmp_LoopInconsistency-group;
        }
    }

    grouping snmp_Inconsistency-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_RootInconsistency-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_LoopInconsistency-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tsysmgr-group {

        // sysmgr CseFailSwCoreNotifyExtended trap
        container cseFailSwCoreNotifyExtended-items {

            // Added containment as a singleton: Prefix=cseFailSwCoreNotifyExtended
            // Acquired From Package snmp
            uses snmp_CseFailSwCoreNotifyExtended-group;
        }
    }

    grouping snmp_CseFailSwCoreNotifyExtended-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tsystem-group {

        // system ClockChangeNotification trap
        container Clockchangenotification-items {

            // Added containment as a singleton: Prefix=Clockchangenotification
            // Acquired From Package snmp
            uses snmp_ClockChangeNotification-group;
        }
    }

    grouping snmp_ClockChangeNotification-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tupgrade-group {

        // upgrade UpgradeJobStatusNotify trap
        container UpgradeJobStatusNotify-items {

            // Added containment as a singleton: Prefix=UpgradeJobStatusNotify
            // Acquired From Package snmp
            uses snmp_UpgradeJobStatusNotify-group;
        }
    }

    grouping snmp_UpgradeJobStatusNotify-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tvsan-group {

        // vsan PortMembershipChange trap
        container vsanPortMembershipChange-items {

            // Added containment as a singleton: Prefix=vsanPortMembershipChange
            // Acquired From Package snmp
            uses snmp_VsanPortMembershipChange-group;
        }

        // vsan vsanStatusChange trap
        container vsanStatusChange-items {

            // Added containment as a singleton: Prefix=vsanStatusChange
            // Acquired From Package snmp
            uses snmp_VsanStatusChange-group;
        }
    }

    grouping snmp_VsanPortMembershipChange-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_VsanStatusChange-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tvtp-group {

        // vtp notifs trap
        container notifs-items {

            // Added containment as a singleton: Prefix=notifs
            // Acquired From Package snmp
            uses snmp_Notifs-group;
        }

        // vtp vlancreate trap
        container vlancreate-items {

            // Added containment as a singleton: Prefix=vlancreate
            // Acquired From Package snmp
            uses snmp_Vlancreate-group;
        }

        // vtp vlandelete trap
        container vlandelete-items {

            // Added containment as a singleton: Prefix=vlandelete
            // Acquired From Package snmp
            uses snmp_Vlandelete-group;
        }
    }

    grouping snmp_Notifs-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Vlancreate-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Vlandelete-group {
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_Tportsecurity-group {

        // port-security access-secure-mac-violation
        container accesssecuremacviolation-items {

            // Added containment as a singleton: Prefix=accesssecuremacviolation
            // Acquired From Package snmp
            uses snmp_AccessSecureMacViolation-group;
        }

        // port-security trunk-secure-mac-violation
        container trunksecuremacviolation-items {

            // Added containment as a singleton: Prefix=trunksecuremacviolation
            // Acquired From Package snmp
            uses snmp_TrunkSecureMacViolation-group;
        }
    }

    grouping snmp_AccessSecureMacViolation-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_TrunkSecureMacViolation-group {

        // Type is an MO-Defined-Type
        leaf trapConfigStatus {
            config "false";
            description "Config State either successful / failed";

            // Type is an MO-Defined-Type
            type snmp_TrapConfigErrorType;
        }
        leaf toggleState {
            config "false";
            type uint16;
        }
        leaf toggleStateCount {
            config "false";
            type uint16;
        }

        // Inherited From snmp:ATraps
        // Type is an MO-Defined-Type
        leaf trapstatus {
            description "Status to show enabled/disable trap";

            // Type is an MO-Defined-Type
            type snmp_SnmpTrapSt;
        }
        leaf isToggleAction {
            config "false";
            type uint16;
        }
    }

    grouping snmp_RemoteUser-group {

        // User name
        // Inherited From snmp:User
        // Type is an MO-Defined-Type
        leaf userName {
            description "snmp-server user name";

            // Type is an MO-Defined-Type
            type snmp_hostNameT;
        }

        // Inherited From snmp:User
        // Type is an MO-Defined-Type
        leaf authpwd {
            description "Auth Password";

            // Type is an MO-Defined-Type
            type snmp_AuthPasswd;
        }

        // Inherited From snmp:User
        // Type is an MO-Defined-Type
        leaf encAuthpwd {
            config "false";
            description "Encrypted Auth Password";

            // Type is an MO-Defined-Type
            type snmp_EncryptedAuthArray;
        }
        leaf authPwdLen {
            config "false";
            type uint32;
        }

        // Inherited From snmp:User
        // Type is an MO-Defined-Type
        leaf authtype {
            description "Auth Protocol Type";

            // Type is an MO-Defined-Type
            type snmp_AuthTypeT;
        }

        // Inherited From snmp:User
        // Type is an MO-Defined-Type
        leaf privpwd {
            description "Priv Password";

            // Type is an MO-Defined-Type
            type snmp_PrivPasswd;
        }

        // Inherited From snmp:User
        // Type is an MO-Defined-Type
        leaf encPrivpwd {
            config "false";
            description "Encrypted Priv Password";

            // Type is an MO-Defined-Type
            type snmp_EncryptedPrivArray;
        }
        leaf privPwdLen {
            config "false";
            type uint32;
        }

        // Inherited From snmp:User
        // Type is an MO-Defined-Type
        leaf privtype {
            description "Priv Protocol Type";

            // Type is an MO-Defined-Type
            type snmp_PrivTypeT;
        }
        leaf islocalizedkey {
            type boolean;
        }
        leaf isenforcepriv {
            type boolean;
        }

        // Inherited From snmp:User
        // Type is an MO-Defined-Type
        leaf usrengineId {
            description "Configured Engine Id";

            // Type is an MO-Defined-Type
            type snmp_EngId;
        }

        // Inherited From snmp:User
        // Type is an MO-Defined-Type
        leaf usrengineIdlen {
            description "Configured Engine Id len";

            // Type is an MO-Defined-Type
            type snmp_EngIdLen;
        }

        // Inherited From snmp:User
        // Type is an MO-Defined-Type
        leaf isAaaNotify {
            config "false";
            description "Notify to AAA";

            // Type is an MO-Defined-Type
            type snmp_Boolean;
        }
    }

    grouping snmp_LocalUser-group {

        // User name
        // Inherited From snmp:User
        // Type is an MO-Defined-Type
        leaf userName {
            description "snmp-server user name";

            // Type is an MO-Defined-Type
            type snmp_hostNameT;
        }

        // Inherited From snmp:User
        // Type is an MO-Defined-Type
        leaf authpwd {
            description "Auth Password";

            // Type is an MO-Defined-Type
            type snmp_AuthPasswd;
        }

        // Inherited From snmp:User
        // Type is an MO-Defined-Type
        leaf encAuthpwd {
            config "false";
            description "Encrypted Auth Password";

            // Type is an MO-Defined-Type
            type snmp_EncryptedAuthArray;
        }
        leaf authPwdLen {
            config "false";
            type uint32;
        }

        // Inherited From snmp:User
        // Type is an MO-Defined-Type
        leaf authtype {
            description "Auth Protocol Type";

            // Type is an MO-Defined-Type
            type snmp_AuthTypeT;
        }

        // Inherited From snmp:User
        // Type is an MO-Defined-Type
        leaf privpwd {
            description "Priv Password";

            // Type is an MO-Defined-Type
            type snmp_PrivPasswd;
        }

        // Inherited From snmp:User
        // Type is an MO-Defined-Type
        leaf encPrivpwd {
            config "false";
            description "Encrypted Priv Password";

            // Type is an MO-Defined-Type
            type snmp_EncryptedPrivArray;
        }
        leaf privPwdLen {
            config "false";
            type uint32;
        }

        // Inherited From snmp:User
        // Type is an MO-Defined-Type
        leaf privtype {
            description "Priv Protocol Type";

            // Type is an MO-Defined-Type
            type snmp_PrivTypeT;
        }
        leaf islocalizedkey {
            type boolean;
        }
        leaf isenforcepriv {
            type boolean;
        }

        // Inherited From snmp:User
        // Type is an MO-Defined-Type
        leaf usrengineId {
            description "Configured Engine Id";

            // Type is an MO-Defined-Type
            type snmp_EngId;
        }

        // Inherited From snmp:User
        // Type is an MO-Defined-Type
        leaf usrengineIdlen {
            description "Configured Engine Id len";

            // Type is an MO-Defined-Type
            type snmp_EngIdLen;
        }

        // Inherited From snmp:User
        // Type is an MO-Defined-Type
        leaf isAaaNotify {
            config "false";
            description "Notify to AAA";

            // Type is an MO-Defined-Type
            type snmp_Boolean;
        }
        container group-items {
            list UserGroup-list {
                key "groupName";

                // Added containment: Prefix=group
                // Acquired From Package snmp
                uses snmp_UserGroup-group;
            }
        }
    }

    grouping snmp_UserGroup-group {

        // Group name
        // Type is an MO-Defined-Type
        leaf groupName {
            description "snmp-server user name";

            // Type is an MO-Defined-Type
            type snmp_hostNameT;
        }
    }

    grouping syslog_Acct-group {
        leaf timerTick {
            type uint32;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }
    }

    grouping syslog_Syslog-group {

        container timestamp-items {

            // Added containment as a singleton: Prefix=timestamp
            // Acquired From Package syslog
            uses syslog_TimeStamp-group;
        }
        container level-items {
            list Level-list {
                key "facility";

                // Added containment: Prefix=level
                // Acquired From Package syslog
                uses syslog_Level-group;
            }
        }

        container monitor-items {

            // Added containment as a singleton: Prefix=monitor
            // Acquired From Package syslog
            uses syslog_TermMonitor-group;
        }

        container console-items {

            // Added containment as a singleton: Prefix=console
            // Acquired From Package syslog
            uses syslog_Console-group;
        }
        container rdst-items {
            list RemoteDest-list {
                key "host";

                // Added containment: Prefix=rdst
                // Acquired From Package syslog
                uses syslog_RemoteDest-group;
            }
        }

        container source-items {

            // Added containment as a singleton: Prefix=source
            // Acquired From Package syslog
            uses syslog_SourceInterface-group;
        }

        container file-items {

            // Added containment as a singleton: Prefix=file
            // Acquired From Package syslog
            uses syslog_File-group;
        }

        container inst-items {

            // Added containment as a singleton: Prefix=inst
            // Acquired From Package syslog
            uses syslog_Inst-group;
        }
    }

    grouping syslog_TimeStamp-group {

        // Type is an MO-Defined-Type
        leaf format {
            description "Format";

            // Type is an MO-Defined-Type
            type syslog_TimeStampFormat;
        }
    }

    grouping syslog_Level-group {

        // Type is an MO-Defined-Type
        leaf facility {
            description "Facility Name";

            // Type is an MO-Defined-Type
            type syslog_Facility;
        }

        // Type is an MO-Defined-Type
        // Default value handled in local MO type
        leaf severity {
            description "Severity";

            // Type is a Local-MO-Defined-Type
            type syslog_Severity_Level_severity;
        }
    }

    grouping syslog_TermMonitor-group {

        // Type is an MO-Defined-Type
        leaf adminState {
            description "TBD";

            // Type is an MO-Defined-Type
            type mon_AdminState;
        }

        // Type is an MO-Defined-Type
        leaf severity {
            description "Severity";

            // Type is an MO-Defined-Type
            type syslog_Severity;
        }
    }

    grouping syslog_SourceInterface-group {

        // Type is an MO-Defined-Type
        leaf adminState {
            description "TBD";

            // Type is an MO-Defined-Type
            type mon_AdminState;
        }

        // Type is an MO-Defined-Type
        leaf ifName {
            description "Interface";

            // Type is an MO-Defined-Type
            type nw_IfId;
        }

        // Type is an MO-Defined-Type
        leaf operState {
            config "false";
            description "TBD";

            // Type is an MO-Defined-Type
            type syslog_OperState;
        }
    }

    grouping syslog_Inst-group {

        // Type is an MO-Defined-Type
        leaf modAdminState {
            description "TBD";

            // Type is an MO-Defined-Type
            type mon_AdminState;
        }

        // Type is an MO-Defined-Type
        leaf modSeverity {
            description "Severity level";

            // Type is an MO-Defined-Type
            type syslog_Severity;
        }
    }

    grouping nat_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        container inst-items {

            // Added containment as a singleton: Prefix=inst
            // Acquired From Package nat
            uses nat_Inst-group;
        }
    }

    grouping nat_Inst-group {

        // Holds TCP Timer values
        // Type is an MO-Defined-Type
        leaf tcpTimeout {
            description "NAT tcp timeout values ";

            // Type is an MO-Defined-Type
            type nat_NatTimeout;
        }

        // Holds UDP Timer values
        // Type is an MO-Defined-Type
        leaf udpTimeout {
            description "NAT udp timeout value";

            // Type is an MO-Defined-Type
            type nat_NatTimeout;
        }

        // Holds DYN Timerout value
        // Type is an MO-Defined-Type
        leaf timeout {
            description "NAT timeout value";

            // Type is an MO-Defined-Type
            type nat_NatTimeout;
        }

        // Type is an MO-Defined-Type
        leaf maxtranslation {
            description "NAT max trasnaltions";

            // Type is an MO-Defined-Type
            type nat_NatMaxTranslation;
        }

        // Type is an MO-Defined-Type
        leaf allhost {
            description "NAT max trasnaltions all host";

            // Type is an MO-Defined-Type
            type nat_NatMaxTranslationAllHost;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
        container pool-items {
            list Pool-list {
                key "poolname";

                // Added containment: Prefix=pool
                // Acquired From Package nat
                uses nat_Pool-group;
            }
        }
    }

    grouping nat_Pool-group {

        // Properties Starts here
        // Type is an MO-Defined-Type
        leaf poolname {
            description "NAT pool name";

            // Type is an MO-Defined-Type
            type nat_NatPoolname;
        }
        leaf mask {
            type address_Ip;
        }

        // Type is an MO-Defined-Type
        leaf prefixlen {
            description "NAT prefix len";

            // Type is an MO-Defined-Type
            type nat_NatPrefixType;
        }

        // Type is an MO-Defined-Type
        leaf noalias {
            description "NAT no alias";

            // Type is an MO-Defined-Type
            type nat_booltype;
        }
        container startip-items {
            list PoolAddress-list {
                key "startip endip";

                // Added containment: Prefix=startip
                // Acquired From Package nat
                uses nat_PoolAddress-group;
            }
        }
    }

    grouping nat_PoolAddress-group {
        leaf startip {
            type address_Ip;
        }
        leaf endip {
            type address_Ip;
        }

        // Type is an MO-Defined-Type
        leaf configErr {
            config "false";
            description "Config error pool address";

            // Type is an MO-Defined-Type
            type nat_ConfigErrNat;
        }

        // Type is an MO-Defined-Type
        leaf castToModify {
            description "Cast to Modify";

            // Type is an MO-Defined-Type
            type nat_booltype;
        }

        // Type is an MO-Defined-Type
        leaf poolAddrDeleted {
            config "false";
            description "Pool address deleted";

            // Type is an MO-Defined-Type
            type nat_booltype;
        }
    }

    grouping opflex_ODevCmdReq-group {
        leaf req {
            config "false";
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }
        leaf devId {
            config "false";
            type uint32;
        }
        leaf sessId {
            config "false";
            type uint32;
        }
        leaf cmdId {
            config "false";
            type uint32;
        }
    }

    grouping opflex_ODevCmdResp-group {
        leaf resp {
            config "false";
            type string;
        }

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }
        leaf devId {
            config "false";
            type uint32;
        }
        leaf sessId {
            config "false";
            type uint32;
        }
        leaf cmdId {
            config "false";
            type uint32;
        }
    }

    grouping ospf_Entity-group {

        // Inherited From nw:Conn
        // Modified by Override: nw:CpEntity->name
        // Modified by Override: ospf:AEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per ospf instance information
        container inst-items {
            list Inst-list {
                key "name";

                // Added containment: Prefix=inst
                // Acquired From Package ospf
                uses ospf_Inst-group;
            }
        }

        // This object holds ospf information that is operated at a
        // interface level
        container if-items {
            list InternalIf-list {
                config "false";
                key "id instanceid";

                // Added containment: Prefix=if
                // Acquired From Package ospf
                uses ospf_InternalIf-group;
            }
        }
    }

    grouping ospf_Inst-group {

        // Inherited From nw:Conn
        // Modified by Override: nw:CpInst->name
        // Modified by Override: ospf:AInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Modified by Override: ospf:AInst->ctrl
        // Type is an MO-Defined-Type
        // Default value handled in local MO type
        leaf ctrl {
            description "Controls";

            // Type is a Local-MO-Defined-Type
            type nw_InstCtrl_Inst_ctrl;
        }

        // Operational errors qualifier
        // Inherited From nw:CpInst
        // Type is an MO-Defined-Type
        leaf operErr {
            config "false";
            description "Operational Errors Qualifier";

            // Type is an MO-Defined-Type
            type nw_OperErrQual;
        }

        // Memory alert level
        // Inherited From ospf:AInst
        // Type is an MO-Defined-Type
        leaf memAlert {
            config "false";
            description "Memory Alert Level";

            // Type is an MO-Defined-Type
            type nw_MemAlertLevel;
        }
        leaf deletedViaCLI {
            config "false";
            type boolean;
        }

        // This objects hold per ospf domain (vrf) information
        container dom-items {
            list Dom-list {
                key "name";

                // Added containment: Prefix=dom
                // Acquired From Package ospf
                uses ospf_Dom-group;
            }
        }

        // This object holds the size of the Logfiles for
        // various types of OSPF events
        container evtlogs-items {
            list EventLogs-list {
                key "eventType";

                // Added containment: Prefix=evtlogs
                // Acquired From Package ospf
                uses ospf_EventLogs-group;
            }
        }
    }

    grouping ospf_Dom-group {

        // Inherited From nw:Conn
        // Modified by Override: nw:CpDom->name
        // Modified by Override: ospf:ADom->name
        // Type is an MO-Defined-Type
        leaf name {
            description "Name";

            // Type is an MO-Defined-Type
            type naming_Name {
                length "1..64";
            }
        }

        // Router id for this domain, if this is not specified
        // the router-id is automatically picked up based on the
        // first interface that comes up in that domain
        // Inherited From ospf:ADom
        // Type is an MO-Defined-Type
        leaf rtrId {
            description "Router ID";

            // Type is an MO-Defined-Type
            type ip_RtrId;
        }

        // Dom controls
        // Inherited From ospf:ADom
        // Type is an MO-Defined-Type
        leaf ctrl {
            description "Controls";

            // Type is an MO-Defined-Type
            type ospf_DomControl;
        }

        // Admin state
        // Inherited From ospf:ADom
        // Type is an MO-Defined-Type
        leaf adminSt {
            description "Administrative state";

            // Type is an MO-Defined-Type
            type nw_AdminSt;
        }

        // Administrative distance preference
        // Inherited From ospf:ADom
        // Type is an MO-Defined-Type
        leaf dist {
            description "Distance";

            // Type is an MO-Defined-Type
            type ospf_Dist;
        }

        // MAX ECMP
        // Inherited From ospf:ADom
        // Type is an MO-Defined-Type
        leaf maxEcmp {
            description "Max ECMP";

            // Type is an MO-Defined-Type
            type ospf_Ecmp;
        }

        // Bandwidth Reference value. If bwRefUnit is mbps, then the
        // range is 1 to 4000000 and if bwRefUnit is gbps, then the
        // range is 1 to 4000
        // Inherited From ospf:ADom
        // Type is an MO-Defined-Type
        leaf bwRef {
            description "Bandwidth Reference value";

            // Type is an MO-Defined-Type
            type ospf_BwRef;
        }

        // Bandwidth Reference Unit
        // Inherited From ospf:ADom
        // Type is an MO-Defined-Type
        leaf bwRefUnit {
            description "Bandwidth Reference Unit (Mbps or Gbps)";

            // Type is an MO-Defined-Type
            type ospf_BwRefUnit;
        }

        // Default Metric for redistributed routes
        // Inherited From ospf:ADom
        // Type is an MO-Defined-Type
        leaf defMetric {
            description "Default metric cost";

            // Type is an MO-Defined-Type
            type ospf_Metric;
        }
        leaf rfc1583Compat {
            type boolean;
        }
        leaf deletedViaCLI {
            config "false";
            type boolean;
        }

        // Adjacency change logging level
        // Inherited From ospf:ADom
        // Type is an MO-Defined-Type
        leaf adjChangeLogLevel {
            description "Adjacency change logging level";

            // Type is an MO-Defined-Type
            type ospf_AdjChangeLogLevel;
        }

        // L3VM Operational state
        // Inherited From ospf:ADom
        // Type is an MO-Defined-Type
        leaf operSt {
            config "false";
            description "L3vm Operational State";

            // Type is an MO-Defined-Type
            type ospf_OperSt;
        }

        // Operational Router id for this dom, if it is not specified
        // the router-id is automatically picked up based on the
        // first interface that comes up in that domain
        // Inherited From ospf:ADom
        // Type is an MO-Defined-Type
        leaf operRtrId {
            config "false";
            description "Operational Router ID";

            // Type is an MO-Defined-Type
            type ip_RtrId;
        }

        // Discard Route Bits
        // Inherited From ospf:ADom
        // Type is an MO-Defined-Type
        leaf discardRoute {
            description "Ctrl bits for discard-route external and internal";

            // Type is an MO-Defined-Type
            type ospf_DiscardRoute;
        }
        leaf downbitIgnore {
            type boolean;
        }

        // Capability vrf-lite
        // Inherited From ospf:ADom
        // Type is an MO-Defined-Type
        leaf capVrfLite {
            description "capability vrf-lite";

            // Type is an MO-Defined-Type
            type ospf_VrfLiteControl;
        }

        // This object holds ospf information that is operated at a
        // interface level
        container area-items {
            list Area-list {
                key "id";

                // Added containment: Prefix=area
                // Acquired From Package ospf
                uses ospf_Area-group;
            }
        }

        // OSPF databases
        container db-items {
            list Db-list {
                config "false";
                key "type";

                // Added containment: Prefix=db
                // Acquired From Package ospf
                uses ospf_Db-group;
            }
        }

        // This object holds spf computation frequency controls, none
        // of these need to be exposed to the user
        container spfcomp-items {

            // Added containment as a singleton: Prefix=spfcomp
            // Acquired From Package ospf
            uses ospf_SpfComp-group;
        }

        // This object holds lsa related frequency controls, none of
        // these need to be exposed to the user
        container lsactrl-items {

            // Added containment as a singleton: Prefix=lsactrl
            // Acquired From Package ospf
            uses ospf_LsaCtrl-group;
        }

        // This object holds the ospf dom related statistics
        container domstats-items {

            // Added containment as a singleton: Prefix=domstats
            // Acquired From Package ospf
            uses ospf_DomStats-group;
        }

        // This objects hold per domain graceful restart information
        container gr-items {

            // Added containment as a singleton: Prefix=gr
            // Acquired From Package ospf
            uses ospf_Gr-group;
        }

        // This object holds ospf information that is operated at a
        // interface level
        container if-items {
            list If-list {
                key "id";

                // Added containment: Prefix=if
                // Acquired From Package ospf
                uses ospf_If-group;
            }
        }

        // This object holds per domain max-lsa information
        container maxlsap-items {

            // Added containment as a singleton: Prefix=maxlsap
            // Acquired From Package ospf
            uses ospf_MaxLsaP-group;
        }

        // This object holds per domain max-lsa information
        container maxmetriclsap-items {

            // Added containment as a singleton: Prefix=maxmetriclsap
            // Acquired From Package ospf
            uses ospf_MaxMetricLsaP-group;
        }

        // This objects holds default route leak policy,
        // this is not needed for FCS in our solution
        container defrtleak-items {

            // Added containment as a singleton: Prefix=defrtleak
            // Acquired From Package ospf
            uses ospf_DefRtLeakP-group;
        }

        // Inter protocol route leak policy. This defines distribution
        // of routes from other protocols to ospf
        container interleak-items {
            list InterLeakP-list {
                key "proto inst asn";

                // Added containment: Prefix=interleak
                // Acquired From Package ospf
                uses ospf_InterLeakP-group;
            }
        }

        // Leak controls related to the number of routes leaked
        container leakctrl-items {

            // Added containment as a singleton: Prefix=leakctrl
            // Acquired From Package ospf
            uses ospf_LeakCtrlP-group;
        }

        container ribleak-items {

            // Added containment as a singleton: Prefix=ribleak
            // Acquired From Package ospf
            uses ospf_RibLeakP-group;
        }

        // External route summarization is specific to external
        // routes that are injected into OSPF using route leak.
        // Configure external route summarization on ASBRs that
        // are leaking routes into OSPF
        container extrtsum-items {
            list ExtRtSum-list {
                key "addr";

                // Added containment: Prefix=extrtsum
                // Acquired From Package ospf
                uses ospf_ExtRtSum-group;
            }
        }

        // This object holds the ospf traffic related information
        container trstats-items {

            // Added containment as a singleton: Prefix=trstats
            // Acquired From Package ospf
            uses ospf_TrafficStats-group;
        }
    }

    grouping ospf_Area-group {

        // Inherited From nw:Conn
        // Modified by Override: nw:CpDom->name
        // Modified by Override: ospf:AArea->name
        // Type is an MO-Defined-Type
        leaf name {
            description "Name";

            // Type is an MO-Defined-Type
            type naming_Name {
                length "1..64";
            }
        }

        // Area id
        // Inherited From ospf:AArea
        // Type is an MO-Defined-Type
        leaf id {
            description "ID";

            // Type is an MO-Defined-Type
            type ospf_AreaId;
        }

        // Area type (stub | nssa | backbone, etc)
        // Inherited From ospf:AArea
        // Type is an MO-Defined-Type
        leaf type {
            description "Type";

            // Type is an MO-Defined-Type
            type ospf_AreaT;
        }

        // Area controls
        // Inherited From ospf:AArea
        // Type is an MO-Defined-Type
        leaf ctrl {
            description "Controls";

            // Type is an MO-Defined-Type
            type ospf_AreaControl;
        }

        // Area cost, specifies cost for default summary LSAs.
        // Used with nssa/stub area types. Not applicable in
        // our fabric solution
        // Inherited From ospf:AArea
        // Type is an MO-Defined-Type
        leaf cost {
            description "Cost";

            // Type is an MO-Defined-Type
            type ospf_AreaCost;
        }

        // NSSA translator role
        // Inherited From ospf:AArea
        // Type is an MO-Defined-Type
        leaf nssaTransRole {
            description "NSSA Translator Role";

            // Type is an MO-Defined-Type
            type ospf_NssaTransRole;
        }

        // Border router count
        // Inherited From ospf:AArea
        // Type is an MO-Defined-Type
        leaf brCnt {
            config "false";
            description "Area Border Router Count";

            // Type is an MO-Defined-Type
            type ospf_BrCnt;
        }

        // AS Border router count
        // Inherited From ospf:AArea
        // Type is an MO-Defined-Type
        leaf asbrCnt {
            config "false";
            description "AS Border Router Count";

            // Type is an MO-Defined-Type
            type ospf_AsbrCnt;
        }

        // LSA checksum sum
        // Inherited From ospf:AArea
        // Type is an MO-Defined-Type
        leaf lsaCksumSum {
            config "false";
            description "LSA Checksum Sum";

            // Type is an MO-Defined-Type
            type ospf_LsaCksumSum;
        }

        // NSSA translator state
        // Inherited From ospf:AArea
        // Type is an MO-Defined-Type
        leaf nssaTransSt {
            config "false";
            description "NSSA Translator State";

            // Type is an MO-Defined-Type
            type ospf_NssaTransSt;
        }

        // NSSA translator stability interval
        // Inherited From ospf:AArea
        // Type is an MO-Defined-Type
        leaf nssaTransStabIntvl {
            config "false";
            description "NSSA Translator Stability Interval";

            // Type is an MO-Defined-Type
            type ospf_NssaTransStabIntvl;
        }

        // Authentication type
        // Inherited From ospf:AArea
        // Type is an MO-Defined-Type
        leaf authType {
            description "Type";

            // Type is an MO-Defined-Type
            type ospf_AuthT;
        }

        // This object holds the ospf area related statistics
        container areastats-items {

            // Added containment as a singleton: Prefix=areastats
            // Acquired From Package ospf
            uses ospf_AreaStats-group;
        }

        // OSPF databases
        container db-items {
            list Db-list {
                config "false";
                key "type";

                // Added containment: Prefix=db
                // Acquired From Package ospf
                uses ospf_Db-group;
            }
        }

        // This object holds ospf information about OSPF virtual
        // links
        container vlink-items {
            list VLink-list {
                key "nbrRtrId";

                // Added containment: Prefix=vlink
                // Acquired From Package ospf
                uses ospf_VLink-group;
            }
        }

        // This object holds ospf information about OSPF sham
        // links
        container slink-items {
            list SLink-list {
                config "false";
                key "srcAddr dstAddr";

                // Added containment: Prefix=slink
                // Acquired From Package ospf
                uses ospf_SLink-group;
            }
        }

        // Lsa Leak concrete class.
        container lsaleakp-items {

            // Added containment as a singleton: Prefix=lsaleakp
            // Acquired From Package ospf
            uses ospf_LsaLeakP-group;
        }

        // Lsa Leak Control concrete class.
        container lsaleakctrlp-items {
            list LsaLeakCtrlP-list {
                key "dir";

                // Added containment: Prefix=lsaleakctrlp
                // Acquired From Package ospf
                uses ospf_LsaLeakCtrlP-group;
            }
        }

        // This objects holds default route leak policy,
        // this is not needed for FCS in our solution
        container defrtleak-items {

            // Added containment as a singleton: Prefix=defrtleak
            // Acquired From Package ospf
            uses ospf_DefRtLeakP-group;
        }

        // Inter-area route summarization. This is configured
        // on ABRs, summarizing routes between areas in the
        // autonomous system
        container iartsum-items {
            list InterAreaRtSum-list {
                key "addr";

                // Added containment: Prefix=iartsum
                // Acquired From Package ospf
                uses ospf_InterAreaRtSum-group;
            }
        }
    }

    grouping ospf_AreaStats-group {
        leaf areaCreatedTs {
            config "false";
            type uint64;
        }

        // Number of SPF runs
        // Inherited From ospf:AAreaStats
        // Type is an MO-Defined-Type
        leaf spfRuns {
            config "false";
            description "SPF Runs";

            // Type is an MO-Defined-Type
            type ospf_Counter32;
        }

        // LSA count
        // Inherited From ospf:AAreaStats
        // Type is an MO-Defined-Type
        leaf lsaCnt {
            config "false";
            description "LSA Count";

            // Type is an MO-Defined-Type
            type ospf_Counter32;
        }
        leaf lastSpfDuration {
            config "false";
            type uint32;
        }

        // Total number of interfaces
        // Inherited From ospf:AAreaStats
        // Type is an MO-Defined-Type
        leaf ifCnt {
            config "false";
            description "Interface Count";

            // Type is an MO-Defined-Type
            type ospf_Counter32;
        }

        // Number of active interfaces
        // Inherited From ospf:AAreaStats
        // Type is an MO-Defined-Type
        leaf activeIfCnt {
            config "false";
            description "Active Interface Count";

            // Type is an MO-Defined-Type
            type ospf_Counter32;
        }

        // Number of passive interfaces
        // Inherited From ospf:AAreaStats
        // Type is an MO-Defined-Type
        leaf passiveIfCnt {
            config "false";
            description "Passive Interface Count";

            // Type is an MO-Defined-Type
            type ospf_Counter32;
        }

        // Number of loopback interfaces
        // Inherited From ospf:AAreaStats
        // Type is an MO-Defined-Type
        leaf lpbkIfCnt {
            config "false";
            description "Loopback Interface Count";

            // Type is an MO-Defined-Type
            type ospf_Counter32;
        }

        // Number of adjacency
        // Inherited From ospf:AAreaStats
        // Type is an MO-Defined-Type
        leaf adjCnt {
            config "false";
            description "Adjacency Count";

            // Type is an MO-Defined-Type
            type ospf_Counter32;
        }

        // Number of peers in hitless helper mode
        // Inherited From ospf:AAreaStats
        // Type is an MO-Defined-Type
        leaf grHelperPeerCnt {
            config "false";
            description "GR Helper Peer Count";

            // Type is an MO-Defined-Type
            type ospf_Counter32;
        }
    }

    grouping ospf_Db-group {

        // Inherited From nw:Conn
        // Modified by Override: nw:Db->name
        // Type is an MO-Defined-Type
        leaf name {
            description "Name";

            // Type is an MO-Defined-Type
            type naming_Name {
                length "1..64";
            }
        }

        // Type of the repository
        // Inherited From ospf:ADb
        // Type is an MO-Defined-Type
        leaf type {
            config "false";
            description "Type";

            // Type is an MO-Defined-Type
            type ospf_DbT;
        }

        // LSA records
        container lsa-items {
            list LsaRec-list {
                config "false";
                key "type id advRtr";

                // Added containment: Prefix=lsa
                // Acquired From Package ospf
                uses ospf_LsaRec-group;
            }
        }

        // This object holds the ospf route information
        container rt-items {
            list Route-list {
                config "false";
                key "pfx";

                // Added containment: Prefix=rt
                // Acquired From Package ospf
                uses ospf_Route-group;
            }
        }
    }

    grouping ospf_LsaRec-group {

        // Inherited From nw:Conn
        // Modified by Override: nw:DbRec->name
        // Type is an MO-Defined-Type
        leaf name {
            description "Name";

            // Type is an MO-Defined-Type
            type naming_Name {
                length "1..64";
            }
        }

        // Lsa type
        // Inherited From ospf:ALsaRec
        // Type is an MO-Defined-Type
        leaf type {
            config "false";
            description "Type";

            // Type is an MO-Defined-Type
            type ospf_LsaT;
        }

        // Lsa id
        // Inherited From ospf:ALsaRec
        // Type is an MO-Defined-Type
        leaf id {
            config "false";
            description "ID";

            // Type is an MO-Defined-Type
            type ospf_LsaId;
        }

        // Router id
        // Inherited From ospf:ALsaRec
        // Type is an MO-Defined-Type
        leaf advRtr {
            config "false";
            description "Advertising Router";

            // Type is an MO-Defined-Type
            type ospf_LsaAdvRtr;
        }

        // Sequence number
        // Inherited From ospf:ALsaRec
        // Type is an MO-Defined-Type
        leaf seq {
            config "false";
            description "Sequence Number";

            // Type is an MO-Defined-Type
            type ospf_LsaSeq;
        }

        // Age
        // Inherited From ospf:ALsaRec
        // Type is an MO-Defined-Type
        leaf age {
            config "false";
            description "Age";

            // Type is an MO-Defined-Type
            type ospf_LsaAge;
        }
        leaf arrivalTs {
            config "false";
            type uint64;
        }

        // Checksum
        // Inherited From ospf:ALsaRec
        // Type is an MO-Defined-Type
        leaf cksum {
            config "false";
            description "Checksum";

            // Type is an MO-Defined-Type
            type ospf_LsaCksum;
        }

        // Advertisement
        // Inherited From ospf:ALsaRec
        // Type is an MO-Defined-Type
        leaf advert {
            config "false";
            description "LSA Advertisement";

            // Type is an MO-Defined-Type
            type ospf_LsaAdvert;
        }
    }

    grouping ospf_Route-group {

        // Inherited From nw:Conn
        // Modified by Override: nw:DbRec->name
        // Type is an MO-Defined-Type
        leaf name {
            description "Name";

            // Type is an MO-Defined-Type
            type naming_Name {
                length "1..64";
            }
        }
        leaf pfx {
            config "false";
            type address_Ip;
        }

        // Path type
        // Inherited From ospf:ARoute
        // Type is an MO-Defined-Type
        leaf pathT {
            config "false";
            description "Path Type";

            // Type is an MO-Defined-Type
            type ospf_PathT;
        }

        // Area id
        // Inherited From ospf:ARoute
        // Type is an MO-Defined-Type
        leaf area {
            config "false";
            description "Area ID";

            // Type is an MO-Defined-Type
            type ospf_AreaId;
        }

        // Flags
        // Inherited From ospf:ARoute
        // Type is an MO-Defined-Type
        leaf flags {
            config "false";
            description "Flags";

            // Type is an MO-Defined-Type
            type ospf_RtFlags;
        }

        // Unicast cost
        // Inherited From ospf:ARoute
        // Type is an MO-Defined-Type
        leaf ucastCost {
            config "false";
            description "Unicast Cost";

            // Type is an MO-Defined-Type
            type ospf_RtCost;
        }

        // Multicast cost
        // Inherited From ospf:ARoute
        // Type is an MO-Defined-Type
        leaf mcastCost {
            config "false";
            description "Multicast Cost";

            // Type is an MO-Defined-Type
            type ospf_RtCost;
        }

        // Route Tag
        // Inherited From ospf:ARoute
        // Type is an MO-Defined-Type
        leaf tag {
            config "false";
            description "Route Tag";

            // Type is an MO-Defined-Type
            type ospf_RtTag;
        }

        // Administrative distance preference
        // Inherited From ospf:ARoute
        // Type is an MO-Defined-Type
        leaf dist {
            config "false";
            description "Distance";

            // Type is an MO-Defined-Type
            type ospf_Dist;
        }

        // Unicast nexthop
        container ucnh-items {
            list UcNexthop-list {
                config "false";
                key "if addr";

                // Added containment: Prefix=ucnh
                // Acquired From Package ospf
                uses ospf_UcNexthop-group;
            }
        }

        // Multicast nexthop
        container mcnh-items {
            list McNexthop-list {
                config "false";
                key "if addr";

                // Added containment: Prefix=mcnh
                // Acquired From Package ospf
                uses ospf_McNexthop-group;
            }
        }
    }

    grouping ospf_UcNexthop-group {

        // Inherited From nw:Conn
        // Modified by Override: nw:DbRec->name
        // Type is an MO-Defined-Type
        leaf name {
            description "Name";

            // Type is an MO-Defined-Type
            type naming_Name {
                length "1..64";
            }
        }

        // Nexhop interface
        // Inherited From ospf:ANexthop
        // Type is an MO-Defined-Type
        leaf if {
            config "false";
            description "Interface";

            // Type is an MO-Defined-Type
            type nw_IfId;
        }
        leaf addr {
            config "false";
            type address_Ip;
        }

        // Flags
        // Inherited From ospf:ANexthop
        // Type is an MO-Defined-Type
        leaf flags {
            config "false";
            description "Flags";

            // Type is an MO-Defined-Type
            type ospf_NhFlags;
        }
    }

    grouping ospf_McNexthop-group {

        // Inherited From nw:Conn
        // Modified by Override: nw:DbRec->name
        // Type is an MO-Defined-Type
        leaf name {
            description "Name";

            // Type is an MO-Defined-Type
            type naming_Name {
                length "1..64";
            }
        }

        // Nexhop interface
        // Inherited From ospf:ANexthop
        // Type is an MO-Defined-Type
        leaf if {
            config "false";
            description "Interface";

            // Type is an MO-Defined-Type
            type nw_IfId;
        }
        leaf addr {
            config "false";
            type address_Ip;
        }

        // Flags
        // Inherited From ospf:ANexthop
        // Type is an MO-Defined-Type
        leaf flags {
            config "false";
            description "Flags";

            // Type is an MO-Defined-Type
            type ospf_NhFlags;
        }
    }

    grouping ospf_VLink-group {

        // Router id associated with virtual link neighbor
        // Inherited From ospf:AVLink
        // Type is an MO-Defined-Type
        leaf nbrRtrId {
            description "Router ID";

            // Type is an MO-Defined-Type
            type ip_RtrId;
        }

        // Hello interval, interval between hello packets that
        // OSPF sends on the interface
        // From Interface ospf:IIntfIntvl
        // Inherited From ospf:AVLink
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:AVLink
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:AVLink
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:AVLink
        // Type is an MO-Defined-Type
        leaf xmitDelay {
            description "Transmit Delay";

            // Type is an MO-Defined-Type
            type ospf_XmitDelay;
        }

        // This object holds ospf neighbor information
        container adj-items {
            list AdjEp-list {
                config "false";
                key "id";

                // Added containment: Prefix=adj
                // Acquired From Package ospf
                uses ospf_AdjEp-group;
            }
        }

        // This object holds authentication new policy information
        container authnew-items {

            // Added containment as a singleton: Prefix=authnew
            // Acquired From Package ospf
            uses ospf_AuthNewP-group;
        }
    }

    grouping ospf_AdjEp-group {

        // Inherited From nw:Conn
        // Modified by Override: nw:Ep->name
        // Type is an MO-Defined-Type
        leaf name {
            description "Name";

            // Type is an MO-Defined-Type
            type naming_Name {
                length "1..64";
            }
        }

        // Neighbor's router id
        // Inherited From ospf:AAdjEp
        // Type is an MO-Defined-Type
        leaf id {
            config "false";
            description "ID";

            // Type is an MO-Defined-Type
            type ospf_AdjId;
        }

        // Neighbor's interface id
        // Inherited From ospf:AAdjEp
        // Type is an MO-Defined-Type
        leaf ifId {
            config "false";
            description "Interface ID";

            // Type is an MO-Defined-Type
            type ospf_AdjIfId;
        }

        // Adjacency state
        // Inherited From ospf:AAdjEp
        // Type is an MO-Defined-Type
        leaf operSt {
            config "false";
            description "Operational State";

            // Type is an MO-Defined-Type
            type ospf_AdjOperSt;
        }

        // BFD state
        // Inherited From ospf:AAdjEp
        // Type is an MO-Defined-Type
        leaf bfdSt {
            config "false";
            description "BFD State";

            // Type is an MO-Defined-Type
            type ospf_BfdOperSt;
        }

        // Area id
        // Inherited From ospf:AAdjEp
        // Type is an MO-Defined-Type
        leaf area {
            config "false";
            description "Area ID";

            // Type is an MO-Defined-Type
            type ospf_AreaId;
        }

        // Neighbor priority
        // Inherited From ospf:AAdjEp
        // Type is an MO-Defined-Type
        leaf prio {
            config "false";
            description "Priority";

            // Type is an MO-Defined-Type
            type ospf_DesigPrio;
        }

        // Designated router address
        // Inherited From ospf:AAdjEp
        // Type is an MO-Defined-Type
        leaf dr {
            config "false";
            description "Designated Router";

            // Type is an MO-Defined-Type
            type ospf_DesigAddr;
        }

        // Backup designated router address
        // Inherited From ospf:AAdjEp
        // Type is an MO-Defined-Type
        leaf bdr {
            config "false";
            description "Backup Designated Router";

            // Type is an MO-Defined-Type
            type ospf_DesigAddr;
        }
        leaf peerIp {
            config "false";
            type address_Ip;
        }

        // Peer options from hello packet
        // Inherited From ospf:AAdjEp
        // Type is an MO-Defined-Type
        leaf helloOptions {
            config "false";
            description "Hello Options";

            // Type is an MO-Defined-Type
            type ospf_Options;
        }

        // Peer options from DBD packet
        // Inherited From ospf:AAdjEp
        // Type is an MO-Defined-Type
        leaf dbdOptions {
            config "false";
            description "DBD Options";

            // Type is an MO-Defined-Type
            type ospf_Options;
        }

        // Flags
        // Inherited From ospf:AAdjEp
        // Type is an MO-Defined-Type
        leaf flags {
            config "false";
            description "Flags";

            // Type is an MO-Defined-Type
            type ospf_AdjFlags;
        }
        leaf peerName {
            config "false";
            type string;
        }

        // This object holds the ospf neighbor related statistics
        container adjstats-items {

            // Added containment as a singleton: Prefix=adjstats
            // Acquired From Package ospf
            uses ospf_AdjStats-group;
        }

        // This object holds ospf graceful restart operational
        // information
        container gr-items {

            // Added containment as a singleton: Prefix=gr
            // Acquired From Package ospf
            uses ospf_GrSt-group;
        }
    }

    grouping ospf_AdjStats-group {

        // State change count
        // Inherited From ospf:AAdjStats
        // Type is an MO-Defined-Type
        leaf stChgCnt {
            config "false";
            description "State Change Count";

            // Type is an MO-Defined-Type
            type ospf_Counter32;
        }
        leaf lastStChgTs {
            config "false";
            type uint64;
        }
        leaf lastNonHelloPktTs {
            config "false";
            type uint64;
        }

        // DBD Sequence number
        // Inherited From ospf:AAdjStats
        // Type is an MO-Defined-Type
        leaf dbdSeqNum {
            config "false";
            description "DBD Sequence Number";

            // Type is an MO-Defined-Type
            type ospf_Counter32;
        }

        // Number of LSAs on request list
        // Inherited From ospf:AAdjStats
        // Type is an MO-Defined-Type
        leaf reqLsaCnt {
            config "false";
            description "Request LSA Count";

            // Type is an MO-Defined-Type
            type ospf_Counter32;
        }

        // Outstanding LSAs from last request
        // Inherited From ospf:AAdjStats
        // Type is an MO-Defined-Type
        leaf outstandingLsaCnt {
            config "false";
            description "Outstanding LSA Count";

            // Type is an MO-Defined-Type
            type ospf_Counter32;
        }

        // Number of retransmissions of LSA request
        // Inherited From ospf:AAdjStats
        // Type is an MO-Defined-Type
        leaf lsaReqRexmitCnt {
            config "false";
            description "LSA Request Retransmission Count";

            // Type is an MO-Defined-Type
            type ospf_Counter32;
        }
        leaf deadTimerExpTs {
            config "false";
            type uint64;
        }
    }

    grouping ospf_GrSt-group {

        // Peer restart helper Status
        // Inherited From ospf:AGrSt
        // Type is an MO-Defined-Type
        leaf helperSt {
            config "false";
            description "Peer Restart Helper Status";

            // Type is an MO-Defined-Type
            type ospf_HelperSt;
        }

        // Peer restart helper age
        // Inherited From ospf:AGrSt
        // Type is an MO-Defined-Type
        leaf helperAge {
            config "false";
            description "Peer Restart Helper Age";

            // Type is an MO-Defined-Type
            type ospf_HelperAge;
        }

        // Peer restart helper exit qualifier
        // Inherited From ospf:AGrSt
        // Type is an MO-Defined-Type
        leaf helperExitQual {
            config "false";
            description "Peer Restart Helper Exit Qualifier";

            // Type is an MO-Defined-Type
            type ospf_HelperExitQual;
        }
    }

    grouping ospf_AuthNewP-group {

        // Authentication type
        // Type is an MO-Defined-Type
        leaf type {
            description "Type";

            // Type is an MO-Defined-Type
            type ospf_AuthT;
        }

        // Authentication key id
        // Type is an MO-Defined-Type
        leaf keyId {
            description "Key ID";

            // Type is an MO-Defined-Type
            type ospf_AuthKeyId;
        }

        // Authentication key
        // Type is an MO-Defined-Type
        leaf key {
            description "Key";

            // Type is an MO-Defined-Type
            type ospf_AuthKey;
        }
        leaf keySecureMode {
            type boolean;
            default "true";
        }

        // Authentication md5 key
        // Type is an MO-Defined-Type
        leaf md5key {
            description "Key";

            // Type is an MO-Defined-Type
            type ospf_AuthKey;
        }
        leaf md5keySecureMode {
            type boolean;
            default "true";
        }
        leaf keychain {
            type string;
        }

        // From Interface naming:Named
        // Inherited From naming:NamedObject
        // Modified by Override: ospf:AuthNewP->name
        // Modified by Override: pol:Obj->name
        // Type is an MO-Defined-Type
        leaf name {
            description "Name";

            // Type is an MO-Defined-Type
            type naming_Name {
                length "0..64";
            }
        }

        // From Interface naming:Described
        // Inherited From pol:Instr
        // Modified by Override: ospf:AuthNewP->descr
        // Type is an MO-Defined-Type
        leaf descr {
            config "false";
            description "Description";

            // Type is an MO-Defined-Type
            type naming_Descr;
        }
    }

    grouping ospf_SLink-group {
        leaf srcAddr {
            config "false";
            type address_Ip;
        }
        leaf dstAddr {
            config "false";
            type address_Ip;
        }
        leaf demandCkt {
            config "false";
            type boolean;
        }

        // Hello interval, interval between hello packets that
        // OSPF sends on the interface
        // From Interface ospf:IIntfIntvl
        // Inherited From ospf:ASLink
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:ASLink
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:ASLink
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:ASLink
        // Type is an MO-Defined-Type
        leaf xmitDelay {
            description "Transmit Delay";

            // Type is an MO-Defined-Type
            type ospf_XmitDelay;
        }

        // Cost of the interface
        // From Interface ospf:IIntfCost
        // Inherited From ospf:ASLink
        // Type is an MO-Defined-Type
        leaf cost {
            description "Cost";

            // Type is an MO-Defined-Type
            type ospf_IfCost;
        }

        // This object holds authentication new policy information
        container authnew-items {

            // Added containment as a singleton: Prefix=authnew
            // Acquired From Package ospf
            uses ospf_AuthNewP-group;
        }
    }

    grouping ospf_LsaLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Type is an MO-Defined-Type
        leaf scope {
            description "Scope";

            // Type is an MO-Defined-Type
            type rtleak_Scope;
        }
        leaf rtMap {
            type string;
        }

        // Operational state
        // Inherited From ospf:ALsaLeakP
        // Type is an MO-Defined-Type
        leaf operSt {
            config "false";
            description "Operational State";

            // Type is an MO-Defined-Type
            type ospf_LsaLeakOperSt;
        }
    }

    grouping ospf_LsaLeakCtrlP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Type is an MO-Defined-Type
        leaf scope {
            description "Scope";

            // Type is an MO-Defined-Type
            type rtleak_Scope;
        }
        leaf rtMap {
            type string;
        }

        // Inherited From ospf:ALsaLeakCtrlP
        // Type is an MO-Defined-Type
        leaf dir {
            description "Filter Type";

            // Type is an MO-Defined-Type
            type rtleak_RtCtrlDir;
        }

        // Operational state
        // Inherited From ospf:ALsaLeakCtrlP
        // Type is an MO-Defined-Type
        leaf operSt {
            config "false";
            description "Operational State";

            // Type is an MO-Defined-Type
            type ospf_LsaLeakOperSt;
        }
    }

    grouping ospf_DefRtLeakP-group {

        // From Interface naming:Named
        // Inherited From naming:NamedObject
        // Modified by Override: pol:Obj->name
        // Modified by Override: ospf:ADefRtLeakP->name
        // Type is an MO-Defined-Type
        leaf name {
            description "Name";

            // Type is an MO-Defined-Type
            type naming_Name {
                length "0..64";
            }
        }

        // From Interface naming:Described
        // Inherited From pol:Instr
        // Modified by Override: ospf:ADefRtLeakP->descr
        // Type is an MO-Defined-Type
        leaf descr {
            config "false";
            description "Description";

            // Type is an MO-Defined-Type
            type naming_Descr;
        }

        // Scope of the policy (intra protocol, inter protcol,
        // default route)
        // Inherited From rtleak:LeakP
        // Modified by Override: rtleak:DefRtLeakP->scope
        // Type is an MO-Defined-Type
        leaf scope {
            description "Scope";

            // Type is an MO-Defined-Type
            type rtleak_Scope;
        }
        leaf rtMap {
            type string {
            }
        }

        // DefRtLeak always advertise
        // Inherited From ospf:ADefRtLeakP
        // Type is an MO-Defined-Type
        leaf always {
            description "Always advertise default leak";

            // Type is an MO-Defined-Type
            type ospf_Always;
        }
    }

    grouping ospf_InterAreaRtSum-group {

        // From Interface naming:Named
        // Inherited From naming:NamedObject
        // Modified by Override: pol:Obj->name
        // Modified by Override: ospf:ARtSum->name
        // Type is an MO-Defined-Type
        leaf name {
            description "Name";

            // Type is an MO-Defined-Type
            type naming_Name {
                length "0..64";
            }
        }

        // From Interface naming:Described
        // Inherited From pol:Instr
        // Modified by Override: ospf:ARtSum->descr
        // Type is an MO-Defined-Type
        leaf descr {
            config "false";
            description "Description";

            // Type is an MO-Defined-Type
            type naming_Descr;
        }
        leaf addr {
            type address_Ip;
        }

        // Summary address no Advertise
        // Inherited From ospf:ARtSum
        // Type is an MO-Defined-Type
        leaf ctrl {
            description "Controls";

            // Type is an MO-Defined-Type
            type ospf_SumControl;
        }

        // Number of component routes
        // Inherited From ospf:ARtSum
        // Type is an MO-Defined-Type
        leaf compRtCnt {
            config "false";
            description "Number of component routes";

            // Type is an MO-Defined-Type
            type nw_Counter32;
        }

        // Route summary cost
        // Inherited From ospf:ARtSum
        // Type is an MO-Defined-Type
        leaf operCost {
            config "false";
            description "Route Summary Operational Cost";

            // Type is an MO-Defined-Type
            type ospf_SumCost;
        }

        // Area range cost
        // Inherited From ospf:AInterAreaRtSum
        // Type is an MO-Defined-Type
        leaf cost {
            description "Area range cost";

            // Type is an MO-Defined-Type
            type ospf_SumCost;
        }
    }

    grouping ospf_SpfComp-group {

        // From Interface naming:Named
        // Inherited From naming:NamedObject
        // Modified by Override: pol:Obj->name
        // Modified by Override: ospf:ASpfComp->name
        // Type is an MO-Defined-Type
        leaf name {
            description "Name";

            // Type is an MO-Defined-Type
            type naming_Name {
                length "0..64";
            }
        }

        // From Interface naming:Described
        // Inherited From pol:Instr
        // Modified by Override: ospf:ASpfComp->descr
        // Type is an MO-Defined-Type
        leaf descr {
            config "false";
            description "Description";

            // Type is an MO-Defined-Type
            type naming_Descr;
        }

        // Initial spf schedule delay interval
        // Inherited From ospf:ASpfComp
        // Type is an MO-Defined-Type
        leaf initIntvl {
            description "Initial Interval";

            // Type is an MO-Defined-Type
            type ospf_SpfCompInitIntvl;
        }

        // Minimum hold time between spf calculations
        // Inherited From ospf:ASpfComp
        // Type is an MO-Defined-Type
        leaf holdIntvl {
            description "Hold Interval";

            // Type is an MO-Defined-Type
            type ospf_SpfCompHoldIntvl;
        }

        // Maximum wait time between spf calculations
        // Inherited From ospf:ASpfComp
        // Type is an MO-Defined-Type
        leaf maxIntvl {
            description "Maximum Interval";

            // Type is an MO-Defined-Type
            type ospf_SpfCompMaxIntvl;
        }
    }

    grouping ospf_LsaCtrl-group {

        // From Interface naming:Named
        // Inherited From naming:NamedObject
        // Modified by Override: pol:Obj->name
        // Modified by Override: ospf:ALsaCtrl->name
        // Type is an MO-Defined-Type
        leaf name {
            description "Name";

            // Type is an MO-Defined-Type
            type naming_Name {
                length "0..64";
            }
        }

        // From Interface naming:Described
        // Inherited From pol:Instr
        // Modified by Override: ospf:ALsaCtrl->descr
        // Type is an MO-Defined-Type
        leaf descr {
            config "false";
            description "Description";

            // Type is an MO-Defined-Type
            type naming_Descr;
        }

        // LSA group pacing interval
        // Inherited From ospf:ALsaCtrl
        // Type is an MO-Defined-Type
        leaf gpPacingIntvl {
            description "Group Pacing Interval";

            // Type is an MO-Defined-Type
            type ospf_LsaGpPacingIntvl;
        }

        // Minimum interval between arrival of a LSA
        // Inherited From ospf:ALsaCtrl
        // Type is an MO-Defined-Type
        leaf arrivalIntvl {
            description "Arrival Interval";

            // Type is an MO-Defined-Type
            type ospf_LsaArrivalIntvl;
        }

        // LSA generation throttle start wait interval
        // Inherited From ospf:ALsaCtrl
        // Type is an MO-Defined-Type
        leaf startIntvl {
            description "Start Interval";

            // Type is an MO-Defined-Type
            type ospf_LsaThStartIntvl;
        }

        // LSA generation throttle hold interval
        // Inherited From ospf:ALsaCtrl
        // Type is an MO-Defined-Type
        leaf holdIntvl {
            description "Hold Interval";

            // Type is an MO-Defined-Type
            type ospf_LsaThHoldIntvl;
        }

        // LSA generation throttle maximum interval
        // Inherited From ospf:ALsaCtrl
        // Type is an MO-Defined-Type
        leaf maxIntvl {
            description "Maximum Interval";

            // Type is an MO-Defined-Type
            type ospf_LsaThMaxIntvl;
        }
    }

    grouping ospf_DomStats-group {

        // Interface count
        // Inherited From ospf:ADomStats
        // Type is an MO-Defined-Type
        leaf ifCnt {
            config "false";
            description "Interface Count";

            // Type is an MO-Defined-Type
            type ospf_Counter32;
        }

        // Area count
        // Inherited From ospf:ADomStats
        // Type is an MO-Defined-Type
        leaf areaCnt {
            config "false";
            description "Area Count";

            // Type is an MO-Defined-Type
            type ospf_Counter32;
        }

        // Stub area count
        // Inherited From ospf:ADomStats
        // Type is an MO-Defined-Type
        leaf stubAreaCnt {
            config "false";
            description "Stub Area Count";

            // Type is an MO-Defined-Type
            type ospf_Counter32;
        }

        // NSSA area count
        // Inherited From ospf:ADomStats
        // Type is an MO-Defined-Type
        leaf nssaAreaCnt {
            config "false";
            description "NSSA Area Count";

            // Type is an MO-Defined-Type
            type ospf_Counter32;
        }

        // External area count
        // Inherited From ospf:ADomStats
        // Type is an MO-Defined-Type
        leaf extAreaCnt {
            config "false";
            description "External Area Count";

            // Type is an MO-Defined-Type
            type ospf_Counter32;
        }

        // Active stub area count
        // Inherited From ospf:ADomStats
        // Type is an MO-Defined-Type
        leaf activeStubAreaCnt {
            config "false";
            description "Active Stub Area Count";

            // Type is an MO-Defined-Type
            type ospf_Counter32;
        }

        // Active NSSA area count
        // Inherited From ospf:ADomStats
        // Type is an MO-Defined-Type
        leaf activeNssaAreaCnt {
            config "false";
            description "Active NSSA Area Count";

            // Type is an MO-Defined-Type
            type ospf_Counter32;
        }

        // Active external area count
        // Inherited From ospf:ADomStats
        // Type is an MO-Defined-Type
        leaf activeExtAreaCnt {
            config "false";
            description "Active External Area Count";

            // Type is an MO-Defined-Type
            type ospf_Counter32;
        }

        // Active Area count
        // Inherited From ospf:ADomStats
        // Type is an MO-Defined-Type
        leaf activeAreaCnt {
            config "false";
            description "Active Area Count";

            // Type is an MO-Defined-Type
            type ospf_Counter32;
        }
        leaf lastStatsClearTs {
            config "false";
            type uint64;
        }

        // Neighbor count
        // Inherited From ospf:ADomStats
        // Type is an MO-Defined-Type
        leaf peerCnt {
            config "false";
            description "Peer Count";

            // Type is an MO-Defined-Type
            type ospf_Counter32;
        }

        // External LSA count
        // Inherited From ospf:ADomStats
        // Type is an MO-Defined-Type
        leaf extLsaCnt {
            config "false";
            description "External LSA Count";

            // Type is an MO-Defined-Type
            type ospf_Counter32;
        }

        // Opaque AS LSA count
        // Inherited From ospf:ADomStats
        // Type is an MO-Defined-Type
        leaf opaqueAsLsaCnt {
            config "false";
            description "Opaque AS LSA Count";

            // Type is an MO-Defined-Type
            type ospf_Counter32;
        }

        // Total AS LSA count
        // Inherited From ospf:ADomStats
        // Type is an MO-Defined-Type
        leaf totalAsLsaCnt {
            config "false";
            description "Total AS LSA Count";

            // Type is an MO-Defined-Type
            type ospf_Counter32;
        }

        // New LSA Rx count
        // Inherited From ospf:ADomStats
        // Type is an MO-Defined-Type
        leaf newLsaRxCnt {
            config "false";
            description "New LSA Rx Count";

            // Type is an MO-Defined-Type
            type ospf_Counter32;
        }

        // New LSA Tx count
        // Inherited From ospf:ADomStats
        // Type is an MO-Defined-Type
        leaf newLsaTxCnt {
            config "false";
            description "New LSA Tx Count";

            // Type is an MO-Defined-Type
            type ospf_Counter32;
        }

        // Area Border Router Status
        // Inherited From ospf:ADomStats
        // Type is an MO-Defined-Type
        leaf areaBdrRtr {
            config "false";
            description "Area Border Router";

            // Type is an MO-Defined-Type
            type ospf_AreaBdrRtr;
        }

        // ASBR Router Status
        // Inherited From ospf:ADomStats
        // Type is an MO-Defined-Type
        leaf asBdrRtr {
            config "false";
            description "Autonomous System Boundary Router";

            // Type is an MO-Defined-Type
            type ospf_ASBdrRtr;
        }
    }

    grouping ospf_Gr-group {

        // From Interface naming:Named
        // Inherited From naming:NamedObject
        // Modified by Override: pol:Obj->name
        // Modified by Override: ospf:AGr->name
        // Type is an MO-Defined-Type
        leaf name {
            description "Name";

            // Type is an MO-Defined-Type
            type naming_Name {
                length "0..64";
            }
        }

        // From Interface naming:Described
        // Inherited From pol:Instr
        // Modified by Override: ospf:AGr->descr
        // Type is an MO-Defined-Type
        leaf descr {
            config "false";
            description "Description";

            // Type is an MO-Defined-Type
            type naming_Descr;
        }

        // Graceful restart controls
        // Inherited From ospf:AGr
        // Type is an MO-Defined-Type
        leaf ctrl {
            description "Control";

            // Type is an MO-Defined-Type
            type ospf_GrCtrl;
        }
        leaf helper {
            type boolean;
            default "true";
        }

        // Graceful restart period
        // Inherited From ospf:AGr
        // Type is an MO-Defined-Type
        leaf gracePeriod {
            description "Control";

            // Type is an MO-Defined-Type
            type ospf_GrPeriod;
        }

        // Graceful restart status
        // Inherited From ospf:AGr
        // Type is an MO-Defined-Type
        leaf restartStatus {
            config "false";
            description "Restart Status";

            // Type is an MO-Defined-Type
            type ospf_RestartStatus;
        }
        leaf restartAge {
            config "false";
            type uint32;
        }

        // Graceful restart exit reason
        // Inherited From ospf:AGr
        // Type is an MO-Defined-Type
        leaf restartExitReason {
            config "false";
            description "Restart Exit Reason";

            // Type is an MO-Defined-Type
            type ospf_RestartExitReason;
        }
    }

    grouping ospf_If-group {

        // Inherited From nw:Conn
        // Modified by Override: nw:Ep->name
        // Modified by Override: ospf:AIf->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: ospf:AIf->descr
        // Type is an MO-Defined-Type
        leaf descr {
            config "false";
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ospf:AIf
        // Type is an MO-Defined-Type
        leaf ctrl {
            description "Controls";

            // Type is an MO-Defined-Type
            type ospf_IfControl;
        }

        // Passive interface control
        // Inherited From ospf:AIf
        // Type is an MO-Defined-Type
        leaf passiveCtrl {
            description "Passive Interface Control";

            // Type is an MO-Defined-Type
            type ospf_PassiveControl;
        }

        // BFD control
        // Inherited From ospf:AIf
        // Type is an MO-Defined-Type
        leaf bfdCtrl {
            description "BFD Control";

            // Type is an MO-Defined-Type
            type ospf_BfdControl;
        }

        // Network type
        // Inherited From ospf:AIf
        // Type is an MO-Defined-Type
        leaf nwT {
            description "Network Type";

            // Type is an MO-Defined-Type
            type ospf_NwT;
        }

        // Priority, used in determining the designated router on
        // this network
        // Inherited From ospf:AIf
        // Type is an MO-Defined-Type
        leaf prio {
            description "Priority";

            // Type is an MO-Defined-Type
            type ospf_DesigPrio;
        }

        // Area to which this interface belongs to
        // Inherited From ospf:AIf
        // Type is an MO-Defined-Type
        leaf area {
            description "Area ID";

            // Type is an MO-Defined-Type
            type ospf_AreaId;
        }
        leaf advertiseSecondaries {
            type boolean;
            default "true";
        }

        // Operational state
        // Inherited From ospf:AIf
        // Type is an MO-Defined-Type
        leaf operSt {
            config "false";
            description "Operational State";

            // Type is an MO-Defined-Type
            type ospf_IfOperSt;
        }

        // Operational failed state qualifier
        // Inherited From ospf:AIf
        // Type is an MO-Defined-Type
        leaf failStQual {
            config "false";
            description "Failed State Qualifier";

            // Type is an MO-Defined-Type
            type ospf_FailStQual;
        }

        // Interface type
        // Inherited From ospf:AIf
        // Type is an MO-Defined-Type
        leaf type {
            config "false";
            description "Type";

            // Type is an MO-Defined-Type
            type ospf_IfType;
        }

        // Flags
        // Inherited From ospf:AIf
        // Type is an MO-Defined-Type
        leaf flags {
            config "false";
            description "Flags";

            // Type is an MO-Defined-Type
            type ospf_IfFlags;
        }
        leaf addr {
            config "false";
            type address_Ip;
        }
        leaf dr {
            config "false";
            type address_Ip;
        }
        leaf bdr {
            config "false";
            type address_Ip;
        }

        // Designated router id
        // Inherited From ospf:AIf
        // Type is an MO-Defined-Type
        leaf drId {
            config "false";
            description "DR Id";

            // Type is an MO-Defined-Type
            type ip_RtrId;
        }

        // Backup designated router id
        // Inherited From ospf:AIf
        // Type is an MO-Defined-Type
        leaf bdrId {
            config "false";
            description "BDR Id";

            // Type is an MO-Defined-Type
            type ip_RtrId;
        }

        // LSA checksum sum
        // Inherited From ospf:AIf
        // Type is an MO-Defined-Type
        leaf lsaCksumSum {
            config "false";
            description "LSA Checksum Sum";

            // Type is an MO-Defined-Type
            type ospf_LsaCksumSum;
        }

        // Operational Cost
        // Inherited From ospf:AIf
        // Type is an MO-Defined-Type
        leaf operCost {
            config "false";
            description "Operational Cost";

            // Type is an MO-Defined-Type
            type ospf_IfCost;
        }

        // Operational Dead interval
        // Inherited From ospf:AIf
        // Type is an MO-Defined-Type
        leaf operDeadIntvl {
            config "false";
            description "Operational Dead Interval";

            // Type is an MO-Defined-Type
            type ospf_DeadIntvl;
        }

        // Hello interval, interval between hello packets that
        // OSPF sends on the interface
        // From Interface ospf:IIntfIntvl
        // Inherited From ospf:AIf
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:AIf
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:AIf
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:AIf
        // Type is an MO-Defined-Type
        leaf xmitDelay {
            description "Transmit Delay";

            // Type is an MO-Defined-Type
            type ospf_XmitDelay;
        }

        // Cost of the interface
        // From Interface ospf:IIntfCost
        // Inherited From ospf:AIf
        // Type is an MO-Defined-Type
        leaf cost {
            description "Cost";

            // Type is an MO-Defined-Type
            type ospf_IfCost;
        }

        // This object holds ospf neighbor information
        container adj-items {
            list AdjEp-list {
                config "false";
                key "id";

                // Added containment: Prefix=adj
                // Acquired From Package ospf
                uses ospf_AdjEp-group;
            }
        }

        // This object holds authentication policy information
        container auth-items {

            // Added containment as a singleton: Prefix=auth
            // Acquired From Package ospf
            uses ospf_AuthP-group;
        }

        // This object holds authentication new policy information
        container authnew-items {

            // Added containment as a singleton: Prefix=authnew
            // Acquired From Package ospf
            uses ospf_AuthNewP-group;
        }

        // OSPF databases
        container db-items {
            list Db-list {
                config "false";
                key "type";

                // Added containment: Prefix=db
                // Acquired From Package ospf
                uses ospf_Db-group;
            }
        }

        // This object holds the ospf interface related statistics
        container ifstats-items {

            // Added containment as a singleton: Prefix=ifstats
            // Acquired From Package ospf
            uses ospf_IfStats-group;
        }

        // This object holds multi-area information
        // at a interface level
        container multiarea-items {
            list MultiArea-list {
                key "multiareaid";

                // Added containment: Prefix=multiarea
                // Acquired From Package ospf
                uses ospf_MultiArea-group;
            }
        }

        // This object holds the ospf traffic related information
        container trstats-items {

            // Added containment as a singleton: Prefix=trstats
            // Acquired From Package ospf
            uses ospf_TrafficStats-group;
        }

        // Rel-def target from IfDefToOspfIf
        // Inherited From ospf:If
        container rtospfIfDefToOspfIf-items {

            // Abstract containment of rtospfIfDefToOspfIf derived from ospf:If
            list RtOspfIfDefToOspfIf-list {
                config "false";
                key "tDn";

                // Added containment: Prefix=rtospfIfDefToOspfIf
                // Acquired From Package ospf
                uses ospf_RtOspfIfDefToOspfIf_target-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ospf_AuthP-group {

        // Authentication type
        // Type is an MO-Defined-Type
        leaf type {
            description "Type";

            // Type is an MO-Defined-Type
            type ospf_AuthT;
        }

        // Authentication key id
        // Type is an MO-Defined-Type
        leaf keyId {
            description "Key ID";

            // Type is an MO-Defined-Type
            type ospf_AuthKeyId;
        }

        // Authentication key
        // Type is an MO-Defined-Type
        leaf key {
            description "Key";

            // Type is an MO-Defined-Type
            type ospf_AuthKey;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping ospf_IfStats-group {

        // If events count
        // Inherited From ospf:AIfStats
        // Type is an MO-Defined-Type
        leaf evCnt {
            config "false";
            description "If Events Count";

            // Type is an MO-Defined-Type
            type ospf_Counter32;
        }

        // LSA count
        // Inherited From ospf:AIfStats
        // Type is an MO-Defined-Type
        leaf lsaCnt {
            config "false";
            description "LSA Count";

            // Type is an MO-Defined-Type
            type ospf_Counter32;
        }

        // Neighbor count
        // Inherited From ospf:AIfStats
        // Type is an MO-Defined-Type
        leaf peerCnt {
            config "false";
            description "Peer Count";

            // Type is an MO-Defined-Type
            type ospf_Counter32;
        }

        // Flood to neighbor count
        // Inherited From ospf:AIfStats
        // Type is an MO-Defined-Type
        leaf floodToPeerCnt {
            config "false";
            description "Flood To Peer Count";

            // Type is an MO-Defined-Type
            type ospf_Counter32;
        }

        // Number of adjacency
        // Inherited From ospf:AIfStats
        // Type is an MO-Defined-Type
        leaf adjCnt {
            config "false";
            description "Adjacency Count";

            // Type is an MO-Defined-Type
            type ospf_Counter32;
        }

        // Number of peers in hitless helper mode
        // Inherited From ospf:AIfStats
        // Type is an MO-Defined-Type
        leaf grHelperPeerCnt {
            config "false";
            description "GR Helper Peer Count";

            // Type is an MO-Defined-Type
            type ospf_Counter32;
        }
    }

    grouping ospf_MultiArea-group {

        // Multi Area id
        // Inherited From ospf:AMultiArea
        // Type is an MO-Defined-Type
        leaf multiareaid {
            description "Multi Area ID";

            // Type is an MO-Defined-Type
            type ospf_AreaId;
        }
    }

    grouping ospf_TrafficStats-group {

        // Total packets received
        // Inherited From ospf:ATrafficStats
        // Type is an MO-Defined-Type
        leaf totalPktsRcvd {
            config "false";
            description "Total Packets Received";

            // Type is an MO-Defined-Type
            type ospf_Counter32;
        }

        // Hello packets received
        // Inherited From ospf:ATrafficStats
        // Type is an MO-Defined-Type
        leaf helloPktsRcvd {
            config "false";
            description "Hello Packets Received";

            // Type is an MO-Defined-Type
            type ospf_Counter32;
        }

        // Database description packets received
        // Inherited From ospf:ATrafficStats
        // Type is an MO-Defined-Type
        leaf dbdPktsRcvd {
            config "false";
            description "DBD Packets Received";

            // Type is an MO-Defined-Type
            type ospf_Counter32;
        }

        // Link-state request packets received
        // Inherited From ospf:ATrafficStats
        // Type is an MO-Defined-Type
        leaf lsReqPktsRcvd {
            config "false";
            description "LSREQ Packets Received";

            // Type is an MO-Defined-Type
            type ospf_Counter32;
        }

        // Link-state update packets received
        // Inherited From ospf:ATrafficStats
        // Type is an MO-Defined-Type
        leaf lsUpdPktsRcvd {
            config "false";
            description "LSU Packets Received";

            // Type is an MO-Defined-Type
            type ospf_Counter32;
        }

        // Link-state ack packets received
        // Inherited From ospf:ATrafficStats
        // Type is an MO-Defined-Type
        leaf lsAckPktsRcvd {
            config "false";
            description "LSACK Packets Received";

            // Type is an MO-Defined-Type
            type ospf_Counter32;
        }

        // Received packets dropped
        // Inherited From ospf:ATrafficStats
        // Type is an MO-Defined-Type
        leaf rcvdPktsDropped {
            config "false";
            description "Received Packets Dropped";

            // Type is an MO-Defined-Type
            type ospf_Counter32;
        }

        // Error packets rcvd
        // Inherited From ospf:ATrafficStats
        // Type is an MO-Defined-Type
        leaf errPktsRcvd {
            config "false";
            description "Error Packets Received";

            // Type is an MO-Defined-Type
            type ospf_Counter32;
        }

        // Error hello packets received
        // Inherited From ospf:ATrafficStats
        // Type is an MO-Defined-Type
        leaf errHelloPktsRcvd {
            config "false";
            description "Error Hello Packets Received";

            // Type is an MO-Defined-Type
            type ospf_Counter32;
        }

        // Error database description packets received
        // Inherited From ospf:ATrafficStats
        // Type is an MO-Defined-Type
        leaf errDbdPktsRcvd {
            config "false";
            description "Error DBD Packets Received";

            // Type is an MO-Defined-Type
            type ospf_Counter32;
        }

        // Error link-state request packets received
        // Inherited From ospf:ATrafficStats
        // Type is an MO-Defined-Type
        leaf errLsReqPktsRcvd {
            config "false";
            description "Error LSREQ Packets Received";

            // Type is an MO-Defined-Type
            type ospf_Counter32;
        }

        // Error link-state update packets received
        // Inherited From ospf:ATrafficStats
        // Type is an MO-Defined-Type
        leaf errLsUpdPktsRcvd {
            config "false";
            description "Error LSU Packets Received";

            // Type is an MO-Defined-Type
            type ospf_Counter32;
        }

        // Error link-state ack packets received
        // Inherited From ospf:ATrafficStats
        // Type is an MO-Defined-Type
        leaf errLsAckPktsRcvd {
            config "false";
            description "Error LSACK Packets Received";

            // Type is an MO-Defined-Type
            type ospf_Counter32;
        }

        // Unknown packets received
        // Inherited From ospf:ATrafficStats
        // Type is an MO-Defined-Type
        leaf unknownPktsRcvd {
            config "false";
            description "Unknown Packets Received";

            // Type is an MO-Defined-Type
            type ospf_Counter32;
        }

        // Duplicate routerid packets received
        // Inherited From ospf:ATrafficStats
        // Type is an MO-Defined-Type
        leaf dupRtrIdPktsRcvd {
            config "false";
            description "Duplicate RouterId Packets Received";

            // Type is an MO-Defined-Type
            type ospf_Counter32;
        }

        // Duplicate source addr packets received
        // Inherited From ospf:ATrafficStats
        // Type is an MO-Defined-Type
        leaf dupSrcAddrPktsRcvd {
            config "false";
            description "Duplicate Source Addr Packets Received";

            // Type is an MO-Defined-Type
            type ospf_Counter32;
        }

        // Wrong area packets received
        // Inherited From ospf:ATrafficStats
        // Type is an MO-Defined-Type
        leaf wrongAreaPktsRcvd {
            config "false";
            description "Wrong Area Packets Received";

            // Type is an MO-Defined-Type
            type ospf_Counter32;
        }

        // Invalid source addr packets received
        // Inherited From ospf:ATrafficStats
        // Type is an MO-Defined-Type
        leaf invalidSrcAddrPktsRcvd {
            config "false";
            description "Invalid Source Addr Packets Received";

            // Type is an MO-Defined-Type
            type ospf_Counter32;
        }

        // Invalid destination addr packets received
        // Inherited From ospf:ATrafficStats
        // Type is an MO-Defined-Type
        leaf invalidDestAddrPktsRcvd {
            config "false";
            description "Invalid Destination Addr Packets Received";

            // Type is an MO-Defined-Type
            type ospf_Counter32;
        }

        // Bad CRC packets received
        // Inherited From ospf:ATrafficStats
        // Type is an MO-Defined-Type
        leaf badCRCPktsRcvd {
            config "false";
            description "Bad CRC Packets Received";

            // Type is an MO-Defined-Type
            type ospf_Counter32;
        }

        // Bad version packets received
        // Inherited From ospf:ATrafficStats
        // Type is an MO-Defined-Type
        leaf badVersionPktsRcvd {
            config "false";
            description "Bad Version Packets Received";

            // Type is an MO-Defined-Type
            type ospf_Counter32;
        }

        // Bad reserved fields packets received
        // Inherited From ospf:ATrafficStats
        // Type is an MO-Defined-Type
        leaf badResvFieldPktsRcvd {
            config "false";
            description "Bad Reserved Field Packets Received";

            // Type is an MO-Defined-Type
            type ospf_Counter32;
        }

        // Changed neighbor routerId or ip address packets received
        // Inherited From ospf:ATrafficStats
        // Type is an MO-Defined-Type
        leaf peerRtrIdChgdPktsRcvd {
            config "false";
            description "Peer RouterId Changed Packets Received";

            // Type is an MO-Defined-Type
            type ospf_Counter32;
        }

        // Non hello received packets for which neighbor is not found
        // Inherited From ospf:ATrafficStats
        // Type is an MO-Defined-Type
        leaf peerNotFoundPktsRcvd {
            config "false";
            description "Peer Not Found Packets Received";

            // Type is an MO-Defined-Type
            type ospf_Counter32;
        }

        // Authentication failed packets received
        // Inherited From ospf:ATrafficStats
        // Type is an MO-Defined-Type
        leaf badAuthPktsRcvd {
            config "false";
            description "Bad Authentication Packets Received";

            // Type is an MO-Defined-Type
            type ospf_Counter32;
        }

        // Bad length packets received
        // Inherited From ospf:ATrafficStats
        // Type is an MO-Defined-Type
        leaf badLenPktsRcvd {
            config "false";
            description "Bad Length Packets Received";

            // Type is an MO-Defined-Type
            type ospf_Counter32;
        }

        // Packets received on passive interface
        // Inherited From ospf:ATrafficStats
        // Type is an MO-Defined-Type
        leaf passiveIntfPktsRcvd {
            config "false";
            description "Passive Interface Packets Received";

            // Type is an MO-Defined-Type
            type ospf_Counter32;
        }

        // Packets received on OSPF not enabled interface
        // Inherited From ospf:ATrafficStats
        // Type is an MO-Defined-Type
        leaf noOspfIntfPktsRcvd {
            config "false";
            description "No OSPF Interface Packets Received";

            // Type is an MO-Defined-Type
            type ospf_Counter32;
        }

        // Received LSA packets ignored
        // Inherited From ospf:ATrafficStats
        // Type is an MO-Defined-Type
        leaf rcvdLsaPktsIgnored {
            config "false";
            description "Received LSA Packets Ignored";

            // Type is an MO-Defined-Type
            type ospf_Counter32;
        }

        // Number of LSA packets dropped during SPF run
        // Inherited From ospf:ATrafficStats
        // Type is an MO-Defined-Type
        leaf droppedLsaPktsWhileSPF {
            config "false";
            description "LSA Packets Dropped During SPF";

            // Type is an MO-Defined-Type
            type ospf_Counter32;
        }

        // Number of LSA packets dropped during graceful restart
        // Inherited From ospf:ATrafficStats
        // Type is an MO-Defined-Type
        leaf droppedLsaPktsWhileGR {
            config "false";
            description "LSA Packets Dropped During GR";

            // Type is an MO-Defined-Type
            type ospf_Counter32;
        }

        // Total packets sent
        // Inherited From ospf:ATrafficStats
        // Type is an MO-Defined-Type
        leaf totalPktsSent {
            config "false";
            description "Total Packets Sent";

            // Type is an MO-Defined-Type
            type ospf_Counter32;
        }

        // Hello packets sent
        // Inherited From ospf:ATrafficStats
        // Type is an MO-Defined-Type
        leaf helloPktsSent {
            config "false";
            description "Hello Packets Sent";

            // Type is an MO-Defined-Type
            type ospf_Counter32;
        }

        // Database description packets sent
        // Inherited From ospf:ATrafficStats
        // Type is an MO-Defined-Type
        leaf dbdPktsSent {
            config "false";
            description "DBD Packets Sent";

            // Type is an MO-Defined-Type
            type ospf_Counter32;
        }

        // Link-state request packets sent
        // Inherited From ospf:ATrafficStats
        // Type is an MO-Defined-Type
        leaf lsReqPktsSent {
            config "false";
            description "LSREQ Packets Sent";

            // Type is an MO-Defined-Type
            type ospf_Counter32;
        }

        // Link-state update packets sent
        // Inherited From ospf:ATrafficStats
        // Type is an MO-Defined-Type
        leaf lsUpdPktsSent {
            config "false";
            description "LSU Packets Sent";

            // Type is an MO-Defined-Type
            type ospf_Counter32;
        }

        // Link-state ack packets sent
        // Inherited From ospf:ATrafficStats
        // Type is an MO-Defined-Type
        leaf lsAckPktsSent {
            config "false";
            description "LSACK Packets Sent";

            // Type is an MO-Defined-Type
            type ospf_Counter32;
        }

        // Dropped send packets
        // Inherited From ospf:ATrafficStats
        // Type is an MO-Defined-Type
        leaf droppedSendPkts {
            config "false";
            description "Dropped Send Packets";

            // Type is an MO-Defined-Type
            type ospf_Counter32;
        }

        // Error send packets
        // Inherited From ospf:ATrafficStats
        // Type is an MO-Defined-Type
        leaf errSendPkts {
            config "false";
            description "Error Send Packets";

            // Type is an MO-Defined-Type
            type ospf_Counter32;
        }

        // Unknown send packets
        // Inherited From ospf:ATrafficStats
        // Type is an MO-Defined-Type
        leaf unknownSendPkts {
            config "false";
            description "Unknown Send Packets";

            // Type is an MO-Defined-Type
            type ospf_Counter32;
        }

        // Number of first transmission of LSU packets
        // Inherited From ospf:ATrafficStats
        // Type is an MO-Defined-Type
        leaf lsuFirstTxPkts {
            config "false";
            description "LSU First Tx Packets";

            // Type is an MO-Defined-Type
            type ospf_Counter32;
        }

        // Number of retransmissions of LSU packets
        // Inherited From ospf:ATrafficStats
        // Type is an MO-Defined-Type
        leaf lsuRexmitPkts {
            config "false";
            description "LSU Retransmission Packets";

            // Type is an MO-Defined-Type
            type ospf_Counter32;
        }

        // Number of LSU packets sent in response to LSREQ packets
        // Inherited From ospf:ATrafficStats
        // Type is an MO-Defined-Type
        leaf lsuForLsreqPkts {
            config "false";
            description "LSU Packets For LSREQ Packets";

            // Type is an MO-Defined-Type
            type ospf_Counter32;
        }

        // Number of LSU packets sent to a neighbor specifically
        // Inherited From ospf:ATrafficStats
        // Type is an MO-Defined-Type
        leaf lsuPeerTxPkts {
            config "false";
            description "LSU Packets To Peer";

            // Type is an MO-Defined-Type
            type ospf_Counter32;
        }

        // Number of times flooding packets dropped due to IP queue throttling
        // Inherited From ospf:ATrafficStats
        // Type is an MO-Defined-Type
        leaf floodPktSendIpThrottle {
            config "false";
            description "Flood Packet Send IP Throttle";

            // Type is an MO-Defined-Type
            type ospf_Counter32;
        }

        // Number of times flooding packets dropped due to token throttling
        // Inherited From ospf:ATrafficStats
        // Type is an MO-Defined-Type
        leaf floodPktSendTokenThrottle {
            config "false";
            description "Flood Packet Send Token Throttle";

            // Type is an MO-Defined-Type
            type ospf_Counter32;
        }
        leaf lastStatsClearTs {
            config "false";
            type uint64;
        }
    }

    grouping ospf_MaxLsaP-group {

        // From Interface naming:Named
        // Inherited From naming:NamedObject
        // Modified by Override: pol:Obj->name
        // Modified by Override: ospf:AMaxLsaP->name
        // Type is an MO-Defined-Type
        leaf name {
            description "Name";

            // Type is an MO-Defined-Type
            type naming_Name {
                length "0..64";
            }
        }

        // From Interface naming:Described
        // Inherited From pol:Instr
        // Modified by Override: ospf:AMaxLsaP->descr
        // Type is an MO-Defined-Type
        leaf descr {
            description "Description";

            // Type is an MO-Defined-Type
            type naming_Descr;
        }

        // maximum number of non self-generated LSAs
        // Inherited From ospf:AMaxLsaP
        // Type is an MO-Defined-Type
        leaf maxLsa {
            description "Maximum # of non self-generated LSAs";

            // Type is an MO-Defined-Type
            type ospf_MaxLsa;
        }

        // Threshold value (%) at which to generate a warning message
        // Inherited From ospf:AMaxLsaP
        // Type is an MO-Defined-Type
        leaf thresh {
            description "Threshold";

            // Type is an MO-Defined-Type
            type ospf_MaxLsaThresh;
        }

        // Specifies the number of times the OSPF process can
        // consecutively be placed into the sleep state.
        // Inherited From ospf:AMaxLsaP
        // Type is an MO-Defined-Type
        leaf sleepCnt {
            description "Sleep Count";

            // Type is an MO-Defined-Type
            type ospf_SleepCnt;
        }

        // Specifies the time (in minutes) to ignore all neighbors after
        // the maximum limit of LSAs has been exceeded
        // Inherited From ospf:AMaxLsaP
        // Type is an MO-Defined-Type
        leaf sleepIntvl {
            description "Sleep Interval";

            // Type is an MO-Defined-Type
            type ospf_SleepIntvl;
        }

        // Specifies the time, in minutes, after which the
        // sleep count is reset to zero.
        // Inherited From ospf:AMaxLsaP
        // Type is an MO-Defined-Type
        leaf resetIntvl {
            description "Reset Interval";

            // Type is an MO-Defined-Type
            type ospf_ResetIntvl;
        }

        // Inherited From ospf:AMaxLsaP
        // Type is an MO-Defined-Type
        leaf action {
            description "Action";

            // Type is an MO-Defined-Type
            type ospf_MaxLsaAct;
        }

        // Inherited From ospf:AMaxLsaP
        // Type is an MO-Defined-Type
        leaf operSt {
            config "false";
            description "OperSt";

            // Type is an MO-Defined-Type
            type ospf_MaxLsaOperSt;
        }

        // Inherited From ospf:AMaxLsaP
        // Type is an MO-Defined-Type
        leaf operStQual {
            config "false";
            description "Operational State Qualifier";

            // Type is an MO-Defined-Type
            type ospf_MaxLsaOperStQual;
        }

        // Inherited From ospf:AMaxLsaP
        // Type is an MO-Defined-Type
        leaf nonSelfLsaCnt {
            config "false";
            description "Current # of non self-generated LSAs";

            // Type is an MO-Defined-Type
            type ospf_NonSelfLsaCnt;
        }

        // Inherited From ospf:AMaxLsaP
        // Type is an MO-Defined-Type
        leaf currSleepCnt {
            config "false";
            description "Current # of non self-generated LSAs";

            // Type is an MO-Defined-Type
            type ospf_CurrSleepCnt;
        }
    }

    grouping ospf_MaxMetricLsaP-group {

        // Max metric controls - specifies when to send max
        // metric LSAs and for which routes/links
        // Inherited From ospf:AMaxMetricLsaP
        // Type is an MO-Defined-Type
        leaf ctrl {
            description "Maximum Metric Controls";

            // Type is an MO-Defined-Type
            type ospf_MaxMetricControl;
        }

        // Max metric value to be used for external LSAs
        // Inherited From ospf:AMaxMetricLsaP
        // Type is an MO-Defined-Type
        leaf maxMetricExtLsa {
            description "Maximum metric value for external LSAs";

            // Type is an MO-Defined-Type
            type ospf_MaxMetric;
        }

        // Max metric value to be used for summary LSAs
        // Inherited From ospf:AMaxMetricLsaP
        // Type is an MO-Defined-Type
        leaf maxMetricSummLsa {
            description "Maximum metric value for summary LSAs";

            // Type is an MO-Defined-Type
            type ospf_MaxMetric;
        }

        // Time (in secs) for which max metric should be advertised
        // at startup
        // Inherited From ospf:AMaxMetricLsaP
        // Type is an MO-Defined-Type
        leaf startupIntvl {
            description "Startup interval";

            // Type is an MO-Defined-Type
            type ospf_StartupIntvl;
        }

        // At startup, advertise max metric until convergence of BGP ASN
        // Inherited From ospf:AMaxMetricLsaP
        // Type is an MO-Defined-Type
        leaf awaitConvBgpAsn {
            description "BGP ASN to wait for";

            // Type is an MO-Defined-Type
            type rtleak_Asn;
        }
    }

    grouping ospf_InterLeakP-group {

        // From Interface naming:Named
        // Inherited From naming:NamedObject
        // Modified by Override: pol:Obj->name
        // Modified by Override: ospf:AInterLeakP->name
        // Type is an MO-Defined-Type
        leaf name {
            description "Name";

            // Type is an MO-Defined-Type
            type naming_Name {
                length "0..64";
            }
        }

        // From Interface naming:Described
        // Inherited From pol:Instr
        // Modified by Override: ospf:AInterLeakP->descr
        // Type is an MO-Defined-Type
        leaf descr {
            config "false";
            description "Description";

            // Type is an MO-Defined-Type
            type naming_Descr;
        }

        // Scope of the policy (intra protocol, inter protcol,
        // default route)
        // Inherited From rtleak:LeakP
        // Modified by Override: rtleak:InterLeakP->scope
        // Type is an MO-Defined-Type
        leaf scope {
            description "Scope";

            // Type is an MO-Defined-Type
            type rtleak_Scope;
        }
        leaf rtMap {
            type string {
            }
        }

        // Protocol from where the routes are leaked
        // Inherited From rtleak:InterLeakP
        // Type is an MO-Defined-Type
        leaf proto {
            description "Protocol";

            // Type is an MO-Defined-Type
            type rtleak_Proto;
        }

        // Routing protocol instance, the routing instance of the
        // protocol from where the routes are being leaked
        // Inherited From rtleak:InterLeakP
        // Type is an MO-Defined-Type
        leaf inst {
            description "Instance";

            // Type is an MO-Defined-Type
            type rtleak_Inst;
        }

        // Leak BGP routes from this Autonomous System (AS)    <1-4294967295>|<1-65535>[.<0-65535>]  Autonomous system number
        // Inherited From rtleak:InterLeakP
        // Type is an MO-Defined-Type
        leaf asn {
            description "Autonomous System Number";

            // Type is an MO-Defined-Type
            type rtleak_Asn {
            }
        }

        // DefRtLeak always advertise
        // Inherited From ospf:AInterLeakP
        // Type is an MO-Defined-Type
        leaf always {
            description "Always advertise default leak";

            // Type is an MO-Defined-Type
            type ospf_Always;
        }
    }

    grouping ospf_LeakCtrlP-group {

        // From Interface naming:Named
        // Inherited From naming:NamedObject
        // Modified by Override: pol:Obj->name
        // Modified by Override: ospf:ALeakCtrlP->name
        // Type is an MO-Defined-Type
        leaf name {
            description "Name";

            // Type is an MO-Defined-Type
            type naming_Name {
                length "0..64";
            }
        }

        // From Interface naming:Described
        // Inherited From pol:Instr
        // Modified by Override: ospf:ALeakCtrlP->descr
        // Type is an MO-Defined-Type
        leaf descr {
            config "false";
            description "Description";

            // Type is an MO-Defined-Type
            type naming_Descr;
        }

        // Controls on what to do when the number of routes cross
        // the maximum route/prefix limit
        // Inherited From rtleak:LeakCtrlP
        // Type is an MO-Defined-Type
        leaf ctrl {
            description "Controls";

            // Type is an MO-Defined-Type
            type rtleak_Ctrl;
        }

        // Maximum limit on routes leaked
        // Inherited From rtleak:LeakCtrlP
        // Type is an MO-Defined-Type
        leaf max {
            description "Maximum Limit";

            // Type is an MO-Defined-Type
            type rtleak_MaxPfx;
        }

        // Threshold at which warning is issued when number of
        // routes crosses the threshold
        // Inherited From rtleak:LeakCtrlP
        // Type is an MO-Defined-Type
        leaf thresh {
            description "Threshold";

            // Type is an MO-Defined-Type
            type rtleak_Thresh;
        }

        // Maximum number of retries to retrieve the leaked routes,
        // this is applicable only when the routes are withdrawn
        // Inherited From rtleak:LeakCtrlP
        // Type is an MO-Defined-Type
        leaf retries {
            description "Retries";

            // Type is an MO-Defined-Type
            type rtleak_Retries;
        }

        // Duration between the retries
        // Inherited From rtleak:LeakCtrlP
        // Type is an MO-Defined-Type
        leaf duration {
            description "Duration";

            // Type is an MO-Defined-Type
            type rtleak_Duration;
        }
    }

    grouping ospf_RibLeakP-group {
        leaf rtMap {
            type string {
            }
        }

        // If always is set to false, only routes that are permitted
        // by the route map(rtMap) configuration are downloaded to the
        // routing information base (RIB).
        // Inherited From rtleak:RibLeakP
        // Type is an MO-Defined-Type
        leaf always {
            description "Filter routes into RIB";

            // Type is an MO-Defined-Type
            type rtleak_Always;
        }
    }

    grouping ospf_ExtRtSum-group {

        // From Interface naming:Named
        // Inherited From naming:NamedObject
        // Modified by Override: pol:Obj->name
        // Modified by Override: ospf:ARtSum->name
        // Type is an MO-Defined-Type
        leaf name {
            description "Name";

            // Type is an MO-Defined-Type
            type naming_Name {
                length "0..64";
            }
        }

        // From Interface naming:Described
        // Inherited From pol:Instr
        // Modified by Override: ospf:ARtSum->descr
        // Type is an MO-Defined-Type
        leaf descr {
            config "false";
            description "Description";

            // Type is an MO-Defined-Type
            type naming_Descr;
        }
        leaf addr {
            type address_Ip;
        }

        // Summary address no Advertise
        // Inherited From ospf:ARtSum
        // Type is an MO-Defined-Type
        leaf ctrl {
            description "Controls";

            // Type is an MO-Defined-Type
            type ospf_SumControl;
        }

        // Number of component routes
        // Inherited From ospf:ARtSum
        // Type is an MO-Defined-Type
        leaf compRtCnt {
            config "false";
            description "Number of component routes";

            // Type is an MO-Defined-Type
            type nw_Counter32;
        }

        // Route summary cost
        // Inherited From ospf:ARtSum
        // Type is an MO-Defined-Type
        leaf operCost {
            config "false";
            description "Route Summary Operational Cost";

            // Type is an MO-Defined-Type
            type ospf_SumCost;
        }

        // Summary address tag
        // Inherited From ospf:AExtRtSum
        // Type is an MO-Defined-Type
        leaf tag {
            description "Route Tag";

            // Type is an MO-Defined-Type
            type ospf_RtTag;
        }
    }

    grouping ospf_EventLogs-group {

        // Event LogType
        // Inherited From ospf:AEventLogs
        // Type is an MO-Defined-Type
        leaf eventType {
            description "Event Log Type";

            // Type is an MO-Defined-Type
            type ospf_EventType;
        }

        // Event LogSize
        // Inherited From ospf:AEventLogs
        // Type is an MO-Defined-Type
        leaf logSize {
            description "Event Log Size";

            // Type is an MO-Defined-Type
            type ospf_EventLogSize;
        }

        // Event Log size in bytes
        // Inherited From ospf:AEventLogs
        // Type is an MO-Defined-Type
        leaf logSizeKBytes {
            description "Event Log Size in KBytes";

            // Type is an MO-Defined-Type
            type ospf_EventLogSizeKBytes;
        }
    }

    grouping ospf_InternalIf-group {

        // Inherited From nw:Conn
        // Modified by Override: nw:Ep->name
        // Modified by Override: ospf:AIf->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: ospf:AIf->descr
        // Type is an MO-Defined-Type
        leaf descr {
            config "false";
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ospf:AIf
        // Type is an MO-Defined-Type
        leaf ctrl {
            description "Controls";

            // Type is an MO-Defined-Type
            type ospf_IfControl;
        }

        // Passive interface control
        // Inherited From ospf:AIf
        // Type is an MO-Defined-Type
        leaf passiveCtrl {
            description "Passive Interface Control";

            // Type is an MO-Defined-Type
            type ospf_PassiveControl;
        }

        // BFD control
        // Inherited From ospf:AIf
        // Type is an MO-Defined-Type
        leaf bfdCtrl {
            description "BFD Control";

            // Type is an MO-Defined-Type
            type ospf_BfdControl;
        }

        // Network type
        // Inherited From ospf:AIf
        // Type is an MO-Defined-Type
        leaf nwT {
            description "Network Type";

            // Type is an MO-Defined-Type
            type ospf_NwT;
        }

        // Priority, used in determining the designated router on
        // this network
        // Inherited From ospf:AIf
        // Type is an MO-Defined-Type
        leaf prio {
            description "Priority";

            // Type is an MO-Defined-Type
            type ospf_DesigPrio;
        }

        // Area to which this interface belongs to
        // Inherited From ospf:AIf
        // Type is an MO-Defined-Type
        leaf area {
            description "Area ID";

            // Type is an MO-Defined-Type
            type ospf_AreaId;
        }
        leaf advertiseSecondaries {
            type boolean;
            default "true";
        }

        // Operational state
        // Inherited From ospf:AIf
        // Type is an MO-Defined-Type
        leaf operSt {
            config "false";
            description "Operational State";

            // Type is an MO-Defined-Type
            type ospf_IfOperSt;
        }

        // Operational failed state qualifier
        // Inherited From ospf:AIf
        // Type is an MO-Defined-Type
        leaf failStQual {
            config "false";
            description "Failed State Qualifier";

            // Type is an MO-Defined-Type
            type ospf_FailStQual;
        }

        // Interface type
        // Inherited From ospf:AIf
        // Type is an MO-Defined-Type
        leaf type {
            config "false";
            description "Type";

            // Type is an MO-Defined-Type
            type ospf_IfType;
        }

        // Flags
        // Inherited From ospf:AIf
        // Type is an MO-Defined-Type
        leaf flags {
            config "false";
            description "Flags";

            // Type is an MO-Defined-Type
            type ospf_IfFlags;
        }
        leaf addr {
            config "false";
            type address_Ip;
        }
        leaf dr {
            config "false";
            type address_Ip;
        }
        leaf bdr {
            config "false";
            type address_Ip;
        }

        // Designated router id
        // Inherited From ospf:AIf
        // Type is an MO-Defined-Type
        leaf drId {
            config "false";
            description "DR Id";

            // Type is an MO-Defined-Type
            type ip_RtrId;
        }

        // Backup designated router id
        // Inherited From ospf:AIf
        // Type is an MO-Defined-Type
        leaf bdrId {
            config "false";
            description "BDR Id";

            // Type is an MO-Defined-Type
            type ip_RtrId;
        }

        // LSA checksum sum
        // Inherited From ospf:AIf
        // Type is an MO-Defined-Type
        leaf lsaCksumSum {
            config "false";
            description "LSA Checksum Sum";

            // Type is an MO-Defined-Type
            type ospf_LsaCksumSum;
        }

        // Operational Cost
        // Inherited From ospf:AIf
        // Type is an MO-Defined-Type
        leaf operCost {
            config "false";
            description "Operational Cost";

            // Type is an MO-Defined-Type
            type ospf_IfCost;
        }

        // Operational Dead interval
        // Inherited From ospf:AIf
        // Type is an MO-Defined-Type
        leaf operDeadIntvl {
            config "false";
            description "Operational Dead Interval";

            // Type is an MO-Defined-Type
            type ospf_DeadIntvl;
        }

        // Hello interval, interval between hello packets that
        // OSPF sends on the interface
        // From Interface ospf:IIntfIntvl
        // Inherited From ospf:AIf
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:AIf
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:AIf
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:AIf
        // Type is an MO-Defined-Type
        leaf xmitDelay {
            description "Transmit Delay";

            // Type is an MO-Defined-Type
            type ospf_XmitDelay;
        }

        // Cost of the interface
        // From Interface ospf:IIntfCost
        // Inherited From ospf:AIf
        // Type is an MO-Defined-Type
        leaf cost {
            description "Cost";

            // Type is an MO-Defined-Type
            type ospf_IfCost;
        }

        // Instance name
        // Inherited From ospf:AInternalIf
        // Type is an MO-Defined-Type
        leaf instance {
            config "false";
            description "Owning Instance";

            // Type is an MO-Defined-Type
            type ospf_InstanceName;
        }

        // Instance id
        // Inherited From ospf:AInternalIf
        // Type is an MO-Defined-Type
        leaf instanceid {
            config "false";
            description "Instance ID to be used in OSPF packets";

            // Type is an MO-Defined-Type
            type ospf_InstanceID;
        }

        // Dom name
        // Inherited From ospf:AInternalIf
        // Type is an MO-Defined-Type
        leaf dom {
            config "false";
            description "Dom to which the interface belongs to";

            // Type is an MO-Defined-Type
            type ospf_DomName;
        }

        // Instance name deleted by CLI
        // Inherited From ospf:AInternalIf
        // Type is an MO-Defined-Type
        leaf instanceDeletedViaCLI {
            config "false";
            description "Instance Name deleted via CLI";

            // Type is an MO-Defined-Type
            type ospf_InstanceName;
        }

        // This object holds authentication new policy information
        container authnew-items {

            // Added containment as a singleton: Prefix=authnew
            // Acquired From Package ospf
            uses ospf_AuthNewP-group;
        }

        // This object holds multi-area information
        // at a interface level
        container multiarea-items {
            list MultiArea-list {
                key "multiareaid";

                // Added containment: Prefix=multiarea
                // Acquired From Package ospf
                uses ospf_MultiArea-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping rtctrl_L2Evpn-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds Bridge Domain
        // Ethernet VPN instance information
        container bdevi-items {
            list BDEvi-list {
                key "encap";

                // Added containment: Prefix=bdevi
                // Acquired From Package rtctrl
                uses rtctrl_BDEvi-group;
            }
        }
    }

    grouping rtctrl_BDEvi-group {

        // Config source set by controller
        // Type is an MO-Defined-Type
        leaf cfgSrcCtrlr {
            description "Config Source set by controller";

            // Type is an MO-Defined-Type
            type bgp_AdminSt;
        }
        leaf operRd {
            config "false";
            type mtx_array_community;
        }

        // Inherited From nw:Conn
        // Modified by Override: nw:CpDom->name
        // Type is an MO-Defined-Type
        leaf name {
            description "Name";

            // Type is an MO-Defined-Type
            type naming_Name {
                length "1..64";
            }
        }
        leaf rd {
            type mtx_array_community;
        }
        leaf encap {
            type string;
        }

        // Route policy holds all route policy entries and route controls
        container rttp-items {
            list RttP-list {
                key "type";

                // Added containment: Prefix=rttp
                // Acquired From Package rtctrl
                uses rtctrl_RttP-group;
            }
        }
    }

    grouping rtctrl_RttP-group {

        // Config source set by controller
        // Type is an MO-Defined-Type
        leaf cfgSrcCtrlr {
            description "Config Source set by controller";

            // Type is an MO-Defined-Type
            type bgp_AdminSt;
        }
        leaf operRttAuto {
            config "false";
            type mtx_array_community;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtctrl:ARtP
        // Type is an MO-Defined-Type
        leaf type {
            description "Type";

            // Type is an MO-Defined-Type
            type rtctrl_RttPType;
        }

        // List of route policy entries
        container ent-items {
            list RttEntry-list {
                key "rtt";

                // Added containment: Prefix=ent
                // Acquired From Package rtctrl
                uses rtctrl_RttEntry-group;
            }
        }

        // Route control map policy for routes imported/exported
        // into an AF. Control is through route maps.
        container rtctrlmap-items {

            // Added containment as a singleton: Prefix=rtctrlmap
            // Acquired From Package rtctrl
            uses rtctrl_MapP-group;
        }

        // Route control map policy for routes imported/exported
        // into an AF in the default VRF. Control is through route maps.
        container rtctrldefmap-items {

            // Added containment as a singleton: Prefix=rtctrldefmap
            // Acquired From Package rtctrl
            uses rtctrl_DomDefMapP-group;
        }
    }

    grouping rtctrl_RttEntry-group {
        leaf rtt {
            type mtx_array_community;
        }

        // Config source set by controller
        // Type is an MO-Defined-Type
        leaf cfgSrcCtrlr {
            description "Config Source set by controller";

            // Type is an MO-Defined-Type
            type bgp_AdminSt;
        }
    }

    grouping rtctrl_MapP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf rtMap {
            type string {
            }
        }
    }

    grouping rtctrl_DomDefMapP-group {
        leaf pfxLimit {
            type uint32 {
                range "0..2147483647";
            }
            default "0";
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf rtMap {
            type string {
            }
        }
    }

    // Has Polymorphic containment of abstract object aaa:Ep
    // Has Polymorphic containment of abstract object aaa:Banner
    grouping aaa_UserEp-group {

        // Type is an MO-Defined-Type
        leaf pwdStrengthCheck {
            description "Password Strength Check";

            // Type is an MO-Defined-Type
            type aaa_Boolean;
        }

        // Type is an MO-Defined-Type
        leaf pwdSecureMode {
            description "Password secure-mode";

            // Type is an MO-Defined-Type
            type aaa_Boolean;
        }
        leaf pwdMinLength {
            type uint16;
            default "8";
        }
        leaf pwdMaxLength {
            type uint16;
            default "127";
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Polymorphic containment of derivative object aaa:RadiusEp (from aaa:Ep)
        container radiusext-items {

            // Added containment as a singleton: Prefix=radiusext
            // Acquired From Package aaa
            uses aaa_RadiusEp-group;
        }

        // Polymorphic containment of derivative object aaa:LdapEp (from aaa:Ep)
        container ldapext-items {

            // Added containment as a singleton: Prefix=ldapext
            // Acquired From Package aaa
            uses aaa_LdapEp-group;
        }

        // Polymorphic containment of derivative object aaa:TacacsPlusEp (from aaa:Ep)
        container tacacsext-items {

            // Added containment as a singleton: Prefix=tacacsext
            // Acquired From Package aaa
            uses aaa_TacacsPlusEp-group;
        }

        container authrealm-items {

            // Added containment as a singleton: Prefix=authrealm
            // Acquired From Package aaa
            uses aaa_AuthRealm-group;
        }

        // This MO represents an AAA (accounting/authorization/accounting)
        // domain. The AAA configuration can be configured per domain.
        container logindomain-items {
            list LoginDomain-list {
                key "name";

                // Added containment: Prefix=logindomain
                // Acquired From Package aaa
                uses aaa_LoginDomain-group;
            }
        }

        // Banner presented to the user prior to the console, serial and ssh login prompts
        container preloginbanner-items {

            // Added containment as a singleton: Prefix=preloginbanner
            // Acquired From Package aaa
            uses aaa_PreLoginBanner-group;
        }
        container remoteuser-items {
            list RemoteUser-list {
                key "name";

                // Added containment: Prefix=remoteuser
                // Acquired From Package aaa
                uses aaa_RemoteUser-group;
            }
        }
        container user-items {
            list User-list {
                key "name";

                // Added containment: Prefix=user
                // Acquired From Package aaa
                uses aaa_User-group;
            }
        }
        container role-items {
            list Role-list {
                key "name";

                // Added containment: Prefix=role
                // Acquired From Package aaa
                uses aaa_Role-group;
            }
        }
        container factoryrole-items {
            list FactoryRole-list {
                key "name";

                // Added containment: Prefix=factoryrole
                // Acquired From Package aaa
                uses aaa_FactoryRole-group;
            }
        }
        container domain-items {
            list Domain-list {
                key "name";

                // Added containment: Prefix=domain
                // Acquired From Package aaa
                uses aaa_Domain-group;
            }
        }

        // This MO stores information about password constratints
        // applicable to all the local users.
        container pwdprofile-items {

            // Added containment as a singleton: Prefix=pwdprofile
            // Acquired From Package aaa
            uses aaa_PwdProfile-group;
        }

        // PKI config: keyrings and CA certs
        container pkiext-items {

            // Added containment as a singleton: Prefix=pkiext
            // Acquired From Package pki
            uses pki_Ep-group;
        }

        // Rel-def target from resUserEp
        // Inherited From aaa:UserEp
        container rtfabricResUserEp-items {

            // Abstract containment of rtfabricResUserEp derived from aaa:UserEp
            list RtFabricResUserEp-list {
                config "false";
                key "tDn";

                // Added containment: Prefix=rtfabricResUserEp
                // Acquired From Package fabric
                uses fabric_RtFabricResUserEp_target-group;
            }
        }

        // Rel-def target from userEp
        // Inherited From aaa:UserEp
        container rtaaaUserEp-items {

            // Abstract containment of rtaaaUserEp derived from aaa:UserEp
            list RtAaaUserEp-list {
                config "false";
                key "tDn";

                // Added containment: Prefix=rtaaaUserEp
                // Acquired From Package aaa
                uses aaa_RtAaaUserEp_target-group;
            }
        }
    }

    grouping aaa_RadiusEp-group {

        // Type is an MO-Defined-Type
        leaf deadtime {
            description "Duration for which non-reachable server is skipped";

            // Type is an MO-Defined-Type
            type aaa_TimeMin;
        }

        // Type is an MO-Defined-Type
        leaf key {
            description "Global RADIUS server shared secret";

            // Type is an MO-Defined-Type
            type aaa_EncKey;
        }

        // Type is an MO-Defined-Type
        leaf keyEnc {
            description "Default key encryption";

            // Type is an MO-Defined-Type
            type aaa_KeyEnc;
        }

        // Type is an MO-Defined-Type
        leaf loggingLevel {
            description "Radius Logging level";

            // Type is an MO-Defined-Type
            type aaa_LoggingLevel;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // add units for timeout. This helps display in CLI
        // Inherited From aaa:Ep
        // Type is an MO-Defined-Type
        leaf timeout {
            description "Timeout in Seconds";

            // Type is an MO-Defined-Type
            type aaa_TimeSec;
        }

        // Inherited From aaa:Ep
        // Type is an MO-Defined-Type
        leaf retries {
            description "Retries";

            // Type is an MO-Defined-Type
            type aaa_Retries;
        }

        // Source interface
        // Inherited From aaa:Ep
        // Type is an MO-Defined-Type
        leaf srcIf {
            description "Source Interface";

            // Type is an MO-Defined-Type
            type nw_IfId;
        }
        container radiusprovider-items {
            list RadiusProvider-list {
                key "name";

                // Added containment: Prefix=radiusprovider
                // Acquired From Package aaa
                uses aaa_RadiusProvider-group;
            }
        }

        // This MO represents a group of AAA RADIUS servers.
        // A member of this group is represented by ProviderRef MO
        container radiusprovidergroup-items {
            list RadiusProviderGroup-list {
                key "name";

                // Added containment: Prefix=radiusprovidergroup
                // Acquired From Package aaa
                uses aaa_RadiusProviderGroup-group;
            }
        }

        container radiusservermonitor-items {

            // Added containment as a singleton: Prefix=radiusservermonitor
            // Acquired From Package aaa
            uses aaa_RadiusServerMonitor-group;
        }

        // Rel-def target from resRadiusEp
        // Inherited From aaa:RadiusEp
        container rtfabricResRadiusEp-items {

            // Abstract containment of rtfabricResRadiusEp derived from aaa:RadiusEp
            list RtFabricResRadiusEp-list {
                config "false";
                key "tDn";

                // Added containment: Prefix=rtfabricResRadiusEp
                // Acquired From Package fabric
                uses fabric_RtFabricResRadiusEp_target-group;
            }
        }
    }

    grouping aaa_RadiusProvider-group {

        // Type is an MO-Defined-Type
        leaf useType {
            description "Usage for the radius server";

            // Type is an MO-Defined-Type
            type aaa_RadSrvUseType;
        }

        // Type is an MO-Defined-Type
        leaf authPort {
            description "authPort";

            // Type is an MO-Defined-Type
            type aaa_RadPort;
        }

        // Type is an MO-Defined-Type
        leaf acctPort {
            description "acctPort";

            // Type is an MO-Defined-Type
            type aaa_RadPort;
        }

        // Per provider configuration,
        // if set to 0, it uses global settings value
        // <override name="timeout"
        // mod="explicit"
        // >
        // <range min="0" max="60"/>
        // <default value="5"/>
        // </override>
        // Type is an MO-Defined-Type
        leaf authProtocol {
            description "Authentication Protocol";

            // Type is an MO-Defined-Type
            type aaa_authenticationProtocol;
        }

        // From Interface naming:Named
        // Inherited From naming:NamedObject
        // Modified by Override: pol:Obj->name
        // Modified by Override: aaa:Definition->name
        // Modified by Override: aaa:AProvider->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:AProvider
        // Type is an MO-Defined-Type
        leaf key {
            description "Key";

            // Type is an MO-Defined-Type
            type aaa_EncKey;
        }
        leaf keySet {
            config "false";
            type boolean;
        }

        // Inherited From aaa:AProvider
        // Type is an MO-Defined-Type
        // Default value handled in local MO type
        leaf keyEnc {
            description "Default key encryption";

            // Type is a Local-MO-Defined-Type
            type aaa_KeyEnc_RadiusProvider_keyEnc;
        }

        // The following two properties are also defined in Ep MO.
        // Here they reperesent per server configuration which would
        // take precedence over global configuration defined in Ep MO
        // Inherited From aaa:AProvider
        // Type is an MO-Defined-Type
        // Default value handled in local MO type
        leaf timeout {
            description "Timeout in Seconds";

            // Type is a Local-MO-Defined-Type
            type aaa_TimeSec_RadiusProvider_timeout;
        }

        // Inherited From aaa:AProvider
        // Type is an MO-Defined-Type
        // Default value handled in local MO type
        leaf retries {
            description "Retries";

            // Type is a Local-MO-Defined-Type
            type aaa_Retries_RadiusProvider_retries;
        }

        // Inherited From aaa:AProvider
        // Type is an MO-Defined-Type
        leaf operState {
            config "false";
            description "Provider Operational State";

            // Type is an MO-Defined-Type
            type aaa_ProviderState;
        }

        // Inherited From aaa:AProvider
        // Type is an MO-Defined-Type
        leaf monitorServer {
            description "Periodic Server Monitoring";

            // Type is an MO-Defined-Type
            type aaa_MonitorServerType;
        }

        // Inherited From aaa:AProvider
        // Type is an MO-Defined-Type
        leaf monitoringUser {
            description "Periodic Server Monitoring Username";

            // Type is an MO-Defined-Type
            type aaa_MonitoringUserType;
        }

        // Inherited From aaa:AProvider
        // Type is an MO-Defined-Type
        leaf monitoringPassword {
            description "Periodic Server Monitoring Password";

            // Type is an MO-Defined-Type
            type aaa_MonitoringPasswordType;
        }
        leaf epgDn {
            config "false";
            type string;
        }

        // The vrf that this client group belongs to
        // Inherited From aaa:AProvider
        // Type is an MO-Defined-Type
        leaf vrfName {
            config "false";
            description "Vrf Name";

            // Type is an MO-Defined-Type
            type l3_VrfName;
        }

        // Inherited From aaa:AProvider
        // Type is an MO-Defined-Type
        leaf snmpIndex {
            config "false";
            description "Provider SNMP Index";

            // Type is an MO-Defined-Type
            type aaa_ProviderSnmpIndex;
        }
    }

    grouping aaa_RadiusProviderGroup-group {

        // Type is an MO-Defined-Type
        leaf deadtime {
            description "Duration for which non-reachable server is skipped";

            // Type is an MO-Defined-Type
            type aaa_ProviderGroupDeadtime;
        }

        // From Interface naming:Named
        // Inherited From naming:NamedObject
        // Modified by Override: pol:Obj->name
        // Modified by Override: aaa:Definition->name
        // Modified by Override: aaa:ProviderGroup->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:ProviderGroup
        // Type is an MO-Defined-Type
        leaf snmpIndex {
            config "false";
            description "Provider Group SNMP Index";

            // Type is an MO-Defined-Type
            type aaa_ProviderGroupSnmpIndex;
        }

        // Source interface
        // Inherited From aaa:ProviderGroup
        // Type is an MO-Defined-Type
        leaf srcIf {
            description "Source Interface";

            // Type is an MO-Defined-Type
            type nw_IfId;
        }

        // Inherited From aaa:ProviderGroup
        // Type is an MO-Defined-Type
        leaf vrf {
            description "VRF";

            // Type is an MO-Defined-Type
            type l3_VrfName;
        }

        // The MO represents member of ProviderGroup
        container providerref-items {
            list ProviderRef-list {
                key "name";

                // Added containment: Prefix=providerref
                // Acquired From Package aaa
                uses aaa_ProviderRef-group;
            }
        }
    }

    grouping aaa_ProviderRef-group {

        // This property dicates the order in which the Provider
        // referred by this MO will be tried within the ProviderGroup
        // Type is an MO-Defined-Type
        leaf order {
            description "Order in which Providers are Tried";

            // Type is an MO-Defined-Type
            type aaa_Order;
        }

        // Type is an MO-Defined-Type
        leaf snmpIndex {
            config "false";
            description "Provider SNMP Index";

            // Type is an MO-Defined-Type
            type aaa_ProviderSnmpIndex;
        }

        // From Interface naming:Named
        // Inherited From naming:NamedObject
        // Modified by Override: aaa:ProviderRef->name
        // Modified by Override: pol:Obj->name
        // Modified by Override: aaa:Definition->name
        // Type is an MO-Defined-Type
        leaf name {
            description "Name";

            // Type is an MO-Defined-Type
            type naming_Name {

                // Copied from "ProviderName" type
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_RadiusServerMonitor-group {

        // Type is an MO-Defined-Type
        leaf pwd {
            description "Password";

            // Type is an MO-Defined-Type
            type aaa_Passwd;
        }

        // Type is an MO-Defined-Type
        leaf idleTime {
            description "Idle timer to monitor tacacs/radius server";

            // Type is an MO-Defined-Type
            type aaa_IdleTimer;
        }

        // From Interface naming:Named
        // Inherited From naming:NamedObject
        // Modified by Override: aaa:RadiusServerMonitor->name
        // Modified by Override: pol:Obj->name
        // Modified by Override: aaa:Definition->name
        // Type is an MO-Defined-Type
        leaf name {
            description "Name";

            // Type is an MO-Defined-Type
            type naming_Name {

                // Copied from "aaa:User" type
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_LdapEp-group {

        // Type is an MO-Defined-Type
        leaf attribute {
            description "LDAP Attribute";

            // Type is an MO-Defined-Type
            type aaa_LdapAttribute;
        }

        // Type is an MO-Defined-Type
        leaf basedn {
            description "LDAP Base DN";

            // Type is an MO-Defined-Type
            type aaa_LdapDn;
        }

        // Type is an MO-Defined-Type
        leaf filter {
            description "LDAP Filter";

            // Type is an MO-Defined-Type
            type aaa_LdapFilter;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // add units for timeout. This helps display in CLI
        // Inherited From aaa:Ep
        // Modified by Override: aaa:LdapEp->timeout
        // Type is an MO-Defined-Type
        leaf timeout {
            description "Timeout in Seconds";

            // Type is an MO-Defined-Type
            type aaa_TimeSec;
        }

        // Inherited From aaa:Ep
        // Type is an MO-Defined-Type
        leaf retries {
            description "Retries";

            // Type is an MO-Defined-Type
            type aaa_Retries;
        }

        // Source interface
        // Inherited From aaa:Ep
        // Type is an MO-Defined-Type
        leaf srcIf {
            description "Source Interface";

            // Type is an MO-Defined-Type
            type nw_IfId;
        }

        // This MO represents a group of AAA LDAP servers.
        // A member of this group is represented by ProviderRef MO
        container ldapprovidergroup-items {
            list LdapProviderGroup-list {
                key "name";

                // Added containment: Prefix=ldapprovidergroup
                // Acquired From Package aaa
                uses aaa_LdapProviderGroup-group;
            }
        }
        container ldapprovider-items {
            list LdapProvider-list {
                key "name";

                // Added containment: Prefix=ldapprovider
                // Acquired From Package aaa
                uses aaa_LdapProvider-group;
            }
        }

        // Rel-def target from resLdapEp
        // Inherited From aaa:LdapEp
        container rtfabricResLdapEp-items {

            // Abstract containment of rtfabricResLdapEp derived from aaa:LdapEp
            list RtFabricResLdapEp-list {
                config "false";
                key "tDn";

                // Added containment: Prefix=rtfabricResLdapEp
                // Acquired From Package fabric
                uses fabric_RtFabricResLdapEp_target-group;
            }
        }
    }

    grouping aaa_LdapProviderGroup-group {

        // From Interface naming:Named
        // Inherited From naming:NamedObject
        // Modified by Override: pol:Obj->name
        // Modified by Override: aaa:Definition->name
        // Modified by Override: aaa:ProviderGroup->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:ProviderGroup
        // Type is an MO-Defined-Type
        leaf snmpIndex {
            config "false";
            description "Provider Group SNMP Index";

            // Type is an MO-Defined-Type
            type aaa_ProviderGroupSnmpIndex;
        }

        // Source interface
        // Inherited From aaa:ProviderGroup
        // Type is an MO-Defined-Type
        leaf srcIf {
            description "Source Interface";

            // Type is an MO-Defined-Type
            type nw_IfId;
        }

        // Inherited From aaa:ProviderGroup
        // Type is an MO-Defined-Type
        leaf vrf {
            description "VRF";

            // Type is an MO-Defined-Type
            type l3_VrfName;
        }

        // The MO represents member of ProviderGroup
        container providerref-items {
            list ProviderRef-list {
                key "name";

                // Added containment: Prefix=providerref
                // Acquired From Package aaa
                uses aaa_ProviderRef-group;
            }
        }
    }

    grouping aaa_LdapProvider-group {

        // Type is an MO-Defined-Type
        leaf rootdn {
            description "Root DN";

            // Type is an MO-Defined-Type
            type aaa_LdapDn;
        }

        // Type is an MO-Defined-Type
        leaf port {
            description "Port";

            // Type is an MO-Defined-Type
            type aaa_Port;
        }
        leaf enableSSL {
            type boolean;
        }

        // Type is an MO-Defined-Type
        leaf SSLValidationLevel {
            description "SSL certificate validation level";

            // Type is an MO-Defined-Type
            type aaa_LdapSSLStrictnessLevel;
        }

        // This property names the attribute to be downloaded
        // which has user's roles and domains information.
        // The value of this property takes precendence over the
        // value of 'attribute' property in LdapEp MO
        // Type is an MO-Defined-Type
        leaf attribute {
            description "LDAP Attribute";

            // Type is an MO-Defined-Type
            type aaa_LdapAttribute;
        }

        // Ldap Base DN to be used while searching for the user.
        // The value of this property takes precendence over the value
        // of 'basedn' property in LdapEp MO
        // Type is an MO-Defined-Type
        leaf basedn {
            description "LDAP Base DN";

            // Type is an MO-Defined-Type
            type aaa_LdapDn;
        }

        // Ldap filter to be used while searching for the user.
        // The value of this property takes precendence over the
        // value of 'filter' property in LdapEp MO
        // Type is an MO-Defined-Type
        leaf filter {
            description "LDAP Filter";

            // Type is an MO-Defined-Type
            type aaa_LdapFilter;
        }

        // From Interface naming:Named
        // Inherited From naming:NamedObject
        // Modified by Override: pol:Obj->name
        // Modified by Override: aaa:Definition->name
        // Modified by Override: aaa:AProvider->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:AProvider
        // Type is an MO-Defined-Type
        leaf key {
            description "Key";

            // Type is an MO-Defined-Type
            type aaa_EncKey;
        }
        leaf keySet {
            config "false";
            type boolean;
        }

        // Inherited From aaa:AProvider
        // Type is an MO-Defined-Type
        // Default value handled in local MO type
        leaf keyEnc {
            description "Default key encryption";

            // Type is a Local-MO-Defined-Type
            type aaa_KeyEnc_LdapProvider_keyEnc;
        }

        // The following two properties are also defined in Ep MO.
        // Here they reperesent per server configuration which would
        // take precedence over global configuration defined in Ep MO
        // Inherited From aaa:AProvider
        // Modified by Override: aaa:LdapProvider->timeout
        // Type is an MO-Defined-Type
        // Default value handled in local MO type
        leaf timeout {
            description "Timeout in Seconds";

            // Type is a Local-MO-Defined-Type
            type aaa_TimeSec_LdapProvider_timeout {
                range "5..60";
            }
        }

        // Inherited From aaa:AProvider
        // Type is an MO-Defined-Type
        // Default value handled in local MO type
        leaf retries {
            description "Retries";

            // Type is a Local-MO-Defined-Type
            type aaa_Retries_LdapProvider_retries;
        }

        // Inherited From aaa:AProvider
        // Type is an MO-Defined-Type
        leaf operState {
            config "false";
            description "Provider Operational State";

            // Type is an MO-Defined-Type
            type aaa_ProviderState;
        }

        // Inherited From aaa:AProvider
        // Type is an MO-Defined-Type
        leaf monitorServer {
            description "Periodic Server Monitoring";

            // Type is an MO-Defined-Type
            type aaa_MonitorServerType;
        }

        // Inherited From aaa:AProvider
        // Type is an MO-Defined-Type
        leaf monitoringUser {
            description "Periodic Server Monitoring Username";

            // Type is an MO-Defined-Type
            type aaa_MonitoringUserType;
        }

        // Inherited From aaa:AProvider
        // Type is an MO-Defined-Type
        leaf monitoringPassword {
            description "Periodic Server Monitoring Password";

            // Type is an MO-Defined-Type
            type aaa_MonitoringPasswordType;
        }
        leaf epgDn {
            config "false";
            type string;
        }

        // The vrf that this client group belongs to
        // Inherited From aaa:AProvider
        // Type is an MO-Defined-Type
        leaf vrfName {
            config "false";
            description "Vrf Name";

            // Type is an MO-Defined-Type
            type l3_VrfName;
        }

        // Inherited From aaa:AProvider
        // Type is an MO-Defined-Type
        leaf snmpIndex {
            config "false";
            description "Provider SNMP Index";

            // Type is an MO-Defined-Type
            type aaa_ProviderSnmpIndex;
        }
    }

    grouping aaa_TacacsPlusEp-group {

        // Type is an MO-Defined-Type
        leaf deadtime {
            description "Duration for which non-reachable server is skipped";

            // Type is an MO-Defined-Type
            type aaa_TimeMin;
        }

        // Type is an MO-Defined-Type
        leaf key {
            description "Global TACACS+ server shared secret";

            // Type is an MO-Defined-Type
            type aaa_EncKey;
        }

        // Type is an MO-Defined-Type
        leaf keyEnc {
            description "Default key encryption";

            // Type is an MO-Defined-Type
            type aaa_KeyEnc;
        }

        // Type is an MO-Defined-Type
        leaf loggingLevel {
            description "Tacacs Logging level";

            // Type is an MO-Defined-Type
            type aaa_LoggingLevel;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // add units for timeout. This helps display in CLI
        // Inherited From aaa:Ep
        // Type is an MO-Defined-Type
        leaf timeout {
            description "Timeout in Seconds";

            // Type is an MO-Defined-Type
            type aaa_TimeSec;
        }

        // Inherited From aaa:Ep
        // Type is an MO-Defined-Type
        leaf retries {
            description "Retries";

            // Type is an MO-Defined-Type
            type aaa_Retries;
        }

        // Source interface
        // Inherited From aaa:Ep
        // Type is an MO-Defined-Type
        leaf srcIf {
            description "Source Interface";

            // Type is an MO-Defined-Type
            type nw_IfId;
        }
        container tacacsplusprovider-items {
            list TacacsPlusProvider-list {
                key "name";

                // Added containment: Prefix=tacacsplusprovider
                // Acquired From Package aaa
                uses aaa_TacacsPlusProvider-group;
            }
        }

        // This MO represents a group of AAA TACACS+ servers.
        container tacacsplusprovidergroup-items {
            list TacacsPlusProviderGroup-list {
                key "name";

                // Added containment: Prefix=tacacsplusprovidergroup
                // Acquired From Package aaa
                uses aaa_TacacsPlusProviderGroup-group;
            }
        }

        container tacacsservermonitor-items {

            // Added containment as a singleton: Prefix=tacacsservermonitor
            // Acquired From Package aaa
            uses aaa_TacacsServerMonitor-group;
        }

        // Rel-def target from resTacacsPlusEp
        // Inherited From aaa:TacacsPlusEp
        container rtfabricResTacacsPlusEp-items {

            // Abstract containment of rtfabricResTacacsPlusEp derived from aaa:TacacsPlusEp
            list RtFabricResTacacsPlusEp-list {
                config "false";
                key "tDn";

                // Added containment: Prefix=rtfabricResTacacsPlusEp
                // Acquired From Package fabric
                uses fabric_RtFabricResTacacsPlusEp_target-group;
            }
        }
    }

    grouping aaa_TacacsPlusProvider-group {

        // Type is an MO-Defined-Type
        leaf port {
            description "Port";

            // Type is an MO-Defined-Type
            type aaa_Port;
        }

        // Type is an MO-Defined-Type
        leaf authProtocol {
            description "TACACS+ Authentication Protocol";

            // Type is an MO-Defined-Type
            type aaa_authenticationProtocol;
        }

        // From Interface naming:Named
        // Inherited From naming:NamedObject
        // Modified by Override: pol:Obj->name
        // Modified by Override: aaa:Definition->name
        // Modified by Override: aaa:AProvider->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:AProvider
        // Type is an MO-Defined-Type
        leaf key {
            description "Key";

            // Type is an MO-Defined-Type
            type aaa_EncKey;
        }
        leaf keySet {
            config "false";
            type boolean;
        }

        // Inherited From aaa:AProvider
        // Type is an MO-Defined-Type
        // Default value handled in local MO type
        leaf keyEnc {
            description "Default key encryption";

            // Type is a Local-MO-Defined-Type
            type aaa_KeyEnc_TacacsPlusProvider_keyEnc;
        }

        // The following two properties are also defined in Ep MO.
        // Here they reperesent per server configuration which would
        // take precedence over global configuration defined in Ep MO
        // Inherited From aaa:AProvider
        // Modified by Override: aaa:TacacsPlusProvider->timeout
        // Type is an MO-Defined-Type
        // Default value handled in local MO type
        leaf timeout {
            description "Timeout in Seconds";

            // Type is a Local-MO-Defined-Type
            type aaa_TimeSec_TacacsPlusProvider_timeout {
                range "0..60";
            }
        }

        // Inherited From aaa:AProvider
        // Type is an MO-Defined-Type
        // Default value handled in local MO type
        leaf retries {
            description "Retries";

            // Type is a Local-MO-Defined-Type
            type aaa_Retries_TacacsPlusProvider_retries;
        }

        // Inherited From aaa:AProvider
        // Type is an MO-Defined-Type
        leaf operState {
            config "false";
            description "Provider Operational State";

            // Type is an MO-Defined-Type
            type aaa_ProviderState;
        }

        // Inherited From aaa:AProvider
        // Type is an MO-Defined-Type
        leaf monitorServer {
            description "Periodic Server Monitoring";

            // Type is an MO-Defined-Type
            type aaa_MonitorServerType;
        }

        // Inherited From aaa:AProvider
        // Type is an MO-Defined-Type
        leaf monitoringUser {
            description "Periodic Server Monitoring Username";

            // Type is an MO-Defined-Type
            type aaa_MonitoringUserType;
        }

        // Inherited From aaa:AProvider
        // Type is an MO-Defined-Type
        leaf monitoringPassword {
            description "Periodic Server Monitoring Password";

            // Type is an MO-Defined-Type
            type aaa_MonitoringPasswordType;
        }
        leaf epgDn {
            config "false";
            type string;
        }

        // The vrf that this client group belongs to
        // Inherited From aaa:AProvider
        // Type is an MO-Defined-Type
        leaf vrfName {
            config "false";
            description "Vrf Name";

            // Type is an MO-Defined-Type
            type l3_VrfName;
        }

        // Inherited From aaa:AProvider
        // Type is an MO-Defined-Type
        leaf snmpIndex {
            config "false";
            description "Provider SNMP Index";

            // Type is an MO-Defined-Type
            type aaa_ProviderSnmpIndex;
        }
    }

    grouping aaa_TacacsPlusProviderGroup-group {

        // Type is an MO-Defined-Type
        leaf deadtime {
            description "Duration for which non-reachable server is skipped";

            // Type is an MO-Defined-Type
            type aaa_ProviderGroupDeadtime;
        }

        // From Interface naming:Named
        // Inherited From naming:NamedObject
        // Modified by Override: pol:Obj->name
        // Modified by Override: aaa:Definition->name
        // Modified by Override: aaa:ProviderGroup->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:ProviderGroup
        // Type is an MO-Defined-Type
        leaf snmpIndex {
            config "false";
            description "Provider Group SNMP Index";

            // Type is an MO-Defined-Type
            type aaa_ProviderGroupSnmpIndex;
        }

        // Source interface
        // Inherited From aaa:ProviderGroup
        // Type is an MO-Defined-Type
        leaf srcIf {
            description "Source Interface";

            // Type is an MO-Defined-Type
            type nw_IfId;
        }

        // Inherited From aaa:ProviderGroup
        // Type is an MO-Defined-Type
        leaf vrf {
            description "VRF";

            // Type is an MO-Defined-Type
            type l3_VrfName;
        }

        // The MO represents member of ProviderGroup
        container providerref-items {
            list ProviderRef-list {
                key "name";

                // Added containment: Prefix=providerref
                // Acquired From Package aaa
                uses aaa_ProviderRef-group;
            }
        }
    }

    grouping aaa_TacacsServerMonitor-group {

        // Type is an MO-Defined-Type
        leaf pwd {
            description "Password";

            // Type is an MO-Defined-Type
            type aaa_Passwd;
        }

        // Type is an MO-Defined-Type
        leaf idleTime {
            description "Idle timer to monitor tacacs/radius server";

            // Type is an MO-Defined-Type
            type aaa_IdleTimer;
        }

        // From Interface naming:Named
        // Inherited From naming:NamedObject
        // Modified by Override: aaa:TacacsServerMonitor->name
        // Modified by Override: pol:Obj->name
        // Modified by Override: aaa:Definition->name
        // Type is an MO-Defined-Type
        leaf name {
            description "Name";

            // Type is an MO-Defined-Type
            type naming_Name {

                // Copied from "aaa:User" type
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_AuthRealm-group {

        // default role policy for remote user
        // Type is an MO-Defined-Type
        leaf defRolePolicy {
            description "Default Role Policy";

            // Type is an MO-Defined-Type
            type aaa_NoRolePolicy;
        }

        // Type is an MO-Defined-Type
        leaf radDirectedReq {
            description "Enable direct authentication requests to server";

            // Type is an MO-Defined-Type
            type aaa_Boolean;
        }

        // Type is an MO-Defined-Type
        leaf tacDirectedReq {
            description "Enable direct authentication requests to server";

            // Type is an MO-Defined-Type
            type aaa_Boolean;
        }

        // for aaa logging level
        // Type is an MO-Defined-Type
        leaf loggingLevel {
            description "AAA Logging level";

            // Type is an MO-Defined-Type
            type aaa_LoggingLevel;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        container aaagroup-items {
            list AaaServerGroup-list {
                config "false";
                key "name";

                // Added containment: Prefix=aaagroup
                // Acquired From Package aaa
                uses aaa_AaaServerGroup-group;
            }
        }

        // MO representing the Default Authentication configuration for
        // all logins
        container defaultauth-items {

            // Added containment as a singleton: Prefix=defaultauth
            // Acquired From Package aaa
            uses aaa_DefaultAuth-group;
        }
        container defaultauthor-items {
            list DefaultAuthor-list {
                key "cmdType";

                // Added containment: Prefix=defaultauthor
                // Acquired From Package aaa
                uses aaa_DefaultAuthor-group;
            }
        }
        container consoleauthor-items {
            list ConsoleAuthor-list {
                key "cmdType";

                // Added containment: Prefix=consoleauthor
                // Acquired From Package aaa
                uses aaa_ConsoleAuthor-group;
            }
        }

        container defaultacc-items {

            // Added containment as a singleton: Prefix=defaultacc
            // Acquired From Package aaa
            uses aaa_DefaultAcc-group;
        }

        container pkisshcert-items {

            // Added containment as a singleton: Prefix=pkisshcert
            // Acquired From Package aaa
            uses aaa_PkiSSHCertificate-group;
        }

        container pkisshpubkey-items {

            // Added containment as a singleton: Prefix=pkisshpubkey
            // Acquired From Package aaa
            uses aaa_PkiSSHPublicKey-group;
        }

        // MO representing the Authentication configuration for Console
        // Login
        container consoleauth-items {

            // Added containment as a singleton: Prefix=consoleauth
            // Acquired From Package aaa
            uses aaa_ConsoleAuth-group;
        }

        // Rel-def target from resAuthRealm
        // Inherited From aaa:AuthRealm
        container rtfabricResAuthRealm-items {

            // Abstract containment of rtfabricResAuthRealm derived from aaa:AuthRealm
            list RtFabricResAuthRealm-list {
                config "false";
                key "tDn";

                // Added containment: Prefix=rtfabricResAuthRealm
                // Acquired From Package fabric
                uses fabric_RtFabricResAuthRealm_target-group;
            }
        }
    }

    grouping aaa_AaaServerGroup-group {

        // Type is an MO-Defined-Type
        leaf name {
            config "false";
            description "server Group";

            // Type is an MO-Defined-Type
            type aaa_ProviderGroupName;
        }

        // Type is an MO-Defined-Type
        leaf protocol {
            config "false";
            description "server Group protocol";

            // Type is an MO-Defined-Type
            type aaa_ProviderGroupProtocol;
        }
    }

    grouping aaa_DefaultAuth-group {

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Type is an MO-Defined-Type
        leaf realm {
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf errEn {
            type boolean;
            default "true";
        }

        // Inherited From aaa:AuthConfig
        // Type is an MO-Defined-Type
        leaf authProtocol {
            description "Authentication Protocol";

            // Type is an MO-Defined-Type
            type aaa_authenticationProtocol;
        }

        // Inherited From aaa:AuthConfig
        // Type is an MO-Defined-Type
        leaf fallback {
            description "Fallback in case all AAA servers configured for remote authentication are unreachable";

            // Type is an MO-Defined-Type
            type aaa_Boolean;
        }

        // Inherited From aaa:AuthConfig
        // Type is an MO-Defined-Type
        leaf local {
            description "Use local username authentication";

            // Type is an MO-Defined-Type
            type aaa_Boolean;
        }

        // Inherited From aaa:AuthConfig
        // Type is an MO-Defined-Type
        leaf none {
            description "No authentication";

            // Type is an MO-Defined-Type
            type aaa_Boolean;
        }
    }

    grouping aaa_DefaultAuthor-group {

        // From Interface naming:Named
        // Inherited From naming:NamedObject
        // Modified by Override: aaa:DefaultAuthor->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Modified by Override: aaa:DefaultAuthor->realm
        // Type is an MO-Defined-Type
        leaf realm {
            config "false";
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf authorMethodNone {
            type boolean;
        }
        leaf localRbac {
            type boolean;
            default "true";
        }

        // Inherited From aaa:AuthorConfig
        // Type is an MO-Defined-Type
        leaf cmdType {
            description "Type of command for authorization";

            // Type is an MO-Defined-Type
            type aaa_CmdType;
        }
    }

    grouping aaa_ConsoleAuthor-group {

        // From Interface naming:Named
        // Inherited From naming:NamedObject
        // Modified by Override: aaa:ConsoleAuthor->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Modified by Override: aaa:ConsoleAuthor->realm
        // Type is an MO-Defined-Type
        leaf realm {
            config "false";
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf authorMethodNone {
            type boolean;
        }
        leaf localRbac {
            type boolean;
            default "true";
        }

        // Inherited From aaa:AuthorConfig
        // Type is an MO-Defined-Type
        leaf cmdType {
            description "Type of command for authorization";

            // Type is an MO-Defined-Type
            type aaa_CmdType;
        }
    }

    grouping aaa_DefaultAcc-group {

        // From Interface naming:Named
        // Inherited From naming:NamedObject
        // Modified by Override: aaa:DefaultAcc->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Type is an MO-Defined-Type
        leaf realm {
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf accMethodNone {
            type boolean;
            default "true";
        }
        leaf localRbac {
            type boolean;
            default "true";
        }
    }

    grouping aaa_PkiSSHCertificate-group {
        leaf local {
            type boolean;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Type is an MO-Defined-Type
        leaf realm {
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
    }

    grouping aaa_PkiSSHPublicKey-group {
        leaf local {
            type boolean;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Type is an MO-Defined-Type
        leaf realm {
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
    }

    grouping aaa_ConsoleAuth-group {

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Type is an MO-Defined-Type
        leaf realm {
            description "Realm";

            // Type is an MO-Defined-Type
            type aaa_Realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf errEn {
            type boolean;
            default "true";
        }

        // Inherited From aaa:AuthConfig
        // Type is an MO-Defined-Type
        leaf authProtocol {
            description "Authentication Protocol";

            // Type is an MO-Defined-Type
            type aaa_authenticationProtocol;
        }

        // Inherited From aaa:AuthConfig
        // Type is an MO-Defined-Type
        leaf fallback {
            description "Fallback in case all AAA servers configured for remote authentication are unreachable";

            // Type is an MO-Defined-Type
            type aaa_Boolean;
        }

        // Inherited From aaa:AuthConfig
        // Modified by Override: aaa:ConsoleAuth->local
        // Type is an MO-Defined-Type
        leaf local {
            description "Use local username authentication";

            // Type is an MO-Defined-Type
            type aaa_Boolean;
        }

        // Inherited From aaa:AuthConfig
        // Type is an MO-Defined-Type
        leaf none {
            description "No authentication";

            // Type is an MO-Defined-Type
            type aaa_Boolean;
        }
    }

    grouping aaa_LoginDomain-group {

        // From Interface naming:Named
        // Inherited From naming:NamedObject
        // Modified by Override: aaa:LoginDomain->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // MO representing the Authentication configuration for
        // a domain login - this is always a child of a LoginDomain object
        container domainauth-items {

            // Added containment as a singleton: Prefix=domainauth
            // Acquired From Package aaa
            uses aaa_DomainAuth-group;
        }

        // Rel-def target from loginDomain
        // Inherited From aaa:LoginDomain
        container rtaaaLoginDomain-items {

            // Abstract containment of rtaaaLoginDomain derived from aaa:LoginDomain
            list RtAaaLoginDomain-list {
                config "false";
                key "tDn";

                // Added containment: Prefix=rtaaaLoginDomain
                // Acquired From Package aaa
                uses aaa_RtAaaLoginDomain_target-group;
            }
        }
    }

    grouping aaa_DomainAuth-group {

        // From Interface naming:Named
        // Inherited From naming:NamedObject
        // Modified by Override: aaa:DomainAuth->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // The realm to be used for processing
        // authentication/accounting requests
        // Inherited From aaa:Config
        // Modified by Override: aaa:DomainAuth->realm
        // Type is an MO-Defined-Type
        leaf realm {
            description "Realm";

            // Type is a Local-MO-Defined-Type
            type aaa_Realm_DomainAuth_realm;
        }

        // This property specifies the name of ProviderGroup which
        // will be used for for authentication/accounting.The usage
        // of this property value depends on the value of 'realm'
        // property above. When an value is provided for property,
        // this would restrict the servers which will be tried.
        // When no value is provided, then all the servers will be
        // tried for the protocol realm configured in the 'realm'
        // property above.
        // Inherited From aaa:Config
        // Type is an MO-Defined-Type
        leaf providerGroup {
            description "Provider Group";

            // Type is an MO-Defined-Type
            type aaa_ProviderGroupName;
        }

        // Inherited From aaa:Config
        // Type is an MO-Defined-Type
        leaf providerGroup2 {
            description "Provider Group";

            // Type is an MO-Defined-Type
            type aaa_ProviderGroupName;
        }

        // Inherited From aaa:Config
        // Type is an MO-Defined-Type
        leaf providerGroup3 {
            description "Provider Group";

            // Type is an MO-Defined-Type
            type aaa_ProviderGroupName;
        }

        // Inherited From aaa:Config
        // Type is an MO-Defined-Type
        leaf providerGroup4 {
            description "Provider Group";

            // Type is an MO-Defined-Type
            type aaa_ProviderGroupName;
        }

        // Inherited From aaa:Config
        // Type is an MO-Defined-Type
        leaf providerGroup5 {
            description "Provider Group";

            // Type is an MO-Defined-Type
            type aaa_ProviderGroupName;
        }

        // Inherited From aaa:Config
        // Type is an MO-Defined-Type
        leaf providerGroup6 {
            description "Provider Group";

            // Type is an MO-Defined-Type
            type aaa_ProviderGroupName;
        }

        // Inherited From aaa:Config
        // Type is an MO-Defined-Type
        leaf providerGroup7 {
            description "Provider Group";

            // Type is an MO-Defined-Type
            type aaa_ProviderGroupName;
        }

        // Inherited From aaa:Config
        // Type is an MO-Defined-Type
        leaf providerGroup8 {
            description "Provider Group";

            // Type is an MO-Defined-Type
            type aaa_ProviderGroupName;
        }
        leaf errEn {
            type boolean;
            default "true";
        }

        // Inherited From aaa:AuthConfig
        // Type is an MO-Defined-Type
        leaf authProtocol {
            description "Authentication Protocol";

            // Type is an MO-Defined-Type
            type aaa_authenticationProtocol;
        }

        // Inherited From aaa:AuthConfig
        // Type is an MO-Defined-Type
        leaf fallback {
            description "Fallback in case all AAA servers configured for remote authentication are unreachable";

            // Type is an MO-Defined-Type
            type aaa_Boolean;
        }

        // Inherited From aaa:AuthConfig
        // Type is an MO-Defined-Type
        leaf local {
            description "Use local username authentication";

            // Type is an MO-Defined-Type
            type aaa_Boolean;
        }

        // Inherited From aaa:AuthConfig
        // Type is an MO-Defined-Type
        leaf none {
            description "No authentication";

            // Type is an MO-Defined-Type
            type aaa_Boolean;
        }

        // MO representing the Default Authentication configuration for
        // all logins
        container defaultauth-items {

            // Added containment as a singleton: Prefix=defaultauth
            // Acquired From Package aaa
            uses aaa_DefaultAuth-group;
        }

        // MO representing the Authentication configuration for Console
        // Login
        container consoleauth-items {

            // Added containment as a singleton: Prefix=consoleauth
            // Acquired From Package aaa
            uses aaa_ConsoleAuth-group;
        }
    }

    grouping aaa_PreLoginBanner-group {

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Inherited From aaa:Banner
        // Modified by Override: aaa:PreLoginBanner->message
        // Type is an MO-Defined-Type
        leaf message {
            description "Login Banner Message";

            // Type is an MO-Defined-Type
            type aaa_BannerMsg;
        }

        // Inherited From aaa:Banner
        // Modified by Override: aaa:PreLoginBanner->guiMessage
        // Type is an MO-Defined-Type
        leaf guiMessage {
            description "Login GUI Message";

            // Type is an MO-Defined-Type
            type aaa_BannerMsg;
        }

        // Inherited From aaa:Banner
        // Modified by Override: aaa:PreLoginBanner->delimiter
        // Type is an MO-Defined-Type
        leaf delimiter {
            description "Delimiter character";

            // Type is an MO-Defined-Type
            type aaa_Delimiter;
        }

        // Rel-def target from preLoginBanner
        // Inherited From aaa:PreLoginBanner
        container rtpreLoginBanner-items {

            // Added containment as a singleton: Prefix=rtpreLoginBanner
            // Acquired From Package aaa
            uses aaa_RtPreLoginBanner_target-group;
        }
    }

    grouping aaa_RemoteUser-group {

        // Type is an MO-Defined-Type
        leaf loginTime {
            config "false";
            description "TBD";

            // Type is an MO-Defined-Type
            type aaa_Date;
        }

        // Type is an MO-Defined-Type
        leaf unixUserId {
            config "false";
            description "TBD";

            // Type is an MO-Defined-Type
            type aaa_ExternalUnixUID;
        }
        leaf ciscoAvPair {
            config "false";
            type string;
        }
        leaf loginDomain {
            config "false";
            type string;
        }

        // A boolean value indicating whether this has to be deleted or not
        // Type is an MO-Defined-Type
        leaf deleteFlag {
            description "delete remote user";

            // Type is an MO-Defined-Type
            type aaa_Boolean;
        }
        leaf sequenceNumber {
            config "false";
            type uint64;
            default "1";
        }

        // From Interface naming:Named
        // Inherited From naming:NamedObject
        // Modified by Override: aaa:RemoteUser->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Modified by Override: aaa:RemoteUser->descr
        // Type is an MO-Defined-Type
        leaf descr {
            config "false";
            description "Description";

            // Type is an MO-Defined-Type
            type naming_Descr;
        }
        container userdomain-items {
            list UserDomain-list {
                key "name";

                // Added containment: Prefix=userdomain
                // Acquired From Package aaa
                uses aaa_UserDomain-group;
            }
        }
    }

    grouping aaa_UserDomain-group {

        // From Interface naming:Named
        // Inherited From naming:NamedObject
        // Modified by Override: aaa:UserDomain->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        container role-items {
            list UserRole-list {
                key "name";

                // Added containment: Prefix=role
                // Acquired From Package aaa
                uses aaa_UserRole-group;
            }
        }
    }

    grouping aaa_UserRole-group {

        // Type is an MO-Defined-Type
        leaf privType {
            description "Privilege Type";

            // Type is an MO-Defined-Type
            type aaa_UserRolePrivType;
        }

        // From Interface naming:Named
        // Inherited From naming:NamedObject
        // Modified by Override: aaa:UserRole->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_User-group {

        // The user's first name
        // Type is an MO-Defined-Type
        leaf firstName {
            description "First Name";

            // Type is an MO-Defined-Type
            type naming_Name {
                length "0..32";
            }
        }

        // The user's last name
        // Type is an MO-Defined-Type
        leaf lastName {
            description "Last Name";

            // Type is an MO-Defined-Type
            type naming_Name {
                length "0..32";
            }
        }

        // The user's e-mail address
        // Type is an MO-Defined-Type
        leaf email {
            description "Email Address";

            // Type is an MO-Defined-Type
            type aaa_Email;
        }

        // The user's phone number
        // Type is an MO-Defined-Type
        leaf phone {
            description "Phone Number";

            // Type is an MO-Defined-Type
            type aaa_Phone;
        }

        // The expiration date of this account
        // Type is an MO-Defined-Type
        // Default value handled in local MO type
        leaf expiration {
            description "Account Expiration Date";

            // Type is a Local-MO-Defined-Type
            type aaa_Date_User_expiration;
        }

        // A boolean value indicating whether this account has an expiration date or not
        // Type is an MO-Defined-Type
        leaf expires {
            description "Expiration Set Status";

            // Type is an MO-Defined-Type
            type aaa_Boolean;
        }

        // Type is an MO-Defined-Type
        leaf allowExpired {
            description "Allow expired user to be configured";

            // Type is an MO-Defined-Type
            type aaa_Boolean;
        }

        // Type is an MO-Defined-Type
        leaf accountStatus {
            description "Account Status";

            // Type is an MO-Defined-Type
            type aaa_AccountStatus;
        }

        // Type is an MO-Defined-Type
        leaf pwd {
            description "Password";

            // Type is an MO-Defined-Type
            type aaa_Passwd;
        }

        // Type is an MO-Defined-Type
        leaf encPwd {
            config "false";
            description "BI encrypted password";

            // Type is an MO-Defined-Type
            type aaa_EncryptedArray;
        }

        // Type is an MO-Defined-Type
        leaf pwdLen {
            config "false";
            description "Length of user password";

            // Type is an MO-Defined-Type
            type aaa_PwdLen;
        }
        leaf pwdSet {
            config "false";
            type boolean;
            default "true";
        }

        // Type is an MO-Defined-Type
        leaf pwdEncryptType {
            description "Password Encryption Type";

            // Type is an MO-Defined-Type
            type aaa_KeyEncUserPass;
        }

        // Adding a property to hold the old value
        // Type is an MO-Defined-Type
        leaf oldPwdEncryptType {
            config "false";
            description "Old Password Encryption Type";

            // Type is an MO-Defined-Type
            type aaa_KeyEncUserPass;
        }

        // Type is an MO-Defined-Type
        leaf isSnmpNotify {
            config "false";
            description "Notify to snmp";

            // Type is an MO-Defined-Type
            type aaa_Boolean;
        }

        // Type is an MO-Defined-Type
        leaf pwdLifeTime {
            description "Password Life Time";

            // Type is an MO-Defined-Type
            type aaa_PwdLifeTime;
        }

        // This is to allow the admin/aaa users to clear
        // locally-authenticated users's password history
        // Type is an MO-Defined-Type
        leaf clearPwdHistory {
            description "Clear Password History";

            // Type is an MO-Defined-Type
            type aaa_Clear;
        }

        // Type is an MO-Defined-Type
        leaf unixUserId {
            description "TBD";

            // Type is an MO-Defined-Type
            type aaa_UnixUID;
        }

        // From Interface naming:Named
        // Inherited From naming:NamedObject
        // Modified by Override: aaa:User->name
        // Modified by Override: pol:Obj->name
        // Modified by Override: aaa:Definition->name
        // Type is an MO-Defined-Type
        leaf name {
            description "Name";

            // Type is an MO-Defined-Type
            type naming_Name {

                // Copied from "aaa:UserName" type
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        container sshauth-items {

            // Added containment as a singleton: Prefix=sshauth
            // Acquired From Package aaa
            uses aaa_SshAuth-group;
        }
        container usercert-items {
            list UserCert-list {
                key "name";

                // Added containment: Prefix=usercert
                // Acquired From Package aaa
                uses aaa_UserCert-group;
            }
        }
        container userdomain-items {
            list UserDomain-list {
                key "name";

                // Added containment: Prefix=userdomain
                // Acquired From Package aaa
                uses aaa_UserDomain-group;
            }
        }

        // Do not taking backup of this MO, this user data become invalid
        // with time
        container userdata-items {

            // Added containment as a singleton: Prefix=userdata
            // Acquired From Package aaa
            uses aaa_UserData-group;
        }
    }

    grouping aaa_SshAuth-group {

        // Type is an MO-Defined-Type
        leaf data {
            description "Ssh Authorization Data";

            // Type is an MO-Defined-Type
            type aaa_SshData;
        }
        leaf fingerprint {
            config "false";
            type string;
        }

        // From Interface naming:Named
        // Inherited From naming:NamedObject
        // Modified by Override: aaa:SshAuth->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_UserCert-group {

        // Type is an MO-Defined-Type
        leaf data {
            description "User X509 Certificate";

            // Type is an MO-Defined-Type
            type aaa_UserCertDataType;
        }
        leaf fingerprint {
            config "false";
            type string;
        }

        // Populated with the output of openssl output of the x509 certificate analysis
        // Type is an MO-Defined-Type
        leaf certificateDecodeInformation {
            config "false";
            description "TBD";

            // Type is an MO-Defined-Type
            type aaa_UserCertDataType;
        }

        // Populated with the PEM format public key extracted from the x509 certificate
        // Type is an MO-Defined-Type
        leaf publicKey {
            config "false";
            description "TBD";

            // Type is an MO-Defined-Type
            type aaa_UserCertDataType;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_UserData-group {
        leaf pwdChangedDate {
            config "false";
            type uint64;
        }

        // User password history, stores encrypted passwords
        // max of PwdProfile.historyCount recent passwords are stored
        // Type is an MO-Defined-Type
        leaf pwdHistory {
            config "false";
            description "Password History";

            // Type is an MO-Defined-Type
            type aaa_PwdHistory;
        }

        // How many times user has changed the password within
        // the given time interval
        // (pwdChangeIntervalBegin + PwdProfile.changeInterval)
        // Type is an MO-Defined-Type
        leaf pwdChangeCount {
            config "false";
            description "Password Change Count";

            // Type is an MO-Defined-Type
            type aaa_PwdChangeCount;
        }
        leaf pwdChangeIntervalBegin {
            config "false";
            type uint64;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_Role-group {

        // Type is an MO-Defined-Type
        leaf denyVRF {
            description "Deny all VRF except allowed ones";

            // Type is an MO-Defined-Type
            type aaa_Boolean;
        }

        // Type is an MO-Defined-Type
        leaf allowedVRF {
            description "mention the allowed VRF if denyVRF is set to yes";

            // Type is an MO-Defined-Type
            type aaa_RuleEntityType;
        }

        // Type is an MO-Defined-Type
        leaf denyVLAN {
            description "Deny all VLAN except allowed ones";

            // Type is an MO-Defined-Type
            type aaa_Boolean;
        }

        // Type is an MO-Defined-Type
        leaf allowedVLAN {
            description "mention the allowed VLAN if denyVLAN is set to yes";

            // Type is an MO-Defined-Type
            type aaa_RuleEntityType;
        }

        // Type is an MO-Defined-Type
        leaf denyIntf {
            description "Deny all interfaces except allowed ones";

            // Type is an MO-Defined-Type
            type aaa_Boolean;
        }
        leaf priv {
            type string;
        }

        // Type is an MO-Defined-Type
        leaf rolePrivType {
            description "Privilege Type";

            // Type is an MO-Defined-Type
            type aaa_UserRolePrivType;
        }

        // Type is an MO-Defined-Type
        leaf roleIsBuiltin {
            config "false";
            description "Role is Built-in";

            // Type is an MO-Defined-Type
            type aaa_Boolean;
        }

        // Type is an MO-Defined-Type
        leaf resetToFactory {
            description "Trigger Reset to Factory settings";

            // Type is an MO-Defined-Type
            type aaa_Boolean;
        }

        // From Interface naming:Named
        // Inherited From naming:NamedObject
        // Modified by Override: aaa:Role->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Modified by Override: aaa:Role->descr
        // Type is an MO-Defined-Type
        leaf descr {
            description "Description";

            // Type is an MO-Defined-Type
            type naming_Descr;
        }
        container rule-items {
            list RoleRule-list {
                key "ruleNumber";

                // Added containment: Prefix=rule
                // Acquired From Package aaa
                uses aaa_RoleRule-group;
            }
        }
        container intf-items {
            list RoleIntf-list {
                key "intfName";

                // Added containment: Prefix=intf
                // Acquired From Package aaa
                uses aaa_RoleIntf-group;
            }
        }
    }

    grouping aaa_RoleRule-group {

        // Type is an MO-Defined-Type
        leaf ruleNumber {
            description "Role Rule number";

            // Type is an MO-Defined-Type
            type aaa_RuleNumberType;
        }

        // Type is an MO-Defined-Type
        leaf permission {
            description "Permission type permit or deny";

            // Type is an MO-Defined-Type
            type aaa_RulePermissionType;
        }

        // Type is an MO-Defined-Type
        leaf ruleAccess {
            description "Rule access type command or read or read-write";

            // Type is an MO-Defined-Type
            type aaa_RuleAccessType;
        }

        // Type is an MO-Defined-Type
        leaf ruleScope {
            description "Role Rule scope feature or feature-group or OID";

            // Type is an MO-Defined-Type
            type aaa_RuleScopeType;
        }

        // Type is an MO-Defined-Type
        leaf cmdStr {
            description "Allowed command string pattern";

            // Type is an MO-Defined-Type
            type aaa_RuleCmdStrType;
        }

        // Type is an MO-Defined-Type
        leaf scopeEntity {
            description "Allowed scope string";

            // Type is an MO-Defined-Type
            type aaa_RuleEntityType;
        }
    }

    grouping aaa_RoleIntf-group {
        leaf intfName {
            type string;
        }

        // Type is an MO-Defined-Type
        leaf allowInst {
            description "interface instances which can be allowed and deny rest";

            // Type is an MO-Defined-Type
            type aaa_RuleEntityType;
        }
    }

    grouping aaa_FactoryRole-group {
        leaf priv {
            config "false";
            type string;
        }

        // Type is an MO-Defined-Type
        leaf resetToFactory {
            description "Trigger Reset to Factory settings";

            // Type is an MO-Defined-Type
            type aaa_Boolean;
        }

        // From Interface naming:Named
        // Inherited From naming:NamedObject
        // Modified by Override: aaa:FactoryRole->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_Domain-group {

        // From Interface naming:Named
        // Inherited From naming:NamedObject
        // Modified by Override: aaa:Domain->name
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping aaa_PwdProfile-group {

        // Interval used to warn the users whose password is closed
        // to expiry date. warn the user before expirationWarnTime
        // days of actual password expiration.
        // Type is an MO-Defined-Type
        leaf expirationWarnTime {
            description "Password Expiration Warn Time in Days";

            // Type is an MO-Defined-Type
            type aaa_PwdExpWarnTime;
        }

        // How many recent user passwords should be stored in user
        // password history.
        // Type is an MO-Defined-Type
        leaf historyCount {
            description "Password History Count";

            // Type is an MO-Defined-Type
            type aaa_HistoryDepth;
        }

        // There are two ways of restricting the user from changing
        // the password frequently.
        // 1. allow no passwd changes within given time interval.
        // 2. allow max of n psswd changes within give time interval.
        // noChangeInterval holds the 1st policy mentioned above
        // Type is an MO-Defined-Type
        leaf noChangeInterval {
            description "No Password Change Interval in Hours";

            // Type is an MO-Defined-Type
            type aaa_PwdChangeInterval;
        }

        // ChangeInterval holds the 2nd policy mentioned above
        // Type is an MO-Defined-Type
        leaf changeInterval {
            description "Change Interval in Hours";

            // Type is an MO-Defined-Type
            type aaa_PwdChangeInterval;
        }

        // stores which one of the above two policies is active now
        // Type is an MO-Defined-Type
        leaf changeDuringInterval {
            description "Password Policy";

            // Type is an MO-Defined-Type
            type aaa_PwdPolicy;
        }

        // How many password changes allowed within changeInterval
        // Type is an MO-Defined-Type
        leaf changeCount {
            description "Number of Password Changes in Interval";

            // Type is an MO-Defined-Type
            type aaa_PwdChangeCount;
        }

        // From Interface naming:Named
        // Inherited From naming:NamedObject
        // Modified by Override: pol:Obj->name
        // Modified by Override: aaa:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping pki_Ep-group {

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        container webtokendata-items {

            // Added containment as a singleton: Prefix=webtokendata
            // Acquired From Package pki
            uses pki_WebTokenData-group;
        }

        // Csync2 Pre Shared Key - used to distribute the key to all IFC nodes
        container csyncsharedkey-items {

            // Added containment as a singleton: Prefix=csyncsharedkey
            // Acquired From Package pki
            uses pki_CsyncSharedKey-group;
        }

        // Csync2 Policy - used to control csync timeout and enable/disable
        container csyncpolicy-items {

            // Added containment as a singleton: Prefix=csyncpolicy
            // Acquired From Package pki
            uses pki_CsyncPolicy-group;
        }

        container dbgplgch-items {

            // Added containment as a singleton: Prefix=dbgplgch
            // Acquired From Package pki
            uses pki_DebugPluginChallenge-group;
        }
        container keyring-items {
            list KeyRing-list {
                key "name";

                // Added containment: Prefix=keyring
                // Acquired From Package pki
                uses pki_KeyRing-group;
            }
        }

        // CertificateAuthority object, also called Trust Points in DCOS
        container tp-items {
            list TP-list {
                key "name";

                // Added containment: Prefix=tp
                // Acquired From Package pki
                uses pki_TP-group;
            }
        }

        // Rel-def target from resPkiEp
        // Inherited From pki:Ep
        container rtfabricResPkiEp-items {

            // Abstract containment of rtfabricResPkiEp derived from pki:Ep
            list RtFabricResPkiEp-list {
                config "false";
                key "tDn";

                // Added containment: Prefix=rtfabricResPkiEp
                // Acquired From Package fabric
                uses fabric_RtFabricResPkiEp_target-group;
            }
        }
    }

    grouping pki_WebTokenData-group {

        // The encryption parameters cannot be modified by a client request
        // Type is an MO-Defined-Type
        leaf key {
            config "false";
            description "TBD";

            // Type is an MO-Defined-Type
            type pki_AES128Key {
                length "24";
            }
        }

        // Type is an MO-Defined-Type
        leaf initializationVector {
            config "false";
            description "TBD";

            // Type is an MO-Defined-Type
            type pki_AES128IV {
                length "24";
            }
        }

        // Type is an MO-Defined-Type
        leaf hashSecret {
            config "false";
            description "TBD";

            // Type is an MO-Defined-Type
            type pki_SHA256_SharedSecret16 {
                length "24";
            }
        }

        // Token timeout modifications are allowed
        // Type is an MO-Defined-Type
        leaf webtokenTimeoutSeconds {
            description "Timeout in Seconds";

            // Type is an MO-Defined-Type
            type pki_WebTokenTimeoutType;
        }

        // Knob to control absolute maximum validity period for a webtoken beyond which it cannot be refreshed    Units are in hours - minimum 4 hours, maximum 24 hours
        // Type is an MO-Defined-Type
        leaf maximumValidityPeriod {
            description "Maximum Validity Period in hours";

            // Type is an MO-Defined-Type
            type pki_WebTokenValidityPeriodType;
        }

        // Type is an MO-Defined-Type
        leaf uiIdleTimeoutSeconds {
            description "GUI Idle Timeout in Seconds";

            // Type is an MO-Defined-Type
            type pki_GuiIdleTimeoutType;
        }

        // Type is an MO-Defined-Type
        leaf sessionRecordFlags {
            description "Session Recording Options";

            // Type is an MO-Defined-Type
            type pki_SessionRecordFlags;
        }
        leaf siteFingerprint {
            config "false";
            type string;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping pki_CsyncSharedKey-group {

        // The encryption parameters cannot be modified by any client requests
        // Type is an MO-Defined-Type
        leaf key {
            config "false";
            description "TBD";

            // Type is an MO-Defined-Type
            type pki_Csync2KeyType;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping pki_CsyncPolicy-group {

        // Type is an MO-Defined-Type
        leaf state {
            description "TBD";

            // Type is an MO-Defined-Type
            type pki_CsyncActivationStateType;
        }

        // Type is an MO-Defined-Type
        leaf interval {
            description "TBD";

            // Type is an MO-Defined-Type
            type pki_CsyncRefreshIntervalType;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Csync2 Element - contains
        // a) file pattern
        // b) type of pattern (include or exclude)
        // c) symbolic name of the pattern
        container csyncelem-items {
            list CsyncElement-list {
                key "name";

                // Added containment: Prefix=csyncelem
                // Acquired From Package pki
                uses pki_CsyncElement-group;
            }
        }
    }

    grouping pki_CsyncElement-group {
        leaf pattern {
            type string;
        }

        // Type is an MO-Defined-Type
        leaf type {
            description "TBD";

            // Type is an MO-Defined-Type
            type pki_CsyncElementType;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping pki_DebugPluginChallenge-group {
        leaf challenge {
            type string;
        }
        leaf oldChallenge {
            type string;
        }
        leaf timeGenerated {
            type uint64;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping pki_KeyRing-group {

        // Type is an MO-Defined-Type
        leaf adminState {
            description "TBD";

            // Type is an MO-Defined-Type
            type pki_KeyringState;
        }
        leaf regen {
            type boolean;
            default "true";
        }

        // Type is an MO-Defined-Type
        leaf key {
            description "TBD";

            // Type is an MO-Defined-Type
            type pki_PrivateKey;
        }

        // Type is an MO-Defined-Type
        leaf modulus {
            description "Modulus";

            // Type is an MO-Defined-Type
            type pki_Modulus;
        }

        // Type is an MO-Defined-Type
        leaf cert {
            description "Certificate";

            // Type is an MO-Defined-Type
            type pki_Cert;
        }

        // Type is an MO-Defined-Type
        leaf certValidUntil {
            config "false";
            description "Certificate Validity";

            // Type is an MO-Defined-Type
            type pki_CertValidity;
        }

        // Populated with the output of openssl output of the x509 certificate analysis
        // Type is an MO-Defined-Type
        leaf certificateDecodeInformation {
            config "false";
            description "Certificate Decode Information";

            // Type is an MO-Defined-Type
            type pki_Cert;
        }

        // trust point (CA) reference
        // DN IS IMPLIED AND RESOLVED PROGRAMATICALLY
        // refers="pki:TP"
        // Type is an MO-Defined-Type
        leaf tp {
            description "Certificate Authority";

            // Type is an MO-Defined-Type
            type naming_Name;
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        container certreq-items {

            // Added containment as a singleton: Prefix=certreq
            // Acquired From Package pki
            uses pki_CertReq-group;
        }

        // Rel-def target from KeyRing
        // Inherited From pki:KeyRing
        container rtcommKeyRing-items {

            // Abstract containment of rtcommKeyRing derived from pki:KeyRing
            list RtCommKeyRing-list {
                key "tDn";

                // Added containment: Prefix=rtcommKeyRing
                // Acquired From Package comm
                uses comm_RtCommKeyRing_target-group;
            }
        }

        // Rel-def target from keyringRef
        // Inherited From pki:KeyRing
        container rtaaaKeyringRef-items {

            // Abstract containment of rtaaaKeyringRef derived from pki:KeyRing
            list RtAaaKeyringRef-list {
                config "false";
                key "tDn";

                // Added containment: Prefix=rtaaaKeyringRef
                // Acquired From Package aaa
                uses aaa_RtAaaKeyringRef_target-group;
            }
        }
    }

    grouping pki_CertReq-group {
        leaf pwd {
            type string;
        }

        // TODO how to set this value to hostname by default
        // Type is an MO-Defined-Type
        leaf subjName {
            description "Subject Name";

            // Type is an MO-Defined-Type
            type naming_Name {
                length "1..64";
            }
        }

        // Type is an MO-Defined-Type
        leaf email {
            description "Email Address";

            // Type is an MO-Defined-Type
            type naming_Name {
                length "0..40";
            }
        }

        // Type is an MO-Defined-Type
        leaf country {
            description "Country";

            // Type is an MO-Defined-Type
            type naming_Name {
            }
        }

        // Type is an MO-Defined-Type
        leaf state {
            description "State";

            // Type is an MO-Defined-Type
            type naming_Name {
                length "0..64";
            }
        }

        // Type is an MO-Defined-Type
        leaf locality {
            description "Locality";

            // Type is an MO-Defined-Type
            type naming_Name {
                length "0..64";
            }
        }

        // Type is an MO-Defined-Type
        leaf orgUnitName {
            description "Organization Unit Name";

            // Type is an MO-Defined-Type
            type naming_Name {
                length "0..64";
            }
        }

        // Type is an MO-Defined-Type
        leaf orgName {
            description "Organization Name";

            // Type is an MO-Defined-Type
            type naming_Name {
                length "0..64";
            }
        }

        // PEM encoded certificate request
        // Type is an MO-Defined-Type
        leaf req {
            config "false";
            description "TBD";

            // Type is an MO-Defined-Type
            type pki_Cert;
        }
    }

    grouping pki_TP-group {

        // Type is an MO-Defined-Type
        leaf certChain {
            description "Certificate Chain";

            // Type is an MO-Defined-Type
            type pki_Cert;
        }

        // Certificate Fingerprint populated by backend
        // Type is an MO-Defined-Type
        leaf fp {
            config "false";
            description "TBD";

            // Type is an MO-Defined-Type
            type pki_FP;
        }
        leaf numCerts {
            config "false";
            type uint32;
            default "0";
        }

        // From Interface naming:Named
        // Inherited From naming:NamedObject
        // Modified by Override: pol:Obj->name
        // Modified by Override: pki:Definition->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping mock_MockRoot-group {
        leaf disable {
            type boolean;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        container session-items {
            list MockSession-list {
                key "name";

                // Added containment: Prefix=session
                // Acquired From Package mock
                uses mock_MockSession-group;
            }
        }
    }

    grouping mock_MockSession-group {

        // The DN of the mocked Observable
        // Type is an MO-Defined-Type
        leaf observable {
            description "DN of a Mocked Mo";

            // Type is an MO-Defined-Type
            type mock_Observable;
        }

        // The duration of the mock operation
        // Type is an MO-Defined-Type
        leaf duration {
            description "Duration of Mock Session ";

            // Type is an MO-Defined-Type
            type mock_Duration;
        }

        // The duration of the mock operation
        // Type is an MO-Defined-Type
        leaf mode {
            description "Mock Session Mode ";

            // Type is an MO-Defined-Type
            type mock_Mode;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        container stat-items {
            list Stats-list {
                key "nameSpace statName";

                // Added containment: Prefix=stat
                // Acquired From Package mock
                uses mock_Stats-group;
            }
        }
    }

    grouping mock_Stats-group {

        // The namespace of the Stats
        // Type is an MO-Defined-Type
        leaf nameSpace {
            description "Stat Namespace ";

            // Type is an MO-Defined-Type
            type naming_Name;
        }

        // The name of the Stats
        // Type is an MO-Defined-Type
        leaf statName {
            description "Stat Name ";

            // Type is an MO-Defined-Type
            type naming_Name;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
        container counter-items {
            list Counter-list {
                key "name";

                // Added containment: Prefix=counter
                // Acquired From Package mock
                uses mock_Counter-group;
            }
        }
    }

    grouping mock_Counter-group {

        // The start value of the mocked counter
        // Type is an MO-Defined-Type
        leaf start {
            description "Start Value of Mocked Counter ";

            // Type is an MO-Defined-Type
            type mock_Value;
        }

        // The end value of the mocked counter
        // Type is an MO-Defined-Type
        leaf end {
            description "End Value of Mocked Counter ";

            // Type is an MO-Defined-Type
            type mock_Value;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping stp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per stp instance information. There is
        // only one instance of stp running in the system today
        container inst-items {

            // Added containment as a singleton: Prefix=inst
            // Acquired From Package stp
            uses stp_Inst-group;
        }
    }

    grouping stp_Inst-group {

        // Spanning Tree operating mode
        // Type is an MO-Defined-Type
        leaf mode {
            description "Protocol Mode";

            // Type is an MO-Defined-Type
            type stp_Mode;
        }

        // Linecard ISSU type
        // Type is an MO-Defined-Type
        leaf lcIssu {
            description "Linecard ISSU type";

            // Type is an MO-Defined-Type
            type stp_LcIssu;
        }

        // pathcost options
        // Type is an MO-Defined-Type
        leaf pathcostOp {
            description "Spanning tree pathcost options";

            // Type is an MO-Defined-Type
            type stp_PathcostOp;
        }

        // Enable STP for FCoE VLANs
        // Type is an MO-Defined-Type
        leaf fcoe {
            description "enable spanning tree for fcoe vlan";

            // Type is an MO-Defined-Type
            type nw_AdminSt;
        }

        // Enable spanning tree bridge assurance
        // Type is an MO-Defined-Type
        leaf bridge {
            description "enable spanning-tree bridge assurance on all ports";

            // Type is an MO-Defined-Type
            type stp_AdminSt;
        }

        // spanning tree loopguard options
        // Type is an MO-Defined-Type
        leaf loopguard {
            description "enable loop guard on all ports";

            // Type is an MO-Defined-Type
            type stp_AdminSt;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Modified by Override: stp:Inst->ctrl
        // Type is an MO-Defined-Type
        // Default value handled in local MO type
        leaf ctrl {
            description "Controls";

            // Type is a Local-MO-Defined-Type
            type nw_InstCtrl_Inst_ctrl;
        }

        // Operational errors qualifier
        // Inherited From nw:CpInst
        // Type is an MO-Defined-Type
        leaf operErr {
            config "false";
            description "Operational Errors Qualifier";

            // Type is an MO-Defined-Type
            type nw_OperErrQual;
        }

        // This object holds mcp information that is operated at a
        // interface level
        container if-items {
            list If-list {
                key "id";

                // Added containment: Prefix=if
                // Acquired From Package stp
                uses stp_If-group;
            }
        }

        // Holds mst informaton at switch level
        container mstent-items {

            // Added containment as a singleton: Prefix=mstent
            // Acquired From Package stp
            uses stp_MstEntity-group;
        }

        // stp pseudo-information, placeholder for future implementation
        container pseudo-items {

            // Added containment as a singleton: Prefix=pseudo
            // Acquired From Package stp
            uses stp_PseudoInfo-group;
        }

        // This object holds stp information that is operated at
        // vlan level
        container vlan-items {
            list Vlan-list {
                key "id";

                // Added containment: Prefix=vlan
                // Acquired From Package stp
                uses stp_Vlan-group;
            }
        }
    }

    grouping stp_If-group {

        // Port mode
        // Type is an MO-Defined-Type
        leaf mode {
            description "Mode";

            // Type is an MO-Defined-Type
            type stp_IfMode;
        }

        // Interface controls
        // Type is an MO-Defined-Type
        leaf ctrl {
            config "false";
            description "Controls";

            // Type is an MO-Defined-Type
            type stp_IfControl;
        }

        // Path Cost
        // Type is an MO-Defined-Type
        leaf cost {
            description "Path Cost";

            // Type is an MO-Defined-Type
            type stp_Cost;
        }

        // guard mode
        // Type is an MO-Defined-Type
        leaf guard {
            description "Guard Mode";

            // Type is an MO-Defined-Type
            type stp_Guard;
        }

        // bpdufilter mode
        // Type is an MO-Defined-Type
        leaf bpdufilter {
            description "bpdufilter mode";

            // Type is an MO-Defined-Type
            type stp_Bpdufilter;
        }

        // bpduguard mode
        // Type is an MO-Defined-Type
        leaf bpduguard {
            description "Guard Mode";

            // Type is an MO-Defined-Type
            type stp_BPDUGuard;
        }

        // Linecard Issu options
        // Type is an MO-Defined-Type
        leaf lcIssu {
            description "LC Issu options";

            // Type is an MO-Defined-Type
            type stp_LcIssu;
        }

        // Link Type
        // Type is an MO-Defined-Type
        leaf linkType {
            description "Link Type";

            // Type is an MO-Defined-Type
            type stp_LinkType;
        }

        // Port Priority
        // Type is an MO-Defined-Type
        leaf priority {
            description "Port Priority";

            // Type is an MO-Defined-Type
            type stp_PortPriority;
        }

        // PortFast
        // Type is an MO-Defined-Type
        leaf portFast {
            description "Port Fast";

            // Type is an MO-Defined-Type
            type stp_PortFast;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object describes interface level config per vlan
        container vlan-items {
            list VlanCfg-list {
                key "vlanId";

                // Added containment: Prefix=vlan
                // Acquired From Package stp
                uses stp_VlanCfg-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping stp_VlanCfg-group {

        // Vlan Id
        // Type is an MO-Defined-Type
        leaf vlanId {
            description "Vlan Id";

            // Type is an MO-Defined-Type
            type stp_VlanId;
        }

        // Port Priority in increments of 32
        // Type is an MO-Defined-Type
        leaf priority {
            description "Port Priority";

            // Type is an MO-Defined-Type
            type stp_PortPriority;
        }

        // Port path cost
        // Type is an MO-Defined-Type
        leaf cost {
            description "Port Path Cost";

            // Type is an MO-Defined-Type
            type stp_Cost;
        }
    }

    grouping stp_MstEntity-group {

        // max hops value for spanning tree
        // Type is an MO-Defined-Type
        leaf maxHops {
            description "STP mst max hops value";

            // Type is an MO-Defined-Type
            type stp_MaxHops;
        }

        // enable spanning tree simulation
        // Type is an MO-Defined-Type
        leaf simulate {
            description "spanning tree simulation";

            // Type is an MO-Defined-Type
            type stp_Simulate;
        }

        // operation error
        // Type is an MO-Defined-Type
        leaf operErr {
            config "false";
            description "Operation Error Qualifier";

            // Type is an MO-Defined-Type
            type nw_OperErrQual;
        }

        // spanning tree state: enabled or disabled
        // Inherited From stp:StEntity
        // Modified by Override: stp:MstEntity->adminSt
        // Type is an MO-Defined-Type
        leaf adminSt {
            description "Admin State";

            // Type is an MO-Defined-Type
            type nw_AdminSt;
        }

        // spanning tree forward delay
        // Inherited From stp:StEntity
        // Type is an MO-Defined-Type
        leaf fwdTime {
            description "STP forward delay";

            // Type is an MO-Defined-Type
            type stp_FwdTime;
        }

        // spanning tree hello interval
        // Inherited From stp:StEntity
        // Type is an MO-Defined-Type
        leaf helloTime {
            description "STP Hello interval";

            // Type is an MO-Defined-Type
            type stp_HelloTime;
        }

        // spanning tree max age interval
        // Inherited From stp:StEntity
        // Type is an MO-Defined-Type
        leaf maxAge {
            description "STP max age interval";

            // Type is an MO-Defined-Type
            type stp_MaxAge;
        }

        // Holds stp domain information
        container mst-items {
            list Region-list {
                key "name";

                // Added containment: Prefix=mst
                // Acquired From Package stp
                uses stp_Region-group;
            }
        }
    }

    grouping stp_Region-group {

        // Region name
        // Type is an MO-Defined-Type
        leaf regName {
            config "false";
            description "Region Name";

            // Type is an MO-Defined-Type
            type stp_RegName;
        }

        // Region revision
        // Type is an MO-Defined-Type
        leaf rev {
            config "false";
            description "Region Revision";

            // Type is an MO-Defined-Type
            type stp_RegRev;
        }

        // Inherited From nw:Conn
        // Modified by Override: nw:CpDom->name
        // Type is an MO-Defined-Type
        leaf name {
            description "Name";

            // Type is an MO-Defined-Type
            type naming_Name {
                length "1..64";
            }
        }

        // This objects describes an mst instance
        container mst-items {
            list MstDom-list {
                config "false";
                key "id";

                // Added containment: Prefix=mst
                // Acquired From Package stp
                uses stp_MstDom-group;
            }
        }
    }

    grouping stp_MstDom-group {

        // Id
        // Type is an MO-Defined-Type
        leaf id {
            config "false";
            description "ID";

            // Type is an MO-Defined-Type
            type stp_MstId;
        }

        // root type
        // Type is an MO-Defined-Type
        leaf root {
            description "Root Options";

            // Type is an MO-Defined-Type
            type stp_Root;
        }

        // network diameter
        // Type is an MO-Defined-Type
        leaf diameter {
            description "Network Diameter";

            // Type is an MO-Defined-Type
            type stp_Diameter;
        }

        // hello interval
        // Type is an MO-Defined-Type
        leaf helloTime {
            description "Hello interval";

            // Type is an MO-Defined-Type
            type stp_HelloTime;
        }

        // priority
        // Type is an MO-Defined-Type
        leaf priority {
            description "Bridge Priority";

            // Type is an MO-Defined-Type
            type stp_BridgePriority;
        }

        // Inherited From nw:Conn
        // Modified by Override: nw:CpDom->name
        // Type is an MO-Defined-Type
        leaf name {
            description "Name";

            // Type is an MO-Defined-Type
            type naming_Name {
                length "1..64";
            }
        }

        // This objects describes a vlan range
        container vlan-items {
            list VlanRange-list {
                config "false";
                key "start end";

                // Added containment: Prefix=vlan
                // Acquired From Package stp
                uses stp_VlanRange-group;
            }
        }
    }

    grouping stp_VlanRange-group {

        // Start of the range
        // Type is an MO-Defined-Type
        leaf start {
            config "false";
            description "Start";

            // Type is an MO-Defined-Type
            type stp_VlanId;
        }

        // End of the range
        // Type is an MO-Defined-Type
        leaf end {
            config "false";
            description "End";

            // Type is an MO-Defined-Type
            type stp_VlanId;
        }
    }

    grouping stp_PseudoInfo-group;

    grouping stp_Vlan-group {

        // vlan id
        // Type is an MO-Defined-Type
        leaf id {
            description "Access Encapsulation";

            // Type is an MO-Defined-Type
            type stp_VlanId;
        }

        // bridge priority
        // Type is an MO-Defined-Type
        leaf priority {
            description "Bridge Priority";

            // Type is an MO-Defined-Type
            type stp_Priority;
        }

        // root options
        // Type is an MO-Defined-Type
        leaf root {
            description "Root Options";

            // Type is an MO-Defined-Type
            type stp_Root;
        }

        // network diameter of spanning tree
        // Type is an MO-Defined-Type
        leaf diameter {
            description "network diameter";

            // Type is an MO-Defined-Type
            type stp_Diameter;
        }

        // operation error
        // Type is an MO-Defined-Type
        leaf operErr {
            config "false";
            description "Operation Error Qualifier";

            // Type is an MO-Defined-Type
            type nw_OperErrQual;
        }

        // Spanning tree protocol
        // Type is an MO-Defined-Type
        leaf protocol {
            config "false";
            description "Spanning tree protocol";

            // Type is an MO-Defined-Type
            type stp_Protocol;
        }
        leaf bridgePriority {
            type uint16;
        }
        leaf bridgeAddress {
            config "false";
            type address_Mac;
        }
        leaf rootPriority {
            type uint16;
        }
        leaf rootAddress {
            config "false";
            type address_Mac;
        }
        leaf rootPortPriority {
            type uint16;
        }
        leaf rootPortNumber {
            config "false";
            type uint16;
        }

        // Root port name. The interface name that corresponds to the
        // root port. E.g. eth1/1.
        // From Interface stp:RootPort
        // Type is an MO-Defined-Type
        leaf rootPort {
            config "false";
            description "Root port name";

            // Type is an MO-Defined-Type
            type nw_IfId;
        }
        leaf rootPathCost {
            config "false";
            type uint32;
        }

        // spanning tree state: enabled or disabled
        // Inherited From stp:StEntity
        // Modified by Override: stp:Vlan->adminSt
        // Type is an MO-Defined-Type
        leaf adminSt {
            description "Admin State";

            // Type is an MO-Defined-Type
            type nw_AdminSt;
        }

        // spanning tree forward delay
        // Inherited From stp:StEntity
        // Type is an MO-Defined-Type
        leaf fwdTime {
            description "STP forward delay";

            // Type is an MO-Defined-Type
            type stp_FwdTime;
        }

        // spanning tree hello interval
        // Inherited From stp:StEntity
        // Type is an MO-Defined-Type
        leaf helloTime {
            description "STP Hello interval";

            // Type is an MO-Defined-Type
            type stp_HelloTime;
        }

        // spanning tree max age interval
        // Inherited From stp:StEntity
        // Type is an MO-Defined-Type
        leaf maxAge {
            description "STP max age interval";

            // Type is an MO-Defined-Type
            type stp_MaxAge;
        }

        // This object holds STP VLAN interface operational
        // information.
        container if-items {
            list VlanIf-list {
                config "false";
                key "id";

                // Added containment: Prefix=if
                // Acquired From Package stp
                uses stp_VlanIf-group;
            }
        }
    }

    grouping stp_VlanIf-group {

        // Interface ID.
        // Type is an MO-Defined-Type
        leaf id {
            config "false";
            description "Interface ID";

            // Type is an MO-Defined-Type
            type nw_IfId;
        }
        leaf designatedRootPriority {
            type uint16;
        }
        leaf designatedRootAddress {
            config "false";
            type address_Mac;
        }
        leaf designatedRootCost {
            config "false";
            type uint32;
        }
        leaf designatedBridgePriority {
            type uint16;
        }
        leaf designatedBridgeAddress {
            config "false";
            type address_Mac;
        }
        leaf designatedPortPriority {
            type uint16;
        }
        leaf designatedPortNumber {
            config "false";
            type uint16;
        }
        leaf portPriority {
            type uint16;
        }
        leaf portNumber {
            config "false";
            type uint16;
        }
        leaf portPathCost {
            config "false";
            type uint32;
        }

        // Port role
        // From Interface stp:Port
        // Type is an MO-Defined-Type
        leaf portRole {
            config "false";
            description "Port role";

            // Type is an MO-Defined-Type
            type stp_PortRole;
        }

        // Port state
        // From Interface stp:Port
        // Type is an MO-Defined-Type
        leaf portState {
            config "false";
            description "Port state";

            // Type is an MO-Defined-Type
            type stp_PortState;
        }
    }

    grouping aggregate_BdTable-group {

        // Aggregate BdEntry
        container vlan-items {
            list BdEntry-list {
                key "vlan";

                // Added containment: Prefix=vlan
                // Acquired From Package aggregate
                uses aggregate_BdEntry-group;
            }
        }
    }

    grouping aggregate_BdEntry-group {
        leaf vlan {
            type string;
        }
        leaf bd {
            type uint32;
        }
        leaf vnid {
            type string;
        }

        // Type is an MO-Defined-Type
        leaf replicationMode {
            description "ReplicationMode";

            // Type is an MO-Defined-Type
            type aggregate_ReplicationModeType;
        }

        // Type is an MO-Defined-Type
        leaf ingressRepProtocol {
            description "ReplicationMode";

            // Type is an MO-Defined-Type
            type aggregate_IngressRepProtocolType;
        }
        leaf gipo {
            type address_Ip;
        }

        // Type is an MO-Defined-Type
        leaf suppressArp {
            description "SuppressArp";

            // Type is an MO-Defined-Type
            type aggregate_BooleanFlag;
        }

        // Type is an MO-Defined-Type
        leaf resourceStatus {
            description "Backend Resource Status";

            // Type is an MO-Defined-Type
            type aggregate_ResourceStatus;
        }

        // Type is an MO-Defined-Type
        leaf isL3 {
            description "Is L3 Vlan";

            // Type is an MO-Defined-Type
            type aggregate_BooleanFlag;
        }
        leaf description {
            type string;
        }

        container floodList-items {

            // Added containment as a singleton: Prefix=floodList
            // Acquired From Package aggregate
            uses aggregate_FloodList-group;
        }

        // Domain (vrf) information    <mo name="Domain"
        // concrete="yes"
        // label="Domain"
        // read-access="access-protocol-util"
        // access="tenant-ext-protocol-util"
        // >
        // <property name="vrf"
        // type="string:Basic"
        // owner="management"
        // mod="explicit"
        // label="VRF"
        // />
        // <property name="rd"
        // type="base:Community"
        // owner="management"
        // mod="explicit"
        // label="Route Distinguisher"
        // />
        // </mo>
        // <chunk target="Domain"
        // owner="policyelem"
        // type="primary">
        // <prop target="vrf"/>
        // </chunk>
        // <rn mo="Domain">
        // <item prefix="dom" property="vrf"/>
        // </rn>
        // <contains parent="BdEntry"
        // child="Domain"
        // />   List of route types
        container af-items {
            list DomainAf-list {
                key "type";

                // Added containment: Prefix=af
                // Acquired From Package aggregate
                uses aggregate_DomainAf-group;
            }
        }

        // Rel-def target from vlanMemberAtt
        // Inherited From aggregate:BdEntry
        container rtaggregateVlanMemberAtt-items {

            // Abstract containment of rtaggregateVlanMemberAtt derived from aggregate:BdEntry
            list RtAggregateVlanMemberAtt-list {
                config "false";
                key "tDn";

                // Added containment: Prefix=rtaggregateVlanMemberAtt
                // Acquired From Package aggregate
                uses aggregate_RtAggregateVlanMemberAtt_target-group;
            }
        }
    }

    grouping aggregate_FloodList-group {

        container localFloodList-items {

            // Added containment as a singleton: Prefix=localFloodList
            // Acquired From Package aggregate
            uses aggregate_LocalFloodList-group;
        }

        container remoteFloodList-items {

            // Added containment as a singleton: Prefix=remoteFloodList
            // Acquired From Package aggregate
            uses aggregate_RemoteFloodList-group;
        }
    }

    grouping aggregate_LocalFloodList-group {
        container intf-items {
            list LocalFloodListEntry-list {
                key "intf";

                // Added containment: Prefix=intf
                // Acquired From Package aggregate
                uses aggregate_LocalFloodListEntry-group;
            }
        }
    }

    grouping aggregate_LocalFloodListEntry-group {

        // Type is an MO-Defined-Type
        leaf intf {
            description "Interface";

            // Type is an MO-Defined-Type
            type nw_IfId;
        }
    }

    grouping aggregate_RemoteFloodList-group {
        container vtep-items {
            list RemoteFloodListEntry-list {
                key "vtep";

                // Added containment: Prefix=vtep
                // Acquired From Package aggregate
                uses aggregate_RemoteFloodListEntry-group;
            }
        }
    }

    grouping aggregate_RemoteFloodListEntry-group {
        leaf vtep {
            type address_Ip;
        }

        // Rel-def from vtepAtt
        container rsvtepAtt-items {

            // Abstract containment of rsvtepAtt derived from aggregate:RemoteFloodListEntry
            list RsVtepAtt-list {
                config "false";
                key "tDn";

                // Added containment: Prefix=rsvtepAtt
                // Acquired From Package aggregate
                uses aggregate_RsVtepAtt_source-group;
            }
        }
    }

    grouping aggregate_DomainAf-group {

        // Type is an MO-Defined-Type
        leaf type {
            description "Type";

            // Type is an MO-Defined-Type
            type aggregate_AfT;
        }
        leaf vrf {
            type string;
        }
        leaf rd {
            type mtx_array_community;
        }

        // Route target policy
        container rttp-items {
            list RttP-list {
                key "type";

                // Added containment: Prefix=rttp
                // Acquired From Package aggregate
                uses aggregate_RttP-group;
            }
        }

        // <mo name="DomAf"
        // read-access="access-protocol-util"
        // access="tenant-ext-protocol-util"
        // concrete="yes"
        // label="Domain Address Family"
        // >
        // <property name="type"
        // type="AfT"
        // owner="management"
        // mod="explicit"
        // label="Type"
        // />
        // </mo>
        // <chunk target="DomAf"
        // owner="policyelem">
        // <prop target="type"/>
        // </chunk>
        // <rn mo="DomAf">
        // <item prefix="af" property="type" />
        // </rn>
        // <contains parent="VrfEntry"
        // child="DomAf"
        // />
        // This object holds policy to control vpn af
        // information for a given vrf
        container ctrl-items {
            list AfCtrl-list {
                key "type";

                // Added containment: Prefix=ctrl
                // Acquired From Package aggregate
                uses aggregate_AfCtrl-group;
            }
        }
    }

    grouping aggregate_RttP-group {

        // Type
        // Type is an MO-Defined-Type
        leaf type {
            description "Type";

            // Type is an MO-Defined-Type
            type aggregate_RttPType;
        }

        // isL3 VRF
        // Type is an MO-Defined-Type
        leaf isL3 {
            description "IsL3";

            // Type is an MO-Defined-Type
            type aggregate_BooleanFlag;
        }

        // List of route types
        container ent-items {
            list RttEntry-list {
                key "rtt";

                // Added containment: Prefix=ent
                // Acquired From Package aggregate
                uses aggregate_RttEntry-group;
            }
        }
    }

    grouping aggregate_RttEntry-group {
        leaf rtt {
            type mtx_array_community;
        }
    }

    grouping aggregate_AfCtrl-group {

        // Type
        // Type is an MO-Defined-Type
        leaf type {
            description "Type";

            // Type is an MO-Defined-Type
            type aggregate_AfT;
        }

        // Route target policy
        container rttp-items {
            list RttP-list {
                key "type";

                // Added containment: Prefix=rttp
                // Acquired From Package aggregate
                uses aggregate_RttP-group;
            }
        }
    }

    grouping aggregate_GlobalConfTable-group {

        // Type is an MO-Defined-Type
        leaf vxLanMC {
            description "VxLan Multicast Flag";

            // Type is an MO-Defined-Type
            type aggregate_BooleanFlag;
        }
        leaf agMac {
            type address_Mac;
        }
    }

    grouping aggregate_IntfTable-group {
        container intf-items {
            list IntfEntry-list {
                key "name";

                // Added containment: Prefix=intf
                // Acquired From Package aggregate
                uses aggregate_IntfEntry-group;
            }
        }
        container svi-items {
            list Svi-list {
                key "intf";

                // Added containment: Prefix=svi
                // Acquired From Package aggregate
                uses aggregate_Svi-group;
            }
        }
    }

    grouping aggregate_IntfEntry-group {

        // Type is an MO-Defined-Type
        leaf name {
            description "Name";

            // Type is an MO-Defined-Type
            type nw_IfId;
        }

        // Type is an MO-Defined-Type
        leaf type {
            description "Name";

            // Type is an MO-Defined-Type
            type aggregate_IntfType;
        }

        // Type is an MO-Defined-Type
        leaf adminState {
            description "Admin State";

            // Type is an MO-Defined-Type
            type aggregate_AdminState;
        }

        // Type is an MO-Defined-Type
        leaf operState {
            description "Operational State";

            // Type is an MO-Defined-Type
            type aggregate_OperState;
        }

        // Type is an MO-Defined-Type
        leaf trunkVlans {
            description "Allowed Vlans";

            // Type is an MO-Defined-Type
            type aggregate_IntfTrunkVlans;
        }
        leaf isControllerOwnedIntf {
            config "false";
            type boolean;
        }

        // Type is an MO-Defined-Type
        leaf ownerControllersIdList {
            config "false";
            description "OwnerControllersIdList";

            // Type is an MO-Defined-Type
            type aggregate_ControllerIdBitmap;
        }

        container vlanMemberTable-items {

            // Added containment as a singleton: Prefix=vlanMemberTable
            // Acquired From Package aggregate
            uses aggregate_VlanMemberTable-group;
        }

        // Rel-def target from vpcIntfEntryAtt
        // Inherited From aggregate:IntfEntry
        container rtvpcIntfEntryAtt-items {

            // Added containment as a singleton: Prefix=rtvpcIntfEntryAtt
            // Acquired From Package aggregate
            uses aggregate_RtVpcIntfEntryAtt_target-group;
        }
    }

    grouping aggregate_VlanMemberTable-group {
        container member-items {
            list VlanMemberEntry-list {
                key "vlan";

                // Added containment: Prefix=member
                // Acquired From Package aggregate
                uses aggregate_VlanMemberEntry-group;
            }
        }

        // Rel-def from vlanMemberAtt
        container rsvlanMemberAtt-items {

            // Abstract containment of rsvlanMemberAtt derived from aggregate:VlanMemberTable
            list RsVlanMemberAtt-list {
                config "false";
                key "tDn";

                // Added containment: Prefix=rsvlanMemberAtt
                // Acquired From Package aggregate
                uses aggregate_RsVlanMemberAtt_source-group;
            }
        }
    }

    grouping aggregate_VlanMemberEntry-group {
        leaf vlan {
            type string;
        }
    }

    grouping aggregate_Svi-group {
        leaf intf {
            type string;
        }

        // Type is an MO-Defined-Type
        leaf adminState {
            description "Admin State";

            // Type is an MO-Defined-Type
            type aggregate_AdminState;
        }

        // Type is an MO-Defined-Type
        leaf operState {
            description "Operational State";

            // Type is an MO-Defined-Type
            type aggregate_OperState;
        }
        leaf ip {
            type address_Ip;
        }
        leaf isCtrlrOwnedIntf {
            config "false";
            type boolean;
        }

        // Type is an MO-Defined-Type
        leaf ownerCtrlrsIdList {
            config "false";
            description "OwnerControllersIdList";

            // Type is an MO-Defined-Type
            type aggregate_ControllerIdBitmap;
        }

        // Type is an MO-Defined-Type
        leaf mtu {
            description "MTU Of SVI";

            // Type is an MO-Defined-Type
            type aggregate_MTU;
        }

        // Type is an MO-Defined-Type
        leaf bw {
            description "Bandwidth Of SVI";

            // Type is an MO-Defined-Type
            type aggregate_Bw;
        }

        // Type is an MO-Defined-Type
        leaf fwdMode {
            description "Fabric Forwarding Mode";

            // Type is an MO-Defined-Type
            type aggregate_fabFwdMode;
        }

        // Type is an MO-Defined-Type
        leaf vrf {
            description "VRF context";

            // Type is an MO-Defined-Type
            type l3_VrfName;
        }
    }

    grouping aggregate_MacTable-group {

        container dynamic-items {

            // Added containment as a singleton: Prefix=dynamic
            // Acquired From Package aggregate
            uses aggregate_DynamicMac-group;
        }

        container static-items {

            // Added containment as a singleton: Prefix=static
            // Acquired From Package aggregate
            uses aggregate_StaticMac-group;
        }
    }

    grouping aggregate_DynamicMac-group {

        // Aggregate MacEntry
        container mac-items {
            list MacEntry-list {
                key "mac vlan";

                // Added containment: Prefix=mac
                // Acquired From Package aggregate
                uses aggregate_MacEntry-group;
            }
        }
    }

    grouping aggregate_MacEntry-group {
        leaf mac {
            type address_Mac;
        }
        leaf vlan {
            type string;
        }

        // Type is an MO-Defined-Type
        leaf intf {
            description "Interface";

            // Type is an MO-Defined-Type
            type nw_IfId;
        }
        leaf tunnelDstIp {
            type address_Ip;
        }
        leaf isIntf {
            type boolean;
        }

        // Type is an MO-Defined-Type
        leaf type {
            description "MacType";

            // Type is an MO-Defined-Type
            type aggregate_MacType;
        }
        leaf pushedMacToBackEnd {
            type boolean;
            default "true";
        }

        // Rel-def target from mac
        // Inherited From aggregate:MacEntry
        container rtmac-items {

            // Added containment as a singleton: Prefix=rtmac
            // Acquired From Package aggregate
            uses aggregate_RtMac_target-group;
        }
    }

    grouping aggregate_StaticMac-group {

        // Aggregate MacEntry
        container mac-items {
            list MacEntry-list {
                key "mac vlan";

                // Added containment: Prefix=mac
                // Acquired From Package aggregate
                uses aggregate_MacEntry-group;
            }
        }
    }

    grouping aggregate_SystemTable-group {

        // Type is an MO-Defined-Type
        leaf stTime {
            description "System Start Time";

            // Type is an MO-Defined-Type
            type mo_TStamp;
        }
        leaf mgmtIp {
            config "false";
            type address_Ip;
        }
        leaf switchType {
            type string;
        }

        // Type is an MO-Defined-Type
        leaf purgeDBRequest {
            description "Client DB Purge Request";

            // Type is an MO-Defined-Type
            type mo_TStamp;
        }
        leaf isControllerConfigured {
            type boolean;
        }
        leaf nxdbEnabled {
            config "false";
            type boolean;
        }

        container controllerTable-items {

            // Added containment as a singleton: Prefix=controllerTable
            // Acquired From Package aggregate
            uses aggregate_ControllerTable-group;
        }

        container cpuTable-items {

            // Added containment as a singleton: Prefix=cpuTable
            // Acquired From Package aggregate
            uses aggregate_CPUTable-group;
        }

        container moduleTable-items {

            // Added containment as a singleton: Prefix=moduleTable
            // Acquired From Package aggregate
            uses aggregate_ModuleTable-group;
        }

        container vxlanTable-items {

            // Added containment as a singleton: Prefix=vxlanTable
            // Acquired From Package aggregate
            uses aggregate_VxlanTable-group;
        }

        container shadowVxlanTable-items {

            // Added containment as a singleton: Prefix=shadowVxlanTable
            // Acquired From Package aggregate
            uses aggregate_ShadowVxlanTable-group;
        }
    }

    grouping aggregate_ControllerTable-group {
        container controller-items {
            list ControllerEntry-list {
                key "id";

                // Added containment: Prefix=controller
                // Acquired From Package aggregate
                uses aggregate_ControllerEntry-group;
            }
        }
    }

    grouping aggregate_ControllerEntry-group {
        leaf id {
            type uint32;
        }
        leaf readRole {
            type string;
        }
        leaf writeRole {
            type string;
        }
        leaf controllerDescription {
            type string;
        }
        leaf controllerType {
            type string;
        }

        // Type is an MO-Defined-Type
        leaf dedicatedVlans {
            config "false";
            description "Dedicated Vlans";

            // Type is an MO-Defined-Type
            type l2_VlanBitmap;
        }

        // Type is an MO-Defined-Type
        leaf sharedVlans {
            config "false";
            description "Shared Vlans";

            // Type is an MO-Defined-Type
            type l2_VlanBitmap;
        }

        // Type is an MO-Defined-Type
        leaf configuredVlans {
            config "false";
            description "Configured Vlans";

            // Type is an MO-Defined-Type
            type l2_VlanBitmap;
        }

        // Type is an MO-Defined-Type
        leaf publishedVlans {
            config "false";
            description "Published Vlans";

            // Type is an MO-Defined-Type
            type l2_VlanBitmap;
        }

        // Type is an MO-Defined-Type
        leaf vlanResourceStatus {
            config "false";
            description "Carved VLAN Status";

            // Type is an MO-Defined-Type
            type aggregate_ResourceStatus;
        }

        // Type is an MO-Defined-Type
        leaf intfResourceStatus {
            config "false";
            description "Carved Interface Status";

            // Type is an MO-Defined-Type
            type aggregate_ResourceStatus;
        }

        // Type is an MO-Defined-Type
        leaf isSystemReadyForController {
            description "IsSystemReadyForController";

            // Type is an MO-Defined-Type
            type aggregate_ConfigStatus;
        }

        // Type is an MO-Defined-Type
        leaf controllerConfigMgmt {
            description "ContorllerConfigMgmt";

            // Type is an MO-Defined-Type
            type aggregate_ConfigMgmtStatus;
        }

        // Type is an MO-Defined-Type
        leaf type {
            description "Controller Type";

            // Type is an MO-Defined-Type
            type aggregate_CtrlrType;
        }
        leaf vrfPrefix {
            type string;
        }
        leaf numVrf {
            type uint32;
        }
        leaf publishVrf {
            type boolean;
        }
        leaf publishNumVrf {
            type uint32;
        }

        container controllerAssignedIntfTable-items {

            // Added containment as a singleton: Prefix=controllerAssignedIntfTable
            // Acquired From Package aggregate
            uses aggregate_ControllerAssignedIntfTable-group;
        }
    }

    grouping aggregate_ControllerAssignedIntfTable-group {
        container controllerAssignedIntfEntry-items {
            list ControllerAssignedIntfEntry-list {
                key "intfName";

                // Added containment: Prefix=controllerAssignedIntfEntry
                // Acquired From Package aggregate
                uses aggregate_ControllerAssignedIntfEntry-group;
            }
        }
    }

    grouping aggregate_ControllerAssignedIntfEntry-group {

        // Type is an MO-Defined-Type
        leaf intfName {
            description "IntfName";

            // Type is an MO-Defined-Type
            type nw_IfId;
        }

        // Port channel id
        // Type is an MO-Defined-Type
        leaf pcId {
            description "Port channel id";

            // Type is an MO-Defined-Type
            type pc_PcId;
        }

        // Type is an MO-Defined-Type
        leaf type {
            description "Name";

            // Type is an MO-Defined-Type
            type aggregate_IntfType;
        }

        // Type is an MO-Defined-Type
        leaf mode {
            description "Assign Mode";

            // Type is an MO-Defined-Type
            type aggregate_IntfAssignMode;
        }
        leaf published {
            type boolean;
        }
    }

    grouping aggregate_CPUTable-group {
        container cpuEntry-items {
            list CPUEntry-list {
                key "type";

                // Added containment: Prefix=cpuEntry
                // Acquired From Package aggregate
                uses aggregate_CPUEntry-group;
            }
        }
    }

    grouping aggregate_CPUEntry-group {

        // Type is an MO-Defined-Type
        leaf type {
            description "CPU Type";

            // Type is an MO-Defined-Type
            type aggregate_CpuType;
        }
    }

    grouping aggregate_ModuleTable-group {
        container moduleEntry-items {
            list ModuleEntry-list {
                key "type";

                // Added containment: Prefix=moduleEntry
                // Acquired From Package aggregate
                uses aggregate_ModuleEntry-group;
            }
        }
    }

    grouping aggregate_ModuleEntry-group {

        // Type is an MO-Defined-Type
        leaf type {
            description "Type";

            // Type is an MO-Defined-Type
            type aggregate_ModuleType;
        }
    }

    grouping aggregate_VxlanTable-group {
        container intf-items {
            list VxlanInterfaceEntry-list {
                key "name";

                // Added containment: Prefix=intf
                // Acquired From Package aggregate
                uses aggregate_VxlanInterfaceEntry-group;
            }
        }
    }

    grouping aggregate_VxlanInterfaceEntry-group {
        leaf name {
            type string;
        }

        // Inherited From aggregate:NveIntf
        // Type is an MO-Defined-Type
        leaf myTepStatus {
            config "false";
            description "MyTepStatus";

            // Type is an MO-Defined-Type
            type aggregate_OperState;
        }

        // Inherited From aggregate:NveIntf
        // Type is an MO-Defined-Type
        leaf hostReachability {
            config "false";
            description "HostReachability";

            // Type is an MO-Defined-Type
            type aggregate_HostReachabilityMode;
        }
        leaf controllerId {
            type uint32;
        }

        // Inherited From aggregate:NveIntf
        // Type is an MO-Defined-Type
        leaf configSource {
            config "false";
            description "configSource";

            // Type is an MO-Defined-Type
            type aggregate_ConfigSourceType;
        }
        leaf primaryTunnelIp {
            config "false";
            type address_Ip;
        }
        leaf secondaryTunnelIp {
            config "false";
            type address_Ip;
        }

        container localBfd-items {

            // Added containment as a singleton: Prefix=localBfd
            // Acquired From Package aggregate
            uses aggregate_LocalBfd-group;
        }
    }

    grouping aggregate_LocalBfd-group {
        leaf mac {
            type address_Mac;
        }
        leaf ip {
            type address_Ip;
        }

        // Inherited From aggregate:Bfd
        // Type is an MO-Defined-Type
        leaf minTxIntvl {
            description "Desired Minimum TX Interval";

            // Type is an MO-Defined-Type
            type aggregate_MinTxIntvl;
        }

        // Inherited From aggregate:Bfd
        // Type is an MO-Defined-Type
        leaf minRxIntvl {
            description "Desired Minimum RX Interval";

            // Type is an MO-Defined-Type
            type aggregate_MinRxIntvl;
        }
    }

    grouping aggregate_ShadowVxlanTable-group {
        container intf-items {
            list ShadowVxlanInterfaceEntry-list {
                key "name";

                // Added containment: Prefix=intf
                // Acquired From Package aggregate
                uses aggregate_ShadowVxlanInterfaceEntry-group;
            }
        }
    }

    grouping aggregate_ShadowVxlanInterfaceEntry-group {
        leaf name {
            type string;
        }

        // Inherited From aggregate:NveIntf
        // Type is an MO-Defined-Type
        leaf myTepStatus {
            config "false";
            description "MyTepStatus";

            // Type is an MO-Defined-Type
            type aggregate_OperState;
        }

        // Inherited From aggregate:NveIntf
        // Type is an MO-Defined-Type
        leaf hostReachability {
            config "false";
            description "HostReachability";

            // Type is an MO-Defined-Type
            type aggregate_HostReachabilityMode;
        }
        leaf controllerId {
            type uint32;
        }

        // Inherited From aggregate:NveIntf
        // Type is an MO-Defined-Type
        leaf configSource {
            config "false";
            description "configSource";

            // Type is an MO-Defined-Type
            type aggregate_ConfigSourceType;
        }
        leaf primaryTunnelIp {
            config "false";
            type address_Ip;
        }
        leaf secondaryTunnelIp {
            config "false";
            type address_Ip;
        }
    }

    grouping aggregate_TunnelIntfTable-group {
        container intf-items {
            list TunnelIntfEntry-list {
                key "destIp";

                // Added containment: Prefix=intf
                // Acquired From Package aggregate
                uses aggregate_TunnelIntfEntry-group;
            }
        }
    }

    grouping aggregate_TunnelIntfEntry-group {
        leaf description {
            type string;
        }

        // Type is an MO-Defined-Type
        leaf ifId {
            description "IfId";

            // Type is an MO-Defined-Type
            type nw_IfId;
        }

        // Type is an MO-Defined-Type
        leaf type {
            description "TunnelType";

            // Type is an MO-Defined-Type
            type aggregate_TunnelType;
        }
        leaf srcIp {
            type address_Ip;
        }
        leaf destIp {
            type address_Ip;
        }

        // Type is an MO-Defined-Type
        leaf mtu {
            description "MTU";

            // Type is an MO-Defined-Type
            type aggregate_MTU;
        }

        // Type is an MO-Defined-Type
        leaf state {
            description "State";

            // Type is an MO-Defined-Type
            type aggregate_OperState;
        }

        // Type is an MO-Defined-Type
        leaf vrf {
            description "VRF";

            // Type is an MO-Defined-Type
            type l3_VrfName;
        }

        // Type is an MO-Defined-Type
        leaf ipVnidBinding {
            description "IPVnidBinding";

            // Type is an MO-Defined-Type
            type aggregate_BooleanFlag;
        }
        leaf isTunnelCreated {
            config "false";
            type boolean;
            default "true";
        }
        leaf isTunnelCreatedByController {
            config "false";
            type boolean;
            default "true";
        }
        leaf noOfMacsSeenBeforeTunnelCreatedbyController {
            config "false";
            type uint32;
        }

        // Type is an MO-Defined-Type
        leaf epType {
            description "End point type";

            // Type is an MO-Defined-Type
            type aggregate_EpType;
        }

        container tunMacTable-items {

            // Added containment as a singleton: Prefix=tunMacTable
            // Acquired From Package aggregate
            uses aggregate_TunMacTable-group;
        }

        container vnidTable-items {

            // Added containment as a singleton: Prefix=vnidTable
            // Acquired From Package aggregate
            uses aggregate_VnidTable-group;
        }

        container remoteBfd-items {

            // Added containment as a singleton: Prefix=remoteBfd
            // Acquired From Package aggregate
            uses aggregate_RemoteBfd-group;
        }

        // Rel-def target from vtepAtt
        // Inherited From aggregate:TunnelIntfEntry
        container rtaggregateVtepAtt-items {

            // Abstract containment of rtaggregateVtepAtt derived from aggregate:TunnelIntfEntry
            list RtAggregateVtepAtt-list {
                config "false";
                key "tDn";

                // Added containment: Prefix=rtaggregateVtepAtt
                // Acquired From Package aggregate
                uses aggregate_RtAggregateVtepAtt_target-group;
            }
        }
    }

    grouping aggregate_TunMacTable-group {

        // Rel-def from mac
        container rsmac-items {

            // Abstract containment of rsmac derived from aggregate:TunMacTable
            list RsMac-list {
                config "false";
                key "tDn";

                // Added containment: Prefix=rsmac
                // Acquired From Package aggregate
                uses aggregate_RsMac_source-group;
            }
        }
    }

    grouping aggregate_VnidTable-group {
        container vnid-items {
            list VnidEntry-list {
                key "vnid";

                // Added containment: Prefix=vnid
                // Acquired From Package aggregate
                uses aggregate_VnidEntry-group;
            }
        }
    }

    grouping aggregate_VnidEntry-group {
        leaf vnid {
            type string;
        }

        // Type is an MO-Defined-Type
        leaf groupAddr {
            description "GroupAddr";

            // Type is an MO-Defined-Type
            type aggregate_GroupAddr;
        }
    }

    grouping aggregate_RemoteBfd-group {

        // Type is an MO-Defined-Type
        leaf bfdStatus {
            description "Vnid";

            // Type is an MO-Defined-Type
            type aggregate_BfdStatus;
        }
        leaf mac {
            type address_Mac;
        }
        leaf ip {
            type address_Ip;
        }

        // Inherited From aggregate:Bfd
        // Type is an MO-Defined-Type
        leaf minTxIntvl {
            description "Desired Minimum TX Interval";

            // Type is an MO-Defined-Type
            type aggregate_MinTxIntvl;
        }

        // Inherited From aggregate:Bfd
        // Type is an MO-Defined-Type
        leaf minRxIntvl {
            description "Desired Minimum RX Interval";

            // Type is an MO-Defined-Type
            type aggregate_MinRxIntvl;
        }
    }

    grouping aggregate_VlanTable-group {

        // Aggregate VlanEntry
        container vlan-items {
            list VlanEntry-list {
                key "id";

                // Added containment: Prefix=vlan
                // Acquired From Package aggregate
                uses aggregate_VlanEntry-group;
            }
        }
    }

    grouping aggregate_VlanEntry-group {
        leaf id {
            type string;
        }

        // Type is an MO-Defined-Type
        leaf adminState {
            description "AdminState";

            // Type is an MO-Defined-Type
            type aggregate_AdminState;
        }
    }

    grouping aggregate_VpcDomTable-group {
        container vpcDom-items {
            list VpcDomEntry-list {
                key "domainId";

                // Added containment: Prefix=vpcDom
                // Acquired From Package aggregate
                uses aggregate_VpcDomEntry-group;
            }
        }
    }

    grouping aggregate_VpcDomEntry-group {

        // Type is an MO-Defined-Type
        leaf domainId {
            description "Domain Id";

            // Type is an MO-Defined-Type
            type vpc_DomId;
        }
        leaf keepaliveDestIp {
            type address_Ip;
        }
        leaf keepaliveSrcIp {
            type address_Ip;
        }
        leaf virtualIp {
            type address_Ip;
        }

        // Type is an MO-Defined-Type
        leaf keepaliveSts {
            config "false";
            description "Kpa Status";

            // Type is an MO-Defined-Type
            type aggregate_VpcKeepaliveStatus;
        }

        // Type is an MO-Defined-Type
        leaf peerLinkSts {
            config "false";
            description "Peer Link Status";

            // Type is an MO-Defined-Type
            type aggregate_VpcPeerLinkStatus;
        }

        // Type is an MO-Defined-Type
        leaf vpcRole {
            config "false";
            description "Vpc Role";

            // Type is an MO-Defined-Type
            type vpc_Role;
        }
        leaf peerGW {
            type boolean;
        }
        leaf dualActive {
            type boolean;
        }

        // Type is an MO-Defined-Type
        leaf peerLinkIf {
            description "Port channel interface of the peer link";

            // Type is an MO-Defined-Type
            type nw_IfId;
        }

        // VPCTAB
        container vpcTable-items {

            // Added containment as a singleton: Prefix=vpcTable
            // Acquired From Package aggregate
            uses aggregate_VpcTable-group;
        }
    }

    grouping aggregate_VpcTable-group {
        container vpc-items {
            list VpcEntry-list {
                key "vpcnum";

                // Added containment: Prefix=vpc
                // Acquired From Package aggregate
                uses aggregate_VpcEntry-group;
            }
        }
    }

    grouping aggregate_VpcEntry-group {

        // Type is an MO-Defined-Type
        leaf vpcnum {
            description "Vpc Num";

            // Type is an MO-Defined-Type
            type vpc_Id;
        }

        // Type is an MO-Defined-Type
        leaf ifId {
            description "IfId";

            // Type is an MO-Defined-Type
            type nw_IfId;
        }

        // Type is an MO-Defined-Type
        leaf operState {
            description "Oper State";

            // Type is an MO-Defined-Type
            type aggregate_VpcOperStatus;
        }

        // Type is an MO-Defined-Type
        leaf consCheckSts {
            config "false";
            description "Kpa Status";

            // Type is an MO-Defined-Type
            type vpc_CompatSt;
        }

        // Type is an MO-Defined-Type
        leaf consCheckReason {
            config "false";
            description "Cons Check Reason";

            // Type is an MO-Defined-Type
            type vpc_CompatQual;
        }

        container vpcintf-items {

            // Added containment as a singleton: Prefix=vpcintf
            // Acquired From Package aggregate
            uses aggregate_VpcIntfEntry-group;
        }
    }

    grouping aggregate_VpcIntfEntry-group {

        // Rel-def from vpcIntfEntryAtt
        container rsvpcIntfEntryAtt-items {

            // Added containment as a singleton: Prefix=rsvpcIntfEntryAtt
            // Acquired From Package aggregate
            uses aggregate_RsVpcIntfEntryAtt_source-group;
        }
    }

    grouping aggregate_VrfTable-group {
        container vrf-items {
            list VrfEntry-list {
                key "name";

                // Added containment: Prefix=vrf
                // Acquired From Package aggregate
                uses aggregate_VrfEntry-group;
            }
        }
    }

    grouping aggregate_VrfEntry-group {

        // Type is an MO-Defined-Type
        leaf name {
            description "Name";

            // Type is an MO-Defined-Type
            type l3_VrfName;
        }

        // Type is an MO-Defined-Type
        leaf genName {
            description "Name";

            // Type is an MO-Defined-Type
            type l3_VrfName;
        }

        // Type is an MO-Defined-Type
        leaf ctrlrId {
            description "Controller ID";

            // Type is an MO-Defined-Type
            type aggregate_ControllerID;
        }
        leaf vnid {
            type string;
        }
        leaf rd {
            type mtx_array_community;
        }
        leaf genExtraRt {
            type boolean;
        }

        // Domain (vrf) information    <mo name="Domain"
        // concrete="yes"
        // label="Domain"
        // read-access="access-protocol-util"
        // access="tenant-ext-protocol-util"
        // >
        // <property name="vrf"
        // type="string:Basic"
        // owner="management"
        // mod="explicit"
        // label="VRF"
        // />
        // <property name="rd"
        // type="base:Community"
        // owner="management"
        // mod="explicit"
        // label="Route Distinguisher"
        // />
        // </mo>
        // <chunk target="Domain"
        // owner="policyelem"
        // type="primary">
        // <prop target="vrf"/>
        // </chunk>
        // <rn mo="Domain">
        // <item prefix="dom" property="vrf"/>
        // </rn>
        // <contains parent="BdEntry"
        // child="Domain"
        // />   List of route types
        container af-items {
            list DomainAf-list {
                key "type";

                // Added containment: Prefix=af
                // Acquired From Package aggregate
                uses aggregate_DomainAf-group;
            }
        }
    }

    grouping ac_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Ip entry
        container ruleIp-items {
            list RuleIp-list {
                config "false";
                key "ruleId";

                // Added containment: Prefix=ruleIp
                // Acquired From Package ac
                uses ac_RuleIp-group;
            }
        }

        // Mac entry
        container ruleMac-items {
            list RuleMac-list {
                config "false";
                key "ruleId";

                // Added containment: Prefix=ruleMac
                // Acquired From Package ac
                uses ac_RuleMac-group;
            }
        }

        // Arp entry
        container ruleArp-items {
            list RuleArp-list {
                config "false";
                key "ruleId";

                // Added containment: Prefix=ruleArp
                // Acquired From Package ac
                uses ac_RuleArp-group;
            }
        }
    }

    grouping ac_RuleIp-group {
        leaf src {
            config "false";
            type address_Ip;
        }
        leaf dst {
            config "false";
            type address_Ip;
        }

        // Ip protocol
        // Type is an MO-Defined-Type
        leaf prot {
            config "false";
            description "Protocol";

            // Type is an MO-Defined-Type
            type l3_IpProt;
        }

        // Ip flags
        // Type is an MO-Defined-Type
        leaf flags {
            config "false";
            description "IP Flags";

            // Type is an MO-Defined-Type
            type ac_IpFlags;
        }

        // Ip flags mask
        // Type is an MO-Defined-Type
        leaf flagsMask {
            config "false";
            description "IP Flags Mask";

            // Type is an MO-Defined-Type
            type ac_IpFlags;
        }

        // TTL
        // Type is an MO-Defined-Type
        leaf ttl {
            config "false";
            description "TTL";

            // Type is an MO-Defined-Type
            type l3_Ttl;
        }

        // Dscp
        // Type is an MO-Defined-Type
        leaf dscp {
            config "false";
            description "Dscp";

            // Type is an MO-Defined-Type
            type qosp_Dscp;
        }

        // Dscp mask
        // Type is an MO-Defined-Type
        leaf dscpMask {
            config "false";
            description "Dscp Mask";

            // Type is an MO-Defined-Type
            type qosp_Dscp;
        }

        // Ecn
        // Type is an MO-Defined-Type
        leaf ecn {
            config "false";
            description "ECN";

            // Type is an MO-Defined-Type
            type ac_Ecn;
        }

        // Ecn mask
        // Type is an MO-Defined-Type
        leaf ecnMask {
            config "false";
            description "ECN Mask";

            // Type is an MO-Defined-Type
            type ac_Ecn;
        }

        // Payload size
        // Type is an MO-Defined-Type
        leaf payloadSz {
            config "false";
            description "Payload Size";

            // Type is an MO-Defined-Type
            type ac_PayloadSz;
        }

        // Source policy tag
        // Type is an MO-Defined-Type
        leaf sPcTag {
            config "false";
            description "Source PC Tag";

            // Type is an MO-Defined-Type
            type actrl_PcTag;
        }

        // Destination policy tag
        // Type is an MO-Defined-Type
        leaf dPcTag {
            config "false";
            description "Destination PC Tag";

            // Type is an MO-Defined-Type
            type actrl_PcTag;
        }

        // Ip options
        // Type is an MO-Defined-Type
        leaf options {
            config "false";
            description "IP Options";

            // Type is an MO-Defined-Type
            type ac_IpOpt;
        }

        // Ip options mask
        // Type is an MO-Defined-Type
        leaf optionsMask {
            config "false";
            description "IP Options Mask";

            // Type is an MO-Defined-Type
            type ac_IpOpt;
        }

        // ICMP flags
        // Type is an MO-Defined-Type
        leaf icmpFlags {
            config "false";
            description "ICMP Flags";

            // Type is an MO-Defined-Type
            type icmp_Flags;
        }

        // ICMP code
        // Type is an MO-Defined-Type
        leaf icmpCode {
            config "false";
            description "ICMP Code";

            // Type is an MO-Defined-Type
            type icmp_Code;
        }

        // ICMP type
        // Type is an MO-Defined-Type
        leaf icmpType {
            config "false";
            description "ICMP Type";

            // Type is an MO-Defined-Type
            type icmp_Type;
        }

        // Source port
        // Type is an MO-Defined-Type
        leaf srcPort {
            description "Source Port";

            // Type is an MO-Defined-Type
            type l4_Port;
        }

        // Destination port
        // Type is an MO-Defined-Type
        leaf dstPort {
            description "Destination Port";

            // Type is an MO-Defined-Type
            type l4_Port;
        }

        // Tcp flags
        // Type is an MO-Defined-Type
        leaf tcpFlags {
            description "TCP Flags";

            // Type is an MO-Defined-Type
            type l4_TcpFlags;
        }

        // Tcp flags mask
        // Type is an MO-Defined-Type
        leaf tcpFlagsMask {
            description "TCP Flags Mask";

            // Type is an MO-Defined-Type
            type l4_TcpFlags;
        }
        leaf isExt {
            config "false";
            type boolean;
        }

        // Operational State
        // Type is an MO-Defined-Type
        leaf operState {
            description "TBD";

            // Type is an MO-Defined-Type
            type ac_RuleOperSt;
        }

        // Last Operational State
        // Type is an MO-Defined-Type
        leaf lastOperState {
            description "TBD";

            // Type is an MO-Defined-Type
            type ac_RuleOperSt;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf ruleId {
            config "false";
            type uint64;
        }

        // Order
        // Inherited From ac:Rule
        // Type is an MO-Defined-Type
        leaf order {
            config "false";
            description "Order";

            // Type is an MO-Defined-Type
            type ac_Order;
        }

        // Control
        // Inherited From ac:Rule
        // Type is an MO-Defined-Type
        leaf ctrl {
            config "false";
            description "Control";

            // Type is an MO-Defined-Type
            type ac_Control;
        }

        // Control mask, if specified in the mask control bit,
        // it is treated as a wildcard
        // Inherited From ac:Rule
        // Type is an MO-Defined-Type
        leaf ctrlMask {
            config "false";
            description "Control Mask";

            // Type is an MO-Defined-Type
            type ac_Control;
        }

        // fabric port id
        // Inherited From ac:Rule
        // Type is an MO-Defined-Type
        leaf fabricPort {
            config "false";
            description "Fabric Port";

            // Type is an MO-Defined-Type
            type ac_PortId;
        }
        leaf fabricEncap {
            config "false";
            type string;
        }
        leaf remoteTep {
            config "false";
            type address_Ip;
        }

        // l2 source mac, a zero value mean a
        // Inherited From ac:Rule
        // Type is an MO-Defined-Type
        leaf srcMac {
            config "false";
            description "Source MAC";

            // Type is an MO-Defined-Type
            type ac_Mac;
        }

        // l2 destination mac
        // Inherited From ac:Rule
        // Type is an MO-Defined-Type
        leaf dstMac {
            config "false";
            description "Destination MAC";

            // Type is an MO-Defined-Type
            type ac_Mac;
        }

        // dot1p
        // Inherited From ac:Rule
        // Type is an MO-Defined-Type
        leaf dot1p {
            config "false";
            description "Dot1p";

            // Type is an MO-Defined-Type
            type qosp_Dot1P;
        }

        // dot1p mask
        // Inherited From ac:Rule
        // Type is an MO-Defined-Type
        leaf dot1pMask {
            config "false";
            description "Dot1p Mask";

            // Type is an MO-Defined-Type
            type qosp_Dot1P;
        }

        // Policy Name
        // Inherited From ac:Rule
        // Type is an MO-Defined-Type
        leaf policyName {
            config "false";
            description "Atomic Policy Name";

            // Type is an MO-Defined-Type
            type naming_Name;
        }

        // Tenant Name
        // Inherited From ac:Rule
        // Type is an MO-Defined-Type
        leaf tenantName {
            config "false";
            description "Tenant Name for this Atomic Counter Rule";

            // Type is an MO-Defined-Type
            type naming_Name;
        }

        // Vrf Name
        // Inherited From ac:Rule
        // Type is an MO-Defined-Type
        leaf vrfName {
            config "false";
            description "VRF Name for this Atomic Counter Rule";

            // Type is an MO-Defined-Type
            type naming_Name;
        }

        // Each atomic counter rule has two sets of banks to
        // count the packets and bytes
        container bank-items {
            list Bank-list {
                config "false";
                key "type";

                // Added containment: Prefix=bank
                // Acquired From Package ac
                uses ac_Bank-group;
            }
        }
    }

    grouping ac_Bank-group {

        // Type
        // Type is an MO-Defined-Type
        leaf type {
            config "false";
            description "Type";

            // Type is an MO-Defined-Type
            type ac_BankT;
        }

        container dbgIngrHit-items {

            // Added containment as a singleton: Prefix=dbgIngrHit
            // Acquired From Package ac
            uses ac_IngrHit-group;
        }

        container dbgEgrHit-items {

            // Added containment as a singleton: Prefix=dbgEgrHit
            // Acquired From Package ac
            uses ac_EgrHit-group;
        }
    }

    grouping ac_RuleMac-group {

        // Ether type
        // Type is an MO-Defined-Type
        leaf type {
            config "false";
            description "Ether Type";

            // Type is an MO-Defined-Type
            type ac_EtherT;
        }

        // Payload size
        // Type is an MO-Defined-Type
        leaf payloadSz {
            config "false";
            description "Payload Size";

            // Type is an MO-Defined-Type
            type ac_PayloadSz;
        }
        leaf payload {
            config "false";
            type uint64;
        }

        // Source policy tag
        // Type is an MO-Defined-Type
        leaf sPcTag {
            config "false";
            description "Source PC Tag";

            // Type is an MO-Defined-Type
            type actrl_PcTag;
        }

        // Destination policy tag
        // Type is an MO-Defined-Type
        leaf dPcTag {
            config "false";
            description "Destination PC Tag";

            // Type is an MO-Defined-Type
            type actrl_PcTag;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf ruleId {
            config "false";
            type uint64;
        }

        // Order
        // Inherited From ac:Rule
        // Type is an MO-Defined-Type
        leaf order {
            config "false";
            description "Order";

            // Type is an MO-Defined-Type
            type ac_Order;
        }

        // Control
        // Inherited From ac:Rule
        // Type is an MO-Defined-Type
        leaf ctrl {
            config "false";
            description "Control";

            // Type is an MO-Defined-Type
            type ac_Control;
        }

        // Control mask, if specified in the mask control bit,
        // it is treated as a wildcard
        // Inherited From ac:Rule
        // Type is an MO-Defined-Type
        leaf ctrlMask {
            config "false";
            description "Control Mask";

            // Type is an MO-Defined-Type
            type ac_Control;
        }

        // fabric port id
        // Inherited From ac:Rule
        // Type is an MO-Defined-Type
        leaf fabricPort {
            config "false";
            description "Fabric Port";

            // Type is an MO-Defined-Type
            type ac_PortId;
        }
        leaf fabricEncap {
            config "false";
            type string;
        }
        leaf remoteTep {
            config "false";
            type address_Ip;
        }

        // l2 source mac, a zero value mean a
        // Inherited From ac:Rule
        // Type is an MO-Defined-Type
        leaf srcMac {
            config "false";
            description "Source MAC";

            // Type is an MO-Defined-Type
            type ac_Mac;
        }

        // l2 destination mac
        // Inherited From ac:Rule
        // Type is an MO-Defined-Type
        leaf dstMac {
            config "false";
            description "Destination MAC";

            // Type is an MO-Defined-Type
            type ac_Mac;
        }

        // dot1p
        // Inherited From ac:Rule
        // Type is an MO-Defined-Type
        leaf dot1p {
            config "false";
            description "Dot1p";

            // Type is an MO-Defined-Type
            type qosp_Dot1P;
        }

        // dot1p mask
        // Inherited From ac:Rule
        // Type is an MO-Defined-Type
        leaf dot1pMask {
            config "false";
            description "Dot1p Mask";

            // Type is an MO-Defined-Type
            type qosp_Dot1P;
        }

        // Policy Name
        // Inherited From ac:Rule
        // Type is an MO-Defined-Type
        leaf policyName {
            config "false";
            description "Atomic Policy Name";

            // Type is an MO-Defined-Type
            type naming_Name;
        }

        // Tenant Name
        // Inherited From ac:Rule
        // Type is an MO-Defined-Type
        leaf tenantName {
            config "false";
            description "Tenant Name for this Atomic Counter Rule";

            // Type is an MO-Defined-Type
            type naming_Name;
        }

        // Vrf Name
        // Inherited From ac:Rule
        // Type is an MO-Defined-Type
        leaf vrfName {
            config "false";
            description "VRF Name for this Atomic Counter Rule";

            // Type is an MO-Defined-Type
            type naming_Name;
        }

        // Each atomic counter rule has two sets of banks to
        // count the packets and bytes
        container bank-items {
            list Bank-list {
                config "false";
                key "type";

                // Added containment: Prefix=bank
                // Acquired From Package ac
                uses ac_Bank-group;
            }
        }
    }

    grouping ac_RuleArp-group {

        // Opcode
        // Type is an MO-Defined-Type
        leaf opc {
            config "false";
            description "Opcode";

            // Type is an MO-Defined-Type
            type arp_Opcode;
        }

        // Sender mac
        // Type is an MO-Defined-Type
        leaf senderMac {
            config "false";
            description "Sender MAC";

            // Type is an MO-Defined-Type
            type ac_Mac;
        }
        leaf senderIp {
            config "false";
            type address_Ip;
        }

        // Target mac
        // Type is an MO-Defined-Type
        leaf targetMac {
            config "false";
            description "Target MAC";

            // Type is an MO-Defined-Type
            type ac_Mac;
        }
        leaf targetIp {
            config "false";
            type address_Ip;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf ruleId {
            config "false";
            type uint64;
        }

        // Order
        // Inherited From ac:Rule
        // Type is an MO-Defined-Type
        leaf order {
            config "false";
            description "Order";

            // Type is an MO-Defined-Type
            type ac_Order;
        }

        // Control
        // Inherited From ac:Rule
        // Type is an MO-Defined-Type
        leaf ctrl {
            config "false";
            description "Control";

            // Type is an MO-Defined-Type
            type ac_Control;
        }

        // Control mask, if specified in the mask control bit,
        // it is treated as a wildcard
        // Inherited From ac:Rule
        // Type is an MO-Defined-Type
        leaf ctrlMask {
            config "false";
            description "Control Mask";

            // Type is an MO-Defined-Type
            type ac_Control;
        }

        // fabric port id
        // Inherited From ac:Rule
        // Type is an MO-Defined-Type
        leaf fabricPort {
            config "false";
            description "Fabric Port";

            // Type is an MO-Defined-Type
            type ac_PortId;
        }
        leaf fabricEncap {
            config "false";
            type string;
        }
        leaf remoteTep {
            config "false";
            type address_Ip;
        }

        // l2 source mac, a zero value mean a
        // Inherited From ac:Rule
        // Type is an MO-Defined-Type
        leaf srcMac {
            config "false";
            description "Source MAC";

            // Type is an MO-Defined-Type
            type ac_Mac;
        }

        // l2 destination mac
        // Inherited From ac:Rule
        // Type is an MO-Defined-Type
        leaf dstMac {
            config "false";
            description "Destination MAC";

            // Type is an MO-Defined-Type
            type ac_Mac;
        }

        // dot1p
        // Inherited From ac:Rule
        // Type is an MO-Defined-Type
        leaf dot1p {
            config "false";
            description "Dot1p";

            // Type is an MO-Defined-Type
            type qosp_Dot1P;
        }

        // dot1p mask
        // Inherited From ac:Rule
        // Type is an MO-Defined-Type
        leaf dot1pMask {
            config "false";
            description "Dot1p Mask";

            // Type is an MO-Defined-Type
            type qosp_Dot1P;
        }

        // Policy Name
        // Inherited From ac:Rule
        // Type is an MO-Defined-Type
        leaf policyName {
            config "false";
            description "Atomic Policy Name";

            // Type is an MO-Defined-Type
            type naming_Name;
        }

        // Tenant Name
        // Inherited From ac:Rule
        // Type is an MO-Defined-Type
        leaf tenantName {
            config "false";
            description "Tenant Name for this Atomic Counter Rule";

            // Type is an MO-Defined-Type
            type naming_Name;
        }

        // Vrf Name
        // Inherited From ac:Rule
        // Type is an MO-Defined-Type
        leaf vrfName {
            config "false";
            description "VRF Name for this Atomic Counter Rule";

            // Type is an MO-Defined-Type
            type naming_Name;
        }

        // Each atomic counter rule has two sets of banks to
        // count the packets and bytes
        container bank-items {
            list Bank-list {
                config "false";
                key "type";

                // Added containment: Prefix=bank
                // Acquired From Package ac
                uses ac_Bank-group;
            }
        }
    }

    grouping acl_Entity-group {

        // IPv4 and IPv6 port object-group
        container oName-items {
            list PortGroup-list {
                key "name";

                // Added containment: Prefix=oName
                // Acquired From Package acl
                uses acl_PortGroup-group;
            }
        }

        // MO: VLAN ACL
        container vlan-items {
            list VLANACL-list {
                key "name";

                // Added containment: Prefix=vlan
                // Acquired From Package acl
                uses acl_VLANACL-group;
            }
        }

        // IPv4
        container mac-items {

            // Added containment as a singleton: Prefix=mac
            // Acquired From Package macacl
            uses macacl_AF-group;
        }

        // IPv4
        container ipv4-items {

            // Added containment as a singleton: Prefix=ipv4
            // Acquired From Package ipv4acl
            uses ipv4acl_AF-group;
        }

        // IPv6
        container ipv6-items {

            // Added containment as a singleton: Prefix=ipv6
            // Acquired From Package ipv6acl
            uses ipv6acl_AF-group;
        }
    }

    grouping acl_PortGroup-group {

        // object-group name
        // Inherited From acl:OGroup
        // Type is an MO-Defined-Type
        leaf name {
            description "Name";

            // Type is an MO-Defined-Type
            type acl_Name;
        }
        leaf configStatus {
            config "false";
            type uint32;
        }

        // IPv4 and IPv6 Port Object Group member
        container seq-items {
            list PortMember-list {
                key "seqNum";

                // Added containment: Prefix=seq
                // Acquired From Package acl
                uses acl_PortMember-group;
            }
        }
    }

    grouping acl_PortMember-group {

        // port operation
        // Type is an MO-Defined-Type
        leaf portOp {
            description "Source port operations";

            // Type is an MO-Defined-Type
            type acl_Operator;
        }

        // first port
        // Type is an MO-Defined-Type
        leaf port1 {
            description "First source port";

            // Type is an MO-Defined-Type
            type acl_PortNumber;
        }

        // second port
        // Type is an MO-Defined-Type
        leaf port2 {
            description "Second source port";

            // Type is an MO-Defined-Type
            type acl_PortNumber;
        }

        // configState
        // Type is an MO-Defined-Type
        leaf configStatus {
            description "config status";

            // Type is an MO-Defined-Type
            type acl_ConfigState;
        }

        // Object Group Member sequence number
        // Inherited From acl:OMember
        // Type is an MO-Defined-Type
        leaf seqNum {
            description "Sequence number";

            // Type is an MO-Defined-Type
            type acl_SequenceNumber;
        }
        leaf userSetBit {
            type uint64;
            default "1";
        }
    }

    grouping acl_VLANACL-group {

        // VLAN ACL name
        // Type is an MO-Defined-Type
        leaf name {
            description "Vacl name";

            // Type is an MO-Defined-Type
            type acl_Name;
        }
        leaf maxseq {
            config "false";
            type uint32;
        }

        // MO: VLAN sequence number
        container seq-items {
            list VLANSeq-list {
                key "seqNum";

                // Added containment: Prefix=seq
                // Acquired From Package acl
                uses acl_VLANSeq-group;
            }
        }

        // ==== MO: VLAN list ====
        // VLANList:
        // /sys/acl/vlan-[foo]/vlanlist
        // list: given arguments for vlan-list
        // operation: indicate apply/remove
        // listoper:  vlan-list actual in effect.
        // listerr:   erroneous vlan-list, for fault purpose, updated via
        // second trunk by aclmgr.
        container vlanlist-items {

            // Added containment as a singleton: Prefix=vlanlist
            // Acquired From Package acl
            uses acl_VLANList-group;
        }
    }

    grouping acl_VLANSeq-group {
        leaf seqNum {
            type uint32;
        }

        // toggle per-entry statistics
        // Type is an MO-Defined-Type
        leaf perACEStatistics {
            description "Per ACE statistics";

            // Type is an MO-Defined-Type
            type acl_ACEStats;
        }

        // MO: VLAN ACL match
        // /sys/acl/vlan-[foo]/seq-30/match-[ip_ipv6_mac]-address-[acl1]/
        container match-items {
            list VLANACLMatch-list {
                key "acltype aclname";

                // Added containment: Prefix=match
                // Acquired From Package acl
                uses acl_VLANACLMatch-group;
            }
        }

        // MO: VLAN ACL action
        // /sys/acl/vlan-[foo]/seq-30/action.log=[yes_no]/
        // /sys/acl/vlan-[foo]/seq-30/action.actiontype=[forward_redirect_drop]/
        // /sys/acl/vlan-[foo]/seq-30/action.redirectintf=[eth1/31_po1]/
        container action-items {

            // Added containment as a singleton: Prefix=action
            // Acquired From Package acl
            uses acl_VLANACLAction-group;
        }
    }

    grouping acl_VLANACLMatch-group {

        // Match ACL type: ip_ipv4_mac
        // Type is an MO-Defined-Type
        leaf acltype {
            description "match acl type";

            // Type is an MO-Defined-Type
            type acl_VAclMatchType;
        }

        // Match ACL name
        // Type is an MO-Defined-Type
        leaf aclname {
            description "match acl name";

            // Type is an MO-Defined-Type
            type acl_Name;
        }
    }

    grouping acl_VLANACLAction-group {

        // forward_drop_redirect
        // Type is an MO-Defined-Type
        leaf actiontype {
            description "VLAN ACL action";

            // Type is an MO-Defined-Type
            type acl_VAclActionType;
        }

        // toggle log options
        // Type is an MO-Defined-Type
        leaf log {
            description "Log option";

            // Type is an MO-Defined-Type
            type acl_VAclLog;
        }

        // Type is an MO-Defined-Type
        leaf redirectintf {
            description "Redirect Interfaces";

            // Type is an MO-Defined-Type
            type acl_IfName;
        }
    }

    grouping acl_VLANList-group {

        // Type is an MO-Defined-Type
        leaf list {
            description "Vlan List String";

            // Type is an MO-Defined-Type
            type acl_VlanListStr;
        }

        // Type is an MO-Defined-Type
        leaf operation {
            description "Vlan Filter Operation";

            // Type is an MO-Defined-Type
            type acl_operation;
        }

        // Type is an MO-Defined-Type
        leaf listoper {
            config "false";
            description "Vlan List String oper";

            // Type is an MO-Defined-Type
            type acl_VlanListStr;
        }

        // Type is an MO-Defined-Type
        leaf listerr {
            config "false";
            description "Vlan List String error";

            // Type is an MO-Defined-Type
            type acl_VlanListStr;
        }
    }

    grouping macacl_AF-group {

        container statClear-items {

            // Added containment as a singleton: Prefix=statClear
            // Acquired From Package acl
            uses acl_StatClear-group;
        }

        // ACL policies
        container policy-items {

            // Added containment as a singleton: Prefix=policy
            // Acquired From Package acl
            uses acl_Policy-group;
        }

        // IPv4 ACL
        container name-items {
            list ACL-list {
                key "name";

                // Added containment: Prefix=name
                // Acquired From Package macacl
                uses macacl_ACL-group;
            }
        }
    }

    grouping acl_StatClear-group {

        // StatClear ACL name
        // Type is an MO-Defined-Type
        leaf name {
            description "Name";

            // Type is an MO-Defined-Type
            type acl_Name;
        }
        leaf timeStamp {
            type uint64;
        }
    }

    grouping acl_Policy-group {

        // Ingress directions
        container ingress-items {

            // Added containment as a singleton: Prefix=ingress
            // Acquired From Package acl
            uses acl_Ingress-group;
        }

        // Egress directions
        container egress-items {

            // Added containment as a singleton: Prefix=egress
            // Acquired From Package acl
            uses acl_Egress-group;
        }
    }

    grouping acl_Ingress-group {

        // Target interface
        container intf-items {
            list If-list {
                key "name";

                // Added containment: Prefix=intf
                // Acquired From Package acl
                uses acl_If-group;
            }
        }

        container vty-items {

            // Added containment as a singleton: Prefix=vty
            // Acquired From Package acl
            uses acl_Vty-group;
        }
    }

    grouping acl_If-group {

        // interface name string
        // Type is an MO-Defined-Type
        leaf name {
            description "Interface";

            // Type is an MO-Defined-Type
            type acl_IfName;
        }

        // ACL instance
        container acl-items {

            // Added containment as a singleton: Prefix=acl
            // Acquired From Package acl
            uses acl_Inst-group;
        }

        // port ACL instance
        container portacl-items {

            // Added containment as a singleton: Prefix=portacl
            // Acquired From Package acl
            uses acl_PortInst-group;
        }
    }

    grouping acl_Inst-group {

        // Type is an MO-Defined-Type
        leaf name {
            description "Name";

            // Type is an MO-Defined-Type
            type acl_Name;
        }
        leaf configStatus {
            config "false";
            type uint32;
        }
    }

    grouping acl_PortInst-group {

        // Type is an MO-Defined-Type
        leaf name {
            description "Name";

            // Type is an MO-Defined-Type
            type acl_Name;
        }
        leaf configStatus {
            config "false";
            type uint32;
        }
    }

    grouping acl_Vty-group {

        // ACL instance
        container acl-items {

            // Added containment as a singleton: Prefix=acl
            // Acquired From Package acl
            uses acl_Inst-group;
        }
    }

    grouping acl_Egress-group {

        // Target interface
        container intf-items {
            list If-list {
                key "name";

                // Added containment: Prefix=intf
                // Acquired From Package acl
                uses acl_If-group;
            }
        }

        container vty-items {

            // Added containment as a singleton: Prefix=vty
            // Acquired From Package acl
            uses acl_Vty-group;
        }
    }

    grouping macacl_ACL-group {

        // ACL name
        // Inherited From acl:ACL
        // Type is an MO-Defined-Type
        leaf name {
            description "Name";

            // Type is an MO-Defined-Type
            type acl_Name;
        }

        // toggle per-entry statistics
        // Inherited From acl:ACL
        // Type is an MO-Defined-Type
        leaf perACEStatistics {
            description "Per ACE statistics";

            // Type is an MO-Defined-Type
            type acl_ACEStats;
        }
        leaf configStatus {
            config "false";
            type uint32;
        }

        // End of Layer 3 ACE (abstract MO)    resequnce MO
        container reseq-items {

            // Added containment as a singleton: Prefix=reseq
            // Acquired From Package acl
            uses acl_Resequence-group;
        }

        // IPv4 ACE
        container seq-items {
            list SEQ-list {
                key "seqNum";

                // Added containment: Prefix=seq
                // Acquired From Package macacl
                uses macacl_SEQ-group;
            }
        }
    }

    grouping acl_Resequence-group {
        leaf start {
            type uint32;
        }
        leaf step {
            type uint32;
        }
        leaf reseqDone {
            config "false";
            type boolean;
        }

        // resequence Result Entry Mo
        container reseq-items {
            list ReseqResultEntry-list {
                key "beforeSeq";

                // Added containment: Prefix=reseq
                // Acquired From Package acl
                uses acl_ReseqResultEntry-group;
            }
        }
    }

    grouping acl_ReseqResultEntry-group {
        leaf beforeSeq {
            type uint32;
        }
        leaf afterSeq {
            type uint32;
        }
    }

    grouping macacl_SEQ-group {

        // ACE sequence number
        // Type is an MO-Defined-Type
        leaf seqNum {
            description "Sequence number";

            // Type is an MO-Defined-Type
            type acl_SequenceNumber;
        }

        // MAC ACE
        container ace-items {

            // Added containment as a singleton: Prefix=ace
            // Acquired From Package macacl
            uses macacl_ACE-group;
        }

        // Remark ACE
        container remark-items {

            // Added containment as a singleton: Prefix=remark
            // Acquired From Package macacl
            uses macacl_Remark-group;
        }
    }

    grouping macacl_ACE-group {

        // protocol number
        // Type is an MO-Defined-Type
        leaf protocol {
            description "protocol number";

            // Type is an MO-Defined-Type
            type acl_MACProtocol;
        }

        // cos number
        // Type is an MO-Defined-Type
        leaf cos {
            description "Cos number";

            // Type is an MO-Defined-Type
            type acl_cosType;
        }
        leaf redirect {
            type string;
        }

        // time-range
        // Type is an MO-Defined-Type
        leaf timeRange {
            description "time range";

            // Type is an MO-Defined-Type
            type acl_TimeRangeName;
        }

        // vlan number
        // Type is an MO-Defined-Type
        leaf vlan {
            description "vlan number";

            // Type is an MO-Defined-Type
            type acl_VlanType;
        }

        // set-erspan-dscp-
        // Type is an MO-Defined-Type
        leaf erspanDscp {
            description "dscp value";

            // Type is an MO-Defined-Type
            type acl_erspanDscpType;
        }

        // erspan gre proto
        // Type is an MO-Defined-Type
        leaf erspanGre {
            description "dscp gre protocol";

            // Type is an MO-Defined-Type
            type acl_erspanGreType;
        }
        leaf userSetBit {
            type uint64;
            default "1";
        }

        // ACE filtering action
        // Inherited From acl:L2ACE
        // Type is an MO-Defined-Type
        leaf action {
            description "ACE action";

            // Type is an MO-Defined-Type
            type acl_ActionType;
        }
        leaf srcPrefix {
            type address_Mac;
        }
        leaf srcPrefixMask {
            type address_Mac;
        }
        leaf dstPrefix {
            type address_Mac;
        }
        leaf dstPrefixMask {
            type address_Mac;
        }
        leaf packets {
            config "false";
            type uint64;
        }
    }

    grouping macacl_Remark-group {

        // ACE sequence number
        // Type is an MO-Defined-Type
        leaf seqNum {
            description "Sequence number";

            // Type is an MO-Defined-Type
            type acl_SequenceNumber;
        }

        // remark
        // Type is an MO-Defined-Type
        leaf remark {
            description "Remark";

            // Type is an MO-Defined-Type
            type acl_RemarkStr;
        }
    }

    grouping ipv4acl_AF-group {

        container statClear-items {

            // Added containment as a singleton: Prefix=statClear
            // Acquired From Package acl
            uses acl_StatClear-group;
        }

        // ACL policies
        container policy-items {

            // Added containment as a singleton: Prefix=policy
            // Acquired From Package acl
            uses acl_Policy-group;
        }

        // IPv4 ACL
        container name-items {
            list ACL-list {
                key "name";

                // Added containment: Prefix=name
                // Acquired From Package ipv4acl
                uses ipv4acl_ACL-group;
            }
        }

        // IPv4 address object-group
        container oName-items {
            list AddrGroup-list {
                key "name";

                // Added containment: Prefix=oName
                // Acquired From Package ipv4acl
                uses ipv4acl_AddrGroup-group;
            }
        }
    }

    grouping ipv4acl_ACL-group {

        // ACL name
        // Inherited From acl:ACL
        // Type is an MO-Defined-Type
        leaf name {
            description "Name";

            // Type is an MO-Defined-Type
            type acl_Name;
        }

        // toggle per-entry statistics
        // Inherited From acl:ACL
        // Type is an MO-Defined-Type
        leaf perACEStatistics {
            description "Per ACE statistics";

            // Type is an MO-Defined-Type
            type acl_ACEStats;
        }
        leaf configStatus {
            config "false";
            type uint32;
        }

        // End of Layer 3 ACE (abstract MO)    resequnce MO
        container reseq-items {

            // Added containment as a singleton: Prefix=reseq
            // Acquired From Package acl
            uses acl_Resequence-group;
        }

        // IPv4 ACE
        container seq-items {
            list ACE-list {
                key "seqNum";

                // Added containment: Prefix=seq
                // Acquired From Package ipv4acl
                uses ipv4acl_ACE-group;
            }
        }
    }

    grouping ipv4acl_ACE-group {

        // protocol to match
        // Type is an MO-Defined-Type
        leaf protocol {
            description "Protocol for access-list entry";

            // Type is an MO-Defined-Type
            type ipv4acl_Protocol;
        }

        // Protocol Mask
        // Type is an MO-Defined-Type
        leaf protocolMask {
            description "Protocol Mask";

            // Type is an MO-Defined-Type
            type ipv4acl_Protocol;
        }

        // source prefix
        // Type is an MO-Defined-Type
        leaf srcPrefix {
            description "Source IPv4 prefix";

            // Type is an MO-Defined-Type
            type ipv4acl_IPv4Prefix;
        }

        // source prefix wildcard mask
        // Type is an MO-Defined-Type
        leaf srcPrefixMask {
            description "Source IPv4 prefix mask";

            // Type is an MO-Defined-Type
            type ipv4acl_IPv4PrefixMask;
        }

        // source prefix length
        // Type is an MO-Defined-Type
        leaf srcPrefixLength {
            description "Source IPv4 prefix length";

            // Type is an MO-Defined-Type
            type ipv4acl_IPv4PrefixLen;
        }

        // destination prefix
        // Type is an MO-Defined-Type
        leaf dstPrefix {
            description "Destination IPv4 prefix";

            // Type is an MO-Defined-Type
            type ipv4acl_IPv4Prefix;
        }

        // destination prefix wildcard mask
        // Type is an MO-Defined-Type
        leaf dstPrefixMask {
            description "Destination IPv4 prefix mask";

            // Type is an MO-Defined-Type
            type ipv4acl_IPv4PrefixMask;
        }

        // destination prefix length
        // Type is an MO-Defined-Type
        leaf dstPrefixLength {
            description "Destination IPv4 prefix length";

            // Type is an MO-Defined-Type
            type ipv4acl_IPv4PrefixLen;
        }

        // precedence
        // Type is an MO-Defined-Type
        leaf precedence {
            description "IPv4 precedence";

            // Type is an MO-Defined-Type
            type ipv4acl_Precedence;
        }
        leaf ttl {
            type uint8;
        }

        // redirect
        // Type is an MO-Defined-Type
        leaf redirect {
            description "Redirect action";

            // Type is an MO-Defined-Type
            type acl_Name;
        }

        // ICMP Str
        // Type is an MO-Defined-Type
        leaf icmpStr {
            description "ICMP type";

            // Type is an MO-Defined-Type
            type ipv4acl_ICMPEnum;
        }

        // ICMP type
        // Type is an MO-Defined-Type
        leaf icmpType {
            description "ICMP type";

            // Type is an MO-Defined-Type
            type ipv4acl_ICMPType;
        }

        // ICMP code
        // Type is an MO-Defined-Type
        leaf icmpCode {
            description "ICMP code";

            // Type is an MO-Defined-Type
            type ipv4acl_ICMPCode;
        }

        // tos
        // Type is an MO-Defined-Type
        leaf tos {
            description "capture session";

            // Type is an MO-Defined-Type
            type ipv4acl_Tos;
        }

        // configState
        // Type is an MO-Defined-Type
        leaf configStatus {
            description "config status";

            // Type is an MO-Defined-Type
            type acl_ConfigState;
        }

        // remark
        // Inherited From acl:L3ACE
        // Type is an MO-Defined-Type
        leaf remark {
            description "Remark";

            // Type is an MO-Defined-Type
            type acl_RemarkStr;
        }

        // ACE sequence number
        // Inherited From acl:L3ACE
        // Type is an MO-Defined-Type
        leaf seqNum {
            description "Sequence number";

            // Type is an MO-Defined-Type
            type acl_SequenceNumber;
        }
        leaf userSetBit {
            type uint64;
            default "1";
        }

        // ACE filtering action
        // Inherited From acl:L3ACE
        // Type is an MO-Defined-Type
        leaf action {
            description "ACE action";

            // Type is an MO-Defined-Type
            type acl_ActionType;
        }

        // source port operation
        // Inherited From acl:L3ACE
        // Type is an MO-Defined-Type
        leaf srcPortOp {
            description "Source port operations";

            // Type is an MO-Defined-Type
            type acl_Operator;
        }

        // first source port
        // Inherited From acl:L3ACE
        // Type is an MO-Defined-Type
        leaf srcPort1 {
            description "First source port";

            // Type is an MO-Defined-Type
            type acl_PortNumber;
        }

        // second source port
        // Inherited From acl:L3ACE
        // Type is an MO-Defined-Type
        leaf srcPort2 {
            description "Second source port";

            // Type is an MO-Defined-Type
            type acl_PortNumber;
        }

        // Source Port Mask
        // Inherited From acl:L3ACE
        // Type is an MO-Defined-Type
        leaf srcPortMask {
            description "Source Port Mask";

            // Type is an MO-Defined-Type
            type acl_PortNumber;
        }

        // destination port operation
        // Inherited From acl:L3ACE
        // Type is an MO-Defined-Type
        leaf dstPortOp {
            description "Destination port operations";

            // Type is an MO-Defined-Type
            type acl_Operator;
        }

        // first destination port
        // Inherited From acl:L3ACE
        // Type is an MO-Defined-Type
        leaf dstPort1 {
            description "First destination port number";

            // Type is an MO-Defined-Type
            type acl_PortNumber;
        }

        // second destination port
        // Inherited From acl:L3ACE
        // Type is an MO-Defined-Type
        leaf dstPort2 {
            description "Second destination port number";

            // Type is an MO-Defined-Type
            type acl_PortNumber;
        }

        // Destination Port Mask
        // Inherited From acl:L3ACE
        // Type is an MO-Defined-Type
        leaf dstPortMask {
            description "Dest Port Mask";

            // Type is an MO-Defined-Type
            type acl_PortNumber;
        }
        leaf logging {
            type boolean;
            default "true";
        }

        // dscp
        // Inherited From acl:L3ACE
        // Type is an MO-Defined-Type
        leaf dscp {
            description "dscp";

            // Type is an MO-Defined-Type
            type ipqos_Dscp;
        }

        // packet-length operator
        // Inherited From acl:L3ACE
        // Type is an MO-Defined-Type
        leaf pktLenOp {
            description "packet length operator";

            // Type is an MO-Defined-Type
            type acl_Operator;
        }

        // First packet-length
        // Inherited From acl:L3ACE
        // Type is an MO-Defined-Type
        leaf pktLen1 {
            description "packet length";

            // Type is an MO-Defined-Type
            type acl_PktLen;
        }

        // second packet-length
        // Inherited From acl:L3ACE
        // Type is an MO-Defined-Type
        leaf pktLen2 {
            description "packet length";

            // Type is an MO-Defined-Type
            type acl_PktLen;
        }
        leaf urg {
            type boolean;
        }
        leaf ack {
            type boolean;
        }
        leaf psh {
            type boolean;
        }
        leaf rst {
            type boolean;
        }
        leaf syn {
            type boolean;
        }
        leaf fin {
            type boolean;
        }
        leaf est {
            type boolean;
        }
        leaf rev {
            type boolean;
        }

        // Inherited From acl:L3ACE
        // Type is an MO-Defined-Type
        leaf tcpFlagsMask {
            description "tcp flags mask";

            // Type is an MO-Defined-Type
            type acl_TcpFlagsMask;
        }
        leaf packets {
            config "false";
            type uint64;
        }
        leaf fragment {
            type boolean;
        }

        // capture session
        // Inherited From acl:L3ACE
        // Type is an MO-Defined-Type
        leaf captureSession {
            description "capture session";

            // Type is an MO-Defined-Type
            type acl_CaptureSes;
        }

        // http option (http-method)
        // Inherited From acl:L3ACE
        // Type is an MO-Defined-Type
        leaf httpOption {
            description "http option http-method";

            // Type is an MO-Defined-Type
            type acl_HttpOptionType;
        }

        // nve vni ID
        // Inherited From acl:L3ACE
        // Type is an MO-Defined-Type
        leaf vni {
            description "nve vni ID";

            // Type is an MO-Defined-Type
            type acl_VniType;
        }

        // vlan
        // Inherited From acl:L3ACE
        // Type is an MO-Defined-Type
        leaf vlan {
            description "vlan";

            // Type is an MO-Defined-Type
            type acl_VlanType;
        }

        // TCP option length
        // Inherited From acl:L3ACE
        // Type is an MO-Defined-Type
        leaf tcpOptionLength {
            description "TCP options length";

            // Type is an MO-Defined-Type
            type acl_TcpOptionLengthType;
        }

        // time-range
        // Inherited From acl:L3ACE
        // Type is an MO-Defined-Type
        leaf timeRange {
            description "time range";

            // Type is an MO-Defined-Type
            type acl_Name;
        }

        // source address group
        // Inherited From acl:L3ACE
        // Type is an MO-Defined-Type
        leaf srcAddrGroup {
            description "Source address group";

            // Type is an MO-Defined-Type
            type acl_Name;
        }

        // destination address group
        // Inherited From acl:L3ACE
        // Type is an MO-Defined-Type
        leaf dstAddrGroup {
            description "Destination address group";

            // Type is an MO-Defined-Type
            type acl_Name;
        }

        // source port group
        // Inherited From acl:L3ACE
        // Type is an MO-Defined-Type
        leaf srcPortGroup {
            description "Source port group";

            // Type is an MO-Defined-Type
            type acl_Name;
        }

        // destination port group
        // Inherited From acl:L3ACE
        // Type is an MO-Defined-Type
        leaf dstPortGroup {
            description "Destination port group";

            // Type is an MO-Defined-Type
            type acl_Name;
        }

        // UDF
        container udf-items {

            // Added containment as a singleton: Prefix=udf
            // Acquired From Package ipv4acl
            uses ipv4acl_UDF-group;
        }
    }

    grouping ipv4acl_UDF-group {

        // supports at most 18 UDF    udf1 Name
        // Type is an MO-Defined-Type
        leaf udf1Name {
            description "User-defined field match 1";

            // Type is an MO-Defined-Type
            type acl_UdfName;
        }

        // udf1 Value
        // Type is an MO-Defined-Type
        leaf udf1Val {
            description "UDF1 value to match";

            // Type is an MO-Defined-Type
            type acl_UdfVal;
        }

        // udf1 Mask
        // Type is an MO-Defined-Type
        leaf udf1Mask {
            description "Mask to apply to UDF1 value";

            // Type is an MO-Defined-Type
            type acl_UdfMask;
        }

        // udf2 Name
        // Type is an MO-Defined-Type
        leaf udf2Name {
            description "User-defined field match 2";

            // Type is an MO-Defined-Type
            type acl_UdfName;
        }

        // udf2 Value
        // Type is an MO-Defined-Type
        leaf udf2Val {
            description "UDF2 value to match";

            // Type is an MO-Defined-Type
            type acl_UdfVal;
        }

        // udf2 Mask
        // Type is an MO-Defined-Type
        leaf udf2Mask {
            description "Mask to apply to UDF2 value";

            // Type is an MO-Defined-Type
            type acl_UdfMask;
        }

        // udf3 Name
        // Type is an MO-Defined-Type
        leaf udf3Name {
            description "User-defined field match 3";

            // Type is an MO-Defined-Type
            type acl_UdfName;
        }

        // udf3 Value
        // Type is an MO-Defined-Type
        leaf udf3Val {
            description "UDF3 value to match";

            // Type is an MO-Defined-Type
            type acl_UdfVal;
        }

        // udf3 Mask
        // Type is an MO-Defined-Type
        leaf udf3Mask {
            description "Mask to apply to UDF3 value";

            // Type is an MO-Defined-Type
            type acl_UdfMask;
        }

        // udf4 Name
        // Type is an MO-Defined-Type
        leaf udf4Name {
            description "User-defined field match 4";

            // Type is an MO-Defined-Type
            type acl_UdfName;
        }

        // udf4 Value
        // Type is an MO-Defined-Type
        leaf udf4Val {
            description "UDF4 value to match";

            // Type is an MO-Defined-Type
            type acl_UdfVal;
        }

        // udf4 Mask
        // Type is an MO-Defined-Type
        leaf udf4Mask {
            description "Mask to apply to UDF4 value";

            // Type is an MO-Defined-Type
            type acl_UdfMask;
        }

        // udf5 Name
        // Type is an MO-Defined-Type
        leaf udf5Name {
            description "User-defined field match 5";

            // Type is an MO-Defined-Type
            type acl_UdfName;
        }

        // udf5 Value
        // Type is an MO-Defined-Type
        leaf udf5Val {
            description "UDF5 value to match";

            // Type is an MO-Defined-Type
            type acl_UdfVal;
        }

        // udf5 Mask
        // Type is an MO-Defined-Type
        leaf udf5Mask {
            description "Mask to apply to UDF5 value";

            // Type is an MO-Defined-Type
            type acl_UdfMask;
        }

        // udf6 Name
        // Type is an MO-Defined-Type
        leaf udf6Name {
            description "User-defined field match 6";

            // Type is an MO-Defined-Type
            type acl_UdfName;
        }

        // udf6 Value
        // Type is an MO-Defined-Type
        leaf udf6Val {
            description "UDF6 value to match";

            // Type is an MO-Defined-Type
            type acl_UdfVal;
        }

        // udf6 Mask
        // Type is an MO-Defined-Type
        leaf udf6Mask {
            description "Mask to apply to UDF6 value";

            // Type is an MO-Defined-Type
            type acl_UdfMask;
        }

        // udf7 Name
        // Type is an MO-Defined-Type
        leaf udf7Name {
            description "User-defined field match 7";

            // Type is an MO-Defined-Type
            type acl_UdfName;
        }

        // udf7 Value
        // Type is an MO-Defined-Type
        leaf udf7Val {
            description "UDF7 value to match";

            // Type is an MO-Defined-Type
            type acl_UdfVal;
        }

        // udf7 Mask
        // Type is an MO-Defined-Type
        leaf udf7Mask {
            description "Mask to apply to UDF7 value";

            // Type is an MO-Defined-Type
            type acl_UdfMask;
        }

        // udf8 Name
        // Type is an MO-Defined-Type
        leaf udf8Name {
            description "User-defined field match 8";

            // Type is an MO-Defined-Type
            type acl_UdfName;
        }

        // udf8 Value
        // Type is an MO-Defined-Type
        leaf udf8Val {
            description "UDF8 value to match";

            // Type is an MO-Defined-Type
            type acl_UdfVal;
        }

        // udf8 Mask
        // Type is an MO-Defined-Type
        leaf udf8Mask {
            description "Mask to apply to UDF8 value";

            // Type is an MO-Defined-Type
            type acl_UdfMask;
        }

        // udf9 Name
        // Type is an MO-Defined-Type
        leaf udf9Name {
            description "User-defined field match 9";

            // Type is an MO-Defined-Type
            type acl_UdfName;
        }

        // udf9 Value
        // Type is an MO-Defined-Type
        leaf udf9Val {
            description "UDF9 value to match";

            // Type is an MO-Defined-Type
            type acl_UdfVal;
        }

        // udf9 Mask
        // Type is an MO-Defined-Type
        leaf udf9Mask {
            description "Mask to apply to UDF9 value";

            // Type is an MO-Defined-Type
            type acl_UdfMask;
        }

        // udf10 Name
        // Type is an MO-Defined-Type
        leaf udf10Name {
            description "User-defined field match 10";

            // Type is an MO-Defined-Type
            type acl_UdfName;
        }

        // udf10 Value
        // Type is an MO-Defined-Type
        leaf udf10Val {
            description "UDF10 value to match";

            // Type is an MO-Defined-Type
            type acl_UdfVal;
        }

        // udf10 Mask
        // Type is an MO-Defined-Type
        leaf udf10Mask {
            description "Mask to apply to UDF10 value";

            // Type is an MO-Defined-Type
            type acl_UdfMask;
        }

        // udf11 Name
        // Type is an MO-Defined-Type
        leaf udf11Name {
            description "User-defined field match 11";

            // Type is an MO-Defined-Type
            type acl_UdfName;
        }

        // udf11 Value
        // Type is an MO-Defined-Type
        leaf udf11Val {
            description "UDF11 value to match";

            // Type is an MO-Defined-Type
            type acl_UdfVal;
        }

        // udf11 Mask
        // Type is an MO-Defined-Type
        leaf udf11Mask {
            description "Mask to apply to UDF11 value";

            // Type is an MO-Defined-Type
            type acl_UdfMask;
        }

        // udf12 Name
        // Type is an MO-Defined-Type
        leaf udf12Name {
            description "User-defined field match 12";

            // Type is an MO-Defined-Type
            type acl_UdfName;
        }

        // udf12 Value
        // Type is an MO-Defined-Type
        leaf udf12Val {
            description "UDF12 value to match";

            // Type is an MO-Defined-Type
            type acl_UdfVal;
        }

        // udf12 Mask
        // Type is an MO-Defined-Type
        leaf udf12Mask {
            description "Mask to apply to UDF12 value";

            // Type is an MO-Defined-Type
            type acl_UdfMask;
        }

        // udf13 Name
        // Type is an MO-Defined-Type
        leaf udf13Name {
            description "User-defined field match 13";

            // Type is an MO-Defined-Type
            type acl_UdfName;
        }

        // udf13 Value
        // Type is an MO-Defined-Type
        leaf udf13Val {
            description "UDF13 value to match";

            // Type is an MO-Defined-Type
            type acl_UdfVal;
        }

        // udf13 Mask
        // Type is an MO-Defined-Type
        leaf udf13Mask {
            description "Mask to apply to UDF13 value";

            // Type is an MO-Defined-Type
            type acl_UdfMask;
        }

        // udf14 Name
        // Type is an MO-Defined-Type
        leaf udf14Name {
            description "User-defined field match 14";

            // Type is an MO-Defined-Type
            type acl_UdfName;
        }

        // udf14 Value
        // Type is an MO-Defined-Type
        leaf udf14Val {
            description "UDF14 value to match";

            // Type is an MO-Defined-Type
            type acl_UdfVal;
        }

        // udf14 Mask
        // Type is an MO-Defined-Type
        leaf udf14Mask {
            description "Mask to apply to UDF14 value";

            // Type is an MO-Defined-Type
            type acl_UdfMask;
        }

        // udf15 Name
        // Type is an MO-Defined-Type
        leaf udf15Name {
            description "User-defined field match 15";

            // Type is an MO-Defined-Type
            type acl_UdfName;
        }

        // udf15 Value
        // Type is an MO-Defined-Type
        leaf udf15Val {
            description "UDF15 value to match";

            // Type is an MO-Defined-Type
            type acl_UdfVal;
        }

        // udf15 Mask
        // Type is an MO-Defined-Type
        leaf udf15Mask {
            description "Mask to apply to UDF15 value";

            // Type is an MO-Defined-Type
            type acl_UdfMask;
        }

        // udf16 Name
        // Type is an MO-Defined-Type
        leaf udf16Name {
            description "User-defined field match 16";

            // Type is an MO-Defined-Type
            type acl_UdfName;
        }

        // udf16 Value
        // Type is an MO-Defined-Type
        leaf udf16Val {
            description "UDF16 value to match";

            // Type is an MO-Defined-Type
            type acl_UdfVal;
        }

        // udf16 Mask
        // Type is an MO-Defined-Type
        leaf udf16Mask {
            description "Mask to apply to UDF16 value";

            // Type is an MO-Defined-Type
            type acl_UdfMask;
        }

        // udf17 Name
        // Type is an MO-Defined-Type
        leaf udf17Name {
            description "User-defined field match 17";

            // Type is an MO-Defined-Type
            type acl_UdfName;
        }

        // udf17 Value
        // Type is an MO-Defined-Type
        leaf udf17Val {
            description "UDF17 value to match";

            // Type is an MO-Defined-Type
            type acl_UdfVal;
        }

        // udf17 Mask
        // Type is an MO-Defined-Type
        leaf udf17Mask {
            description "Mask to apply to UDF17 value";

            // Type is an MO-Defined-Type
            type acl_UdfMask;
        }

        // udf18 Name
        // Type is an MO-Defined-Type
        leaf udf18Name {
            description "User-defined field match 18";

            // Type is an MO-Defined-Type
            type acl_UdfName;
        }

        // udf18 Value
        // Type is an MO-Defined-Type
        leaf udf18Val {
            description "UDF18 value to match";

            // Type is an MO-Defined-Type
            type acl_UdfVal;
        }

        // udf18 Mask
        // Type is an MO-Defined-Type
        leaf udf18Mask {
            description "Mask to apply to UDF18 value";

            // Type is an MO-Defined-Type
            type acl_UdfMask;
        }
    }

    grouping ipv4acl_AddrGroup-group {

        // object-group name
        // Inherited From acl:OGroup
        // Type is an MO-Defined-Type
        leaf name {
            description "Name";

            // Type is an MO-Defined-Type
            type acl_Name;
        }
        leaf configStatus {
            config "false";
            type uint32;
        }

        // IPv4 Address Object Group member
        container seq-items {
            list AddrMember-list {
                key "seqNum";

                // Added containment: Prefix=seq
                // Acquired From Package ipv4acl
                uses ipv4acl_AddrMember-group;
            }
        }
    }

    grouping ipv4acl_AddrMember-group {

        // prefix
        // Type is an MO-Defined-Type
        leaf prefix {
            description "IPv4 prefix";

            // Type is an MO-Defined-Type
            type ipv4acl_IPv4Prefix;
        }

        // prefix wildcard mask
        // Type is an MO-Defined-Type
        leaf prefixMask {
            description "IPv4 prefix mask";

            // Type is an MO-Defined-Type
            type ipv4acl_IPv4PrefixMask;
        }

        // prefix length
        // Type is an MO-Defined-Type
        leaf prefixLength {
            description "IPv4 prefix length";

            // Type is an MO-Defined-Type
            type ipv4acl_IPv4PrefixLen;
        }

        // configState
        // Type is an MO-Defined-Type
        leaf configStatus {
            description "config status";

            // Type is an MO-Defined-Type
            type acl_ConfigState;
        }

        // Object Group Member sequence number
        // Inherited From acl:OMember
        // Type is an MO-Defined-Type
        leaf seqNum {
            description "Sequence number";

            // Type is an MO-Defined-Type
            type acl_SequenceNumber;
        }
        leaf userSetBit {
            type uint64;
            default "1";
        }
    }

    grouping ipv6acl_AF-group {

        container statClear-items {

            // Added containment as a singleton: Prefix=statClear
            // Acquired From Package acl
            uses acl_StatClear-group;
        }

        // ACL policies
        container policy-items {

            // Added containment as a singleton: Prefix=policy
            // Acquired From Package acl
            uses acl_Policy-group;
        }

        // IPv6 ACL
        container name-items {
            list ACL-list {
                key "name";

                // Added containment: Prefix=name
                // Acquired From Package ipv6acl
                uses ipv6acl_ACL-group;
            }
        }

        // IPv6 address object-group
        container oName-items {
            list AddrGroup-list {
                key "name";

                // Added containment: Prefix=oName
                // Acquired From Package ipv6acl
                uses ipv6acl_AddrGroup-group;
            }
        }
    }

    grouping ipv6acl_ACL-group {

        // ACL name
        // Inherited From acl:ACL
        // Type is an MO-Defined-Type
        leaf name {
            description "Name";

            // Type is an MO-Defined-Type
            type acl_Name;
        }

        // toggle per-entry statistics
        // Inherited From acl:ACL
        // Type is an MO-Defined-Type
        leaf perACEStatistics {
            description "Per ACE statistics";

            // Type is an MO-Defined-Type
            type acl_ACEStats;
        }
        leaf configStatus {
            config "false";
            type uint32;
        }

        // End of Layer 3 ACE (abstract MO)    resequnce MO
        container reseq-items {

            // Added containment as a singleton: Prefix=reseq
            // Acquired From Package acl
            uses acl_Resequence-group;
        }

        // IPv6 ACE
        container seq-items {
            list ACE-list {
                key "seqNum";

                // Added containment: Prefix=seq
                // Acquired From Package ipv6acl
                uses ipv6acl_ACE-group;
            }
        }
    }

    grouping ipv6acl_ACE-group {

        // protocol to match
        // Type is an MO-Defined-Type
        leaf protocol {
            description "Protocol for access-list entry";

            // Type is an MO-Defined-Type
            type ipv6acl_Protocol;
        }

        // Protocol Mask
        // Type is an MO-Defined-Type
        leaf protocolMask {
            description "Protocol Mask";

            // Type is an MO-Defined-Type
            type ipv6acl_Protocol;
        }

        // source prefix
        // Type is an MO-Defined-Type
        leaf srcPrefix {
            description "Source IPv6 prefix";

            // Type is an MO-Defined-Type
            type ipv6acl_IPv6Prefix;
        }

        // source prefix wildcard mask
        // Type is an MO-Defined-Type
        leaf srcPrefixMask {
            description "Source IPv6 prefix mask";

            // Type is an MO-Defined-Type
            type ipv6acl_IPv6PrefixMask;
        }

        // source prefix length
        // Type is an MO-Defined-Type
        leaf srcPrefixLength {
            description "Source IPv6 prefix length";

            // Type is an MO-Defined-Type
            type ipv6acl_IPv6PrefixLen;
        }

        // destination prefix
        // Type is an MO-Defined-Type
        leaf dstPrefix {
            description "Destination IPv6 prefix";

            // Type is an MO-Defined-Type
            type ipv6acl_IPv6Prefix;
        }

        // destination prefix wildcard mask
        // Type is an MO-Defined-Type
        leaf dstPrefixMask {
            description "Destination IPv6 prefix mask";

            // Type is an MO-Defined-Type
            type ipv6acl_IPv6PrefixMask;
        }

        // destination prefix length
        // Type is an MO-Defined-Type
        leaf dstPrefixLength {
            description "Destination IPv6 prefix length";

            // Type is an MO-Defined-Type
            type ipv6acl_IPv6PrefixLen;
        }

        // flow-label
        // Type is an MO-Defined-Type
        leaf flowLabel {
            description "Flow label";

            // Type is an MO-Defined-Type
            type ipv6acl_FlowLabel;
        }

        // ICMP Str
        // Type is an MO-Defined-Type
        leaf icmpStr {
            description "ICMPv6 Str";

            // Type is an MO-Defined-Type
            type ipv6acl_ICMPEnum;
        }

        // ICMP type
        // Type is an MO-Defined-Type
        leaf icmpType {
            description "ICMPv6 type";

            // Type is an MO-Defined-Type
            type ipv6acl_ICMPType;
        }

        // ICMP code
        // Type is an MO-Defined-Type
        leaf icmpCode {
            description "ICMPv6 code";

            // Type is an MO-Defined-Type
            type ipv6acl_ICMPCode;
        }

        // configState
        // Type is an MO-Defined-Type
        leaf configStatus {
            description "config status";

            // Type is an MO-Defined-Type
            type acl_ConfigState;
        }

        // remark
        // Inherited From acl:L3ACE
        // Type is an MO-Defined-Type
        leaf remark {
            description "Remark";

            // Type is an MO-Defined-Type
            type acl_RemarkStr;
        }

        // ACE sequence number
        // Inherited From acl:L3ACE
        // Type is an MO-Defined-Type
        leaf seqNum {
            description "Sequence number";

            // Type is an MO-Defined-Type
            type acl_SequenceNumber;
        }
        leaf userSetBit {
            type uint64;
            default "1";
        }

        // ACE filtering action
        // Inherited From acl:L3ACE
        // Type is an MO-Defined-Type
        leaf action {
            description "ACE action";

            // Type is an MO-Defined-Type
            type acl_ActionType;
        }

        // source port operation
        // Inherited From acl:L3ACE
        // Type is an MO-Defined-Type
        leaf srcPortOp {
            description "Source port operations";

            // Type is an MO-Defined-Type
            type acl_Operator;
        }

        // first source port
        // Inherited From acl:L3ACE
        // Type is an MO-Defined-Type
        leaf srcPort1 {
            description "First source port";

            // Type is an MO-Defined-Type
            type acl_PortNumber;
        }

        // second source port
        // Inherited From acl:L3ACE
        // Type is an MO-Defined-Type
        leaf srcPort2 {
            description "Second source port";

            // Type is an MO-Defined-Type
            type acl_PortNumber;
        }

        // Source Port Mask
        // Inherited From acl:L3ACE
        // Type is an MO-Defined-Type
        leaf srcPortMask {
            description "Source Port Mask";

            // Type is an MO-Defined-Type
            type acl_PortNumber;
        }

        // destination port operation
        // Inherited From acl:L3ACE
        // Type is an MO-Defined-Type
        leaf dstPortOp {
            description "Destination port operations";

            // Type is an MO-Defined-Type
            type acl_Operator;
        }

        // first destination port
        // Inherited From acl:L3ACE
        // Type is an MO-Defined-Type
        leaf dstPort1 {
            description "First destination port number";

            // Type is an MO-Defined-Type
            type acl_PortNumber;
        }

        // second destination port
        // Inherited From acl:L3ACE
        // Type is an MO-Defined-Type
        leaf dstPort2 {
            description "Second destination port number";

            // Type is an MO-Defined-Type
            type acl_PortNumber;
        }

        // Destination Port Mask
        // Inherited From acl:L3ACE
        // Type is an MO-Defined-Type
        leaf dstPortMask {
            description "Dest Port Mask";

            // Type is an MO-Defined-Type
            type acl_PortNumber;
        }
        leaf logging {
            type boolean;
            default "true";
        }

        // dscp
        // Inherited From acl:L3ACE
        // Type is an MO-Defined-Type
        leaf dscp {
            description "dscp";

            // Type is an MO-Defined-Type
            type ipqos_Dscp;
        }

        // packet-length operator
        // Inherited From acl:L3ACE
        // Type is an MO-Defined-Type
        leaf pktLenOp {
            description "packet length operator";

            // Type is an MO-Defined-Type
            type acl_Operator;
        }

        // First packet-length
        // Inherited From acl:L3ACE
        // Type is an MO-Defined-Type
        leaf pktLen1 {
            description "packet length";

            // Type is an MO-Defined-Type
            type acl_PktLen;
        }

        // second packet-length
        // Inherited From acl:L3ACE
        // Type is an MO-Defined-Type
        leaf pktLen2 {
            description "packet length";

            // Type is an MO-Defined-Type
            type acl_PktLen;
        }
        leaf urg {
            type boolean;
        }
        leaf ack {
            type boolean;
        }
        leaf psh {
            type boolean;
        }
        leaf rst {
            type boolean;
        }
        leaf syn {
            type boolean;
        }
        leaf fin {
            type boolean;
        }
        leaf est {
            type boolean;
        }
        leaf rev {
            type boolean;
        }

        // Inherited From acl:L3ACE
        // Type is an MO-Defined-Type
        leaf tcpFlagsMask {
            description "tcp flags mask";

            // Type is an MO-Defined-Type
            type acl_TcpFlagsMask;
        }
        leaf packets {
            config "false";
            type uint64;
        }
        leaf fragment {
            type boolean;
        }

        // capture session
        // Inherited From acl:L3ACE
        // Type is an MO-Defined-Type
        leaf captureSession {
            description "capture session";

            // Type is an MO-Defined-Type
            type acl_CaptureSes;
        }

        // http option (http-method)
        // Inherited From acl:L3ACE
        // Type is an MO-Defined-Type
        leaf httpOption {
            description "http option http-method";

            // Type is an MO-Defined-Type
            type acl_HttpOptionType;
        }

        // nve vni ID
        // Inherited From acl:L3ACE
        // Type is an MO-Defined-Type
        leaf vni {
            description "nve vni ID";

            // Type is an MO-Defined-Type
            type acl_VniType;
        }

        // vlan
        // Inherited From acl:L3ACE
        // Type is an MO-Defined-Type
        leaf vlan {
            description "vlan";

            // Type is an MO-Defined-Type
            type acl_VlanType;
        }

        // TCP option length
        // Inherited From acl:L3ACE
        // Type is an MO-Defined-Type
        leaf tcpOptionLength {
            description "TCP options length";

            // Type is an MO-Defined-Type
            type acl_TcpOptionLengthType;
        }

        // time-range
        // Inherited From acl:L3ACE
        // Type is an MO-Defined-Type
        leaf timeRange {
            description "time range";

            // Type is an MO-Defined-Type
            type acl_Name;
        }

        // source address group
        // Inherited From acl:L3ACE
        // Type is an MO-Defined-Type
        leaf srcAddrGroup {
            description "Source address group";

            // Type is an MO-Defined-Type
            type acl_Name;
        }

        // destination address group
        // Inherited From acl:L3ACE
        // Type is an MO-Defined-Type
        leaf dstAddrGroup {
            description "Destination address group";

            // Type is an MO-Defined-Type
            type acl_Name;
        }

        // source port group
        // Inherited From acl:L3ACE
        // Type is an MO-Defined-Type
        leaf srcPortGroup {
            description "Source port group";

            // Type is an MO-Defined-Type
            type acl_Name;
        }

        // destination port group
        // Inherited From acl:L3ACE
        // Type is an MO-Defined-Type
        leaf dstPortGroup {
            description "Destination port group";

            // Type is an MO-Defined-Type
            type acl_Name;
        }
    }

    grouping ipv6acl_AddrGroup-group {

        // object-group name
        // Inherited From acl:OGroup
        // Type is an MO-Defined-Type
        leaf name {
            description "Name";

            // Type is an MO-Defined-Type
            type acl_Name;
        }
        leaf configStatus {
            config "false";
            type uint32;
        }

        // IPv6 Address Object Group member
        container seq-items {
            list AddrMember-list {
                key "seqNum";

                // Added containment: Prefix=seq
                // Acquired From Package ipv6acl
                uses ipv6acl_AddrMember-group;
            }
        }
    }

    grouping ipv6acl_AddrMember-group {

        // prefix
        // Type is an MO-Defined-Type
        leaf prefix {
            description "IPv6 prefix";

            // Type is an MO-Defined-Type
            type ipv6acl_IPv6Prefix;
        }

        // prefix wildcard mask
        // Type is an MO-Defined-Type
        leaf prefixMask {
            description "IPv6 prefix mask";

            // Type is an MO-Defined-Type
            type ipv6acl_IPv6PrefixMask;
        }

        // prefix length
        // Type is an MO-Defined-Type
        leaf prefixLength {
            description "IPv6 prefix length";

            // Type is an MO-Defined-Type
            type ipv6acl_IPv6PrefixLen;
        }

        // configState
        // Type is an MO-Defined-Type
        leaf configStatus {
            description "config status";

            // Type is an MO-Defined-Type
            type acl_ConfigState;
        }

        // Object Group Member sequence number
        // Inherited From acl:OMember
        // Type is an MO-Defined-Type
        leaf seqNum {
            description "Sequence number";

            // Type is an MO-Defined-Type
            type acl_SequenceNumber;
        }
        leaf userSetBit {
            type uint64;
            default "1";
        }
    }

    grouping actrl_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // The object contains the auxillary state of the process, used
        // for internal information
        container aux-items {

            // Added containment as a singleton: Prefix=aux
            // Acquired From Package actrl
            uses actrl_AuxSt-group;
        }

        // Filter rules identifying a group of filter entries
        container filt-items {
            list Flt-list {
                config "false";
                key "id";

                // Added containment: Prefix=filt
                // Acquired From Package actrl
                uses actrl_Flt-group;
            }
        }

        // Holds actrl instance information
        container inst-items {

            // Added containment as a singleton: Prefix=inst
            // Acquired From Package actrl
            uses actrl_Inst-group;
        }

        // Holds the scope of the zoning rules
        container scope-items {
            list Scope-list {
                config "false";
                key "id";

                // Added containment: Prefix=scope
                // Acquired From Package actrl
                uses actrl_Scope-group;
            }
        }
    }

    grouping actrl_AuxSt-group {

        // From Interface naming:Named
        // Inherited From naming:NamedObject
        // Type is an MO-Defined-Type
        leaf name {
            description "Name";

            // Type is an MO-Defined-Type
            type naming_Name;
        }

        // Scope auxillary information
        container scope-items {
            list AuxScope-list {
                config "false";
                key "id";

                // Added containment: Prefix=scope
                // Acquired From Package actrl
                uses actrl_AuxScope-group;
            }
        }

        // Rule auxillary information
        container rule-items {
            list AuxRule-list {
                config "false";
                key "id";

                // Added containment: Prefix=rule
                // Acquired From Package actrl
                uses actrl_AuxRule-group;
            }
        }

        // Filter auxillary information
        container flt-items {
            list AuxFlt-list {
                config "false";
                key "id";

                // Added containment: Prefix=flt
                // Acquired From Package actrl
                uses actrl_AuxFlt-group;
            }
        }

        // MgmtRule auxillary information
        container mgmtrule-items {
            list MgmtAuxRule-list {
                config "false";
                key "id";

                // Added containment: Prefix=mgmtrule
                // Acquired From Package actrl
                uses actrl_MgmtAuxRule-group;
            }
        }

        // Filter auxillary information
        container mgmtauxflt-items {
            list MgmtAuxFlt-list {
                config "false";
                key "id";

                // Added containment: Prefix=mgmtauxflt
                // Acquired From Package actrl
                uses actrl_MgmtAuxFlt-group;
            }
        }
    }

    grouping actrl_AuxScope-group {

        // Id
        // Type is an MO-Defined-Type
        leaf id {
            config "false";
            description "ID";

            // Type is an MO-Defined-Type
            type actrl_ScopeId;
        }

        // PPF instance node id
        // Type is an MO-Defined-Type
        leaf pinstNodeId {
            config "false";
            description "PPF Node ID";

            // Type is an MO-Defined-Type
            type actrl_PpfNodeId;
        }

        // PPF instance start node id
        // Type is an MO-Defined-Type
        leaf startNodeIdArr {
            config "false";
            description "Start PPF Node ID";

            // Type is an MO-Defined-Type
            type actrl_PpfNodeIdArray;
        }

        // PPF instance end node id
        // Type is an MO-Defined-Type
        leaf endNodeIdArr {
            config "false";
            description "End PPF Node ID";

            // Type is an MO-Defined-Type
            type actrl_PpfNodeIdArray;
        }

        // From Interface naming:Named
        // Inherited From naming:NamedObject
        // Type is an MO-Defined-Type
        leaf name {
            description "Name";

            // Type is an MO-Defined-Type
            type naming_Name;
        }
    }

    grouping actrl_AuxRule-group {

        // Id
        // Type is an MO-Defined-Type
        leaf id {
            config "false";
            description "ID";

            // Type is an MO-Defined-Type
            type actrl_RuleId;
        }

        // Filter Id
        // Type is an MO-Defined-Type
        leaf fltid {
            config "false";
            description "Filter ID";

            // Type is an MO-Defined-Type
            type actrl_FltId;
        }

        // Priority
        // Type is an MO-Defined-Type
        leaf prio {
            config "false";
            description "Priority";

            // Type is an MO-Defined-Type
            type actrl_RulePrio;
        }

        // PPF rule id
        // Type is an MO-Defined-Type
        leaf ruleNodeId {
            config "false";
            description "Rule Node ID";

            // Type is an MO-Defined-Type
            type actrl_PpfNodeId;
        }

        // scope ID
        // Type is an MO-Defined-Type
        leaf scopeId {
            config "false";
            description "Scope ID";

            // Type is an MO-Defined-Type
            type actrl_ScopeId;
        }

        // Direction
        // Type is an MO-Defined-Type
        leaf direction {
            config "false";
            description "Direction";

            // Type is an MO-Defined-Type
            type actrl_Direction;
        }

        // From Interface naming:Named
        // Inherited From naming:NamedObject
        // Type is an MO-Defined-Type
        leaf name {
            description "Name";

            // Type is an MO-Defined-Type
            type naming_Name;
        }
    }

    grouping actrl_AuxFlt-group {

        // Id
        // Type is an MO-Defined-Type
        leaf id {
            config "false";
            description "ID";

            // Type is an MO-Defined-Type
            type actrl_FltId;
        }

        // Rule Id array
        // Type is an MO-Defined-Type
        leaf ruleidArr {
            config "false";
            description "Rule ID";

            // Type is an MO-Defined-Type
            type actrl_RuleIdArray;
        }

        // Rule array index
        // Type is an MO-Defined-Type
        leaf ruleIndex {
            config "false";
            description "Rule Index";

            // Type is an MO-Defined-Type
            type actrl_RuleIndex;
        }

        // PPF filter id
        // Type is an MO-Defined-Type
        leaf fltgroupNodeId {
            config "false";
            description "Filter ID";

            // Type is an MO-Defined-Type
            type actrl_PpfNodeId;
        }

        // From Interface naming:Named
        // Inherited From naming:NamedObject
        // Type is an MO-Defined-Type
        leaf name {
            description "Name";

            // Type is an MO-Defined-Type
            type naming_Name;
        }

        // FilterEntry auxillary information
        container ent-items {
            list AuxEntry-list {
                key "name";

                // Added containment: Prefix=ent
                // Acquired From Package actrl
                uses actrl_AuxEntry-group;
            }
        }
    }

    grouping actrl_AuxEntry-group {

        // Parent Filter Id
        // Type is an MO-Defined-Type
        leaf parentId {
            config "false";
            description "Parent ID";

            // Type is an MO-Defined-Type
            type actrl_FltId;
        }

        // PPF filterEntry node id
        // Type is an MO-Defined-Type
        leaf entryNodeId {
            config "false";
            description "Node ID";

            // Type is an MO-Defined-Type
            type actrl_PpfNodeId;
        }

        // From Interface naming:Named
        // Inherited From naming:NamedObject
        // Type is an MO-Defined-Type
        leaf name {
            description "Name";

            // Type is an MO-Defined-Type
            type naming_Name;
        }
    }

    grouping actrl_MgmtAuxRule-group {

        // Id
        // Type is an MO-Defined-Type
        leaf id {
            config "false";
            description "ID";

            // Type is an MO-Defined-Type
            type actrl_RuleId;
        }
        leaf ctx_id {
            config "false";
            type uint32;
        }

        // Scope Id
        // Type is an MO-Defined-Type
        leaf scope_id {
            config "false";
            description "Scope ID";

            // Type is an MO-Defined-Type
            type actrl_ScopeId;
        }

        // Filter Id
        // Type is an MO-Defined-Type
        leaf fltid {
            config "false";
            description "Filter ID";

            // Type is an MO-Defined-Type
            type actrl_FltId;
        }

        // From Interface naming:Named
        // Inherited From naming:NamedObject
        // Type is an MO-Defined-Type
        leaf name {
            description "Name";

            // Type is an MO-Defined-Type
            type naming_Name;
        }
    }

    grouping actrl_MgmtAuxFlt-group {

        // Id
        // Type is an MO-Defined-Type
        leaf id {
            config "false";
            description "ID";

            // Type is an MO-Defined-Type
            type actrl_FltId;
        }

        // MgmtRule Id array
        // Type is an MO-Defined-Type
        leaf mgmtruleidArr {
            config "false";
            description "Rule ID";

            // Type is an MO-Defined-Type
            type actrl_RuleIdArray;
        }

        // Rule array index
        // Type is an MO-Defined-Type
        leaf mgmtruleIndex {
            config "false";
            description "Rule Index";

            // Type is an MO-Defined-Type
            type actrl_RuleIndex;
        }

        // From Interface naming:Named
        // Inherited From naming:NamedObject
        // Type is an MO-Defined-Type
        leaf name {
            description "Name";

            // Type is an MO-Defined-Type
            type naming_Name;
        }
    }

    grouping actrl_Flt-group {

        // Id
        // Type is an MO-Defined-Type
        leaf id {
            config "false";
            description "TBD";

            // Type is an MO-Defined-Type
            type actrl_FltId;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Filter entry, unique set of classification filters identified
        // by various l4 parameters
        container ent-items {
            list Entry-list {
                key "name";

                // Added containment: Prefix=ent
                // Acquired From Package actrl
                uses actrl_Entry-group;
            }
        }

        // Rel-def target from toRemoteRFltP
        // Inherited From actrl:Flt
        container rtfvToRemoteRFltP-items {

            // Abstract containment of rtfvToRemoteRFltP derived from vz:AFilterableUnit
            list RtFvToRemoteRFltP-list {
                config "false";
                key "tDn";

                // Added containment: Prefix=rtfvToRemoteRFltP
                // Acquired From Package fv
                uses fv_RtFvToRemoteRFltP_target-group;
            }
        }

        // Rel-def target from toRemoteRFltAtt
        // Inherited From actrl:Flt
        container rtfvToRemoteRFltAtt-items {

            // Abstract containment of rtfvToRemoteRFltAtt derived from vz:AFilterableUnit
            list RtFvToRemoteRFltAtt-list {
                config "false";
                key "tDn";

                // Added containment: Prefix=rtfvToRemoteRFltAtt
                // Acquired From Package fv
                uses fv_RtFvToRemoteRFltAtt_target-group;
            }
        }

        // Rel-def from rfltpConn
        container rsrfltpConn-items {

            // Added containment as a singleton: Prefix=rsrfltpConn
            // Acquired From Package actrl
            uses actrl_RsRfltpConn_source-group;
        }

        // Rel-def target from ConnToFltInst
        // Inherited From actrl:Flt
        container rtvnsConnToFltInst-items {

            // Abstract containment of rtvnsConnToFltInst derived from vz:AFilterable
            list RtVnsConnToFltInst-list {
                key "tDn";

                // Added containment: Prefix=rtvnsConnToFltInst
                // Acquired From Package vns
                uses vns_RtVnsConnToFltInst_target-group;
            }
        }

        // Rel-def target from FwdRFltPAtt
        // Inherited From actrl:Flt
        container rtvzFwdRFltPAtt-items {

            // Abstract containment of rtvzFwdRFltPAtt derived from vz:AFilterableUnit
            list RtVzFwdRFltPAtt-list {
                config "false";
                key "tDn";

                // Added containment: Prefix=rtvzFwdRFltPAtt
                // Acquired From Package vz
                uses vz_RtVzFwdRFltPAtt_target-group;
            }
        }

        // Rel-def target from RevRFltPAtt
        // Inherited From actrl:Flt
        container rtvzRevRFltPAtt-items {

            // Abstract containment of rtvzRevRFltPAtt derived from vz:AFilterableUnit
            list RtVzRevRFltPAtt-list {
                config "false";
                key "tDn";

                // Added containment: Prefix=rtvzRevRFltPAtt
                // Acquired From Package vz
                uses vz_RtVzRevRFltPAtt_target-group;
            }
        }

        // Rel-def target from tabooRFltAtt
        // Inherited From actrl:Flt
        container rtvzTabooRFltAtt-items {

            // Abstract containment of rtvzTabooRFltAtt derived from vz:AFilterableUnit
            list RtVzTabooRFltAtt-list {
                config "false";
                key "tDn";

                // Added containment: Prefix=rtvzTabooRFltAtt
                // Acquired From Package vz
                uses vz_RtVzTabooRFltAtt_target-group;
            }
        }

        // Rel-def target from rFltAtt
        // Inherited From actrl:Flt
        container rtvzRFltAtt-items {

            // Abstract containment of rtvzRFltAtt derived from vz:AFilterableUnit
            list RtVzRFltAtt-list {
                config "false";
                key "tDn";

                // Added containment: Prefix=rtvzRFltAtt
                // Acquired From Package vz
                uses vz_RtVzRFltAtt_target-group;
            }
        }
    }

    grouping actrl_Entry-group {

        // Execution order of the entry
        // Type is an MO-Defined-Type
        leaf prio {
            description "Entry Priority";

            // Type is an MO-Defined-Type
            type actrl_EntryPrio;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // L3 Ip Protocol
        // Inherited From vz:AFiltEntry
        // Type is an MO-Defined-Type
        leaf prot {
            description "Protocol";

            // Type is an MO-Defined-Type
            type l3_IpProt;
        }

        // Source From Port
        // Inherited From vz:AFiltEntry
        // Type is an MO-Defined-Type
        leaf sFromPort {
            description "Source from Port";

            // Type is an MO-Defined-Type
            type l4_Port;
        }

        // Source To Port
        // Inherited From vz:AFiltEntry
        // Type is an MO-Defined-Type
        leaf sToPort {
            description "Source to Port";

            // Type is an MO-Defined-Type
            type l4_Port;
        }

        // Destination From Port
        // Inherited From vz:AFiltEntry
        // Type is an MO-Defined-Type
        leaf dFromPort {
            description "Destination from Port";

            // Type is an MO-Defined-Type
            type l4_Port;
        }

        // Destination To Port
        // Inherited From vz:AFiltEntry
        // Type is an MO-Defined-Type
        leaf dToPort {
            description "Destination to Port";

            // Type is an MO-Defined-Type
            type l4_Port;
        }

        // TCP Session Rules
        // Inherited From vz:AFiltEntry
        // Type is an MO-Defined-Type
        leaf tcpRules {
            description "TCP Rules";

            // Type is an MO-Defined-Type
            type l4_TcpFlags;
        }
        leaf applyToFrag {
            type boolean;
            default "true";
        }

        // Ether type
        // Inherited From vz:AFiltEntry
        // Type is an MO-Defined-Type
        leaf etherT {
            description "Ethernet Type";

            // Type is an MO-Defined-Type
            type l2_EtherType;
        }

        // ARP opcodes
        // Inherited From vz:AFiltEntry
        // Type is an MO-Defined-Type
        leaf arpOpc {
            description "ARP Opcodes";

            // Type is an MO-Defined-Type
            type arp_Opcode;
        }

        // ICMPv4 types
        // Inherited From vz:AFiltEntry
        // Type is an MO-Defined-Type
        leaf icmpv4T {
            description "ICMPv4 Type";

            // Type is an MO-Defined-Type
            type icmpv4_Type;
        }

        // ICMPv6 types
        // Inherited From vz:AFiltEntry
        // Type is an MO-Defined-Type
        leaf icmpv6T {
            description "ICMPv6 Type";

            // Type is an MO-Defined-Type
            type icmpv6_Type;
        }
    }

    grouping actrl_Inst-group {

        // Global access controls
        // Type is an MO-Defined-Type
        leaf accCtrl {
            config "false";
            description "Access Controls";

            // Type is an MO-Defined-Type
            type actrl_AccControl;
        }

        // Timer interval to clear security group log
        // Type is an MO-Defined-Type
        leaf logClrIntvl {
            config "false";
            description "Log Clear Interval";

            // Type is an MO-Defined-Type
            type actrl_LogClrIntvl;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping actrl_Scope-group {

        // Id
        // Type is an MO-Defined-Type
        leaf id {
            config "false";
            description "ID";

            // Type is an MO-Defined-Type
            type actrl_ScopeId;
        }

        // SecurityLabel, this must be in sync with l3Ctx:SecLbl
        // Type is an MO-Defined-Type
        leaf secLbl {
            config "false";
            description "Security Label";

            // Type is an MO-Defined-Type
            type actrl_SecLbl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Zoning rules for tenant epgs
        container rule-items {
            list Rule-list {
                config "false";
                key "scopeId sPcTag dPcTag fltId";

                // Added containment: Prefix=rule
                // Acquired From Package actrl
                uses actrl_Rule-group;
            }
        }

        // Zoning rules for management epgs
        container mr-items {
            list MgmtRule-list {
                config "false";
                key "scopeId sPcTag dPcTag fltId";

                // Added containment: Prefix=mr
                // Acquired From Package actrl
                uses actrl_MgmtRule-group;
            }
        }

        // Zoning rules for snmp epgs
        container sr-items {
            list SnmpRule-list {
                config "false";
                key "scopeId sPcTag dPcTag fltId";

                // Added containment: Prefix=sr
                // Acquired From Package actrl
                uses actrl_SnmpRule-group;
            }
        }

        // Rel-def from tenConn
        container rstenConn-items {

            // Abstract containment of rstenConn derived from actrl:Scope
            list RsTenConn-list {
                config "false";
                key "tDn";

                // Added containment: Prefix=rstenConn
                // Acquired From Package actrl
                uses actrl_RsTenConn_source-group;
            }
        }
    }

    grouping actrl_Rule-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Id
        // Inherited From actrl:ARule
        // Type is an MO-Defined-Type
        leaf id {
            description "ID";

            // Type is an MO-Defined-Type
            type actrl_RuleId;
        }

        // Type
        // Inherited From actrl:ARule
        // Type is an MO-Defined-Type
        leaf type {
            config "false";
            description "Type";

            // Type is an MO-Defined-Type
            type actrl_RuleT;
        }

        // Priority
        // Inherited From actrl:ARule
        // Type is an MO-Defined-Type
        leaf prio {
            config "false";
            description "Priority";

            // Type is an MO-Defined-Type
            type actrl_RulePrio;
        }

        // Inherited From actrl:ARule
        // Type is an MO-Defined-Type
        leaf scopeId {
            config "false";
            description "Scope ID";

            // Type is an MO-Defined-Type
            type actrl_ScopeId;
        }

        // Source policy tag
        // Inherited From actrl:ARule
        // Type is an MO-Defined-Type
        leaf sPcTag {
            config "false";
            description "Source PC Tag";

            // Type is an MO-Defined-Type
            type actrl_PcTag;
        }

        // Destination policy tag
        // Inherited From actrl:ARule
        // Type is an MO-Defined-Type
        leaf dPcTag {
            config "false";
            description "Destination PC Tag";

            // Type is an MO-Defined-Type
            type actrl_PcTag;
        }

        // Filter id
        // Inherited From actrl:ARule
        // Type is an MO-Defined-Type
        leaf fltId {
            config "false";
            description "Filter ID";

            // Type is an MO-Defined-Type
            type actrl_FltId;
        }

        // Direction
        // Inherited From actrl:ARule
        // Type is an MO-Defined-Type
        leaf direction {
            config "false";
            description "Direction";

            // Type is an MO-Defined-Type
            type actrl_Direction;
        }

        // Action
        // Inherited From actrl:ARule
        // Type is an MO-Defined-Type
        leaf action {
            config "false";
            description "Action";

            // Type is an MO-Defined-Type
            type actrl_Action;
        }

        // Qos actions, the next two attributes define the qos
        // actions when the rule is matched     Qos group
        // Inherited From actrl:ARule
        // Type is an MO-Defined-Type
        leaf qosGrp {
            config "false";
            description "QOS Group";

            // Type is an MO-Defined-Type
            type qos_Prio;
        }

        // Our Fabric only supportes DSCP mutation. Dot1P mutation
        // is not supported
        // Inherited From actrl:ARule
        // Type is an MO-Defined-Type
        leaf markDscp {
            description "Dscp";

            // Type is an MO-Defined-Type
            type qosp_Dscp;
        }

        // Rule operational state
        // Inherited From actrl:ARule
        // Type is an MO-Defined-Type
        leaf operSt {
            config "false";
            description "Operational State";

            // Type is an MO-Defined-Type
            type actrl_OperSt;
        }

        // Rule operational state disabled reason
        // Inherited From actrl:ARule
        // Type is an MO-Defined-Type
        leaf operStQual {
            config "false";
            description "Operational State Qualifier";

            // Type is an MO-Defined-Type
            type actrl_OperStQual;
        }
    }

    grouping actrl_MgmtRule-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Id
        // Inherited From actrl:ARule
        // Type is an MO-Defined-Type
        leaf id {
            description "ID";

            // Type is an MO-Defined-Type
            type actrl_RuleId;
        }

        // Type
        // Inherited From actrl:ARule
        // Type is an MO-Defined-Type
        leaf type {
            config "false";
            description "Type";

            // Type is an MO-Defined-Type
            type actrl_RuleT;
        }

        // Priority
        // Inherited From actrl:ARule
        // Type is an MO-Defined-Type
        leaf prio {
            config "false";
            description "Priority";

            // Type is an MO-Defined-Type
            type actrl_RulePrio;
        }

        // Inherited From actrl:ARule
        // Type is an MO-Defined-Type
        leaf scopeId {
            config "false";
            description "Scope ID";

            // Type is an MO-Defined-Type
            type actrl_ScopeId;
        }

        // Source policy tag
        // Inherited From actrl:ARule
        // Type is an MO-Defined-Type
        leaf sPcTag {
            config "false";
            description "Source PC Tag";

            // Type is an MO-Defined-Type
            type actrl_PcTag;
        }

        // Destination policy tag
        // Inherited From actrl:ARule
        // Type is an MO-Defined-Type
        leaf dPcTag {
            config "false";
            description "Destination PC Tag";

            // Type is an MO-Defined-Type
            type actrl_PcTag;
        }

        // Filter id
        // Inherited From actrl:ARule
        // Type is an MO-Defined-Type
        leaf fltId {
            config "false";
            description "Filter ID";

            // Type is an MO-Defined-Type
            type actrl_FltId;
        }

        // Direction
        // Inherited From actrl:ARule
        // Type is an MO-Defined-Type
        leaf direction {
            config "false";
            description "Direction";

            // Type is an MO-Defined-Type
            type actrl_Direction;
        }

        // Action
        // Inherited From actrl:ARule
        // Type is an MO-Defined-Type
        leaf action {
            config "false";
            description "Action";

            // Type is an MO-Defined-Type
            type actrl_Action;
        }

        // Qos actions, the next two attributes define the qos
        // actions when the rule is matched     Qos group
        // Inherited From actrl:ARule
        // Type is an MO-Defined-Type
        leaf qosGrp {
            config "false";
            description "QOS Group";

            // Type is an MO-Defined-Type
            type qos_Prio;
        }

        // Our Fabric only supportes DSCP mutation. Dot1P mutation
        // is not supported
        // Inherited From actrl:ARule
        // Type is an MO-Defined-Type
        leaf markDscp {
            description "Dscp";

            // Type is an MO-Defined-Type
            type qosp_Dscp;
        }

        // Rule operational state
        // Inherited From actrl:ARule
        // Type is an MO-Defined-Type
        leaf operSt {
            config "false";
            description "Operational State";

            // Type is an MO-Defined-Type
            type actrl_OperSt;
        }

        // Rule operational state disabled reason
        // Inherited From actrl:ARule
        // Type is an MO-Defined-Type
        leaf operStQual {
            config "false";
            description "Operational State Qualifier";

            // Type is an MO-Defined-Type
            type actrl_OperStQual;
        }
    }

    grouping actrl_SnmpRule-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Id
        // Inherited From actrl:ARule
        // Type is an MO-Defined-Type
        leaf id {
            description "ID";

            // Type is an MO-Defined-Type
            type actrl_RuleId;
        }

        // Type
        // Inherited From actrl:ARule
        // Type is an MO-Defined-Type
        leaf type {
            config "false";
            description "Type";

            // Type is an MO-Defined-Type
            type actrl_RuleT;
        }

        // Priority
        // Inherited From actrl:ARule
        // Type is an MO-Defined-Type
        leaf prio {
            config "false";
            description "Priority";

            // Type is an MO-Defined-Type
            type actrl_RulePrio;
        }

        // Inherited From actrl:ARule
        // Type is an MO-Defined-Type
        leaf scopeId {
            config "false";
            description "Scope ID";

            // Type is an MO-Defined-Type
            type actrl_ScopeId;
        }

        // Source policy tag
        // Inherited From actrl:ARule
        // Type is an MO-Defined-Type
        leaf sPcTag {
            config "false";
            description "Source PC Tag";

            // Type is an MO-Defined-Type
            type actrl_PcTag;
        }

        // Destination policy tag
        // Inherited From actrl:ARule
        // Type is an MO-Defined-Type
        leaf dPcTag {
            config "false";
            description "Destination PC Tag";

            // Type is an MO-Defined-Type
            type actrl_PcTag;
        }

        // Filter id
        // Inherited From actrl:ARule
        // Type is an MO-Defined-Type
        leaf fltId {
            config "false";
            description "Filter ID";

            // Type is an MO-Defined-Type
            type actrl_FltId;
        }

        // Direction
        // Inherited From actrl:ARule
        // Type is an MO-Defined-Type
        leaf direction {
            config "false";
            description "Direction";

            // Type is an MO-Defined-Type
            type actrl_Direction;
        }

        // Action
        // Inherited From actrl:ARule
        // Type is an MO-Defined-Type
        leaf action {
            config "false";
            description "Action";

            // Type is an MO-Defined-Type
            type actrl_Action;
        }

        // Qos actions, the next two attributes define the qos
        // actions when the rule is matched     Qos group
        // Inherited From actrl:ARule
        // Type is an MO-Defined-Type
        leaf qosGrp {
            config "false";
            description "QOS Group";

            // Type is an MO-Defined-Type
            type qos_Prio;
        }

        // Our Fabric only supportes DSCP mutation. Dot1P mutation
        // is not supported
        // Inherited From actrl:ARule
        // Type is an MO-Defined-Type
        leaf markDscp {
            description "Dscp";

            // Type is an MO-Defined-Type
            type qosp_Dscp;
        }

        // Rule operational state
        // Inherited From actrl:ARule
        // Type is an MO-Defined-Type
        leaf operSt {
            config "false";
            description "Operational State";

            // Type is an MO-Defined-Type
            type actrl_OperSt;
        }

        // Rule operational state disabled reason
        // Inherited From actrl:ARule
        // Type is an MO-Defined-Type
        leaf operStQual {
            config "false";
            description "Operational State Qualifier";

            // Type is an MO-Defined-Type
            type actrl_OperStQual;
        }
    }

    grouping actrlcap_Prov-group {

        // Subject consuming the capability.
        // Type is an MO-Defined-Type
        leaf subj {
            config "false";
            description "TBD";

            // Type is an MO-Defined-Type
            type actrlcap_Subj;
        }

        // Every Consumer has a Subject.
        // Subject represents the entity which consumes the capability.
        // Namespaces which have concrete consumers, define the Subject property
        // and its types
        // Max capability available
        // Inherited From cap:Prov
        // Type is an MO-Defined-Type
        leaf total {
            config "false";
            description "TBD";

            // Type is an MO-Defined-Type
            type cap_Counter;
        }

        // Remaining capability available
        // Inherited From cap:Prov
        // Type is an MO-Defined-Type
        leaf remaining {
            config "false";
            description "TBD";

            // Type is an MO-Defined-Type
            type cap_Counter;
        }

        // utilization indicator in percentages of consiumption
        // Inherited From cap:Prov
        // Type is an MO-Defined-Type
        leaf utilization {
            config "false";
            description "TBD";

            // Type is an MO-Defined-Type
            type cap_StorageHint;
        }

        // Type of the Rule consumed by this consumer.
        // Inherited From cap:Prov
        // Type is an MO-Defined-Type
        leaf type {
            config "false";
            description "TBD";

            // Type is an MO-Defined-Type
            type cap_RuleT;
        }
    }

    grouping analytics_Entity-group {

        // Holds netflow and analytics instance information
        container inst-items {
            list Inst-list {
                key "mode";

                // Added containment: Prefix=inst
                // Acquired From Package analytics
                uses analytics_Inst-group;
            }
        }
    }

    grouping analytics_Inst-group {

        // analytics/netflow mode
        // Type is an MO-Defined-Type
        leaf mode {
            description "Mode Select";

            // Type is an MO-Defined-Type
            type analytics_ModeT;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Platform capability informations
        container capability-items {

            // Added containment as a singleton: Prefix=capability
            // Acquired From Package analytics
            uses analytics_Capability-group;
        }

        // Controller information for bootstrapping the analytics agent
        container controller-items {
            list Controller-list {
                key "name";

                // Added containment: Prefix=controller
                // Acquired From Package analytics
                uses analytics_Controller-group;
            }
        }

        // Flow Record
        container recordp-items {
            list RecordP-list {
                key "name";

                // Added containment: Prefix=recordp
                // Acquired From Package analytics
                uses analytics_RecordP-group;
            }
        }

        // Flow Collector
        container collector-items {
            list Collector-list {
                key "name";

                // Added containment: Prefix=collector
                // Acquired From Package analytics
                uses analytics_Collector-group;
            }
        }

        // Flow Monitor    one monitor can be attached to n records
        container monitor-items {
            list Monitor-list {
                key "name";

                // Added containment: Prefix=monitor
                // Acquired From Package analytics
                uses analytics_Monitor-group;
            }
        }

        // Sampler
        container sampler-items {
            list Sampler-list {
                key "name";

                // Added containment: Prefix=sampler
                // Acquired From Package analytics
                uses analytics_Sampler-group;
            }
        }

        // Analytics profile
        container prof-items {
            list Profile-list {
                key "name";

                // Added containment: Prefix=prof
                // Acquired From Package analytics
                uses analytics_Profile-group;
            }
        }

        // Forwarding instance based target
        container fwdinst-items {
            list FwdInstTarget-list {
                key "id";

                // Added containment: Prefix=fwdinst
                // Acquired From Package analytics
                uses analytics_FwdInstTarget-group;
            }
        }

        // Physical interface target
        container if-items {
            list PhysIfTarget-list {
                key "id fltType";

                // Added containment: Prefix=if
                // Acquired From Package analytics
                uses analytics_PhysIfTarget-group;
            }
        }

        // Bridge Domain target
        container bd-items {
            list BDTarget-list {
                key "id";

                // Added containment: Prefix=bd
                // Acquired From Package analytics
                uses analytics_BDTarget-group;
            }
        }

        // Policy Container for ACLs
        container policy-items {
            list Policy-list {
                key "name";

                // Added containment: Prefix=policy
                // Acquired From Package analytics
                uses analytics_Policy-group;
            }
        }
    }

    grouping analytics_Capability-group {

        // Mode
        // Type is an MO-Defined-Type
        leaf fabricMode {
            config "false";
            description "Mode to Indicate Platform Type";

            // Type is an MO-Defined-Type
            type analytics_CModeT;
        }

        // Collector Bucket Hash Width
        // Type is an MO-Defined-Type
        leaf bucketHashWidth {
            config "false";
            description "Bit Width of the Collector Bucket Hash";

            // Type is an MO-Defined-Type
            type analytics_HashWidthT;
        }

        // Number of TCAM entries
        // Type is an MO-Defined-Type
        leaf numTcamEnt {
            config "false";
            description "Number of TCAM Entries";

            // Type is an MO-Defined-Type
            type analytics_numTcamEntT;
        }

        // Number of TCAM entries per V4 type
        // Type is an MO-Defined-Type
        leaf numTcamEntPerV4 {
            config "false";
            description "Number of TCAM Entries per V4 type";

            // Type is an MO-Defined-Type
            type analytics_numTcamEntV4T;
        }

        // Number of TCAM entries per V6 type
        // Type is an MO-Defined-Type
        leaf numTcamEntPerV6 {
            config "false";
            description "Number of TCAM Entries per V6 type";

            // Type is an MO-Defined-Type
            type analytics_numTcamEntV6T;
        }
    }

    grouping analytics_Controller-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Remote node VRF
        // Inherited From analytics:RemoteNode
        // Type is an MO-Defined-Type
        leaf vrfName {
            description "Remote Entity VRF";

            // Type is an MO-Defined-Type
            type l3_VrfName;
        }
        leaf dstAddr {
            type address_Ip;
        }

        // Remote node destination port
        // Inherited From analytics:RemoteNode
        // Type is an MO-Defined-Type
        leaf dstPort {
            description "Remote Entity L4 Port";

            // Type is an MO-Defined-Type
            type l4_Port;
        }

        // IP dscp value
        // Inherited From analytics:RemoteNode
        // Type is an MO-Defined-Type
        leaf dscp {
            description "DSCP Value";

            // Type is an MO-Defined-Type
            type qosp_DscpCP;
        }

        // Source interface
        // Inherited From analytics:RemoteNode
        // Type is an MO-Defined-Type
        leaf srcIf {
            description "Source Interface";

            // Type is an MO-Defined-Type
            type nw_IfId;
        }
        leaf srcAddr {
            type address_Ip;
        }
    }

    grouping analytics_RecordP-group {

        // Match parameters for the flow record
        // Type is an MO-Defined-Type
        leaf match {
            description "Match Params";

            // Type is an MO-Defined-Type
            type analytics_MatchParams;
        }

        // Collect parameters for the flow record
        // Type is an MO-Defined-Type
        leaf collect {
            description "Collect Params";

            // Type is an MO-Defined-Type
            type analytics_CollectParams;
        }

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }
    }

    grouping analytics_Collector-group {

        // Collector version
        // Type is an MO-Defined-Type
        leaf ver {
            description "Collector Version Format";

            // Type is an MO-Defined-Type
            type analytics_CollVersion;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Remote node VRF
        // Inherited From analytics:RemoteNode
        // Type is an MO-Defined-Type
        leaf vrfName {
            description "Remote Entity VRF";

            // Type is an MO-Defined-Type
            type l3_VrfName;
        }
        leaf dstAddr {
            type address_Ip;
        }

        // Remote node destination port
        // Inherited From analytics:RemoteNode
        // Type is an MO-Defined-Type
        leaf dstPort {
            description "Remote Entity L4 Port";

            // Type is an MO-Defined-Type
            type l4_Port;
        }

        // IP dscp value
        // Inherited From analytics:RemoteNode
        // Type is an MO-Defined-Type
        leaf dscp {
            description "DSCP Value";

            // Type is an MO-Defined-Type
            type qosp_DscpCP;
        }

        // Source interface
        // Inherited From analytics:RemoteNode
        // Type is an MO-Defined-Type
        leaf srcIf {
            description "Source Interface";

            // Type is an MO-Defined-Type
            type nw_IfId;
        }
        leaf srcAddr {
            type address_Ip;
        }
    }

    grouping analytics_Monitor-group {

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }

        // Collector bucket info
        container collectorbucket-items {
            list CollectorBucket-list {
                key "id";

                // Added containment: Prefix=collectorbucket
                // Acquired From Package analytics
                uses analytics_CollectorBucket-group;
            }
        }

        // Rel-def from recordPAtt
        container rsrecordPAtt-items {

            // Added containment as a singleton: Prefix=rsrecordPAtt
            // Acquired From Package analytics
            uses analytics_RsRecordPAtt_source-group;
        }
    }

    grouping analytics_CollectorBucket-group {

        // Collector bucket identifier
        // Type is an MO-Defined-Type
        leaf id {
            description "Flow Collector Bucket Id";

            // Type is an MO-Defined-Type
            type analytics_CollBucketId;
        }

        // HashLo value for this collector bucket
        // Type is an MO-Defined-Type
        leaf hashLo {
            description "Hash Low Value";

            // Type is an MO-Defined-Type
            type analytics_HashT;
        }

        // HashHi value for this collector bucket
        // Type is an MO-Defined-Type
        leaf hashHi {
            description "Hash High Value";

            // Type is an MO-Defined-Type
            type analytics_HashT;
        }

        // From Interface naming:Described
        // Type is an MO-Defined-Type
        leaf descr {
            description "Description";

            // Type is an MO-Defined-Type
            type naming_Descr;
        }

        // Rel-def from collectorAtt
        container rscollectorAtt-items {

            // Abstract containment of rscollectorAtt derived from analytics:CollectorBucket
            list RsCollectorAtt-list {
                key "tDn";

                // Added containment: Prefix=rscollectorAtt
                // Acquired From Package analytics
                uses analytics_RsCollectorAtt_source-group;
            }
        }
    }

    grouping analytics_Sampler-group {

        // Sampler mode
        // Type is an MO-Defined-Type
        leaf mode {
            description "Sampler Mode";

            // Type is an MO-Defined-Type
            type analytics_SamplerMode;
        }

        // Numerator of the sampling size expressed as a fraction
        // Type is an MO-Defined-Type
        leaf sampleSz {
            description "Sample Size";

            // Type is an MO-Defined-Type
            type analytics_SampleSzT;
        }

        // Denominator of the sampling size expressed as a fraction
        // Type is an MO-Defined-Type
        leaf windowSz {
            description "Sample Window Size";

            // Type is an MO-Defined-Type
            type analytics_SampleSzT;
        }

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }
    }

    grouping analytics_Profile-group {

        // Collect interval
        // Type is an MO-Defined-Type
        leaf collectIntvl {
            description "Collect Interval in Milliseconds";

            // Type is an MO-Defined-Type
            type analytics_CollIntvl;
        }

        // Source port
        // Type is an MO-Defined-Type
        leaf srcPort {
            description "Source L4 Port";

            // Type is an MO-Defined-Type
            type analytics_L4Port;
        }

        // IP packet id shift
        // Type is an MO-Defined-Type
        leaf ipPktIdShift {
            description "IP Packet Id Shift";

            // Type is an MO-Defined-Type
            type analytics_IpPktIdShift;
        }

        // Burst interval shift
        // Type is an MO-Defined-Type
        leaf burstIntvlShift {
            description "Timestamp Shift Value for Burst Interval";

            // Type is an MO-Defined-Type
            type analytics_BurstIntvlShift;
        }

        // Collector export packet MTU
        // Type is an MO-Defined-Type
        leaf mtu {
            description "MTU";

            // Type is an MO-Defined-Type
            type analytics_Mtu;
        }

        // Sequence number guess threshold low
        // Type is an MO-Defined-Type
        leaf seqNumGuessThreshLo {
            description "Sequence Number Guess Threshold Low";

            // Type is an MO-Defined-Type
            type analytics_ThresholdT;
        }

        // Sequence number guess threshold high
        // Type is an MO-Defined-Type
        leaf seqNumGuessThreshHi {
            description "Sequence Number Guess Threshold High";

            // Type is an MO-Defined-Type
            type analytics_ThresholdT;
        }

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }

        // Payload length bin
        container payloadlenbin-items {
            list PayloadLenBin-list {
                key "id";

                // Added containment: Prefix=payloadlenbin
                // Acquired From Package analytics
                uses analytics_PayloadLenBin-group;
            }
        }

        // TCP options header length bin
        container tcpopthdrlenbin-items {
            list TCPOptHdrLenBin-list {
                key "id";

                // Added containment: Prefix=tcpopthdrlenbin
                // Acquired From Package analytics
                uses analytics_TCPOptHdrLenBin-group;
            }
        }

        // Receive window size bin
        container rcvwindowszbin-items {
            list RcvWindowSzBin-list {
                key "id";

                // Added containment: Prefix=rcvwindowszbin
                // Acquired From Package analytics
                uses analytics_RcvWindowSzBin-group;
            }
        }
    }

    grouping analytics_PayloadLenBin-group {

        // Identifier
        // Type is an MO-Defined-Type
        leaf id {
            description "Payload Length Bin Id";

            // Type is an MO-Defined-Type
            type analytics_PayloadLenIdT;
        }

        // Low value
        // Type is an MO-Defined-Type
        leaf lo {
            description "Bin Low Value";

            // Type is an MO-Defined-Type
            type analytics_PayloadLenT;
        }

        // High value
        // Type is an MO-Defined-Type
        leaf hi {
            description "Bin High Value";

            // Type is an MO-Defined-Type
            type analytics_PayloadLenT;
        }

        // From Interface naming:Described
        // Type is an MO-Defined-Type
        leaf descr {
            description "Description";

            // Type is an MO-Defined-Type
            type naming_Descr;
        }
    }

    grouping analytics_TCPOptHdrLenBin-group {

        // Identifier
        // Type is an MO-Defined-Type
        leaf id {
            description "TCP option header length bin ID";

            // Type is an MO-Defined-Type
            type analytics_TCPOptHdrLenIdT;
        }

        // Low value
        // Type is an MO-Defined-Type
        leaf lo {
            description "Bin Low Value";

            // Type is an MO-Defined-Type
            type analytics_TCPOptHdrLenT;
        }

        // High value
        // Type is an MO-Defined-Type
        leaf hi {
            description "Bin High Value";

            // Type is an MO-Defined-Type
            type analytics_TCPOptHdrLenT;
        }

        // From Interface naming:Described
        // Type is an MO-Defined-Type
        leaf descr {
            description "Description";

            // Type is an MO-Defined-Type
            type naming_Descr;
        }
    }

    grouping analytics_RcvWindowSzBin-group {

        // Identifier
        // Type is an MO-Defined-Type
        leaf id {
            description "Receive window size bin ID";

            // Type is an MO-Defined-Type
            type analytics_RcvWindowSzIdT;
        }

        // Low value
        // Type is an MO-Defined-Type
        leaf lo {
            description "Bin Low Value";

            // Type is an MO-Defined-Type
            type analytics_RcvWindowSzT;
        }

        // High value
        // Type is an MO-Defined-Type
        leaf hi {
            description "Bin High Value";

            // Type is an MO-Defined-Type
            type analytics_RcvWindowSzT;
        }

        // From Interface naming:Described
        // Type is an MO-Defined-Type
        leaf descr {
            description "Description";

            // Type is an MO-Defined-Type
            type naming_Descr;
        }
    }

    grouping analytics_FwdInstTarget-group {

        // Identifier
        // Type is an MO-Defined-Type
        leaf id {
            description "Identifier";

            // Type is an MO-Defined-Type
            type analytics_FwdInstTargetId;
        }

        // Collector identifier provided by the analytics controller
        // Type is an MO-Defined-Type
        leaf collectorId {
            description "Collector Id";

            // Type is an MO-Defined-Type
            type analytics_CollectorId;
        }

        // Default filtering policy
        // Type is an MO-Defined-Type
        leaf DefPolicy {
            description "Default Filtering Policy";

            // Type is an MO-Defined-Type
            type analytics_DefPolicyT;
        }

        // IPv4 Hit Count
        // Type is an MO-Defined-Type
        leaf ipv4Hit {
            description "IPv4 Hit Count";

            // Type is an MO-Defined-Type
            type analytics_hitCount;
        }

        // IPv6 Hit Count
        // Type is an MO-Defined-Type
        leaf ipv6Hit {
            description "IPv6 Hit Count";

            // Type is an MO-Defined-Type
            type analytics_hitCount;
        }

        // CE Hit Count
        // Type is an MO-Defined-Type
        leaf ceHit {
            description "CE Hit Count";

            // Type is an MO-Defined-Type
            type analytics_hitCount;
        }

        // IPv4 Create Count
        // Type is an MO-Defined-Type
        leaf ipv4Create {
            description "IPv4 Create Count";

            // Type is an MO-Defined-Type
            type analytics_createCount;
        }

        // IPv6 Create Count
        // Type is an MO-Defined-Type
        leaf ipv6Create {
            description "IPv6 Create Count";

            // Type is an MO-Defined-Type
            type analytics_createCount;
        }

        // CE Create Count
        // Type is an MO-Defined-Type
        leaf ceCreate {
            description "CE Create Count";

            // Type is an MO-Defined-Type
            type analytics_createCount;
        }
        leaf exportCount {
            type uint32;
        }
        leaf skipCount {
            type uint32;
        }

        // IP filter type
        // Inherited From analytics:Target
        // Type is an MO-Defined-Type
        leaf fltType {
            description "Netflow Target Type";

            // Type is an MO-Defined-Type
            type analytics_FltType;
        }

        // Direction
        // Inherited From analytics:Target
        // Type is an MO-Defined-Type
        leaf dir {
            description "Direction";

            // Type is an MO-Defined-Type
            type analytics_DirectionT;
        }

        // Rel-def from profAtt
        container rsprofAtt-items {

            // Added containment as a singleton: Prefix=rsprofAtt
            // Acquired From Package analytics
            uses analytics_RsProfAtt_source-group;
        }

        // Rel-def from policyAtt
        container rspolicyAtt-items {

            // Added containment as a singleton: Prefix=rspolicyAtt
            // Acquired From Package analytics
            uses analytics_RsPolicyAtt_source-group;
        }
    }

    grouping analytics_PhysIfTarget-group {

        // Identifier
        // Type is an MO-Defined-Type
        leaf id {
            description "Interface Id";

            // Type is an MO-Defined-Type
            type nw_IfId;
        }

        // Operational state of the session
        // Type is an MO-Defined-Type
        leaf operSt {
            config "false";
            description "Operational State";

            // Type is an MO-Defined-Type
            type analytics_OperSt;
        }

        // Operational state qualifier
        // Type is an MO-Defined-Type
        leaf operStQual {
            config "false";
            description "Operational State Qualifier";

            // Type is an MO-Defined-Type
            type analytics_OperStQual;
        }

        // IP filter type
        // Inherited From analytics:Target
        // Type is an MO-Defined-Type
        leaf fltType {
            description "Netflow Target Type";

            // Type is an MO-Defined-Type
            type analytics_FltType;
        }

        // Direction
        // Inherited From analytics:Target
        // Type is an MO-Defined-Type
        leaf dir {
            description "Direction";

            // Type is an MO-Defined-Type
            type analytics_DirectionT;
        }
    }

    grouping analytics_BDTarget-group {
        leaf id {
            type string;
        }
        leaf ctxEncap {
            type string;
        }

        // Operational state of the session
        // Type is an MO-Defined-Type
        leaf operSt {
            config "false";
            description "Operational State";

            // Type is an MO-Defined-Type
            type analytics_OperSt;
        }

        // Operational state qualifier
        // Type is an MO-Defined-Type
        leaf operStQual {
            config "false";
            description "Operational State Qualifier";

            // Type is an MO-Defined-Type
            type analytics_OperStQual;
        }

        // IP filter type
        // Inherited From analytics:Target
        // Type is an MO-Defined-Type
        leaf fltType {
            description "Netflow Target Type";

            // Type is an MO-Defined-Type
            type analytics_FltType;
        }

        // Direction
        // Inherited From analytics:Target
        // Type is an MO-Defined-Type
        leaf dir {
            description "Direction";

            // Type is an MO-Defined-Type
            type analytics_DirectionT;
        }
    }

    grouping analytics_Policy-group {

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }

        // Match ACL
        container acl-items {
            list MatchAcl-list {
                key "name";

                // Added containment: Prefix=acl
                // Acquired From Package analytics
                uses analytics_MatchAcl-group;
            }
        }
    }

    grouping analytics_MatchAcl-group {
        leaf aclName {
            type string;
        }

        // Filter type
        // Type is an MO-Defined-Type
        leaf fltType {
            description "ACL Filter Type";

            // Type is an MO-Defined-Type
            type analytics_FltType;
        }

        // From Interface naming:Described
        // Type is an MO-Defined-Type
        leaf descr {
            description "Description";

            // Type is an MO-Defined-Type
            type naming_Descr;
        }

        // From Interface naming:Named
        // Inherited From naming:NamedObject
        // Modified by Override: pol:Obj->name
        // Type is an MO-Defined-Type
        leaf name {
            description "Name";

            // Type is an MO-Defined-Type
            type naming_Name {
                length "0..64";
            }
        }
    }

    grouping copp_Entity-group {
        leaf error {
            config "false";
            type uint64;
            default "0";
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Holder for copp class policy, each class describes a
        // set of rules describing the policer rates
        container classp-items {
            list Class-list {
                key "cName";

                // Added containment: Prefix=classp
                // Acquired From Package copp
                uses copp_Class-group;
            }
        }

        // Holder for copp class policy, each class describes a
        // set of rules describing the policer rates
        container policy-items {
            list Policy-list {
                key "name";

                // Added containment: Prefix=policy
                // Acquired From Package copp
                uses copp_Policy-group;
            }
        }

        // Model for COPP profile
        container profile-items {

            // Added containment as a singleton: Prefix=profile
            // Acquired From Package copp
            uses copp_Profile-group;
        }

        // Model for Copp Copy profile
        container name-items {
            list CopyProfile-list {
                key "affixName";

                // Added containment: Prefix=name
                // Acquired From Package copp
                uses copp_CopyProfile-group;
            }
        }

        // Scale factor
        container scale-items {
            list Scale-list {
                key "module";

                // Added containment: Prefix=scale
                // Acquired From Package copp
                uses copp_Scale-group;
            }
        }

        // Service-Policy
        container service-items {
            list Service-list {
                key "name";

                // Added containment: Prefix=service
                // Acquired From Package copp
                uses copp_Service-group;
            }
        }
    }

    grouping copp_Class-group {
        leaf cName {
            type string;
        }

        // Match any/all
        // Type is an MO-Defined-Type
        leaf matchOption {
            description "Match Option";

            // Type is an MO-Defined-Type
            type copp_MatchOption;
        }
        leaf flag {
            type boolean;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Allowed rate, committed rate at which the packets
        // are allowed into the system
        // Inherited From policer:Class
        // Type is an MO-Defined-Type
        leaf rate {
            config "false";
            description "Rate";

            // Type is an MO-Defined-Type
            type policer_Rate;
        }

        // Committed burst size, number of packets to absorb during
        // a burst
        // Inherited From policer:Class
        // Type is an MO-Defined-Type
        leaf burst {
            config "false";
            description "Burst";

            // Type is an MO-Defined-Type
            type policer_Burst;
        }

        // Set of match conditions for this copp policer
        container match-items {
            list Match-list {
                key "type";

                // Added containment: Prefix=match
                // Acquired From Package copp
                uses copp_Match-group;
            }
        }

        // Match access-group
        container acl-items {
            list Acl-list {
                key "name";

                // Added containment: Prefix=acl
                // Acquired From Package copp
                uses copp_Acl-group;
            }
        }

        // Match redirect
        container rdirect-items {

            // Added containment as a singleton: Prefix=rdirect
            // Acquired From Package copp
            uses copp_Rdirect-group;
        }

        // Match exception fcoe-fib-miss
        container fcoe-items {

            // Added containment as a singleton: Prefix=fcoe
            // Acquired From Package copp
            uses copp_Fcoe-group;
        }

        // Match exception multicast
        container mcast-items {
            list Multicast-list {
                key "mcastOption";

                // Added containment: Prefix=mcast
                // Acquired From Package copp
                uses copp_Multicast-group;
            }
        }

        // Match exception <options>
        container excep-items {
            list ExeOptions-list {
                key "option";

                // Added containment: Prefix=excep
                // Acquired From Package copp
                uses copp_ExeOptions-group;
            }
        }

        // Match exception ip
        container ip-items {

            // Added containment as a singleton: Prefix=ip
            // Acquired From Package copp
            uses copp_Ip-group;
        }

        // Match exception ip icmp
        container icmp-items {
            list IpIcmp-list {
                key "option";

                // Added containment: Prefix=icmp
                // Acquired From Package copp
                uses copp_IpIcmp-group;
            }
        }

        // Match exception ipv6
        container ipv6-items {

            // Added containment as a singleton: Prefix=ipv6
            // Acquired From Package copp
            uses copp_Ipv6-group;
        }

        // Match exception ipv6 icmp
        container icmpv6-items {
            list Ipv6Icmp-list {
                key "option";

                // Added containment: Prefix=icmpv6
                // Acquired From Package copp
                uses copp_Ipv6Icmp-group;
            }
        }

        // Match Protocol
        container prot-items {
            list Protocol-list {
                key "type";

                // Added containment: Prefix=prot
                // Acquired From Package copp
                uses copp_Protocol-group;
            }
        }
    }

    grouping copp_Match-group {

        // Match type
        // Type is an MO-Defined-Type
        leaf type {
            description "Match type";

            // Type is an MO-Defined-Type
            type copp_MatchT;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping copp_Acl-group {
        leaf name {
            type string;
        }
        leaf error {
            config "false";
            type uint64;
            default "0";
        }
        leaf flag {
            type boolean;
        }
    }

    grouping copp_Rdirect-group {

        // Redirect options
        // Type is an MO-Defined-Type
        leaf rdrct {
            description "Match redirect options";

            // Type is an MO-Defined-Type
            type copp_Rdrct;
        }
    }

    grouping copp_Fcoe-group {

        // Fcoe option
        // Type is an MO-Defined-Type
        leaf option {
            description "fcoe-fib-miss";

            // Type is an MO-Defined-Type
            type copp_Fcoe;
        }
    }

    grouping copp_Multicast-group {

        // Type is an MO-Defined-Type
        leaf mcastOption {
            description "Multicast options";

            // Type is an MO-Defined-Type
            type copp_Mcast;
        }
        leaf flag {
            type boolean;
        }
    }

    grouping copp_ExeOptions-group {

        // Type is an MO-Defined-Type
        leaf option {
            description "Match options";

            // Type is an MO-Defined-Type
            type copp_Excep;
        }
        leaf flag {
            type boolean;
        }
    }

    grouping copp_Ip-group {
        leaf options {
            type boolean;
        }
        leaf flag {
            type boolean;
        }
    }

    grouping copp_IpIcmp-group {

        // ICMP options
        // Type is an MO-Defined-Type
        leaf option {
            description "icmp options";

            // Type is an MO-Defined-Type
            type copp_Icmp;
        }
        leaf flag {
            type boolean;
        }
    }

    grouping copp_Ipv6-group {
        leaf options {
            type boolean;
        }
        leaf flag {
            type boolean;
        }
    }

    grouping copp_Ipv6Icmp-group {

        // ICMP options
        // Type is an MO-Defined-Type
        leaf option {
            description "icmp options";

            // Type is an MO-Defined-Type
            type copp_Icmp;
        }
        leaf flag {
            type boolean;
        }
    }

    grouping copp_Protocol-group {

        // Type is an MO-Defined-Type
        leaf type {
            description "Protocol List";

            // Type is an MO-Defined-Type
            type copp_Proto;
        }
        leaf flag {
            type boolean;
        }

        // Match protocol mpls
        container mpls-items {

            // Added containment as a singleton: Prefix=mpls
            // Acquired From Package copp
            uses copp_MPLSoption-group;
        }
    }

    grouping copp_MPLSoption-group {

        // Type is an MO-Defined-Type
        leaf exp {
            description "Experimental value";

            // Type is an MO-Defined-Type
            type copp_ExpVal;
        }

        // Type is an MO-Defined-Type
        leaf routerAlert {
            description "router-alert";

            // Type is an MO-Defined-Type
            type copp_Ralert;
        }
    }

    grouping copp_Policy-group {
        leaf name {
            type string;
        }
        leaf flag {
            type boolean;
        }

        // Class included in Policy-map
        container classp-items {
            list Classp-list {
                key "name";

                // Added containment: Prefix=classp
                // Acquired From Package copp
                uses copp_Classp-group;
            }
        }
    }

    grouping copp_Classp-group {
        leaf name {
            type string;
        }
        leaf insertBeforeName {
            type string;
        }
        leaf flag {
            type boolean;
        }

        // Set policer action
        container cir-items {
            list PolicerAction-list {
                key "cirVal cirUnit burstC burstUnit";

                // Added containment: Prefix=cir
                // Acquired From Package copp
                uses copp_PolicerAction-group;
            }
        }

        // Set policer action with pir rate
        container policeActionE-items {

            // Added containment as a singleton: Prefix=policeActionE
            // Acquired From Package copp
            uses copp_PolicerActionExc-group;
        }

        // Logging Action
        container logging-items {
            list Logging-list {
                key "threshold levelRange";

                // Added containment: Prefix=logging
                // Acquired From Package copp
                uses copp_Logging-group;
            }
        }

        // Set cos action
        container setCos-items {
            list SetCos-list {
                key "cosVal";

                // Added containment: Prefix=setCos
                // Acquired From Package copp
                uses copp_SetCos-group;
            }
        }

        container setDscp-items {

            // Added containment as a singleton: Prefix=setDscp
            // Acquired From Package copp
            uses copp_SetDscp-group;
        }
    }

    grouping copp_PolicerAction-group {

        // Type is an MO-Defined-Type
        leaf cirVal {
            description "Cir value";

            // Type is an MO-Defined-Type
            type copp_IrVal;
        }

        // Type is an MO-Defined-Type
        leaf cirUnit {
            description "Cir rate";

            // Type is an MO-Defined-Type
            type copp_IrUnit;
        }

        // Type is an MO-Defined-Type
        leaf burstC {
            description "Burst count";

            // Type is an MO-Defined-Type
            type copp_BurstVal;
        }

        // Type is an MO-Defined-Type
        leaf burstUnit {
            description "BC unit";

            // Type is an MO-Defined-Type
            type copp_BurstUnit;
        }

        // Type is an MO-Defined-Type
        leaf conformAction {
            description "Conform Action";

            // Type is an MO-Defined-Type
            type copp_ConformAction;
        }

        // Type is an MO-Defined-Type
        leaf violateAction {
            description "Violate action";

            // Type is an MO-Defined-Type
            type copp_ViolateAction;
        }
        leaf flag {
            type boolean;
        }
    }

    grouping copp_PolicerActionExc-group {

        // Type is an MO-Defined-Type
        leaf cirVal {
            description "Cir value";

            // Type is an MO-Defined-Type
            type copp_IrVal;
        }

        // Type is an MO-Defined-Type
        leaf cirUnit {
            description "Cir rate";

            // Type is an MO-Defined-Type
            type copp_IrUnit;
        }

        // Type is an MO-Defined-Type
        leaf burstC {
            description "Burst count";

            // Type is an MO-Defined-Type
            type copp_BurstVal;
        }

        // Type is an MO-Defined-Type
        leaf burstUnit {
            description "BC unit";

            // Type is an MO-Defined-Type
            type copp_BurstUnit;
        }

        // Type is an MO-Defined-Type
        leaf pirVal {
            description "Pir value";

            // Type is an MO-Defined-Type
            type copp_IrVal;
        }

        // Type is an MO-Defined-Type
        leaf pirUnit {
            description "Pir rate";

            // Type is an MO-Defined-Type
            type copp_IrUnit;
        }

        // Type is an MO-Defined-Type
        leaf burstE {
            description "Burst exceed ";

            // Type is an MO-Defined-Type
            type copp_BurstVal;
        }

        // Type is an MO-Defined-Type
        leaf burstEUnit {
            description "BE unit";

            // Type is an MO-Defined-Type
            type copp_BurstUnit;
        }

        // Type is an MO-Defined-Type
        leaf conformAction {
            description "Conform Action";

            // Type is an MO-Defined-Type
            type copp_ConformAction;
        }

        // Type is an MO-Defined-Type
        leaf exceedAction {
            description "Exceed Action";

            // Type is an MO-Defined-Type
            type copp_ExceedAction;
        }

        // Type is an MO-Defined-Type
        leaf violateAction {
            description "Violate action";

            // Type is an MO-Defined-Type
            type copp_ViolateAction;
        }
    }

    grouping copp_Logging-group {

        // Type is an MO-Defined-Type
        leaf threshold {
            description "Logging Threshold";

            // Type is an MO-Defined-Type
            type copp_IrVal;
        }

        // Type is an MO-Defined-Type
        leaf levelRange {
            description "logging range";

            // Type is an MO-Defined-Type
            type copp_LevelRange;
        }
    }

    grouping copp_SetCos-group {
        leaf inner {
            type boolean;
        }

        // Cos value
        // Type is an MO-Defined-Type
        leaf cosVal {
            description "Cos Value";

            // Type is an MO-Defined-Type
            type copp_CosVal;
        }
        leaf flag {
            type boolean;
        }
    }

    grouping copp_SetDscp-group {
        leaf tunnel {
            type boolean;
        }

        // Type is an MO-Defined-Type
        leaf dscpVal {
            description "Dscp Value";

            // Type is an MO-Defined-Type
            type copp_DscpVal;
        }
    }

    grouping copp_Profile-group {

        // Profile type
        // Type is an MO-Defined-Type
        leaf prof {
            description "Profile type ";

            // Type is an MO-Defined-Type
            type copp_ProfT;
        }
    }

    grouping copp_CopyProfile-group {

        // Profile type
        // Type is an MO-Defined-Type
        leaf profile {
            description "Profile type ";

            // Type is an MO-Defined-Type
            type copp_ProfT;
        }

        // affix type
        // Type is an MO-Defined-Type
        leaf affix {
            description "Affix type";

            // Type is an MO-Defined-Type
            type copp_Affix;
        }
        leaf affixName {
            type string;
        }
        leaf copyNum {
            type uint32;
        }
    }

    grouping copp_Scale-group {
        leaf scaleVal {
            type decimal64 {
                fraction-digits 2;
            }
        }
        leaf module {
            type uint16;
        }
    }

    grouping copp_Service-group {
        leaf name {
            type string;
        }
        leaf error {
            config "false";
            type uint64;
            default "0";
        }
    }

    grouping glean_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Holds glean instance information
        container inst-items {

            // Added containment as a singleton: Prefix=inst
            // Acquired From Package glean
            uses glean_Inst-group;
        }
    }

    grouping glean_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This objects hold per glean domain (vrf) information
        container dom-items {
            list Dom-list {
                key "encap";

                // Added containment: Prefix=dom
                // Acquired From Package glean
                uses glean_Dom-group;
            }
        }
    }

    grouping glean_Dom-group {
        leaf encap {
            type string;
        }

        // Inherited From nw:Conn
        // Modified by Override: nw:CpDom->name
        // Type is an MO-Defined-Type
        leaf name {
            description "Name";

            // Type is an MO-Defined-Type
            type naming_Name {
                length "1..64";
            }
        }

        // This objects hold per glean l2 domain (BD) information
        container bd-items {
            list BD-list {
                key "encap";

                // Added containment: Prefix=bd
                // Acquired From Package glean
                uses glean_BD-group;
            }
        }
    }

    grouping glean_BD-group {
        leaf encap {
            type string;
        }

        // Gateway mac
        // Type is an MO-Defined-Type
        leaf gwMac {
            description "Gateway MAC";

            // Type is an MO-Defined-Type
            type glean_GwMac;
        }

        // Fabric multicast group
        // Type is an MO-Defined-Type
        leaf fmcastGrp {
            description "Fabric Multicast Group";

            // Type is an MO-Defined-Type
            type mcast_GrpIp;
        }

        // Inherited From nw:Conn
        // Modified by Override: nw:CpDom->name
        // Type is an MO-Defined-Type
        leaf name {
            description "Name";

            // Type is an MO-Defined-Type
            type naming_Name {
                length "1..64";
            }
        }

        // This objects holds gateway information. For a given BD,
        // there could be multiple gateways
        container gw-items {
            list Gateway-list {
                key "ip";

                // Added containment: Prefix=gw
                // Acquired From Package glean
                uses glean_Gateway-group;
            }
        }
    }

    grouping glean_Gateway-group {

        // Gateway ip address
        // Type is an MO-Defined-Type
        leaf ip {
            description "Gateway IP Address";

            // Type is an MO-Defined-Type
            type glean_GwIp;
        }
    }

    grouping hmm_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Fabric Forwarding Object
        container fwdinst-items {

            // Added containment as a singleton: Prefix=fwdinst
            // Acquired From Package hmm
            uses hmm_FwdInst-group;
        }
    }

    grouping hmm_FwdInst-group {
        leaf amac {
            type address_Mac;
        }
        leaf limitVlanMac {
            type uint16 {
                range "5..2048";
            }
            default "2048";
        }

        // selective-host-probe
        // Type is an MO-Defined-Type
        leaf selHostProbe {
            description "Selective Host Probe";

            // Type is an MO-Defined-Type
            type hmm_Boolean;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Fabric Forwarding Interface Object
        container if-items {
            list FwdIf-list {
                key "id";

                // Added containment: Prefix=if
                // Acquired From Package hmm
                uses hmm_FwdIf-group;
            }
        }

        // Fabric Forwarding EVPN Object
        container evpn-items {

            // Added containment as a singleton: Prefix=evpn
            // Acquired From Package hmm
            uses hmm_FwdEvpn-group;
        }

        // Holds HMM vrf information
        container tenant-items {
            list TenantDb-list {
                config "false";
                key "vrfName";

                // Added containment: Prefix=tenant
                // Acquired From Package hmm
                uses hmm_TenantDb-group;
            }
        }
    }

    grouping hmm_FwdIf-group {

        // Forwarding mode
        // Type is an MO-Defined-Type
        leaf mode {
            description "Forwarding mode";

            // Type is an MO-Defined-Type
            type hmm_FwdMode;
        }
        leaf VrfName {
            config "false";
            type string;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping hmm_FwdEvpn-group {
        leaf ddHmmoves {
            type uint16 {
                range "1..1000";
            }
            default "5";
        }
        leaf ddHnsecs {
            type uint16 {
                range "2..36000";
            }
            default "180";
        }
        leaf dhrtimeout {
            type uint16 {
                range "30..36000";
            }
            default "30";
        }
        leaf dhrcount {
            type uint16 {
                range "1..3000";
            }
            default "5";
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping hmm_TenantDb-group {
        leaf vrfName {
            config "false";
            type string;
        }
        leaf vrfState {
            config "false";
            type string;
        }
        leaf vniId {
            config "false";
            type uint32;
        }
        leaf refCount {
            config "false";
            type uint32;
        }

        // Holds Address family information
        container af-items {
            list TenantDBAf-list {
                config "false";
                key "type";

                // Added containment: Prefix=af
                // Acquired From Package hmm
                uses hmm_TenantDBAf-group;
            }
        }
    }

    grouping hmm_TenantDBAf-group {

        // Address family type
        // Type is an MO-Defined-Type
        leaf type {
            config "false";
            description "Address family type";

            // Type is an MO-Defined-Type
            type bgp_AfT;
        }
        leaf tblState {
            config "false";
            type string;
        }
        leaf localHosts {
            config "false";
            type uint32;
        }
        leaf remoteHosts {
            config "false";
            type uint32;
        }
        leaf aggregates {
            config "false";
            type uint32;
        }
    }

    grouping ipqos_Entity-group {

        // Type is an MO-Defined-Type
        leaf statsState {
            description "Globally enable/disable QoS statistics";

            // Type is an MO-Defined-Type
            type ipqos_statsState;
        }

        container statClear-items {

            // Added containment as a singleton: Prefix=statClear
            // Acquired From Package ipqos
            uses ipqos_StatClear-group;
        }

        // Queuing QoS
        container queuing-items {

            // Added containment as a singleton: Prefix=queuing
            // Acquired From Package ipqos
            uses ipqos_Queuing-group;
        }

        // Network QoS
        container nw-items {

            // Added containment as a singleton: Prefix=nw
            // Acquired From Package ipqos
            uses ipqos_NwQoS-group;
        }

        // Default QoS
        container dflt-items {

            // Added containment as a singleton: Prefix=dflt
            // Acquired From Package ipqos
            uses ipqos_DefaultQoS-group;
        }
    }

    grouping ipqos_StatClear-group {

        // StatClear pmap type
        // Type is an MO-Defined-Type
        leaf pmapType {
            description "pmap type";

            // Type is an MO-Defined-Type
            type ipqos_policyType;
        }

        // StatClear pmap diretion
        // Type is an MO-Defined-Type
        leaf direction {
            description "direction";

            // Type is an MO-Defined-Type
            type ipqos_policyDirection;
        }

        // StatClear ethernet list
        // Type is an MO-Defined-Type
        leaf ethernet {
            description "ethernet list";

            // Type is an MO-Defined-Type
            type ipqos_ethernetList;
        }

        // StatClear vlan list
        // Type is an MO-Defined-Type
        leaf vlan {
            description "vlan list";

            // Type is an MO-Defined-Type
            type ipqos_vlanList;
        }

        // StatClear portChan list
        // Type is an MO-Defined-Type
        leaf portChan {
            description "port-channel list";

            // Type is an MO-Defined-Type
            type ipqos_portChanList;
        }
        leaf timeStamp {
            type uint64;
        }
    }

    grouping ipqos_Queuing-group {

        // service policy applied on target
        container policy-items {

            // Added containment as a singleton: Prefix=policy
            // Acquired From Package ipqos
            uses ipqos_ServPol-group;
        }

        // class-map
        container c-items {

            // Added containment as a singleton: Prefix=c
            // Acquired From Package ipqos
            uses ipqos_CMapEntity-group;
        }

        // policy-map
        container p-items {

            // Added containment as a singleton: Prefix=p
            // Acquired From Package ipqos
            uses ipqos_PMapEntity-group;
        }

        container copyPMap-items {

            // Added containment as a singleton: Prefix=copyPMap
            // Acquired From Package ipqos
            uses ipqos_CopyPMap-group;
        }
    }

    grouping ipqos_ServPol-group {

        // Ingress direction
        container in-items {

            // Added containment as a singleton: Prefix=in
            // Acquired From Package ipqos
            uses ipqos_Ingress-group;
        }

        // Ingress direction
        container out-items {

            // Added containment as a singleton: Prefix=out
            // Acquired From Package ipqos
            uses ipqos_Egress-group;
        }
    }

    grouping ipqos_Ingress-group {

        // Target interface
        container intf-items {
            list If-list {
                key "name";

                // Added containment: Prefix=intf
                // Acquired From Package ipqos
                uses ipqos_If-group;
            }
        }

        // system qos
        container sys-items {

            // Added containment as a singleton: Prefix=sys
            // Acquired From Package ipqos
            uses ipqos_System-group;
        }
    }

    grouping ipqos_If-group {

        // interface name string
        // Type is an MO-Defined-Type
        leaf name {
            description "Interface";

            // Type is an MO-Defined-Type
            type ipqos_IfName;
        }

        // Service policy instance
        container pmap-items {

            // Added containment as a singleton: Prefix=pmap
            // Acquired From Package ipqos
            uses ipqos_Inst-group;
        }
    }

    grouping ipqos_Inst-group {

        // name of policy map
        // Type is an MO-Defined-Type
        leaf name {
            description "Name";

            // Type is an MO-Defined-Type
            type ipqos_PMapName;
        }
        leaf stats {
            type boolean;
            default "true";
        }
        leaf configStatus {
            config "false";
            type uint32;
        }
        container cmap-items {
            list Stats-list {
                key "cmapName type";

                // Added containment: Prefix=cmap
                // Acquired From Package ipqos
                uses ipqos_Stats-group;
            }
        }

        // Rel-def from PolicyInstToPMap
        container rspolicyInstToPMap-items {

            // Added containment as a singleton: Prefix=rspolicyInstToPMap
            // Acquired From Package ipqos
            uses ipqos_RsPolicyInstToPMap_source-group;
        }
    }

    grouping ipqos_Stats-group {

        // Type is an MO-Defined-Type
        leaf cmapName {
            description "Class map name";

            // Type is an MO-Defined-Type
            type ipqos_CMapName;
        }

        // Type is an MO-Defined-Type
        leaf type {
            description "QoS statistics type";

            // Type is an MO-Defined-Type
            type ipqos_StatsType;
        }
        leaf dropPackets {
            config "false";
            type uint64;
        }
        leaf dropBytes {
            config "false";
            type uint64;
        }
        leaf txPackets {
            config "false";
            type uint64;
        }
        leaf txBytes {
            config "false";
            type uint64;
        }
        leaf currQueueDepth {
            config "false";
            type uint64;
        }
        leaf maxQueueDepth {
            config "false";
            type uint64;
        }
        leaf randDropBytes {
            config "false";
            type uint64;
        }
        leaf randDropPackets {
            config "false";
            type uint64;
        }
        leaf conformBytes {
            config "false";
            type uint64;
        }
        leaf exceedBytes {
            config "false";
            type uint64;
        }
        leaf violateBytes {
            config "false";
            type uint64;
        }
    }

    grouping ipqos_System-group {
        leaf userSetBit {
            type uint64;
            default "0";
        }

        // Service policy instance
        container pmap-items {

            // Added containment as a singleton: Prefix=pmap
            // Acquired From Package ipqos
            uses ipqos_Inst-group;
        }
    }

    grouping ipqos_Egress-group {

        // Target interface
        container intf-items {
            list If-list {
                key "name";

                // Added containment: Prefix=intf
                // Acquired From Package ipqos
                uses ipqos_If-group;
            }
        }

        // system qos
        container sys-items {

            // Added containment as a singleton: Prefix=sys
            // Acquired From Package ipqos
            uses ipqos_System-group;
        }
    }

    grouping ipqos_CMapEntity-group {
        container name-items {
            list CMapInst-list {
                key "name";

                // Added containment: Prefix=name
                // Acquired From Package ipqos
                uses ipqos_CMapInst-group;
            }
        }
    }

    grouping ipqos_CMapInst-group {

        // name of class map
        // Type is an MO-Defined-Type
        leaf name {
            description "Name of class-map";

            // Type is an MO-Defined-Type
            type ipqos_CMapName;
        }

        // type of matching
        // Type is an MO-Defined-Type
        leaf matchType {
            description "Match-any, match-all or match-first";

            // Type is an MO-Defined-Type
            type ipqos_QoSMatchType;
        }
        leaf configStatus {
            config "false";
            type uint32;
        }

        // access-group
        container acl-items {
            list Acl-list {
                key "name";

                // Added containment: Prefix=acl
                // Acquired From Package ipqos
                uses ipqos_Acl-group;
            }
        }

        // dscp matching
        container dscp-items {
            list Dscp-list {
                key "val";

                // Added containment: Prefix=dscp
                // Acquired From Package ipqos
                uses ipqos_Dscp-group;
            }
        }

        // ip rtp matching
        container ipRtp-items {

            // Added containment as a singleton: Prefix=ipRtp
            // Acquired From Package ipqos
            uses ipqos_IpRtp-group;
        }

        // packet length matching
        container packetLength-items {

            // Added containment as a singleton: Prefix=packetLength
            // Acquired From Package ipqos
            uses ipqos_PacketLength-group;
        }

        // cos marking
        container cos-items {
            list Cos-list {
                key "val";

                // Added containment: Prefix=cos
                // Acquired From Package ipqos
                uses ipqos_Cos-group;
            }
        }

        // mpls experimental matching
        container mplsExperimental-items {
            list MPLSExperimental-list {
                key "val";

                // Added containment: Prefix=mplsExperimental
                // Acquired From Package ipqos
                uses ipqos_MPLSExperimental-group;
            }
        }

        // precedence matching
        container precedence-items {
            list Precedence-list {
                key "val";

                // Added containment: Prefix=precedence
                // Acquired From Package ipqos
                uses ipqos_Precedence-group;
            }
        }

        // protocol matching
        container protocol-items {
            list Protocol-list {
                key "val";

                // Added containment: Prefix=protocol
                // Acquired From Package ipqos
                uses ipqos_Protocol-group;
            }
        }

        // description
        container Description-items {

            // Added containment as a singleton: Prefix=Description
            // Acquired From Package ipqos
            uses ipqos_Description-group;
        }

        // NOT dscp matching
        container dscpNot-items {
            list NotDscp-list {
                key "val";

                // Added containment: Prefix=dscpNot
                // Acquired From Package ipqos
                uses ipqos_NotDscp-group;
            }
        }

        // NOT cos matching
        container cosNot-items {
            list NotCos-list {
                key "val";

                // Added containment: Prefix=cosNot
                // Acquired From Package ipqos
                uses ipqos_NotCos-group;
            }
        }

        // NOT mpls experimental matching
        container mplsExperimentalNot-items {
            list NotMPLSExperimental-list {
                key "val";

                // Added containment: Prefix=mplsExperimentalNot
                // Acquired From Package ipqos
                uses ipqos_NotMPLSExperimental-group;
            }
        }

        // NOT precedence matching
        container precedenceNot-items {
            list NotPrecedence-list {
                key "val";

                // Added containment: Prefix=precedenceNot
                // Acquired From Package ipqos
                uses ipqos_NotPrecedence-group;
            }
        }

        // NOT protocol matching
        container protocolNot-items {
            list NotProtocol-list {
                key "val";

                // Added containment: Prefix=protocolNot
                // Acquired From Package ipqos
                uses ipqos_NotProtocol-group;
            }
        }

        // NOT ip rtp matching
        container ipRtpNot-items {

            // Added containment as a singleton: Prefix=ipRtpNot
            // Acquired From Package ipqos
            uses ipqos_NotIpRtp-group;
        }

        // packet length matching
        container packetLengthNot-items {

            // Added containment as a singleton: Prefix=packetLengthNot
            // Acquired From Package ipqos
            uses ipqos_NotPacketLength-group;
        }

        // match qos-group
        container grp-items {
            list QoSGrp-list {
                key "id";

                // Added containment: Prefix=grp
                // Acquired From Package ipqos
                uses ipqos_QoSGrp-group;
            }
        }

        // Rel-def from classMapToPolicyMap
        container rsclassMapToPolicyMap-items {

            // Abstract containment of rsclassMapToPolicyMap derived from ipqos:CMapInst
            list RsClassMapToPolicyMap-list {
                key "tDn";

                // Added containment: Prefix=rsclassMapToPolicyMap
                // Acquired From Package ipqos
                uses ipqos_RsClassMapToPolicyMap_source-group;
            }
        }
    }

    grouping ipqos_Acl-group {

        // ACL to match
        // Type is an MO-Defined-Type
        leaf name {
            description "Match using ACL";

            // Type is an MO-Defined-Type
            type acl_Name;
        }
        leaf configStatus {
            config "false";
            type uint32;
        }
    }

    grouping ipqos_Dscp-group {

        // dscp value
        // Type is an MO-Defined-Type
        leaf val {
            description "Dscp value";

            // Type is an MO-Defined-Type
            type ipqos_Dscp;
        }
        leaf configStatus {
            config "false";
            type uint32;
        }
    }

    grouping ipqos_IpRtp-group {
        leaf configStatus {
            config "false";
            type uint32;
        }
        leaf range {
            type string;
        }
    }

    grouping ipqos_PacketLength-group {
        leaf configStatus {
            config "false";
            type uint32;
        }
        leaf range {
            type string;
        }
    }

    grouping ipqos_Cos-group {

        // cos value
        // Type is an MO-Defined-Type
        leaf val {
            description "Cos value";

            // Type is an MO-Defined-Type
            type ipqos_Cos;
        }
        leaf configStatus {
            config "false";
            type uint32;
        }
    }

    grouping ipqos_MPLSExperimental-group {

        // mpls experimental value
        // Type is an MO-Defined-Type
        leaf val {
            description "MPLS experimental value";

            // Type is an MO-Defined-Type
            type ipqos_MPLSExperimental;
        }
        leaf configStatus {
            config "false";
            type uint32;
        }
    }

    grouping ipqos_Precedence-group {

        // dscp value
        // Type is an MO-Defined-Type
        leaf val {
            description "Precedence value";

            // Type is an MO-Defined-Type
            type ipqos_Prec;
        }
        leaf configStatus {
            config "false";
            type uint32;
        }
    }

    grouping ipqos_Protocol-group {

        // protocol value
        // Type is an MO-Defined-Type
        leaf val {
            description "Protocol value";

            // Type is an MO-Defined-Type
            type ipqos_Protocol;
        }
        leaf configStatus {
            config "false";
            type uint32;
        }
    }

    grouping ipqos_Description-group {

        // description value
        // Type is an MO-Defined-Type
        leaf val {
            description "Description string";

            // Type is an MO-Defined-Type
            type ipqos_DescStr;
        }
    }

    grouping ipqos_NotDscp-group {

        // dscp value
        // Type is an MO-Defined-Type
        leaf val {
            description "Not dscp value";

            // Type is an MO-Defined-Type
            type ipqos_Dscp;
        }
        leaf configStatus {
            config "false";
            type uint32;
        }
    }

    grouping ipqos_NotCos-group {

        // cos value
        // Type is an MO-Defined-Type
        leaf val {
            description "Not cos value";

            // Type is an MO-Defined-Type
            type ipqos_Cos;
        }
        leaf configStatus {
            config "false";
            type uint32;
        }
    }

    grouping ipqos_NotMPLSExperimental-group {

        // mpls experimental value
        // Type is an MO-Defined-Type
        leaf val {
            description "Not mpls experimental value";

            // Type is an MO-Defined-Type
            type ipqos_MPLSExperimental;
        }
        leaf configStatus {
            config "false";
            type uint32;
        }
    }

    grouping ipqos_NotPrecedence-group {

        // precedence value
        // Type is an MO-Defined-Type
        leaf val {
            description "Not precedence value";

            // Type is an MO-Defined-Type
            type ipqos_Prec;
        }
        leaf configStatus {
            config "false";
            type uint32;
        }
    }

    grouping ipqos_NotProtocol-group {

        // protocol value
        // Type is an MO-Defined-Type
        leaf val {
            description "Not protocol value";

            // Type is an MO-Defined-Type
            type ipqos_Protocol;
        }
        leaf configStatus {
            config "false";
            type uint32;
        }
    }

    grouping ipqos_NotIpRtp-group {
        leaf configStatus {
            config "false";
            type uint32;
        }
        leaf range {
            type string;
        }
    }

    grouping ipqos_NotPacketLength-group {
        leaf configStatus {
            config "false";
            type uint32;
        }
        leaf range {
            type string;
        }
    }

    grouping ipqos_QoSGrp-group {

        // QoS-Group ID
        // Type is an MO-Defined-Type
        leaf id {
            description "QoS group ID";

            // Type is an MO-Defined-Type
            type ipqos_QoSGrpId;
        }
        leaf configStatus {
            config "false";
            type uint32;
        }
    }

    grouping ipqos_PMapEntity-group {

        // policy map instance
        container name-items {
            list PMapInst-list {
                key "name";

                // Added containment: Prefix=name
                // Acquired From Package ipqos
                uses ipqos_PMapInst-group;
            }
        }
    }

    grouping ipqos_PMapInst-group {

        // policy map name
        // Type is an MO-Defined-Type
        leaf name {
            description "Name of policy-map";

            // Type is an MO-Defined-Type
            type ipqos_PMapName;
        }

        // type of matching
        // Type is an MO-Defined-Type
        leaf matchType {
            description "Match-any, match-all or match-first";

            // Type is an MO-Defined-Type
            type ipqos_QoSMatchType;
        }
        leaf refCount {
            config "false";
            type uint32;
        }
        leaf configStatus {
            config "false";
            type uint32;
        }

        // match a class-map
        container cmap-items {
            list MatchCMap-list {
                key "name";

                // Added containment: Prefix=cmap
                // Acquired From Package ipqos
                uses ipqos_MatchCMap-group;
            }
        }

        // description
        container Description-items {

            // Added containment as a singleton: Prefix=Description
            // Acquired From Package ipqos
            uses ipqos_Description-group;
        }

        // Rel-def target from PolicyInstToPMap
        // Inherited From ipqos:PMapInst
        container rtipqosPolicyInstToPMap-items {

            // Abstract containment of rtipqosPolicyInstToPMap derived from ipqos:PMapInst
            list RtIpqosPolicyInstToPMap-list {
                key "tDn";

                // Added containment: Prefix=rtipqosPolicyInstToPMap
                // Acquired From Package ipqos
                uses ipqos_RtIpqosPolicyInstToPMap_target-group;
            }
        }

        // Rel-def target from classMapToPolicyMap
        // Inherited From ipqos:PMapInst
        container rtclassMapToPolicyMap-items {

            // Added containment as a singleton: Prefix=rtclassMapToPolicyMap
            // Acquired From Package ipqos
            uses ipqos_RtClassMapToPolicyMap_target-group;
        }
    }

    grouping ipqos_MatchCMap-group {

        // use class-map with this name
        // Type is an MO-Defined-Type
        leaf name {
            description "Match using class-map";

            // Type is an MO-Defined-Type
            type ipqos_CMapName;
        }

        // Type is an MO-Defined-Type
        leaf prevCMap {
            description "Insert after the given class-map";

            // Type is an MO-Defined-Type
            type ipqos_MatchCMapName;
        }

        // Type is an MO-Defined-Type
        leaf nextCMap {
            description "Insert before the given class-map";

            // Type is an MO-Defined-Type
            type ipqos_MatchCMapName;
        }
        leaf userSetBit {
            type uint64;
            default "0";
        }
        leaf configStatus {
            config "false";
            type uint32;
        }

        container setCos-items {

            // Added containment as a singleton: Prefix=setCos
            // Acquired From Package ipqos
            uses ipqos_SetCos-group;
        }

        // set MTU
        container mtu-items {

            // Added containment as a singleton: Prefix=mtu
            // Acquired From Package ipqos
            uses ipqos_SetMTU-group;
        }

        // set precedence
        container setPrecedence-items {

            // Added containment as a singleton: Prefix=setPrecedence
            // Acquired From Package ipqos
            uses ipqos_SetPrecedence-group;
        }

        // set dscp
        container setDscp-items {

            // Added containment as a singleton: Prefix=setDscp
            // Acquired From Package ipqos
            uses ipqos_SetDscp-group;
        }

        // set qos-group
        container setGrp-items {

            // Added containment as a singleton: Prefix=setGrp
            // Acquired From Package ipqos
            uses ipqos_SetQoSGrp-group;
        }

        // set dlb-disable
        container setDlbDisable-items {

            // Added containment as a singleton: Prefix=setDlbDisable
            // Acquired From Package ipqos
            uses ipqos_SetDlbDisable-group;
        }

        // queue-limit
        container QueueLimit-items {

            // Added containment as a singleton: Prefix=QueueLimit
            // Acquired From Package ipqos
            uses ipqos_QueueLimit-group;
        }

        // pause
        container pause-items {

            // Added containment as a singleton: Prefix=pause
            // Acquired From Package ipqos
            uses ipqos_Pause-group;
        }

        // dpp
        container dpp-items {

            // Added containment as a singleton: Prefix=dpp
            // Acquired From Package ipqos
            uses ipqos_Dpp-group;
        }

        // bandwidth
        container setBW-items {

            // Added containment as a singleton: Prefix=setBW
            // Acquired From Package ipqos
            uses ipqos_SetBW-group;
        }

        // bandwidth
        container setRemBW-items {

            // Added containment as a singleton: Prefix=setRemBW
            // Acquired From Package ipqos
            uses ipqos_SetRemBW-group;
        }

        // shape traffic
        container shape-items {

            // Added containment as a singleton: Prefix=shape
            // Acquired From Package ipqos
            uses ipqos_Shape-group;
        }

        // police
        container police-items {

            // Added containment as a singleton: Prefix=police
            // Acquired From Package ipqos
            uses ipqos_Police-group;
        }

        // priority
        container prio-items {

            // Added containment as a singleton: Prefix=prio
            // Acquired From Package ipqos
            uses ipqos_Priority-group;
        }

        container RandDet-items {

            // Added containment as a singleton: Prefix=RandDet
            // Acquired From Package ipqos
            uses ipqos_RandomDetect-group;
        }

        container RandDetNonEcn-items {

            // Added containment as a singleton: Prefix=RandDetNonEcn
            // Acquired From Package ipqos
            uses ipqos_RandomDetectNonEcn-group;
        }
    }

    grouping ipqos_SetCos-group {

        // Cos value
        // Type is an MO-Defined-Type
        leaf val {
            description "Cos value";

            // Type is an MO-Defined-Type
            type ipqos_Cos;
        }
        leaf configStatus {
            config "false";
            type uint32;
        }
    }

    grouping ipqos_SetMTU-group {

        // MTU value
        // Type is an MO-Defined-Type
        leaf value {
            description "Set MTU value";

            // Type is an MO-Defined-Type
            type ipqos_MTU;
        }
        leaf configStatus {
            config "false";
            type uint32;
        }
    }

    grouping ipqos_SetPrecedence-group {

        // Precedence value
        // Type is an MO-Defined-Type
        leaf val {
            description "Precedence value";

            // Type is an MO-Defined-Type
            type ipqos_Prec;
        }
        leaf tunnel {
            type boolean;
        }
        leaf configStatus {
            config "false";
            type uint32;
        }
    }

    grouping ipqos_SetDscp-group {

        // Dscp value
        // Type is an MO-Defined-Type
        leaf val {
            description "Dscp value";

            // Type is an MO-Defined-Type
            type ipqos_Dscp;
        }
        leaf tunnel {
            type boolean;
        }
        leaf configStatus {
            config "false";
            type uint32;
        }
    }

    grouping ipqos_SetQoSGrp-group {

        // QoS-Group ID
        // Type is an MO-Defined-Type
        leaf id {
            description "QoS group ID";

            // Type is an MO-Defined-Type
            type ipqos_QoSGrpId;
        }
        leaf configStatus {
            config "false";
            type uint32;
        }
    }

    grouping ipqos_SetDlbDisable-group {
        leaf configStatus {
            config "false";
            type uint32;
        }
    }

    grouping ipqos_QueueLimit-group {

        // queue-limit
        // Type is an MO-Defined-Type
        leaf QueueLimitVal {
            description "Value in bytes/kbytes/mbytes";

            // Type is an MO-Defined-Type
            type ipqos_QueueLimit;
        }

        // queue-limit unit
        // Type is an MO-Defined-Type
        leaf QueueLimitUnit {
            description "Bytes/kbytes/mbytes";

            // Type is an MO-Defined-Type
            type ipqos_QueueLimitUnit;
        }

        // queue-limit dynamic
        // Type is an MO-Defined-Type
        leaf dynamic {
            description "Queue-limit dynamic value";

            // Type is an MO-Defined-Type
            type ipqos_QueueLimitDynamic;
        }
        leaf configStatus {
            config "false";
            type uint32;
        }
    }

    grouping ipqos_Pause-group {

        // buffer-size
        // Type is an MO-Defined-Type
        leaf bufferSize {
            description "size in bytes";

            // Type is an MO-Defined-Type
            type ipqos_BuffSize;
        }

        // pause-threshold
        // Type is an MO-Defined-Type
        leaf pauseThreshold {
            description "xoff bytes";

            // Type is an MO-Defined-Type
            type ipqos_XoffBytes;
        }

        // resume-threshold
        // Type is an MO-Defined-Type
        leaf resumeThreshold {
            description "xon bytes";

            // Type is an MO-Defined-Type
            type ipqos_XonBytes;
        }
        leaf pfcCos0 {
            type boolean;
        }
        leaf pfcCos1 {
            type boolean;
        }
        leaf pfcCos2 {
            type boolean;
        }
        leaf pfcCos3 {
            type boolean;
        }
        leaf pfcCos4 {
            type boolean;
        }
        leaf pfcCos5 {
            type boolean;
        }
        leaf pfcCos6 {
            type boolean;
        }
        leaf pfcCos7 {
            type boolean;
        }
        leaf configStatus {
            config "false";
            type uint32;
        }
    }

    grouping ipqos_Dpp-group {

        // set-qos-group
        // Type is an MO-Defined-Type
        leaf setQosGroup {
            description "QoS Group Value";

            // Type is an MO-Defined-Type
            type ipqos_QoSGrpId;
        }
        leaf configStatus {
            config "false";
            type uint32;
        }
    }

    grouping ipqos_SetBW-group {

        // Percent of available bandwidth
        // Type is an MO-Defined-Type
        leaf val {
            description "Available bandwidth";

            // Type is an MO-Defined-Type
            type ipqos_Percent;
        }
        leaf configStatus {
            config "false";
            type uint32;
        }
    }

    grouping ipqos_SetRemBW-group {

        // Percent of available bandwidth
        // Type is an MO-Defined-Type
        leaf val {
            description "Remaining bandwidth";

            // Type is an MO-Defined-Type
            type ipqos_Percent;
        }
        leaf configStatus {
            config "false";
            type uint32;
        }
    }

    grouping ipqos_Shape-group {

        // Type is an MO-Defined-Type
        leaf min {
            description "Minimum shape rate";

            // Type is an MO-Defined-Type
            type ipqos_ShapeRate;
        }

        // Type is an MO-Defined-Type
        leaf minRateUnit {
            description "Minimum shape rate unit";

            // Type is an MO-Defined-Type
            type ipqos_RateUnit;
        }

        // Type is an MO-Defined-Type
        leaf max {
            description "Maximum shape rate";

            // Type is an MO-Defined-Type
            type ipqos_ShapeRate;
        }

        // Type is an MO-Defined-Type
        leaf maxRateUnit {
            description "Maximum shape rate unit";

            // Type is an MO-Defined-Type
            type ipqos_RateUnit;
        }
        leaf configStatus {
            config "false";
            type uint32;
        }
    }

    grouping ipqos_Police-group {

        // Type is an MO-Defined-Type
        leaf cirRate {
            description "CIR";

            // Type is an MO-Defined-Type
            type ipqos_PoliceRate;
        }

        // Type is an MO-Defined-Type
        leaf cirUnit {
            description "CIR unit";

            // Type is an MO-Defined-Type
            type ipqos_RateUnit;
        }

        // Type is an MO-Defined-Type
        leaf bcRate {
            description "CIR burst";

            // Type is an MO-Defined-Type
            type ipqos_BurstRate;
        }

        // Type is an MO-Defined-Type
        leaf bcUnit {
            description "CIR burst unit";

            // Type is an MO-Defined-Type
            type ipqos_BurstRateUnit;
        }

        // Type is an MO-Defined-Type
        leaf pirRate {
            description "PIR";

            // Type is an MO-Defined-Type
            type ipqos_PoliceRate;
        }

        // Type is an MO-Defined-Type
        leaf pirUnit {
            description "PIR unit";

            // Type is an MO-Defined-Type
            type ipqos_RateUnit;
        }

        // Type is an MO-Defined-Type
        leaf beRate {
            description "PIR burst";

            // Type is an MO-Defined-Type
            type ipqos_BurstRate;
        }

        // Type is an MO-Defined-Type
        leaf beUnit {
            description "PIR burst unit";

            // Type is an MO-Defined-Type
            type ipqos_BurstRateUnit;
        }

        // Type is an MO-Defined-Type
        leaf conformAction {
            description "Conform action";

            // Type is an MO-Defined-Type
            type ipqos_PoliceAction;
        }

        // Type is an MO-Defined-Type
        leaf conformSetCosTransmit {
            description "set cos for conforming traffic";

            // Type is an MO-Defined-Type
            type ipqos_Cos;
        }

        // Type is an MO-Defined-Type
        leaf conformSetDscpTransmit {
            description "set dscp for conforming traffic";

            // Type is an MO-Defined-Type
            type ipqos_Dscp;
        }

        // Type is an MO-Defined-Type
        leaf conformSetPrecTransmit {
            description "set precedence for conforming traffic";

            // Type is an MO-Defined-Type
            type ipqos_Prec;
        }

        // Type is an MO-Defined-Type
        leaf conformSetQosGrpTransmit {
            description "set qos-group for conforming traffic";

            // Type is an MO-Defined-Type
            type ipqos_QoSGrpId;
        }

        // Type is an MO-Defined-Type
        leaf exceedAction {
            description "Exceed action";

            // Type is an MO-Defined-Type
            type ipqos_PoliceAction;
        }

        // Type is an MO-Defined-Type
        leaf exceedSetCosTransmit {
            description "set cos for exceeding traffic";

            // Type is an MO-Defined-Type
            type ipqos_Cos;
        }

        // Type is an MO-Defined-Type
        leaf exceedSetDscpTransmit {
            description "set dscp for exceeding traffic";

            // Type is an MO-Defined-Type
            type ipqos_Dscp;
        }

        // Type is an MO-Defined-Type
        leaf exceedSetPrecTransmit {
            description "set precedence for exceeding traffic";

            // Type is an MO-Defined-Type
            type ipqos_Prec;
        }

        // Type is an MO-Defined-Type
        leaf exceedSetQosGrpTransmit {
            description "set qos-group for exceeding traffic";

            // Type is an MO-Defined-Type
            type ipqos_QoSGrpId;
        }

        // Type is an MO-Defined-Type
        leaf violateAction {
            description "Violate action";

            // Type is an MO-Defined-Type
            type ipqos_PoliceAction;
        }

        // Type is an MO-Defined-Type
        leaf violateSetCosTransmit {
            description "set cos for violating traffic";

            // Type is an MO-Defined-Type
            type ipqos_Cos;
        }

        // Type is an MO-Defined-Type
        leaf violateSetDscpTransmit {
            description "set dscp for violating traffic";

            // Type is an MO-Defined-Type
            type ipqos_Dscp;
        }

        // Type is an MO-Defined-Type
        leaf violateSetPrecTransmit {
            description "set precedence for violating traffic";

            // Type is an MO-Defined-Type
            type ipqos_Prec;
        }

        // Type is an MO-Defined-Type
        leaf violateSetQosGrpTransmit {
            description "set qos-group for violating traffic";

            // Type is an MO-Defined-Type
            type ipqos_QoSGrpId;
        }
        leaf configStatus {
            config "false";
            type uint32;
        }
    }

    grouping ipqos_Priority-group {

        // Type is an MO-Defined-Type
        leaf level {
            description "Optional priority level";

            // Type is an MO-Defined-Type
            type ipqos_PriorityLevel;
        }
        leaf configStatus {
            config "false";
            type uint32;
        }
    }

    grouping ipqos_RandomDetect-group {

        // minimun thresold
        // Type is an MO-Defined-Type
        leaf minThreshold {
            description "min threshold";

            // Type is an MO-Defined-Type
            type ipqos_ThreshVal;
        }

        // minimun thresold unit
        // Type is an MO-Defined-Type
        leaf minThresholdUnit {
            description "min threshold";

            // Type is an MO-Defined-Type
            type ipqos_ThreshUnit;
        }

        // max threshold
        // Type is an MO-Defined-Type
        leaf maxThreshold {
            description "max threshold";

            // Type is an MO-Defined-Type
            type ipqos_ThreshVal;
        }

        // max thresold unit
        // Type is an MO-Defined-Type
        leaf maxThresholdUnit {
            description "max threshold";

            // Type is an MO-Defined-Type
            type ipqos_ThreshUnit;
        }

        // drop availability
        // Type is an MO-Defined-Type
        leaf dropAvail {
            description "drop availability range";

            // Type is an MO-Defined-Type
            type ipqos_DropAvailRange;
        }

        // threshold weight
        // Type is an MO-Defined-Type
        leaf weight {
            description "weight range";

            // Type is an MO-Defined-Type
            type ipqos_Weight;
        }
        leaf capAverage {
            type boolean;
        }

        // mesh or burst optimization
        // Type is an MO-Defined-Type
        leaf optimization {
            description "random optimization type";

            // Type is an MO-Defined-Type
            type ipqos_RandOptType;
        }
        leaf ecn {
            type boolean;
        }
        leaf configStatus {
            config "false";
            type uint32;
        }
    }

    grouping ipqos_RandomDetectNonEcn-group {

        // minimun thresold
        // Type is an MO-Defined-Type
        leaf minThresholdNonEcn {
            description "non ecn min threshold";

            // Type is an MO-Defined-Type
            type ipqos_ThreshVal;
        }

        // minimun thresold unit
        // Type is an MO-Defined-Type
        leaf minThresholdUnitNonEcn {
            description "non ecn min threshold";

            // Type is an MO-Defined-Type
            type ipqos_ThreshUnit;
        }

        // max threshold
        // Type is an MO-Defined-Type
        leaf maxThresholdNonEcn {
            description "non ecn max threshold";

            // Type is an MO-Defined-Type
            type ipqos_ThreshVal;
        }

        // max thresold unit
        // Type is an MO-Defined-Type
        leaf maxThresholdUnitNonEcn {
            description "non ecn max threshold";

            // Type is an MO-Defined-Type
            type ipqos_ThreshUnit;
        }

        // drop availability
        // Type is an MO-Defined-Type
        leaf dropAvailNonEcn {
            description "drop availability range";

            // Type is an MO-Defined-Type
            type ipqos_DropAvailRange;
        }
        leaf configStatus {
            config "false";
            type uint32;
        }
    }

    grouping ipqos_CopyPMap-group {

        // Type is an MO-Defined-Type
        leaf lastFrom {
            config "false";
            description "Name of source policy-map to copy from";

            // Type is an MO-Defined-Type
            type ipqos_PMapName;
        }

        // Type is an MO-Defined-Type
        leaf lastTo {
            config "false";
            description "Name of policy-map resulting from copying";

            // Type is an MO-Defined-Type
            type ipqos_PMapName;
        }
    }

    grouping ipqos_NwQoS-group {

        // service policy applied on target
        container policy-items {

            // Added containment as a singleton: Prefix=policy
            // Acquired From Package ipqos
            uses ipqos_ServPol-group;
        }

        // class-map
        container c-items {

            // Added containment as a singleton: Prefix=c
            // Acquired From Package ipqos
            uses ipqos_CMapEntity-group;
        }

        // policy-map
        container p-items {

            // Added containment as a singleton: Prefix=p
            // Acquired From Package ipqos
            uses ipqos_PMapEntity-group;
        }

        container copyPMap-items {

            // Added containment as a singleton: Prefix=copyPMap
            // Acquired From Package ipqos
            uses ipqos_CopyPMap-group;
        }
    }

    grouping ipqos_DefaultQoS-group {

        // service policy applied on target
        container policy-items {

            // Added containment as a singleton: Prefix=policy
            // Acquired From Package ipqos
            uses ipqos_ServPol-group;
        }

        // class-map
        container c-items {

            // Added containment as a singleton: Prefix=c
            // Acquired From Package ipqos
            uses ipqos_CMapEntity-group;
        }

        // policy-map
        container p-items {

            // Added containment as a singleton: Prefix=p
            // Acquired From Package ipqos
            uses ipqos_PMapEntity-group;
        }

        container copyPMap-items {

            // Added containment as a singleton: Prefix=copyPMap
            // Acquired From Package ipqos
            uses ipqos_CopyPMap-group;
        }
    }

    grouping monitor_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Abstraction of coop database (repository)
        container db-items {
            list Db-list {
                config "false";
                key "type";

                // Added containment: Prefix=db
                // Acquired From Package monitor
                uses monitor_Db-group;
            }
        }

        // Monitor session definition. there could be only few sessions
        // active at a given time (max 4)
        container session-items {
            list Session-list {
                key "name";

                // Added containment: Prefix=session
                // Acquired From Package monitor
                uses monitor_Session-group;
            }
        }
    }

    grouping monitor_Db-group {

        // Type of the database
        // Type is an MO-Defined-Type
        leaf type {
            config "false";
            description "Type";

            // Type is an MO-Defined-Type
            type monitor_DbT;
        }

        // Inherited From nw:Conn
        // Modified by Override: nw:Db->name
        // Type is an MO-Defined-Type
        leaf name {
            description "Name";

            // Type is an MO-Defined-Type
            type naming_Name {
                length "1..64";
            }
        }

        // Ep records
        container epr-items {
            list EpRec-list {
                config "false";
                key "vnid ip";

                // Added containment: Prefix=epr
                // Acquired From Package monitor
                uses monitor_EpRec-group;
            }
        }
    }

    grouping monitor_EpRec-group {
        leaf vnid {
            config "false";
            type string;
        }
        leaf ip {
            config "false";
            type address_Ip;
        }

        // Synthetic vrf
        // Type is an MO-Defined-Type
        leaf synthVrf {
            config "false";
            description "Synthetic VRF";

            // Type is an MO-Defined-Type
            type coop_SynthVrf;
        }

        // Synthetic ip
        // Type is an MO-Defined-Type
        leaf synthIp {
            config "false";
            description "Synthetic IP";

            // Type is an MO-Defined-Type
            type coop_SynthIp;
        }
        leaf tep {
            config "false";
            type address_Ip;
        }

        // Inherited From nw:Conn
        // Modified by Override: nw:DbRec->name
        // Type is an MO-Defined-Type
        leaf name {
            description "Name";

            // Type is an MO-Defined-Type
            type naming_Name {
                length "1..64";
            }
        }
    }

    grouping monitor_Session-group {

        // Identifier of the session
        // Type is an MO-Defined-Type
        leaf id {
            description "ID";

            // Type is an MO-Defined-Type
            type monitor_SessionId;
        }

        // Administrative state of the session
        // Type is an MO-Defined-Type
        leaf adminSt {
            config "false";
            description "Admin State";

            // Type is an MO-Defined-Type
            type nw_AdminSt;
        }

        // Operational state of the session
        // Type is an MO-Defined-Type
        leaf operSt {
            config "false";
            description "Operational State";

            // Type is an MO-Defined-Type
            type monitor_OperSt;
        }

        // Operational state qualifier
        // Type is an MO-Defined-Type
        leaf operStQual {
            config "false";
            description "Operational State Qualifier";

            // Type is an MO-Defined-Type
            type monitor_OperStQual;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Monitor sources. The sources which we want to monitor
        container src-items {
            list Source-list {
                config "false";
                key "type mode dir from to port";

                // Added containment: Prefix=src
                // Acquired From Package monitor
                uses monitor_Source-group;
            }
        }

        // ERSpan destination information
        container erdst-items {

            // Added containment as a singleton: Prefix=erdst
            // Acquired From Package monitor
            uses monitor_ERDest-group;
        }

        // Local span destination information
        container ldst-items {

            // Added containment as a singleton: Prefix=ldst
            // Acquired From Package monitor
            uses monitor_LocalDest-group;
        }
    }

    grouping monitor_Source-group {

        // Source id
        // Type is an MO-Defined-Type
        leaf id {
            description "ID";

            // Type is an MO-Defined-Type
            type monitor_SrcId;
        }

        // Type of the source
        // Type is an MO-Defined-Type
        leaf type {
            config "false";
            description "Type";

            // Type is an MO-Defined-Type
            type monitor_SrcT;
        }

        // The direction of the packets to monitor
        // Type is an MO-Defined-Type
        leaf dir {
            config "false";
            description "Direction";

            // Type is an MO-Defined-Type
            type monitor_Direction;
        }
        leaf from {
            config "false";
            type string;
        }
        leaf to {
            config "false";
            type string;
        }

        // Port to monitor
        // Type is an MO-Defined-Type
        leaf port {
            config "false";
            description "Port";

            // Type is an MO-Defined-Type
            type nw_IfId;
        }

        // Mode of the source (access side or fabric side)
        // Type is an MO-Defined-Type
        leaf mode {
            config "false";
            description "Mode";

            // Type is an MO-Defined-Type
            type monitor_Mode;
        }

        // Operational state of the session
        // Type is an MO-Defined-Type
        leaf operSt {
            config "false";
            description "Operational State";

            // Type is an MO-Defined-Type
            type monitor_OperSt;
        }

        // Operational state qualifier
        // Type is an MO-Defined-Type
        leaf operStQual {
            config "false";
            description "Operational State Qualifier";

            // Type is an MO-Defined-Type
            type monitor_OperStQual;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
    }

    grouping monitor_ERDest-group {

        // Encapsulation type, the encapsulation of the monitored
        // packet sent to the destination
        // Type is an MO-Defined-Type
        leaf type {
            config "false";
            description "Type";

            // Type is an MO-Defined-Type
            type monitor_DestEncapT;
        }
        leaf srcIp {
            config "false";
            type address_Ip;
        }
        leaf dstIp {
            config "false";
            type address_Ip;
        }

        // Erspan version
        // Type is an MO-Defined-Type
        leaf ver {
            config "false";
            description "Version";

            // Type is an MO-Defined-Type
            type monitor_ErSpanVer;
        }

        // Flow id of the erspan packet
        // Type is an MO-Defined-Type
        leaf flowId {
            config "false";
            description "Flow ID";

            // Type is an MO-Defined-Type
            type monitor_FlowId;
        }

        // Ttl used in the erspan packet
        // Type is an MO-Defined-Type
        leaf ttl {
            config "false";
            description "TTL";

            // Type is an MO-Defined-Type
            type l3_Ttl;
        }

        // the vrf on which the erspan packet is sent
        // Type is an MO-Defined-Type
        leaf vrfName {
            config "false";
            description "VRF";

            // Type is an MO-Defined-Type
            type l3_VrfName;
        }
        leaf vnid {
            config "false";
            type string;
        }

        // dscp value to be used when sending the monitored
        // packets using ERSpan
        // Type is an MO-Defined-Type
        leaf dscp {
            config "false";
            description "Dscp";

            // Type is an MO-Defined-Type
            type qosp_Dscp;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // mtu truncation size for the packets
        // Inherited From monitor:Destination
        // Type is an MO-Defined-Type
        leaf mtu {
            config "false";
            description "MTU";

            // Type is an MO-Defined-Type
            type monitor_Mtu;
        }

        // Operational state of the session
        // Inherited From monitor:Destination
        // Type is an MO-Defined-Type
        leaf operSt {
            config "false";
            description "Operational State";

            // Type is an MO-Defined-Type
            type monitor_OperSt;
        }

        // Operational state qualifier
        // Inherited From monitor:Destination
        // Type is an MO-Defined-Type
        leaf operStQual {
            config "false";
            description "Operational State Qualifier";

            // Type is an MO-Defined-Type
            type monitor_OperStQual;
        }
    }

    grouping monitor_LocalDest-group {

        // Port
        // Type is an MO-Defined-Type
        leaf port {
            config "false";
            description "Port";

            // Type is an MO-Defined-Type
            type nw_IfId;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // mtu truncation size for the packets
        // Inherited From monitor:Destination
        // Type is an MO-Defined-Type
        leaf mtu {
            config "false";
            description "MTU";

            // Type is an MO-Defined-Type
            type monitor_Mtu;
        }

        // Operational state of the session
        // Inherited From monitor:Destination
        // Type is an MO-Defined-Type
        leaf operSt {
            config "false";
            description "Operational State";

            // Type is an MO-Defined-Type
            type monitor_OperSt;
        }

        // Operational state qualifier
        // Inherited From monitor:Destination
        // Type is an MO-Defined-Type
        leaf operStQual {
            config "false";
            description "Operational State Qualifier";

            // Type is an MO-Defined-Type
            type monitor_OperStQual;
        }
    }

    grouping flow_Entity-group {

        // Flow Record
        container fr-items {
            list Record-list {
                key "name";

                // Added containment: Prefix=fr
                // Acquired From Package flow
                uses flow_Record-group;
            }
        }

        // Flow Exporter
        container fe-items {
            list Exporter-list {
                key "name";

                // Added containment: Prefix=fe
                // Acquired From Package flow
                uses flow_Exporter-group;
            }
        }

        // Flow Monitor
        container fm-items {
            list Monitor-list {
                key "name";

                // Added containment: Prefix=fm
                // Acquired From Package flow
                uses flow_Monitor-group;
            }
        }

        // Sampler
        container s-items {
            list Sampler-list {
                key "name";

                // Added containment: Prefix=s
                // Acquired From Package flow
                uses flow_Sampler-group;
            }
        }
        container cmap-items {
            list ClassMap-list {
                key "name";

                // Added containment: Prefix=cmap
                // Acquired From Package flow
                uses flow_ClassMap-group;
            }
        }
        container pmap-items {
            list PolicyMap-list {
                key "name";

                // Added containment: Prefix=pmap
                // Acquired From Package flow
                uses flow_PolicyMap-group;
            }
        }

        // Hardware profile
        container hp-items {
            list HwProfile-list {
                key "name";

                // Added containment: Prefix=hp
                // Acquired From Package flow
                uses flow_HwProfile-group;
            }
        }

        // Forwarding instance based target
        container fit-items {
            list FwdInstTarget-list {
                key "slot asic slice";

                // Added containment: Prefix=fit
                // Acquired From Package flow
                uses flow_FwdInstTarget-group;
            }
        }
    }

    grouping flow_Record-group {
        leaf name {
            type string;
        }
        leaf description {
            type string;
        }

        // Type is an MO-Defined-Type
        leaf matchParams {
            description "Match Params";

            // Type is an MO-Defined-Type
            type flow_MatchParams;
        }

        // Type is an MO-Defined-Type
        leaf collectParams {
            description "Collect Params";

            // Type is an MO-Defined-Type
            type flow_CollectParams;
        }
    }

    grouping flow_Exporter-group {
        leaf name {
            type string;
        }
        leaf description {
            type string;
        }

        // Type is an MO-Defined-Type
        leaf vrfName {
            description "Collector VRF";

            // Type is an MO-Defined-Type
            type l3_VrfName;
        }
        leaf destinationIp {
            type address_Ip;
        }

        // Type is an MO-Defined-Type
        leaf destinationPort {
            description "Collector L4 Port";

            // Type is an MO-Defined-Type
            type flow_L4Port;
        }

        // Type is an MO-Defined-Type
        leaf dscp {
            description "DSCP value";

            // Type is an MO-Defined-Type
            type ipqos_Dscp;
        }

        // check
        // Type is an MO-Defined-Type
        leaf sourceInterface {
            description "Source Interface";

            // Type is an MO-Defined-Type
            type nw_IfId;
        }

        // Type is an MO-Defined-Type
        leaf version {
            description "Export version format";

            // Type is an MO-Defined-Type
            type flow_ExportVersion;
        }
    }

    grouping flow_Monitor-group {
        leaf name {
            type string;
        }
        leaf description {
            type string;
        }
        container feb-items {
            list ExporterBucket-list {
                key "id";

                // Added containment: Prefix=feb
                // Acquired From Package flow
                uses flow_ExporterBucket-group;
            }
        }

        // Rel-def from record
        container rsrecord-items {

            // Added containment as a singleton: Prefix=rsrecord
            // Acquired From Package flow
            uses flow_RsRecord_source-group;
        }
    }

    grouping flow_ExporterBucket-group {
        leaf id {
            type uint8;
        }
        leaf description {
            type string;
        }
        leaf hashLo {
            type uint32;
        }
        leaf hashHi {
            type uint32;
        }

        // Rel-def from exporter1
        container rsexporter1-items {

            // Added containment as a singleton: Prefix=rsexporter1
            // Acquired From Package flow
            uses flow_RsExporter1_source-group;
        }

        // Rel-def from exporter2
        container rsexporter2-items {

            // Added containment as a singleton: Prefix=rsexporter2
            // Acquired From Package flow
            uses flow_RsExporter2_source-group;
        }
    }

    grouping flow_Sampler-group {
        leaf name {
            type string;
        }
        leaf description {
            type string;
        }

        // Type is an MO-Defined-Type
        leaf mode {
            description "Sampler mode";

            // Type is an MO-Defined-Type
            type flow_SamplerMode;
        }
        leaf param1 {
            type uint32;
        }
        leaf param2 {
            type uint32;
        }
    }

    grouping flow_ClassMap-group {

        // class map name
        // Type is an MO-Defined-Type
        leaf name {
            description "Name of class-map";

            // Type is an MO-Defined-Type
            type ipqos_CMapName;
        }

        // match access-group
        container acl-items {
            list MatchAcl-list {
                key "name";

                // Added containment: Prefix=acl
                // Acquired From Package flow
                uses flow_MatchAcl-group;
            }
        }
    }

    grouping flow_MatchAcl-group {

        // ACL to match
        // Type is an MO-Defined-Type
        leaf name {
            description "Match using ACL";

            // Type is an MO-Defined-Type
            type acl_Name;
        }
    }

    grouping flow_PolicyMap-group {

        // policy map name
        // Type is an MO-Defined-Type
        leaf name {
            description "Name of policy-map";

            // Type is an MO-Defined-Type
            type ipqos_PMapName;
        }

        // match a class-map
        container cmap-items {
            list MatchClassMap-list {
                key "name";

                // Added containment: Prefix=cmap
                // Acquired From Package flow
                uses flow_MatchClassMap-group;
            }
        }
    }

    grouping flow_MatchClassMap-group {

        // use class-map with this name
        // Type is an MO-Defined-Type
        leaf name {
            description "Match using class-map";

            // Type is an MO-Defined-Type
            type ipqos_CMapName;
        }

        // set Flow Monitor
        container fm-items {

            // Added containment as a singleton: Prefix=fm
            // Acquired From Package flow
            uses flow_SetMonitor-group;
        }
    }

    grouping flow_SetMonitor-group {

        // Rel-def from monitor
        container rsmonitor-items {

            // Added containment as a singleton: Prefix=rsmonitor
            // Acquired From Package flow
            uses flow_RsMonitor_source-group;
        }
    }

    grouping flow_HwProfile-group {
        leaf name {
            type string;
        }
        leaf description {
            type string;
        }
        leaf exportInterval {
            type uint32;
            default "100";
        }

        // Type is an MO-Defined-Type
        leaf sourcePort {
            description "Source L4 Port";

            // Type is an MO-Defined-Type
            type flow_L4Port;
        }
        leaf ipPacketIdShift {
            type uint8;
        }
        leaf burstIntervalShift {
            type uint8;
        }

        // Type is an MO-Defined-Type
        leaf mtu {
            description "MTU";

            // Type is an MO-Defined-Type
            type flow_Mtu;
        }

        container sngt-items {

            // Added containment as a singleton: Prefix=sngt
            // Acquired From Package flow
            uses flow_SeqNumGuessThreshold-group;
        }
        container plb-items {
            list PayloadLenBin-list {
                key "id";

                // Added containment: Prefix=plb
                // Acquired From Package flow
                uses flow_PayloadLenBin-group;
            }
        }
        container tohlb-items {
            list TCPOptHdrLenBin-list {
                key "id";

                // Added containment: Prefix=tohlb
                // Acquired From Package flow
                uses flow_TCPOptHdrLenBin-group;
            }
        }
        container rwsb-items {
            list ReceiveWindowSizeBin-list {
                key "id";

                // Added containment: Prefix=rwsb
                // Acquired From Package flow
                uses flow_ReceiveWindowSizeBin-group;
            }
        }
    }

    grouping flow_SeqNumGuessThreshold-group {
        leaf lo {
            type uint32;
        }
        leaf hi {
            type uint32;
        }
    }

    grouping flow_PayloadLenBin-group {
        leaf id {
            type uint8;
        }
        leaf description {
            type string;
        }

        // Type is an MO-Defined-Type
        leaf lo {
            description "Bin low value";

            // Type is an MO-Defined-Type
            type flow_PayloadLen;
        }

        // Type is an MO-Defined-Type
        leaf hi {
            description "Bin high value";

            // Type is an MO-Defined-Type
            type flow_PayloadLen;
        }
    }

    grouping flow_TCPOptHdrLenBin-group {
        leaf id {
            type uint8;
        }
        leaf description {
            type string;
        }

        // Type is an MO-Defined-Type
        leaf lo {
            description "Bin low value";

            // Type is an MO-Defined-Type
            type flow_TCPOptHdrLen;
        }

        // Type is an MO-Defined-Type
        leaf hi {
            description "Bin high value";

            // Type is an MO-Defined-Type
            type flow_TCPOptHdrLen;
        }
    }

    grouping flow_ReceiveWindowSizeBin-group {
        leaf id {
            type uint8;
        }
        leaf description {
            type string;
        }

        // Type is an MO-Defined-Type
        leaf lo {
            description "Bin low value";

            // Type is an MO-Defined-Type
            type flow_ReceiveWindowSize;
        }

        // Type is an MO-Defined-Type
        leaf hi {
            description "Bin high value";

            // Type is an MO-Defined-Type
            type flow_ReceiveWindowSize;
        }
    }

    grouping flow_FwdInstTarget-group {
        leaf slot {
            type uint8 {
                range "1..64";
            }
        }
        leaf asic {
            type uint8 {
                range "1..10";
            }
        }
        leaf slice {
            type uint8 {
                range "1..10";
            }
        }
        leaf exporterId {
            type uint32;
        }

        // Service Policy
        container sp-items {
            list ServicePolicy-list {
                key "direction";

                // Added containment: Prefix=sp
                // Acquired From Package flow
                uses flow_ServicePolicy-group;
            }
        }

        // Rel-def from hwProfile
        container rshwProfile-items {

            // Added containment as a singleton: Prefix=rshwProfile
            // Acquired From Package flow
            uses flow_RsHwProfile_source-group;
        }
    }

    grouping flow_ServicePolicy-group {

        // Type is an MO-Defined-Type
        leaf direction {
            description "Direction";

            // Type is an MO-Defined-Type
            type flow_Direction;
        }

        // Rel-def from pmap
        container rspmap-items {

            // Added containment as a singleton: Prefix=rspmap
            // Acquired From Package flow
            uses flow_RsPmap_source-group;
        }
    }

    grouping ngoam_Entity-group {

        // NGOAM Profile Object
        container profile-items {
            list Profile-list {
                key "profId";

                // Added containment: Prefix=profile
                // Acquired From Package ngoam
                uses ngoam_Profile-group;
            }
        }

        // NGOAM InstallACL Object
        container installacl-items {

            // Added containment as a singleton: Prefix=installacl
            // Acquired From Package ngoam
            uses ngoam_InstallAcl-group;
        }

        // NGOAM Authentication Object
        container authentication-items {

            // Added containment as a singleton: Prefix=authentication
            // Acquired From Package ngoam
            uses ngoam_Authentication-group;
        }
    }

    grouping ngoam_Profile-group {

        // Prof. ID
        // Type is an MO-Defined-Type
        leaf profId {
            description "Profile ID";

            // Type is an MO-Defined-Type
            type ngoam_ProfId;
        }

        // Description
        // Type is an MO-Defined-Type
        leaf desc {
            description "Description";

            // Type is an MO-Defined-Type
            type ngoam_Desc;
        }

        // dot1q
        // Type is an MO-Defined-Type
        leaf dot1q {
            description "dot1q";

            // Type is an MO-Defined-Type
            type ngoam_Dot1q;
        }

        // dot1q interface
        // Type is an MO-Defined-Type
        leaf dot1qIf {
            description "dot1q";

            // Type is an MO-Defined-Type
            type nw_IfId;
        }

        // hop
        // Type is an MO-Defined-Type
        leaf hop {
            description "hop count";

            // Type is an MO-Defined-Type
            type ngoam_Hop;
        }

        // Egress Interface
        // Type is an MO-Defined-Type
        leaf interface {
            description "Interface";

            // Type is an MO-Defined-Type
            type ngoam_Interface;
        }

        // Oam Channel
        // Type is an MO-Defined-Type
        leaf oamChannel {
            description "OAM channel type";

            // Type is an MO-Defined-Type
            type ngoam_OamChannel;
        }

        // Payload Pad
        // Type is an MO-Defined-Type
        leaf payloadPad {
            description "Payload padding pattern";

            // Type is an MO-Defined-Type
            type ngoam_PayloadPad;
        }

        // source port
        // Type is an MO-Defined-Type
        leaf srcPort {
            description "Source Port Range";

            // Type is an MO-Defined-Type
            type ngoam_Sport;
        }

        // NGOAM FlowFwd Object
        container flowfwd-items {

            // Added containment as a singleton: Prefix=flowfwd
            // Acquired From Package ngoam
            uses ngoam_FlowFwd-group;
        }
    }

    grouping ngoam_FlowFwd-group {
        leaf forward {
            type boolean;
        }

        // dot1q
        // Type is an MO-Defined-Type
        leaf dot1q {
            description "dot1q";

            // Type is an MO-Defined-Type
            type ngoam_Dot1qFlow;
        }
        leaf ipDest {
            type address_Ipv4;
        }
        leaf ipSrc {
            type address_Ipv4;
        }
        leaf ipv6Dest {
            type address_Ipv6;
        }
        leaf ipv6Src {
            type address_Ipv6;
        }
        leaf macDest {
            type address_Mac;
        }
        leaf macSrc {
            type address_Mac;
        }

        // port destination
        // Type is an MO-Defined-Type
        leaf portDest {
            description "TCP or UDP port destination";

            // Type is an MO-Defined-Type
            type ngoam_DestPort;
        }

        // port source
        // Type is an MO-Defined-Type
        leaf portSrc {
            description "TCP or UDP port source";

            // Type is an MO-Defined-Type
            type ngoam_SrcPort;
        }

        // Flow protocol number
        // Type is an MO-Defined-Type
        leaf protocol {
            description "Flow protocol number";

            // Type is an MO-Defined-Type
            type ngoam_Protocol;
        }
        leaf packet {
            type string;
        }
    }

    grouping ngoam_InstallAcl-group {
        leaf enabled {
            type boolean;
        }
    }

    grouping ngoam_Authentication-group {

        // Authentication key
        // Type is an MO-Defined-Type
        leaf key {
            description "Authentication key";

            // Type is an MO-Defined-Type
            type ngoam_AuthKey;
        }
    }

    grouping qosm_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Qos interface defintion. Holds information about qos
        // operated at a class level
        container class-items {
            list Class-list {
                config "false";
                key "qosGrp";

                // Added containment: Prefix=class
                // Acquired From Package qosm
                uses qosm_Class-group;
            }
        }

        // Qos interface defintion. Holds information about qos
        // operated at a interface level
        container if-items {
            list If-list {
                config "false";
                key "id";

                // Added containment: Prefix=if
                // Acquired From Package qosm
                uses qosm_If-group;
            }
        }

        // Holder for qos fabric class policy, each class describes
        // qos attributes like mtu, etc
        container classp-items {
            list Class-list {
                config "false";
                key "qosGrp";

                // Added containment: Prefix=classp
                // Acquired From Package qosp
                uses qosp_Class-group;
            }
        }

        // Qos classification rules based on dscp values
        container dscp-items {
            list DscpRule-list {
                key "from to qosGrp markDscp";

                // Added containment: Prefix=dscp
                // Acquired From Package qosp
                uses qosp_DscpRule-group;
            }
        }

        // Qos classification rules based on dot1p values
        container dot1p-items {
            list Dot1pRule-list {
                key "from to qosGrp markDscp";

                // Added containment: Prefix=dot1p
                // Acquired From Package qosp
                uses qosp_Dot1pRule-group;
            }
        }

        // Qos classification rules based on IP values
        container ip-items {
            list IpRule-list {
                config "false";
                key "addr";

                // Added containment: Prefix=ip
                // Acquired From Package qosp
                uses qosp_IpRule-group;
            }
        }
    }

    grouping qosm_Class-group {

        // QoS Group
        // Type is an MO-Defined-Type
        leaf qosGrp {
            config "false";
            description "ID";

            // Type is an MO-Defined-Type
            type qos_Prio;
        }

        // PPF instance node id
        // Type is an MO-Defined-Type
        leaf ppfInstId {
            config "false";
            description "PPF Instance ID";

            // Type is an MO-Defined-Type
            type qosm_PpfNodeId;
        }

        // PPF start node id
        // Type is an MO-Defined-Type
        leaf ppfStartId {
            config "false";
            description "PPF Start ID";

            // Type is an MO-Defined-Type
            type qosm_PpfNodeId;
        }

        // PPF run time state
        // Type is an MO-Defined-Type
        leaf stateId {
            config "false";
            description "State ID";

            // Type is an MO-Defined-Type
            type qosm_StateId;
        }
    }

    grouping qosm_If-group {

        // Interface ID
        // Type is an MO-Defined-Type
        leaf id {
            config "false";
            description "ID";

            // Type is an MO-Defined-Type
            type nw_IfId;
        }

        // IfClass information. Holds information about qos operated
        // at a per port per class level
        container class-items {
            list IfClass-list {
                config "false";
                key "id";

                // Added containment: Prefix=class
                // Acquired From Package qosm
                uses qosm_IfClass-group;
            }
        }
    }

    grouping qosm_IfClass-group {

        // Class id
        // Type is an MO-Defined-Type
        leaf id {
            config "false";
            description "ID";

            // Type is an MO-Defined-Type
            type qos_Prio;
        }
    }

    grouping qosp_Class-group {

        // Administrative state
        // Type is an MO-Defined-Type
        leaf admin {
            config "false";
            description "Admin State";

            // Type is an MO-Defined-Type
            type nw_AdminSt;
        }

        // mtu
        // Type is an MO-Defined-Type
        leaf mtu {
            config "false";
            description "MTU";

            // Type is an MO-Defined-Type
            type qosp_MTU;
        }

        // Class id
        // Type is an MO-Defined-Type
        leaf qosGrp {
            config "false";
            description "Priority";

            // Type is an MO-Defined-Type
            type qos_Prio;
        }

        // Qos Class operational state
        // Type is an MO-Defined-Type
        leaf operSt {
            config "false";
            description "Operational State";

            // Type is an MO-Defined-Type
            type qosp_OperSt;
        }

        // Rule operational state disabled reason
        // Type is an MO-Defined-Type
        leaf operStQual {
            config "false";
            description "Operational State Qualifier";

            // Type is an MO-Defined-Type
            type qosp_OperStQual;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Congestion policy holder, describes the congestion
        // parameters like congestion algo, ecn etc. These are
        // applied at a per class today in the system
        container cong-items {

            // Added containment as a singleton: Prefix=cong
            // Acquired From Package qosp
            uses qosp_Cong-group;
        }

        // Queue management policy holder, describes the queue
        // threshold parameters like management method, limts,
        // etc. These are applied at a per class today in the
        // system
        container queue-items {

            // Added containment as a singleton: Prefix=queue
            // Acquired From Package qosp
            uses qosp_Queue-group;
        }

        // Buffer policy holder, describes the minimum
        // guaranteed packet buffer reservations. These are
        // applied at a per class today in the system
        container buffer-items {

            // Added containment as a singleton: Prefix=buffer
            // Acquired From Package qosp
            uses qosp_Buffer-group;
        }

        // Schedule policy holder, describes the minimum
        // guaranteed packet buffer reservations. These are
        // applied at a per class today in the system
        container sched-items {

            // Added containment as a singleton: Prefix=sched
            // Acquired From Package qosp
            uses qosp_Sched-group;
        }
    }

    grouping qosp_Cong-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // What algorithm to use when congestion happens
        // Inherited From qos:ACong
        // Type is an MO-Defined-Type
        leaf algo {
            description "TBD";

            // Type is an MO-Defined-Type
            type qosp_CongAlgo;
        }

        // Explicit congestion notification (ecn)    ECN is disabled for FCS, thus this is implicit
        // Inherited From qos:ACong
        // Type is an MO-Defined-Type
        leaf ecn {
            config "false";
            description "TBD";

            // Type is an MO-Defined-Type
            type qosp_ECN;
        }
    }

    grouping qosp_Queue-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Queue control method (static/dynamic)
        // Inherited From qos:AQueue
        // Type is an MO-Defined-Type
        leaf meth {
            description "TBD";

            // Type is an MO-Defined-Type
            type qosp_CtrlMeth;
        }

        // queue limit, only applicable with static control
        // method
        // Inherited From qos:AQueue
        // Type is an MO-Defined-Type
        leaf limit {
            description "TBD";

            // Type is an MO-Defined-Type
            type qosp_QueueLimit;
        }
    }

    grouping qosp_Buffer-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Minimum buffers reserved in units of MTU
        // Inherited From qos:ABuffer
        // Type is an MO-Defined-Type
        leaf min {
            description "TBD";

            // Type is an MO-Defined-Type
            type qosp_MinBuf;
        }
    }

    grouping qosp_Sched-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }

        // Scheduling algorithm
        // Inherited From qos:ASched
        // Type is an MO-Defined-Type
        leaf meth {
            description "TBD";

            // Type is an MO-Defined-Type
            type qosp_SchedAlgo;
        }

        // If wrr, what is the bandwidth allocated (in %)
        // Inherited From qos:ASched
        // Type is an MO-Defined-Type
        leaf bw {
            description "TBD";

            // Type is an MO-Defined-Type
            type qosp_BwPercent;
        }
    }

    grouping qosp_DscpRule-group {

        // Range from
        // Type is an MO-Defined-Type
        leaf from {
            description "From";

            // Type is an MO-Defined-Type
            type qosp_Dscp;
        }

        // Range to
        // Type is an MO-Defined-Type
        leaf to {
            description "To";

            // Type is an MO-Defined-Type
            type qosp_Dscp;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Group Id
        // Inherited From qosp:ClassRule
        // Type is an MO-Defined-Type
        leaf qosGrp {
            description "Group ID";

            // Type is an MO-Defined-Type
            type qos_Prio;
        }

        // Mark Dscp
        // Inherited From qosp:ClassRule
        // Type is an MO-Defined-Type
        leaf markDscp {
            description "DSCP";

            // Type is an MO-Defined-Type
            type qosp_Dscp;
        }

        // Qos Class operational state
        // Inherited From qosp:ClassRule
        // Type is an MO-Defined-Type
        leaf operSt {
            config "false";
            description "Operational State";

            // Type is an MO-Defined-Type
            type qosp_OperSt;
        }

        // Rule operational state disabled reason
        // Inherited From qosp:ClassRule
        // Type is an MO-Defined-Type
        leaf operStQual {
            config "false";
            description "Operational State Qualifier";

            // Type is an MO-Defined-Type
            type qosp_OperStQual;
        }
    }

    grouping qosp_Dot1pRule-group {

        // Range from
        // Type is an MO-Defined-Type
        leaf from {
            description "From";

            // Type is an MO-Defined-Type
            type qosp_Dot1P;
        }

        // Range to
        // Type is an MO-Defined-Type
        leaf to {
            description "To";

            // Type is an MO-Defined-Type
            type qosp_Dot1P;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Group Id
        // Inherited From qosp:ClassRule
        // Type is an MO-Defined-Type
        leaf qosGrp {
            description "Group ID";

            // Type is an MO-Defined-Type
            type qos_Prio;
        }

        // Mark Dscp
        // Inherited From qosp:ClassRule
        // Type is an MO-Defined-Type
        leaf markDscp {
            description "DSCP";

            // Type is an MO-Defined-Type
            type qosp_Dscp;
        }

        // Qos Class operational state
        // Inherited From qosp:ClassRule
        // Type is an MO-Defined-Type
        leaf operSt {
            config "false";
            description "Operational State";

            // Type is an MO-Defined-Type
            type qosp_OperSt;
        }

        // Rule operational state disabled reason
        // Inherited From qosp:ClassRule
        // Type is an MO-Defined-Type
        leaf operStQual {
            config "false";
            description "Operational State Qualifier";

            // Type is an MO-Defined-Type
            type qosp_OperStQual;
        }
    }

    grouping qosp_IpRule-group {
        leaf addr {
            config "false";
            type address_Ip;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Group Id
        // Inherited From qosp:ClassRule
        // Type is an MO-Defined-Type
        leaf qosGrp {
            description "Group ID";

            // Type is an MO-Defined-Type
            type qos_Prio;
        }

        // Mark Dscp
        // Inherited From qosp:ClassRule
        // Type is an MO-Defined-Type
        leaf markDscp {
            description "DSCP";

            // Type is an MO-Defined-Type
            type qosp_Dscp;
        }

        // Qos Class operational state
        // Inherited From qosp:ClassRule
        // Type is an MO-Defined-Type
        leaf operSt {
            config "false";
            description "Operational State";

            // Type is an MO-Defined-Type
            type qosp_OperSt;
        }

        // Rule operational state disabled reason
        // Inherited From qosp:ClassRule
        // Type is an MO-Defined-Type
        leaf operStQual {
            config "false";
            description "Operational State Qualifier";

            // Type is an MO-Defined-Type
            type qosp_OperStQual;
        }
    }

    grouping sts_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Holds sts instance information
        container inst-items {

            // Added containment as a singleton: Prefix=inst
            // Acquired From Package sts
            uses sts_Inst-group;
        }
    }

    grouping sts_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Chain
        container chain-items {
            list Chain-list {
                config "false";
                key "id";

                // Added containment: Prefix=chain
                // Acquired From Package sts
                uses sts_Chain-group;
            }
        }

        // Node
        container node-items {
            list Node-list {
                config "false";
                key "id";

                // Added containment: Prefix=node
                // Acquired From Package sts
                uses sts_Node-group;
            }
        }
    }

    grouping sts_Chain-group {

        // Chain Id
        // Type is an MO-Defined-Type
        leaf id {
            config "false";
            description "ID";

            // Type is an MO-Defined-Type
            type sts_ChainId;
        }

        // A stage denotes a service offered in the chain
        container stage-items {
            list Stage-list {
                config "false";
                key "id";

                // Added containment: Prefix=stage
                // Acquired From Package sts
                uses sts_Stage-group;
            }
        }
    }

    grouping sts_Stage-group {

        // StageId
        // Type is an MO-Defined-Type
        leaf id {
            config "false";
            description "TBD";

            // Type is an MO-Defined-Type
            type sts_StageId;
        }

        // Stage controls
        // Type is an MO-Defined-Type
        leaf ctrl {
            config "false";
            description "TBD";

            // Type is an MO-Defined-Type
            type sts_StageCtrl;
        }

        // Virtual Node, represents a service node in a given
        // service chain
        container vnode-items {
            list VNode-list {
                config "false";
                key "id";

                // Added containment: Prefix=vnode
                // Acquired From Package sts
                uses sts_VNode-group;
            }
        }
    }

    grouping sts_VNode-group {

        // VNode Id
        // Type is an MO-Defined-Type
        leaf id {
            config "false";
            description "TBD";

            // Type is an MO-Defined-Type
            type sts_VNodeId;
        }

        // VNode controls
        // Type is an MO-Defined-Type
        leaf ctrl {
            config "false";
            description "TBD";

            // Type is an MO-Defined-Type
            type sts_VNodeCtrl;
        }

        // Desired slot order for ECMP
        // Type is an MO-Defined-Type
        leaf order {
            config "false";
            description "TBD";

            // Type is an MO-Defined-Type
            type sts_VNodeOrder;
        }

        // Node Weight
        // Type is an MO-Defined-Type
        leaf weight {
            config "false";
            description "TBD";

            // Type is an MO-Defined-Type
            type sts_VNodeWeight;
        }

        // Service node's vrf
        // Type is an MO-Defined-Type
        leaf vrf {
            config "false";
            description "TBD";

            // Type is an MO-Defined-Type
            type l3_VrfName;
        }
        leaf vrfEncap {
            type string;
        }
        leaf ip {
            config "false";
            type address_Ip;
        }
        leaf rwMac {
            config "false";
            type address_Mac;
        }

        // Network reachability state
        // Type is an MO-Defined-Type
        leaf nwReachSt {
            config "false";
            description "TBD";

            // Type is an MO-Defined-Type
            type sts_NwReachSt;
        }
        container extin-items {
            list ExtIn-list {
                config "false";
                key "encap";

                // Added containment: Prefix=extin
                // Acquired From Package sts
                uses sts_ExtIn-group;
            }
        }
        container extout-items {
            list ExtOut-list {
                config "false";
                key "encap";

                // Added containment: Prefix=extout
                // Acquired From Package sts
                uses sts_ExtOut-group;
            }
        }
        container fabin-items {
            list FabIn-list {
                config "false";
                key "encap";

                // Added containment: Prefix=fabin
                // Acquired From Package sts
                uses sts_FabIn-group;
            }
        }
        container fabinrev-items {
            list FabInRev-list {
                config "false";
                key "encap";

                // Added containment: Prefix=fabinrev
                // Acquired From Package sts
                uses sts_FabInRev-group;
            }
        }
        container fabout-items {
            list FabOut-list {
                config "false";
                key "encap";

                // Added containment: Prefix=fabout
                // Acquired From Package sts
                uses sts_FabOut-group;
            }
        }
        container faboutrev-items {
            list FabOutRev-list {
                config "false";
                key "encap";

                // Added containment: Prefix=faboutrev
                // Acquired From Package sts
                uses sts_FabOutRev-group;
            }
        }

        // Rel-def from nodeAtt
        container rsnodeAtt-items {

            // Added containment as a singleton: Prefix=rsnodeAtt
            // Acquired From Package sts
            uses sts_RsNodeAtt_source-group;
        }
    }

    grouping sts_Node-group {

        // NodeId
        // Type is an MO-Defined-Type
        leaf id {
            config "false";
            description "TBD";

            // Type is an MO-Defined-Type
            type sts_NodeId;
        }

        // Node controls
        // Type is an MO-Defined-Type
        leaf ctrl {
            config "false";
            description "TBD";

            // Type is an MO-Defined-Type
            type sts_NodeCtrl;
        }

        // Infra vrf
        // Type is an MO-Defined-Type
        leaf vrf {
            config "false";
            description "TBD";

            // Type is an MO-Defined-Type
            type l3_VrfName;
        }
        leaf tepDst {
            config "false";
            type address_Ip;
        }
    }

    grouping telemetry_Entity-group {

        // Type is an MO-Defined-Type
        leaf adminSt {
            description "TBD";

            // Type is an MO-Defined-Type
            type telemetry_AdminState;
        }

        // certificate
        container certificate-items {

            // Added containment as a singleton: Prefix=certificate
            // Acquired From Package telemetry
            uses telemetry_Certificate-group;
        }

        // sensor-groups
        container sensor-items {
            list SensorGroup-list {
                key "id";

                // Added containment: Prefix=sensor
                // Acquired From Package telemetry
                uses telemetry_SensorGroup-group;
            }
        }

        // destination-groups
        container dest-items {
            list DestGroup-list {
                key "id";

                // Added containment: Prefix=dest
                // Acquired From Package telemetry
                uses telemetry_DestGroup-group;
            }
        }

        // subscriptions
        container subs-items {
            list Subscription-list {
                key "id";

                // Added containment: Prefix=subs
                // Acquired From Package telemetry
                uses telemetry_Subscription-group;
            }
        }
    }

    grouping telemetry_Certificate-group {

        // Type is an MO-Defined-Type
        leaf filename {
            description "TBD";

            // Type is an MO-Defined-Type
            type os_OsString;
        }

        // Type is an MO-Defined-Type
        leaf hostname {
            description "TBD";

            // Type is an MO-Defined-Type
            type os_OsString;
        }
    }

    grouping telemetry_SensorGroup-group {
        leaf id {
            type string;
        }

        // Type is an MO-Defined-Type
        leaf dataSrc {
            description "TBD";

            // Type is an MO-Defined-Type
            type telemetry_DataSource;
        }
        container path-items {
            list SensorPath-list {
                key "path";

                // Added containment: Prefix=path
                // Acquired From Package telemetry
                uses telemetry_SensorPath-group;
            }
        }
    }

    grouping telemetry_SensorPath-group {
        leaf path {
            type string;
        }
        leaf filterCondition {
            type string;
        }
        leaf excludeFilter {
            type string;
        }

        // Type is an MO-Defined-Type
        leaf secondaryPath {
            description "TBD";

            // Type is an MO-Defined-Type
            type reln_Dn;
        }
        leaf secondaryGroup {
            type uint64;
        }

        // Type is an MO-Defined-Type
        leaf depth {
            description "TBD";

            // Type is an MO-Defined-Type
            type telemetry_RetrieveDepth;
        }
        container include-items {
            list IncludeFilter-list {
                key "filter";

                // Added containment: Prefix=include
                // Acquired From Package telemetry
                uses telemetry_IncludeFilter-group;
            }
        }
    }

    grouping telemetry_IncludeFilter-group {
        leaf filter {
            type string;
        }
    }

    grouping telemetry_DestGroup-group {
        leaf id {
            type string;
        }
        container addr-items {
            list Dest-list {
                key "addr port";

                // Added containment: Prefix=addr
                // Acquired From Package telemetry
                uses telemetry_Dest-group;
            }
        }
    }

    grouping telemetry_Dest-group {
        leaf addr {
            type address_Ip;
        }
        leaf port {
            type uint16;
        }

        // Need equivalent type for YANG telemetry-stream-protocol in DME
        // Type is an MO-Defined-Type
        leaf proto {
            description "TBD";

            // Type is an MO-Defined-Type
            type telemetry_Protocol;
        }

        // No equivalent property in YANG
        // Type is an MO-Defined-Type
        leaf enc {
            description "TBD";

            // Type is an MO-Defined-Type
            type telemetry_Encoding;
        }
    }

    grouping telemetry_Subscription-group {
        leaf id {
            type uint64;
        }

        // Rel-def from SensorGroupRel
        container rssensorGroupRel-items {

            // Abstract containment of rssensorGroupRel derived from telemetry:Subscription
            list RsSensorGroupRel-list {
                key "tDn";

                // Added containment: Prefix=rssensorGroupRel
                // Acquired From Package telemetry
                uses telemetry_RsSensorGroupRel_source-group;
            }
        }

        // Rel-def from DestGroupRel
        container rsdestGroupRel-items {

            // Abstract containment of rsdestGroupRel derived from telemetry:Subscription
            list RsDestGroupRel-list {
                key "tDn";

                // Added containment: Prefix=rsdestGroupRel
                // Acquired From Package telemetry
                uses telemetry_RsDestGroupRel_source-group;
            }
        }
    }

    grouping topoctrl_Entity-group {

        // From Interface naming:Named
        // Inherited From naming:NamedObject
        // Modified by Override: pol:Obj->name
        // Type is an MO-Defined-Type
        leaf name {
            description "Name";

            // Type is an MO-Defined-Type
            type naming_Name {
                length "0..64";
            }
        }

        // Fabric load balance policy
        container lbp-items {

            // Added containment as a singleton: Prefix=lbp
            // Acquired From Package topoctrl
            uses topoctrl_LbP-group;
        }

        // Shard redundancy policy
        container shrdnp-items {

            // Added containment as a singleton: Prefix=shrdnp
            // Acquired From Package topoctrl
            uses topoctrl_ShardRdnP-group;
        }

        // Virtual Domain
        container virtdom-items {

            // Added containment as a singleton: Prefix=virtdom
            // Acquired From Package topoctrl
            uses topoctrl_VirtDom-group;
        }

        // Fabric vxlan policy
        container vxlanp-items {

            // Added containment as a singleton: Prefix=vxlanp
            // Acquired From Package topoctrl
            uses topoctrl_VxlanP-group;
        }
    }

    grouping topoctrl_LbP-group {

        // Load balance mode in the fabric
        // Type is an MO-Defined-Type
        leaf mode {
            config "false";
            description "Mode";

            // Type is an MO-Defined-Type
            type topoctrl_LbMode;
        }

        // Dynamic load balancing mode in the fabric
        // Type is an MO-Defined-Type
        leaf dlbMode {
            config "false";
            description "Dynamic Load Balancing Mode";

            // Type is an MO-Defined-Type
            type topoctrl_DLbMode;
        }

        // Prioritization mode in the fabric
        // Type is an MO-Defined-Type
        leaf pri {
            config "false";
            description "Prioritization Mode";

            // Type is an MO-Defined-Type
            type topoctrl_Prioritization;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping topoctrl_ShardRdnP-group {

        // Redundancy factor, determines the number of repliacated
        // copies of the route table that are kept in spine
        // Type is an MO-Defined-Type
        leaf factor {
            config "false";
            description "Factor";

            // Type is an MO-Defined-Type
            type topoctrl_ShardRdnFac;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping topoctrl_VirtDom-group {
        leaf mcastAddr {
            config "false";
            type address_Ip;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Encap blocks
        container from-items {
            list EncapBlk-list {
                key "from to";

                // Added containment: Prefix=from
                // Acquired From Package topoctrl
                uses topoctrl_EncapBlk-group;
            }
        }
    }

    grouping topoctrl_EncapBlk-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Comp
        // Type is an MO-Defined-Type
        leaf descr {
            description "Description";

            // Type is an MO-Defined-Type
            type naming_Descr;
        }
        leaf from {
            type string;
        }
        leaf to {
            type string;
        }
    }

    grouping topoctrl_VxlanP-group {

        // Vxlan udp port in the fabric
        // Type is an MO-Defined-Type
        leaf udpPort {
            config "false";
            description "Udp Port";

            // Type is an MO-Defined-Type
            type l4_Port;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping track_Entity-group {

        // This object represents object of track.
        // The object tracking monitors the status of the tracked objects
        // and communicates any changes made to interested clients.
        // Each tracked object is identified by a unique number
        // (track:Object.id) that clients can use to configure the action
        // to take when a tracked object changes state.
        // Object types that can be tracked:
        // * Interface line protocol state: Tracks whether the line
        // protocol state is UP or Down.
        // * Interface IPv4/IPv6 routing state: Tracks whether the interface
        // has an IPv4 address and if IPv4 routing is enabled and active.
        // * IPv4/IPv6 route reachability: Tracks whether an IPv4 route
        // exists and is reachable from the local switch.
        // * Object track list: Tracks combined states of multiple objects.
        // Capabilities supported: boolean-and, boolean-or,
        // threshold-percentage, threshold-weight.
        // * Object tracking of IP SLA.
        // Specify track:Object.id
        container object-items {
            list Object-list {
                key "id";

                // Added containment: Prefix=object
                // Acquired From Package track
                uses track_Object-group;
            }
        }
    }

    grouping track_Object-group {

        // Track Object ID.
        // Each instance is identified by a unique number,
        // the object ID. Each instance is a parent of only one
        // of 'track:If', 'track:List',
        // 'track:IpRoute' or 'track:IpSla'
        // Type is an MO-Defined-Type
        leaf id {
            description "Track object ID";

            // Type is an MO-Defined-Type
            type track_TrackId;
        }
        leaf clients {
            config "false";
            type uint16;
        }

        // Object tracking for an interface, supports Ethernet,
        // subinterfaces, port-channels, loopback interfaces, and
        // VLAN interfaces. Either the interface line protocol state or
        // the interface IP routing state. When IP routing state is
        // tracked, these conditions are required for the object to be UP:
        // * IP routing must be enabled and active on the interface.
        // * The interface line-protocol state must be UP.
        // * The interface IP address must be known.
        // If all three conditions are not met, IP routing state is Down.
        container if-items {

            // Added containment as a singleton: Prefix=if
            // Acquired From Package track
            uses track_If-group;
        }

        // IP route track object.
        // Tracks whether an IPV4/IPV6 route exists and is reachable from
        // the local switch
        container iprt-items {

            // Added containment as a singleton: Prefix=iprt
            // Acquired From Package track
            uses track_IpRoute-group;
        }

        // IP SLA track object.
        // Object tracking of IP SLAs operations allow clients to
        // track the output from IP SLAs objects and
        // use this information to trigger an action.
        // Two aspects of IP SLAs can be tracked: state and reachability.
        // For state, if the return code is OK, then the track state is UP;
        // if the return code is not OK, then the track state is Down.
        // For reachability, if the return code is OK or OverThreshold, reachability is UP;
        // if not OK, reachability is Down.
        container ipsla-items {

            // Added containment as a singleton: Prefix=ipsla
            // Acquired From Package track
            uses track_IpSla-group;
        }

        // An object track list allows User to track the combined states
        // of multiple objects. Object track lists support the following
        // capabilities:
        // * Boolean "and" function: Each object defined within the track
        // list must be in an UP state so that the track list object
        // can become UP.
        // track:List.type should be specified as 'and'
        // * Boolean "or" function: At least one object defined within the
        // track list must be in UP state so that the tracked object
        // can become UP.
        // track:List.type should be specified as 'or'
        // * Threshold percentage: The percentage of UP objects in the
        // tracked list must be greater than the configured UP
        // threshold for the tracked list to be in the UP state. If the
        // percentage of Down objects in the tracked list is above the
        // configured track list Down threshold, the tracked list is
        // marked as Down.
        // track:List.type should be specified as 'percentage'. The value
        // for  'percentageUp' and 'percentageDown'
        // * Threshold weight: Assign a weight value to each object in the
        // tracked list, and a weight threshold for the track list. If
        // the combined weights of all UP objects exceeds the track list
        // weight UP threshold, the track list is in an UP state. If the
        // combined weights of all the Down objects exceeds the track list
        // weight Down threshold, the track list is in the Down state.
        // track:List.type should be specified as 'weight'. The value for
        // 'weightUp' and 'weightDown'.
        // Mo for List type track
        container list-items {

            // Added containment as a singleton: Prefix=list
            // Acquired From Package track
            uses track_List-group;
        }
    }

    grouping track_If-group {

        // Interface ID to be tracked.
        // This specifies the name of the object tracking interface,
        // examples: 'eth1/1', 'eth1/1.1', 'po10', 'lo0'.
        // The interface MO must be present in objstore to configure
        // this else an error will be reported.
        // Type is an MO-Defined-Type
        leaf id {
            description "Interface to track";

            // Type is an MO-Defined-Type
            type nw_IfId;
        }

        // Interface protocol type that an object can track
        // Type is an MO-Defined-Type
        leaf protocolType {
            description "Protocol type for interface object";

            // Type is an MO-Defined-Type
            type track_IntfProtocolType;
        }
    }

    grouping track_IpRoute-group {

        // IPVX Address family of the route that is to be configured
        // Type is an MO-Defined-Type
        leaf af {
            description "Address family";

            // Type is an MO-Defined-Type
            type track_Af;
        }
        leaf prefix {
            type address_Ip;
        }

        // This specifies IP Route State
        // Type is an MO-Defined-Type
        leaf routeState {
            description "Route State";

            // Type is an MO-Defined-Type
            type track_RouteState;
        }
        leaf vrf {
            type string;
        }

        // This specifies the process owning the route
        // Type is an MO-Defined-Type
        leaf routeOwner {
            description "Owner of the route";

            // Type is an MO-Defined-Type
            type track_RouteOwner;
        }
    }

    grouping track_IpSla-group {
        leaf probeId {
            type uint32 {
                range "1..2147483647";
            }
        }

        // SLA Probe States
        // Type is an MO-Defined-Type
        leaf probeState {
            description "SLA reachability/state type";

            // Type is an MO-Defined-Type
            type track_ProbeState;
        }
    }

    grouping track_List-group {

        // Type of list object.
        // Only 'boolean-and' object can be changed to 'boolean-or'
        // and vice versa is possible. Any other type of object can't
        // be modified to some other type.
        // Type is an MO-Defined-Type
        leaf type {
            description "Type of list object";

            // Type is an MO-Defined-Type
            type track_ListObj;
        }
        leaf percentageUp {
            type uint16 {
                range "0..100";
            }
            default "1";
        }
        leaf percentageDown {
            type uint16 {
                range "0..100";
            }
            default "0";
        }
        leaf weightUp {
            type uint16 {
                range "0..255";
            }
            default "1";
        }
        leaf weightDown {
            type uint16 {
                range "0..255";
            }
            default "0";
        }

        // track list member objects, object-id is a naming property here
        container obj-items {
            list Member-list {
                key "id";

                // Added containment: Prefix=obj
                // Acquired From Package track
                uses track_Member-group;
            }
        }
    }

    grouping track_Member-group {

        // ID of track-list member
        // Type is an MO-Defined-Type
        leaf id {
            description "Track ID of object to be tracked";

            // Type is an MO-Defined-Type
            type track_TrackId;
        }
        leaf weight {
            type uint16 {
                range "1..255";
            }
            default "10";
        }
        leaf not {
            type boolean;
            default "true";
        }
    }

    grouping udld_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This class shall store the global configuration
        // for a running UDLD instance
        container inst-items {

            // Added containment as a singleton: Prefix=inst
            // Acquired From Package udld
            uses udld_Inst-group;
        }
    }

    grouping udld_Inst-group {

        // aggressive mode
        // Type is an MO-Defined-Type
        leaf aggressive {
            description "Global Aggressive Mode";

            // Type is an MO-Defined-Type
            type udld_AdminSt;
        }

        // probe message interval
        // Type is an MO-Defined-Type
        leaf msgIntvl {
            description "Probe Message Interval";

            // Type is an MO-Defined-Type
            type udld_MsgIntvl;
        }
        leaf error {
            config "false";
            type uint64;
            default "0";
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
        container physif-items {
            list PhysIf-list {
                key "id";

                // Added containment: Prefix=physif
                // Acquired From Package udld
                uses udld_PhysIf-group;
            }
        }
    }

    grouping udld_PhysIf-group {

        // aggressive mode
        // Type is an MO-Defined-Type
        leaf aggressive {
            description "Interface Aggressive Mode";

            // Type is an MO-Defined-Type
            type udld_AdminSt;
        }

        // bidirectional detection
        // Type is an MO-Defined-Type
        leaf biDirDetect {
            description "Bidirectional Detection Enabled";

            // Type is an MO-Defined-Type
            type udld_PortEnable;
        }

        // port type is fiber or non-fiber/copper
        // Type is an MO-Defined-Type
        leaf fiber {
            config "false";
            description "Fiber Port";

            // Type is an MO-Defined-Type
            type udld_OperSt;
        }

        // Link state
        // Type is an MO-Defined-Type
        leaf linkState {
            config "false";
            description "Link State";

            // Type is an MO-Defined-Type
            type udld_OperSt;
        }

        // current bidirectional state
        // Type is an MO-Defined-Type
        leaf currBiDirState {
            config "false";
            description "Current Bidirectional State";

            // Type is an MO-Defined-Type
            type udld_NeighborState;
        }

        // bidirectional detection state
        // Type is an MO-Defined-Type
        leaf biDirDetectState {
            config "false";
            description "Bidirectional Detection State";

            // Type is an MO-Defined-Type
            type udld_NeighborState;
        }

        // UDLD FSM state
        // Type is an MO-Defined-Type
        leaf fsmState {
            config "false";
            description "FSM State";

            // Type is an MO-Defined-Type
            type udld_FsmState;
        }
        leaf deepPktInspCnt {
            config "false";
            type uint64;
            default "0";
        }
        leaf pktMismatchCnt {
            config "false";
            type uint64;
            default "0";
        }
        leaf pktDropCnt {
            config "false";
            type uint64;
            default "0";
        }
        leaf error {
            config "false";
            type uint64;
            default "0";
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }
        container ptimest-items {
            list PktTs-list {
                key "dir";

                // Added containment: Prefix=ptimest
                // Acquired From Package udld
                uses udld_PktTs-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping udld_PktTs-group {

        // Send/Recv direction
        // Type is an MO-Defined-Type
        leaf dir {
            description "Packet Direction";

            // Type is an MO-Defined-Type
            type udld_PktDirection;
        }
        leaf Total {
            config "false";
            type uint64;
            default "0";
        }
        leaf Probe {
            config "false";
            type uint64;
            default "0";
        }
        leaf Echo {
            config "false";
            type uint64;
            default "0";
        }
        leaf Flush {
            config "false";
            type uint64;
            default "0";
        }
    }

    grouping acllog_Entity-group {

        // Acllog instance MO
        container inst-items {

            // Added containment as a singleton: Prefix=inst
            // Acquired From Package acllog
            uses acllog_Inst-group;
        }
    }

    grouping acllog_Inst-group {

        container log-items {

            // Added containment as a singleton: Prefix=log
            // Acquired From Package acllog
            uses acllog_LogCache-group;
        }
    }

    grouping acllog_LogCache-group {
        leaf interval {
            type uint64 {
                range "5..86400";
            }
            default "300";
        }
        leaf matchLevel {
            type uint8 {
                range "0..7";
            }
            default "6";
        }
        leaf logLevel {
            type uint8 {
                range "0..7";
            }
            default "2";
        }
    }

    grouping aib_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Domain (vrf) information
        container dom-items {
            list Dom-list {
                key "name";

                // Added containment: Prefix=dom
                // Acquired From Package aib
                uses aib_Dom-group;
            }
        }
    }

    grouping aib_Dom-group {

        // Inherited From nw:Conn
        // Modified by Override: nw:CpDom->name
        // Type is an MO-Defined-Type
        leaf name {
            description "Name";

            // Type is an MO-Defined-Type
            type naming_Name {
                length "1..64";
            }
        }
        container db-items {
            list Db-list {
                config "false";
                key "type";

                // Added containment: Prefix=db
                // Acquired From Package aib
                uses aib_Db-group;
            }
        }
    }

    grouping aib_Db-group {

        // Type of the repository
        // Type is an MO-Defined-Type
        leaf type {
            config "false";
            description "Database Type";

            // Type is an MO-Defined-Type
            type aib_DbT;
        }

        // Inherited From nw:Conn
        // Modified by Override: nw:Db->name
        // Type is an MO-Defined-Type
        leaf name {
            description "Name";

            // Type is an MO-Defined-Type
            type naming_Name {
                length "1..64";
            }
        }

        // Adjacency database record
        container adj-items {
            list Adj-list {
                config "false";
                key "addr if";

                // Added containment: Prefix=adj
                // Acquired From Package aib
                uses aib_Adj-group;
            }
        }
    }

    grouping aib_Adj-group {
        leaf addr {
            config "false";
            type address_Ip;
        }

        // Interface
        // Type is an MO-Defined-Type
        leaf if {
            config "false";
            description "Interface ID";

            // Type is an MO-Defined-Type
            type nw_IfId;
        }

        // Inherited From nw:Conn
        // Modified by Override: nw:Db->name
        // Type is an MO-Defined-Type
        leaf name {
            description "Name";

            // Type is an MO-Defined-Type
            type naming_Name {
                length "1..64";
            }
        }

        // Aadjacency ownership record
        container owner-items {
            list AdjOwner-list {
                config "false";
                key "owner";

                // Added containment: Prefix=owner
                // Acquired From Package aib
                uses aib_AdjOwner-group;
            }
        }
    }

    grouping aib_AdjOwner-group {

        // Owner's name
        // Type is an MO-Defined-Type
        leaf owner {
            config "false";
            description "Adj Owner";

            // Type is an MO-Defined-Type
            type aib_Owner;
        }

        // Adjacency uptime
        // Type is an MO-Defined-Type
        leaf updateTs {
            config "false";
            description "Update TimeStamp";

            // Type is an MO-Defined-Type
            type aib_UpdateTs;
        }

        // Preference
        // Type is an MO-Defined-Type
        leaf pref {
            config "false";
            description "Preference";

            // Type is an MO-Defined-Type
            type aib_Pref;
        }
        leaf mac {
            config "false";
            type address_Mac;
        }

        // L2 interface
        // Type is an MO-Defined-Type
        leaf l2If {
            config "false";
            description "L2 Interface ID";

            // Type is an MO-Defined-Type
            type nw_IfId;
        }
        leaf active {
            config "false";
            type boolean;
        }

        // Inherited From nw:Conn
        // Modified by Override: nw:DbRec->name
        // Type is an MO-Defined-Type
        leaf name {
            description "Name";

            // Type is an MO-Defined-Type
            type naming_Name {
                length "1..64";
            }
        }
    }

    // Has Polymorphic containment of abstract object l2:Dom
    grouping bd_Entity-group {
        leaf descr {
            config "false";
            type string;
        }

        // If false, value is explicitly set globally for all SVIs
        // Type is an MO-Defined-Type
        leaf sysDefaultSVIAutostate {
            description "Disable/enable autoState for SVI interface";

            // Type is an MO-Defined-Type
            type bd_DefaultSVIAutoState;
        }

        // This object holds vlan config information
        container vlanconfig-items {
            list VlanConfig-list {
                key "accEncap";

                // Added containment: Prefix=vlanconfig
                // Acquired From Package l2
                uses l2_VlanConfig-group;
            }
        }

        // Layer2 Bridge-domain. Domain with regular ports and/or
        // epg-vlans as members.
        // Polymorphic containment of derivative object l2:BD (from l2:Dom)
        container bd-items {

            // Abstract containment of l2:BD derived from l2:Dom
            list BD-list {
                key "fabEncap";

                // Added containment: Prefix=bd
                // Acquired From Package l2
                uses l2_BD-group;
            }
        }

        // 802.1q Vlan
        // Polymorphic containment of derivative object vlan:CktEp (from l2:Dom)
        container vlan-items {

            // Abstract containment of vlan:CktEp derived from l2:Dom
            list CktEp-list {
                key "encap";

                // Added containment: Prefix=vlan
                // Acquired From Package vlan
                uses vlan_CktEp-group;
            }
        }

        // Vxlan circuit
        // Polymorphic containment of derivative object vxlan:CktEp (from l2:Dom)
        container vxlan-items {

            // Abstract containment of vxlan:CktEp derived from l2:Dom
            list CktEp-list {
                key "encap";

                // Added containment: Prefix=vxlan
                // Acquired From Package vxlan
                uses vxlan_CktEp-group;
            }
        }
    }

    grouping l2_VlanConfig-group {
        leaf accEncap {
            type string;
        }
    }

    grouping l2_BD-group {
        leaf fabEncap {
            type string;
        }
        leaf accEncap {
            type string;
        }

        // This represents the parameter used by the node
        // (i.e. Leaf) for enabling forwarding modes (route
        // or bridge or both). Default is enable both
        // Type is an MO-Defined-Type
        leaf fwdMode {
            description "Forwarding Mode";

            // Type is an MO-Defined-Type
            type l2_FwdMode;
        }

        // This represents the parameter used by the node
        // (i.e. Leaf) for enabling classical bridging or
        // bridging with IP. Default is bridge with IP
        // Type is an MO-Defined-Type
        leaf bridgeMode {
            description "Bridging Mode";

            // Type is an MO-Defined-Type
            type l2_BridgeMode;
        }

        // Forwarding controls
        // Type is an MO-Defined-Type
        leaf fwdCtrl {
            description "Forwarding Controls";

            // Type is an MO-Defined-Type
            type l2_FwdCtrl;
        }

        // This represents the parameter used by the node
        // (i.e. Leaf) for forwarding data for unknown
        // mac unicast destination, this is valid only in
        // classical bridging case
        // Type is an MO-Defined-Type
        leaf unkMacUcastAct {
            description "Unknown MAC Unicast Destination Action";

            // Type is an MO-Defined-Type
            type l2_UnkMacUcastAct;
        }

        // This represents the parameter used by the node
        // (i.e. Leaf) for forwarding data for unknown
        // multicast destination
        // Type is an MO-Defined-Type
        leaf unkMcastAct {
            description "Unknown Multicast Destination Action";

            // Type is an MO-Defined-Type
            type l2_UnkMcastAct;
        }

        // It represents the default classId for the unknown
        // unicast traffic terminating on this bd.
        // Type is an MO-Defined-Type
        leaf pcTag {
            description "PC Tag";

            // Type is an MO-Defined-Type
            type actrl_PcTag;
        }

        // Ep operational state
        // Type is an MO-Defined-Type
        leaf epOperSt {
            config "false";
            description "EP Operational State";

            // Type is an MO-Defined-Type
            type epm_BdOperSt;
        }
        leaf bdDefDn {
            type string;
        }

        // Controller Id
        // Type is an MO-Defined-Type
        leaf controllerId {
            config "false";
            description "Controller ID for Vlan";

            // Type is an MO-Defined-Type
            type aggregate_ControllerIdBitmap;
        }

        // Media
        // Type is an MO-Defined-Type
        leaf media {
            description "Media";

            // Type is an MO-Defined-Type
            type l2_BdMedia;
        }

        // BdState
        // Type is an MO-Defined-Type
        leaf BdState {
            description "BdState";

            // Type is an MO-Defined-Type
            type l2_DomAdminSt;
        }
        leaf BdOperName {
            config "false";
            type string;
        }

        // Inherited From nw:Conn
        // Modified by Override: nw:FwDom->name
        // Type is an MO-Defined-Type
        leaf name {
            description "Name";

            // Type is an MO-Defined-Type
            type naming_Name {
                length "1..64";
            }
        }

        // domain type
        // Inherited From l2:Dom
        // Type is an MO-Defined-Type
        leaf type {
            description "Type";

            // Type is an MO-Defined-Type
            type l2_DomType;
        }

        // domain id
        // Inherited From l2:Dom
        // Type is an MO-Defined-Type
        leaf id {
            description "Domain ID";

            // Type is an MO-Defined-Type
            type l2_DomId;
        }

        // Internal domain id
        // Inherited From l2:Dom
        // Type is an MO-Defined-Type
        leaf hwId {
            config "false";
            description "Hardware Resource ID";

            // Type is an MO-Defined-Type
            type l2_DomId;
        }

        // Vlan mode
        // Inherited From l2:Dom
        // Type is an MO-Defined-Type
        leaf mode {
            description "Mode";

            // Type is an MO-Defined-Type
            type l2_DomMode;
        }

        // admin state
        // Inherited From l2:Dom
        // Type is an MO-Defined-Type
        leaf adminSt {
            description "Admin State";

            // Type is an MO-Defined-Type
            type l2_DomAdminSt;
        }

        // oper state
        // Inherited From l2:Dom
        // Type is an MO-Defined-Type
        leaf operSt {
            config "false";
            description "Operational State";

            // Type is an MO-Defined-Type
            type l2_DomOperSt;
        }
        leaf createTs {
            config "false";
            type uint64;
        }

        // Controls
        // Inherited From l2:Dom
        // Type is an MO-Defined-Type
        leaf ctrl {
            description "Controls";

            // Type is an MO-Defined-Type
            type l2_DomCtrl;
        }

        // End-Point retention policy identifying the duration
        // of how long information is kept about remote end-point.
        // This is expressed through a set of triggering and
        // aging control parameters
        container epret-items {

            // Added containment as a singleton: Prefix=epret
            // Acquired From Package l2
            uses l2_EpRetPol-group;
        }

        // Multicast group entity, this refers to the multicast
        // group entity that each tenant's bridge domain uses to
        // flood its traffic over the fabric
        container fmgrp-items {
            list Grp-list {
                key "addr";

                // Added containment: Prefix=fmgrp
                // Acquired From Package fmcast
                uses fmcast_Grp-group;
            }
        }

        // Abstraction of epm database
        container db-items {
            list Db-list {
                config "false";
                key "type";

                // Added containment: Prefix=db
                // Acquired From Package epm
                uses epm_Db-group;
            }
        }

        // 802.1q Vlan
        container vlan-items {
            list CktEp-list {
                key "encap";

                // Added containment: Prefix=vlan
                // Acquired From Package vlan
                uses vlan_CktEp-group;
            }
        }

        // Vxlan circuit
        container vxlan-items {
            list CktEp-list {
                key "encap";

                // Added containment: Prefix=vxlan
                // Acquired From Package vxlan
                uses vxlan_CktEp-group;
            }
        }

        // Rel-def from extBD
        container rsextBD-items {

            // Abstract containment of rsextBD derived from l2:BD
            list RsExtBD-list {
                key "tDn";

                // Added containment: Prefix=rsextBD
                // Acquired From Package l2
                uses l2_RsExtBD_source-group;
            }
        }

        // Rel-def target from domIfConn
        // Inherited From l2:BD
        container rtfvDomIfConn-items {

            // Abstract containment of rtfvDomIfConn derived from l2:Dom
            list RtFvDomIfConn-list {
                config "false";
                key "tDn";

                // Added containment: Prefix=rtfvDomIfConn
                // Acquired From Package fv
                uses fv_RtFvDomIfConn_target-group;
            }
        }

        container dbgVlanStats-items {

            // Added containment as a singleton: Prefix=dbgVlanStats
            // Acquired From Package l2
            uses l2_VlanStats-group;
        }
    }

    grouping l2_EpRetPol-group {

        // This represents aging interval for all local
        // endpoints learned in this BD. Once we reach
        // 75% of this interval is reached, 3 ARP requests
        // are sent to check for EP existence. If there is
        // no response, the ep is aged out
        // Type is an MO-Defined-Type
        leaf localEpAgeIntvl {
            description "Local Ep Age Interval";

            // Type is an MO-Defined-Type
            type l2_LocalEpAgeIntvl;
        }

        // This represents aging interval for all remote
        // endpoints learned in this BD. The remote endpoints
        // are learned through conversational learning
        // Type is an MO-Defined-Type
        leaf remoteEpAgeIntvl {
            description "Remote Ep Age Interval";

            // Type is an MO-Defined-Type
            type l2_RemoteEpAgeIntvl;
        }

        // Represents aging interval for bounce entry
        // @@@ Used when the Ep (VM) is moving from one TOR
        // @@@ to another TOR. Ep is marked as "bouncing" for the
        // @@@ specified age interval and is deleted afterwards
        // Type is an MO-Defined-Type
        leaf bounceAgeIntvl {
            description "Bounce Aging Interval";

            // Type is an MO-Defined-Type
            type l2_BounceEpAgeIntvl;
        }

        // Bounce trigger, install the bounce entry using
        // RARP being flooded in the fabric or through coop
        // protocol
        // Type is an MO-Defined-Type
        leaf bounceTrig {
            description "Bounce Trigger";

            // Type is an MO-Defined-Type
            type l2_BounceTrig;
        }

        // EP move frequency, maximum allowed moves per second.
        // If the frequency is exceeded, new learn events will
        // not be honored until a specified duration
        // Type is an MO-Defined-Type
        leaf moveFreq {
            description "Move Frequency";

            // Type is an MO-Defined-Type
            type l2_MoveFreq;
        }

        // If the EP move frequency is exceeded, the duration till
        // the new learn EP learn events are put in hold
        // Type is an MO-Defined-Type
        leaf holdIntvl {
            description "Hold Interval";

            // Type is an MO-Defined-Type
            type l2_HoldIntvl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping fmcast_Grp-group {

        // Inherited From nw:Conn
        // Modified by Override: mcast:Grp->name
        // Type is an MO-Defined-Type
        leaf name {
            description "Name";

            // Type is an MO-Defined-Type
            type naming_Name {
                length "1..64";
            }
        }

        // Multicast group address
        // Inherited From mcast:Grp
        // Type is an MO-Defined-Type
        leaf addr {
            description "Address";

            // Type is an MO-Defined-Type
            type mcast_GrpIp;
        }
    }

    grouping epm_Db-group {

        // Type of the database
        // Type is an MO-Defined-Type
        leaf type {
            config "false";
            description "Type";

            // Type is an MO-Defined-Type
            type epm_DbT;
        }

        // Inherited From nw:Conn
        // Modified by Override: nw:Db->name
        // Type is an MO-Defined-Type
        leaf name {
            description "Name";

            // Type is an MO-Defined-Type
            type naming_Name {
                length "1..64";
            }
        }

        // Ip Ep record
        container ip-items {
            list IpEp-list {
                config "false";
                key "addr";

                // Added containment: Prefix=ip
                // Acquired From Package epm
                uses epm_IpEp-group;
            }
        }

        // Mac Ep record
        container mac-items {
            list MacEp-list {
                config "false";
                key "addr";

                // Added containment: Prefix=mac
                // Acquired From Package epm
                uses epm_MacEp-group;
            }
        }
    }

    grouping epm_IpEp-group {
        leaf addr {
            config "false";
            type address_Ip;
        }

        // Inherited From nw:Conn
        // Modified by Override: nw:DbRec->name
        // Type is an MO-Defined-Type
        leaf name {
            description "Name";

            // Type is an MO-Defined-Type
            type naming_Name {
                length "1..64";
            }
        }

        // Identifier of the logical interface
        // Inherited From epm:EpRec
        // Type is an MO-Defined-Type
        leaf ifId {
            config "false";
            description "Path";

            // Type is an MO-Defined-Type
            type nw_IfId;
        }

        // Ep flags
        // Inherited From epm:EpRec
        // Type is an MO-Defined-Type
        leaf flags {
            config "false";
            description "Endpoint Properties and State";

            // Type is an MO-Defined-Type
            type epm_EpFlags;
        }
        leaf createTs {
            config "false";
            type uint64;
        }

        // Rel-def target from IpEpRslttoIpEpAtt
        // Inherited From epm:IpEp
        container rtIpEpRslttoIpEpAtt-items {

            // Added containment as a singleton: Prefix=rtIpEpRslttoIpEpAtt
            // Acquired From Package eptrk
            uses eptrk_RtIpEpRslttoIpEpAtt_target-group;
        }

        // Rel-def target from MacEpRslttoIpEpAtt
        // Inherited From epm:IpEp
        container rtMacEpRslttoIpEpAtt-items {

            // Added containment as a singleton: Prefix=rtMacEpRslttoIpEpAtt
            // Acquired From Package eptrk
            uses eptrk_RtMacEpRslttoIpEpAtt_target-group;
        }
    }

    grouping epm_MacEp-group {
        leaf addr {
            config "false";
            type address_Mac;
        }

        // Inherited From nw:Conn
        // Modified by Override: nw:DbRec->name
        // Type is an MO-Defined-Type
        leaf name {
            description "Name";

            // Type is an MO-Defined-Type
            type naming_Name {
                length "1..64";
            }
        }

        // Identifier of the logical interface
        // Inherited From epm:EpRec
        // Type is an MO-Defined-Type
        leaf ifId {
            config "false";
            description "Path";

            // Type is an MO-Defined-Type
            type nw_IfId;
        }

        // Ep flags
        // Inherited From epm:EpRec
        // Type is an MO-Defined-Type
        leaf flags {
            config "false";
            description "Endpoint Properties and State";

            // Type is an MO-Defined-Type
            type epm_EpFlags;
        }
        leaf createTs {
            config "false";
            type uint64;
        }

        // Rel-def from macEpToIpEpAtt
        container rsmacEpToIpEpAtt-items {

            // Abstract containment of rsmacEpToIpEpAtt derived from epm:MacEp
            list RsMacEpToIpEpAtt-list {
                config "false";
                key "tDn";

                // Added containment: Prefix=rsmacEpToIpEpAtt
                // Acquired From Package epm
                uses epm_RsMacEpToIpEpAtt_source-group;
            }
        }
    }

    grouping vlan_CktEp-group {
        leaf fabEncap {
            config "false";
            type string;
        }

        // Qos Class operational state
        // Type is an MO-Defined-Type
        leaf operState {
            config "false";
            description "Operational State";

            // Type is an MO-Defined-Type
            type qosp_OperSt;
        }

        // Rule operational state disabled reason
        // Type is an MO-Defined-Type
        leaf operStQual {
            config "false";
            description "Operational State Qualifier";

            // Type is an MO-Defined-Type
            type qosp_OperStQual;
        }

        // Inherited From nw:Conn
        // Modified by Override: nw:FwDom->name
        // Type is an MO-Defined-Type
        leaf name {
            description "Name";

            // Type is an MO-Defined-Type
            type naming_Name {
                length "1..64";
            }
        }

        // domain type
        // Inherited From l2:Dom
        // Type is an MO-Defined-Type
        leaf type {
            description "Type";

            // Type is an MO-Defined-Type
            type l2_DomType;
        }

        // domain id
        // Inherited From l2:Dom
        // Type is an MO-Defined-Type
        leaf id {
            description "Domain ID";

            // Type is an MO-Defined-Type
            type l2_DomId;
        }

        // Internal domain id
        // Inherited From l2:Dom
        // Type is an MO-Defined-Type
        leaf hwId {
            config "false";
            description "Hardware Resource ID";

            // Type is an MO-Defined-Type
            type l2_DomId;
        }

        // Vlan mode
        // Inherited From l2:Dom
        // Type is an MO-Defined-Type
        leaf mode {
            description "Mode";

            // Type is an MO-Defined-Type
            type l2_DomMode;
        }

        // admin state
        // Inherited From l2:Dom
        // Type is an MO-Defined-Type
        leaf adminSt {
            description "Admin State";

            // Type is an MO-Defined-Type
            type l2_DomAdminSt;
        }

        // oper state
        // Inherited From l2:Dom
        // Type is an MO-Defined-Type
        leaf operSt {
            config "false";
            description "Operational State";

            // Type is an MO-Defined-Type
            type l2_DomOperSt;
        }
        leaf createTs {
            config "false";
            type uint64;
        }

        // Controls
        // Inherited From l2:Dom
        // Type is an MO-Defined-Type
        leaf ctrl {
            description "Controls";

            // Type is an MO-Defined-Type
            type l2_DomCtrl;
        }
        leaf encap {
            type string;
        }

        // Enforcement preference
        // Inherited From l2:CktEp
        // Type is an MO-Defined-Type
        leaf enfPref {
            description "Switching Preference";

            // Type is an MO-Defined-Type
            type l2_EnfPref;
        }

        // It represents the classId for the traffic
        // terminating on this circuit
        // Inherited From l2:CktEp
        // Type is an MO-Defined-Type
        leaf pcTag {
            description "PC Tag";

            // Type is an MO-Defined-Type
            type actrl_PcTag;
        }

        // It represents the default qos group for the
        // traffic on this circuit
        // Inherited From l2:CktEp
        // Type is an MO-Defined-Type
        leaf qosPrio {
            description "Qos Priority";

            // Type is an MO-Defined-Type
            type qos_TenantPrio;
        }
        leaf epgDn {
            type string;
        }

        // Static Mac end point
        container mac-items {
            list MacEp-list {
                config "false";
                key "mac";

                // Added containment: Prefix=mac
                // Acquired From Package l2
                uses l2_MacEp-group;
            }
        }

        // Abstraction of epm database
        container db-items {
            list Db-list {
                config "false";
                key "type";

                // Added containment: Prefix=db
                // Acquired From Package epm
                uses epm_Db-group;
            }
        }

        // Rel-def target from spanSrcToL2CktEpAtt
        // Inherited From vlan:CktEp
        container rtspanSpanSrcToL2CktEpAtt-items {

            // Abstract containment of rtspanSpanSrcToL2CktEpAtt derived from l2:CktEp
            list RtSpanSpanSrcToL2CktEpAtt-list {
                config "false";
                key "tDn";

                // Added containment: Prefix=rtspanSpanSrcToL2CktEpAtt
                // Acquired From Package span
                uses span_RtSpanSpanSrcToL2CktEpAtt_target-group;
            }
        }

        // Rel-def target from domIfConn
        // Inherited From l2:BD
        // Inherited From vlan:CktEp
        container rtfvDomIfConn-items {

            // Abstract containment of rtfvDomIfConn derived from l2:Dom
            list RtFvDomIfConn-list {
                config "false";
                key "tDn";

                // Added containment: Prefix=rtfvDomIfConn
                // Acquired From Package fv
                uses fv_RtFvDomIfConn_target-group;
            }
        }

        // Rel-def from vlanEppAtt
        container rsvlanEppAtt-items {

            // Added containment as a singleton: Prefix=rsvlanEppAtt
            // Acquired From Package vlan
            uses vlan_RsVlanEppAtt_source-group;
        }
    }

    grouping l2_MacEp-group {
        leaf mac {
            config "false";
            type address_Mac;
        }

        // The interface on which the endpoint is reachable
        // Type is an MO-Defined-Type
        leaf if {
            config "false";
            description "Interface";

            // Type is an MO-Defined-Type
            type nw_IfId;
        }

        // Operational state
        // Type is an MO-Defined-Type
        leaf operSt {
            config "false";
            description "Operational State";

            // Type is an MO-Defined-Type
            type epm_EpOperSt;
        }

        // Operational state qualifier
        // Type is an MO-Defined-Type
        leaf operStQual {
            config "false";
            description "Operational State Qualifier";

            // Type is an MO-Defined-Type
            type epm_EpOperStQual;
        }

        // Inherited From nw:Conn
        // Modified by Override: nw:Ep->name
        // Type is an MO-Defined-Type
        leaf name {
            description "Name";

            // Type is an MO-Defined-Type
            type naming_Name {
                length "1..64";
            }
        }

        // Rel-def target from EpDefRefToL2MacEp
        // Inherited From l2:MacEp
        container rtfvEpDefRefToL2MacEp-items {

            // Abstract containment of rtfvEpDefRefToL2MacEp derived from l2:MacEp
            list RtFvEpDefRefToL2MacEp-list {
                config "false";
                key "tDn";

                // Added containment: Prefix=rtfvEpDefRefToL2MacEp
                // Acquired From Package fv
                uses fv_RtFvEpDefRefToL2MacEp_target-group;
            }
        }
    }

    grouping vxlan_CktEp-group {

        // Multicast group address (GIPO'), Outer multicast
        // encapsulation ip address for this layer2 domain
        // Type is an MO-Defined-Type
        leaf mcastEncap {
            config "false";
            description "Multicast Encapsulation";

            // Type is an MO-Defined-Type
            type mcast_GrpIp;
        }

        // Inherited From nw:Conn
        // Modified by Override: nw:FwDom->name
        // Type is an MO-Defined-Type
        leaf name {
            description "Name";

            // Type is an MO-Defined-Type
            type naming_Name {
                length "1..64";
            }
        }

        // domain type
        // Inherited From l2:Dom
        // Type is an MO-Defined-Type
        leaf type {
            description "Type";

            // Type is an MO-Defined-Type
            type l2_DomType;
        }

        // domain id
        // Inherited From l2:Dom
        // Type is an MO-Defined-Type
        leaf id {
            description "Domain ID";

            // Type is an MO-Defined-Type
            type l2_DomId;
        }

        // Internal domain id
        // Inherited From l2:Dom
        // Type is an MO-Defined-Type
        leaf hwId {
            config "false";
            description "Hardware Resource ID";

            // Type is an MO-Defined-Type
            type l2_DomId;
        }

        // Vlan mode
        // Inherited From l2:Dom
        // Type is an MO-Defined-Type
        leaf mode {
            description "Mode";

            // Type is an MO-Defined-Type
            type l2_DomMode;
        }

        // admin state
        // Inherited From l2:Dom
        // Type is an MO-Defined-Type
        leaf adminSt {
            description "Admin State";

            // Type is an MO-Defined-Type
            type l2_DomAdminSt;
        }

        // oper state
        // Inherited From l2:Dom
        // Type is an MO-Defined-Type
        leaf operSt {
            config "false";
            description "Operational State";

            // Type is an MO-Defined-Type
            type l2_DomOperSt;
        }
        leaf createTs {
            config "false";
            type uint64;
        }

        // Controls
        // Inherited From l2:Dom
        // Type is an MO-Defined-Type
        leaf ctrl {
            description "Controls";

            // Type is an MO-Defined-Type
            type l2_DomCtrl;
        }
        leaf encap {
            type string;
        }

        // Enforcement preference
        // Inherited From l2:CktEp
        // Type is an MO-Defined-Type
        leaf enfPref {
            description "Switching Preference";

            // Type is an MO-Defined-Type
            type l2_EnfPref;
        }

        // It represents the classId for the traffic
        // terminating on this circuit
        // Inherited From l2:CktEp
        // Type is an MO-Defined-Type
        leaf pcTag {
            description "PC Tag";

            // Type is an MO-Defined-Type
            type actrl_PcTag;
        }

        // It represents the default qos group for the
        // traffic on this circuit
        // Inherited From l2:CktEp
        // Type is an MO-Defined-Type
        leaf qosPrio {
            description "Qos Priority";

            // Type is an MO-Defined-Type
            type qos_TenantPrio;
        }
        leaf epgDn {
            type string;
        }

        // Abstraction of epm database
        container db-items {
            list Db-list {
                config "false";
                key "type";

                // Added containment: Prefix=db
                // Acquired From Package epm
                uses epm_Db-group;
            }
        }

        // Rel-def target from spanSrcToL2CktEpAtt
        // Inherited From vlan:CktEp
        // Inherited From vxlan:CktEp
        container rtspanSpanSrcToL2CktEpAtt-items {

            // Abstract containment of rtspanSpanSrcToL2CktEpAtt derived from l2:CktEp
            list RtSpanSpanSrcToL2CktEpAtt-list {
                config "false";
                key "tDn";

                // Added containment: Prefix=rtspanSpanSrcToL2CktEpAtt
                // Acquired From Package span
                uses span_RtSpanSpanSrcToL2CktEpAtt_target-group;
            }
        }

        // Rel-def target from domIfConn
        // Inherited From l2:BD
        // Inherited From vlan:CktEp
        // Inherited From vxlan:CktEp
        container rtfvDomIfConn-items {

            // Abstract containment of rtfvDomIfConn derived from l2:Dom
            list RtFvDomIfConn-list {
                config "false";
                key "tDn";

                // Added containment: Prefix=rtfvDomIfConn
                // Acquired From Package fv
                uses fv_RtFvDomIfConn_target-group;
            }
        }

        // Rel-def from vxlanEppAtt
        container rsvxlanEppAtt-items {

            // Added containment as a singleton: Prefix=rsvxlanEppAtt
            // Acquired From Package vxlan
            uses vxlan_RsVxlanEppAtt_source-group;
        }
    }

    grouping fm_Entity-group {

        // MPLS Static feature information
        container mplsstatic-items {

            // Added containment as a singleton: Prefix=mplsstatic
            // Acquired From Package fm
            uses fm_MplsStatic-group;
        }

        // MPLS OAM feature information
        container mplsoam-items {

            // Added containment as a singleton: Prefix=mplsoam
            // Acquired From Package fm
            uses fm_MplsOam-group;
        }

        // MPLS Segment-routing feature information
        container mplssgmntrtg-items {

            // Added containment as a singleton: Prefix=mplssgmntrtg
            // Acquired From Package fm
            uses fm_MplsSgmntRtg-group;
        }

        // MPLS EVPN feature information
        container mplsevpn-items {

            // Added containment as a singleton: Prefix=mplsevpn
            // Acquired From Package fm
            uses fm_MplsEvpn-group;
        }

        // BGP feature information
        container bgp-items {

            // Added containment as a singleton: Prefix=bgp
            // Acquired From Package fm
            uses fm_Bgp-group;
        }

        // HMM feature information
        container hmm-items {

            // Added containment as a singleton: Prefix=hmm
            // Acquired From Package fm
            uses fm_Hmm-group;
        }

        // EVPN feature information
        container evpn-items {

            // Added containment as a singleton: Prefix=evpn
            // Acquired From Package fm
            uses fm_Evpn-group;
        }

        // NGOAM feature information
        container ngoam-items {

            // Added containment as a singleton: Prefix=ngoam
            // Acquired From Package fm
            uses fm_Ngoam-group;
        }

        // MSDP feature information
        container msdp-items {

            // Added containment as a singleton: Prefix=msdp
            // Acquired From Package fm
            uses fm_Msdp-group;
        }

        // DHCP feature information
        container dhcp-items {

            // Added containment as a singleton: Prefix=dhcp
            // Acquired From Package fm
            uses fm_Dhcp-group;
        }

        // Interface-Vlan feature information
        container ifvlan-items {

            // Added containment as a singleton: Prefix=ifvlan
            // Acquired From Package fm
            uses fm_InterfaceVlan-group;
        }

        container bashshell-items {

            // Added containment as a singleton: Prefix=bashshell
            // Acquired From Package fm
            uses fm_BashShell-group;
        }

        container scpserver-items {

            // Added containment as a singleton: Prefix=scpserver
            // Acquired From Package fm
            uses fm_ScpServer-group;
        }

        container lldp-items {

            // Added containment as a singleton: Prefix=lldp
            // Acquired From Package fm
            uses fm_Lldp-group;
        }

        // LACP feature information
        container lacp-items {

            // Added containment as a singleton: Prefix=lacp
            // Acquired From Package fm
            uses fm_Lacp-group;
        }

        // Nxapi feature information
        container nxapi-items {

            // Added containment as a singleton: Prefix=nxapi
            // Acquired From Package fm
            uses fm_Nxapi-group;
        }

        // Telnet feature information
        container telnet-items {

            // Added containment as a singleton: Prefix=telnet
            // Acquired From Package fm
            uses fm_Telnet-group;
        }

        // Nxdb feature information
        container nxdb-items {

            // Added containment as a singleton: Prefix=nxdb
            // Acquired From Package fm
            uses fm_Nxdb-group;
        }

        // VnSegment feature information
        container vnsegment-items {

            // Added containment as a singleton: Prefix=vnsegment
            // Acquired From Package fm
            uses fm_VnSegment-group;
        }

        // Tacacs+ feature information
        container tacacsplus-items {

            // Added containment as a singleton: Prefix=tacacsplus
            // Acquired From Package fm
            uses fm_Tacacsplus-group;
        }

        // UDLD feature information
        container udld-items {

            // Added containment as a singleton: Prefix=udld
            // Acquired From Package fm
            uses fm_Udld-group;
        }

        // NAT feature information
        container nat-items {

            // Added containment as a singleton: Prefix=nat
            // Acquired From Package fm
            uses fm_Nat-group;
        }

        // VRRPv3 feature information
        container vrrpv3-items {

            // Added containment as a singleton: Prefix=vrrpv3
            // Acquired From Package fm
            uses fm_Vrrpv3-group;
        }

        // VRRP feature information
        container vrrp-items {

            // Added containment as a singleton: Prefix=vrrp
            // Acquired From Package fm
            uses fm_Vrrp-group;
        }

        // HSRP feature information
        container hsrp-items {

            // Added containment as a singleton: Prefix=hsrp
            // Acquired From Package fm
            uses fm_Hsrp-group;
        }

        // Netflow feature information
        container netflow-items {

            // Added containment as a singleton: Prefix=netflow
            // Acquired From Package fm
            uses fm_Netflow-group;
        }

        // Analytics feature information
        container analytics-items {

            // Added containment as a singleton: Prefix=analytics
            // Acquired From Package fm
            uses fm_Analytics-group;
        }

        // BFD feature information
        container bfd-items {

            // Added containment as a singleton: Prefix=bfd
            // Acquired From Package fm
            uses fm_Bfd-group;
        }

        // Tunnel feature information
        container tunnelif-items {

            // Added containment as a singleton: Prefix=tunnelif
            // Acquired From Package fm
            uses fm_Tunnelif-group;
        }

        // nv overlay feature information
        container nvo-items {

            // Added containment as a singleton: Prefix=nvo
            // Acquired From Package fm
            uses fm_Nvo-group;
        }

        // PBR feature information
        container pbr-items {

            // Added containment as a singleton: Prefix=pbr
            // Acquired From Package fm
            uses fm_Pbr-group;
        }

        // PIM feature information
        container pim-items {

            // Added containment as a singleton: Prefix=pim
            // Acquired From Package fm
            uses fm_Pim-group;
        }

        // VPC feature information
        container vpc-items {

            // Added containment as a singleton: Prefix=vpc
            // Acquired From Package fm
            uses fm_Vpc-group;
        }

        // NTP feature information
        container ntpd-items {

            // Added containment as a singleton: Prefix=ntpd
            // Acquired From Package fm
            uses fm_Ntpd-group;
        }

        // Telemetry feature information
        container telemetry-items {

            // Added containment as a singleton: Prefix=telemetry
            // Acquired From Package fm
            uses fm_Telemetry-group;
        }

        // OSPF feature information
        container ospf-items {

            // Added containment as a singleton: Prefix=ospf
            // Acquired From Package fm
            uses fm_Ospf-group;
        }

        // Holds "vendor interop controller" info
        container vctrl-items {

            // Added containment as a singleton: Prefix=vctrl
            // Acquired From Package fm
            uses fm_VendorCntrl-group;
        }

        // macsec feature information
        container macsec-items {

            // Added containment as a singleton: Prefix=macsec
            // Acquired From Package fm
            uses fm_Macsec-group;
        }
    }

    grouping fm_MplsStatic-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
        leaf conflictingFeature {
            config "false";
            type string;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_ServiceInstance-group {
        leaf id {
            config "false";
            type uint32;
        }

        // Type is an MO-Defined-Type
        leaf operSt {
            config "false";
            description "Operational status of the instance";

            // Type is an MO-Defined-Type
            type fm_InstOperState;
        }
    }

    grouping fm_MplsOam-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
        leaf conflictingFeature {
            config "false";
            type string;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_MplsSgmntRtg-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
        leaf conflictingFeature {
            config "false";
            type string;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_MplsEvpn-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
        leaf conflictingFeature {
            config "false";
            type string;
        }
    }

    grouping fm_Bgp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Hmm-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Evpn-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Ngoam-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Msdp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Dhcp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_InterfaceVlan-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_BashShell-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_ScpServer-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Lldp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Lacp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Nxapi-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Telnet-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
    }

    grouping fm_Nxdb-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_VnSegment-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Tacacsplus-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Udld-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Nat-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Vrrpv3-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Vrrp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Hsrp-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Netflow-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Analytics-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Bfd-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Tunnelif-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Nvo-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Pbr-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Pim-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Vpc-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Ntpd-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }
    }

    grouping fm_Telemetry-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_Ospf-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fm_VendorCntrl-group {

        // To enable/disable feature
        // Type is an MO-Defined-Type
        leaf adminSt {
            description "Admin status";

            // Type is an MO-Defined-Type
            type fm_AdminState;
        }

        // Operational state of the service.
        // Its in enabled state even if one instance is enabled
        // Type is an MO-Defined-Type
        leaf operSt {
            config "false";
            description "Operational status";

            // Type is an MO-Defined-Type
            type fm_OperState;
        }
    }

    grouping fm_Macsec-group {

        // To enable/disable feature
        // Inherited From fm:Feature
        // Type is an MO-Defined-Type
        leaf adminSt {
            description "Admin status";

            // Type is an MO-Defined-Type
            type fm_AdminState;
        }

        // Operational state of the service.
        // Its in enabled state even if one instance is enabled
        // Inherited From fm:Feature
        // Type is an MO-Defined-Type
        leaf operSt {
            config "false";
            description "Operational status";

            // Type is an MO-Defined-Type
            type fm_OperState;
        }

        // Inherited From fm:Feature
        // Type is an MO-Defined-Type
        leaf maxInstance {
            config "false";
            description "Maximum number of instances supported";

            // Type is an MO-Defined-Type
            type fm_Instance;
        }

        // This object contains instance specific operational information
        // common to features. This MO is created when there is a service instance
        // and removed when the service instance is removed.
        container service-items {
            list ServiceInstance-list {
                config "false";
                key "id";

                // Added containment: Prefix=service
                // Acquired From Package fm
                uses fm_ServiceInstance-group;
            }
        }
    }

    grouping fset_FeatureSet-group {
        leaf name {
            type string;
        }

        // To uninstall/install
        // Type is an MO-Defined-Type
        leaf adminSt {
            description "Admin status";

            // Type is an MO-Defined-Type
            type fset_AdminState;
        }
        leaf force {
            type boolean;
        }

        // Operational state of the featureSet
        // Type is an MO-Defined-Type
        leaf operSt {
            config "false";
            description "Operational status";

            // Type is an MO-Defined-Type
            type fset_OperState;
        }
    }

    grouping interface_Entity-group {
        leaf descr {
            config "false";
            type string;
        }

        // Physical ethernet interface information holder
        container phys-items {
            list PhysIf-list {
                key "id";

                // Added containment: Prefix=phys
                // Acquired From Package l1
                uses l1_PhysIf-group;
            }
        }

        // Aggregated interface, collection of physical ports;
        // aka port channel
        container aggr-items {
            list AggrIf-list {
                key "id";

                // Added containment: Prefix=aggr
                // Acquired From Package pc
                uses pc_AggrIf-group;
            }
        }

        // Routed concrete interface (aka routed port)
        container rtd-items {
            list RtdIf-list {
                key "id";

                // Added containment: Prefix=rtd
                // Acquired From Package l3
                uses l3_RtdIf-group;
            }
        }

        // Routed loopback interface
        container lb-items {
            list LbRtdIf-list {
                key "id";

                // Added containment: Prefix=lb
                // Acquired From Package l3
                uses l3_LbRtdIf-group;
            }
        }

        // Routed encap interface (aka sub if)
        container encrtd-items {
            list EncRtdIf-list {
                key "id";

                // Added containment: Prefix=encrtd
                // Acquired From Package l3
                uses l3_EncRtdIf-group;
            }
        }

        // Routed Vlan Interface (SVI)    Svi:If gets created for L2:BD, immediately after
        // l2:BD is attached to l3:Ctx.  Use case: Communication
        // between two Hosts in different BDs. This is achieved
        // through routing. The resource limit of svi is same
        // as the resource limit of BD
        container svi-items {
            list If-list {
                key "id";

                // Added containment: Prefix=svi
                // Acquired From Package svi
                uses svi_If-group;
            }
        }
        container tunnelif-items {
            list If-list {
                key "id";

                // Added containment: Prefix=tunnelif
                // Acquired From Package tunnelif
                uses tunnelif_If-group;
            }
        }
    }

    grouping l1_PhysIf-group {

        // port speed-group
        // Type is an MO-Defined-Type
        leaf speedGroup {
            description "Speed Group";

            // Type is an MO-Defined-Type
            type l1_SpeedGroup;
        }

        // Beacon port state
        // Type is an MO-Defined-Type
        leaf beacon {
            description "Beacon State";

            // Type is an MO-Defined-Type
            type l1_Beacon;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Type is an MO-Defined-Type
        leaf adminSt {
            description "Administrative State";

            // Type is an MO-Defined-Type
            type l1_AdminSt;
        }

        // Administrative port speed    @@@ This comes from the host interface
        // @@@ configuration policy
        // Inherited From l1:If
        // Type is an MO-Defined-Type
        leaf speed {
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Administrative port mode    @@@ Internally set by PE
        // Inherited From l1:EthIf
        // Type is an MO-Defined-Type
        leaf mode {
            description "Mode";

            // Type is an MO-Defined-Type
            type l1_Mode;
        }

        // Administrative port layer    @@@ Internally set by PE
        // Inherited From l1:EthIf
        // Type is an MO-Defined-Type
        leaf layer {
            description "Layer";

            // Type is an MO-Defined-Type
            type l1_Layer;
        }

        // Administrative mdix mode    @@@ Theres no benefit in exposing this property
        // @@@ in IFC. Ask Marketing.
        // Inherited From l1:EthIf
        // Type is an MO-Defined-Type
        leaf mdix {
            description "MDIX";

            // Type is an MO-Defined-Type
            type l1_Mdix;
        }

        // Administrative port delay    @@@ is this exposed in IFC?
        // Inherited From l1:EthIf
        // Type is an MO-Defined-Type
        leaf delay {
            description "Delay";

            // Type is an MO-Defined-Type
            type l1_Delay;
        }

        // Administrative port link debounce interval    @@@ This comes from the interface configuration policy
        // Inherited From l1:EthIf
        // Type is an MO-Defined-Type
        leaf linkDebounce {
            description "Link Debounce Interval";

            // Type is an MO-Defined-Type
            type l1_LinkDebounce;
        }

        // Administrative port dot1q ether-type    @@@ This property is not supported in switch ??
        // Inherited From l1:EthIf
        // Type is an MO-Defined-Type
        leaf dot1qEtherType {
            description "Dot1q Ether Type";

            // Type is an MO-Defined-Type
            type l1_Dot1qEtherType;
        }

        // Administrative port bandwidth    @@@ Comes from QOS Policy
        // Inherited From l1:EthIf
        // Type is an MO-Defined-Type
        leaf bw {
            description "Bandwidth";

            // Type is an MO-Defined-Type
            type l1_Bw;
        }

        // Administrative port medium type    @@@ The fabric & Host connections are P2p.    @@@ No need to expose this property in IFC
        // Inherited From l1:EthIf
        // Type is an MO-Defined-Type
        leaf medium {
            description "Medium";

            // Type is an MO-Defined-Type
            type l1_Medium;
        }

        // Administrative port inherit bandwidth    @@@ It is used for specifying the bandwidth inherited
        // @@@ by the subinterfaces from the parent interface    @@@ It is not exposed in IFC. All the subinterfaces
        // @@@ inherit full parent interface's bandwidth
        // Inherited From l1:EthIf
        // Type is an MO-Defined-Type
        leaf inhBw {
            description "Inherit Bandwidth";

            // Type is an MO-Defined-Type
            type l1_InheritBw;
        }

        // Administrative port span mode    @@@ This comes from the span policy in IFC
        // Inherited From l1:EthIf
        // Type is an MO-Defined-Type
        leaf spanMode {
            description "Span Mode";

            // Type is an MO-Defined-Type
            type l1_SpanMode;
        }

        // Administrative link logging enable    @@@ This come from interface configuration policy
        // Inherited From l1:EthIf
        // Type is an MO-Defined-Type
        leaf linkLog {
            description "Link Logging";

            // Type is an MO-Defined-Type
            type l1_LinkLog;
        }

        // Administrative trunk logging enable    @@@ This come from interface configuration policy
        // Inherited From l1:EthIf
        // Type is an MO-Defined-Type
        leaf trunkLog {
            description "Trunk Logging";

            // Type is an MO-Defined-Type
            type l1_TrunkLog;
        }
        leaf routerMac {
            type address_Mac;
            default "0";
        }

        // Type of the port: Fabric vs Leaf    @@@ This property is not exposed in IFC
        // Inherited From l1:EthIf
        // Type is an MO-Defined-Type
        leaf portT {
            description "Port Type";

            // Type is an MO-Defined-Type
            type eqpt_PortT;
        }

        // Usage of the port: Fabric, Infra, Epg, Controller, Discovery   @@@ This property is not exposed in IFC
        // Inherited From l1:EthIf
        // Type is an MO-Defined-Type
        leaf usage {
            description "Port Usage";

            // Type is an MO-Defined-Type
            type l1_PortUsage;
        }

        // config trunk vlans
        // Inherited From l1:EthIf
        // Type is an MO-Defined-Type
        leaf trunkVlans {
            description "Configed Trunk Vlans";

            // Type is an MO-Defined-Type
            type l1_l1IfTrunkVlans;
        }

        // config access vlan
        // Inherited From l1:EthIf
        // Type is an MO-Defined-Type
        leaf accessVlan {
            description "Configured Access Vlan";

            // Type is an MO-Defined-Type
            type l1_l1IfAccessVlan;
        }

        // Controller Id
        // Inherited From l1:EthIf
        // Type is an MO-Defined-Type
        leaf controllerId {
            description "Controller ID";

            // Type is an MO-Defined-Type
            type aggregate_ControllerIdBitmap;
        }

        // config access vlan
        // Inherited From l1:EthIf
        // Type is an MO-Defined-Type
        leaf nativeVlan {
            description "Configured Native Vlan";

            // Type is an MO-Defined-Type
            type l1_l1IfNativeVlan;
        }

        // port user config flags
        // Inherited From l1:EthIf
        // Type is an MO-Defined-Type
        leaf userCfgdFlags {
            description "Port User Config Flags";

            // Type is an MO-Defined-Type
            type l1_userCfgdFlags;
        }

        container priorflowctrl-items {

            // Added containment as a singleton: Prefix=priorflowctrl
            // Acquired From Package ipqos
            uses ipqos_PriorFlowCtrl-group;
        }

        container physExtd-items {

            // Added containment as a singleton: Prefix=physExtd
            // Acquired From Package l1
            uses l1_PhysIfExtended-group;
        }

        // EEE policy
        container eeep-items {

            // Added containment as a singleton: Prefix=eeep
            // Acquired From Package l1
            uses l1_EeeP-group;
        }

        // Storm control policy
        container stormctrlp-items {

            // Added containment as a singleton: Prefix=stormctrlp
            // Acquired From Package l1
            uses l1_StormCtrlP-group;
        }

        // Load interval policy
        container loadp-items {

            // Added containment as a singleton: Prefix=loadp
            // Acquired From Package l1
            uses l1_LoadP-group;
        }

        // Vlan Mapping policy
        container vlanmapping-items {

            // Added containment as a singleton: Prefix=vlanmapping
            // Acquired From Package l1
            uses l1_VlanMapping-group;
        }

        // This MO is temporary. Needs to be removed when
        // "vrf member <vrf-name>" is objectified
        container vrf-items {

            // Added containment as a singleton: Prefix=vrf
            // Acquired From Package l1
            uses l1_Vrf-group;
        }

        // Physical interface information holder
        container phys-items {

            // Added containment as a singleton: Prefix=phys
            // Acquired From Package ethpm
            uses ethpm_PhysIf-group;
        }

        // AggrMbrIf class
        container aggrmbrif-items {

            // Added containment as a singleton: Prefix=aggrmbrif
            // Acquired From Package pc
            uses pc_AggrMbrIf-group;
        }

        // Dom info
        container dom-items {
            list DomDef-list {
                config "false";
                key "domPKey";

                // Added containment: Prefix=dom
                // Acquired From Package fv
                uses fv_DomDef-group;
            }
        }

        // Rel-def target from InbandConf
        // Inherited From l1:PhysIf
        container rtInbandConf-items {

            // Added containment as a singleton: Prefix=rtInbandConf
            // Acquired From Package l2
            uses l2_RtInbandConf_target-group;
        }

        // Rel-def target from extConf
        // Inherited From l1:PhysIf
        container rtextConf-items {

            // Added containment as a singleton: Prefix=rtextConf
            // Acquired From Package l2
            uses l2_RtExtConf_target-group;
        }

        // Rel-def target from brConf
        // Inherited From l1:PhysIf
        container rtbrConf-items {

            // Added containment as a singleton: Prefix=rtbrConf
            // Acquired From Package l2
            uses l2_RtBrConf_target-group;
        }

        // Rel-def target from NodePortAtt
        // Inherited From l1:PhysIf
        container rtfvNodePortAtt-items {

            // Abstract containment of rtfvNodePortAtt derived from l1:EthIf
            list RtFvNodePortAtt-list {
                config "false";
                key "tDn";

                // Added containment: Prefix=rtfvNodePortAtt
                // Acquired From Package fv
                uses fv_RtFvNodePortAtt_target-group;
            }
        }

        // Rel-def target from mbrIfs
        // Inherited From l1:PhysIf
        container rtmbrIfs-items {

            // Added containment as a singleton: Prefix=rtmbrIfs
            // Acquired From Package pc
            uses pc_RtMbrIfs_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        container rtvrfMbr-items {

            // Added containment as a singleton: Prefix=rtvrfMbr
            // Acquired From Package l3
            uses l3_RtVrfMbr_target-group;
        }

        // Rel-def target from physRtdConf
        // Inherited From l1:PhysIf
        container rtphysRtdConf-items {

            // Added containment as a singleton: Prefix=rtphysRtdConf
            // Acquired From Package l3
            uses l3_RtPhysRtdConf_target-group;
        }

        // Rel-def target from encPhysRtdConf
        // Inherited From l1:PhysIf
        container rtl3EncPhysRtdConf-items {

            // Abstract containment of rtl3EncPhysRtdConf derived from l1:EthIf
            list RtL3EncPhysRtdConf-list {
                key "tDn";

                // Added containment: Prefix=rtl3EncPhysRtdConf
                // Acquired From Package l3
                uses l3_RtL3EncPhysRtdConf_target-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def target from tunnelMbrIfs
        // Inherited From l1:PhysIf
        container rttunnelTunnelMbrIfs-items {

            // Abstract containment of rttunnelTunnelMbrIfs derived from l1:PhysIf
            list RtTunnelTunnelMbrIfs-list {
                config "false";
                key "tDn";

                // Added containment: Prefix=rttunnelTunnelMbrIfs
                // Acquired From Package tunnel
                uses tunnel_RtTunnelTunnelMbrIfs_target-group;
            }
        }

        // Rel-def target from LsNodeToIf
        // Inherited From l1:PhysIf
        container rtLsNodeToIf-items {

            // Added containment as a singleton: Prefix=rtLsNodeToIf
            // Acquired From Package leqpt
            uses leqpt_RtLsNodeToIf_target-group;
        }

        container dbgIfIn-items {

            // Added containment as a singleton: Prefix=dbgIfIn
            // Acquired From Package rmon
            uses rmon_IfIn-group;
        }

        container dbgIfOut-items {

            // Added containment as a singleton: Prefix=dbgIfOut
            // Acquired From Package rmon
            uses rmon_IfOut-group;
        }

        container dbgIpIn-items {

            // Added containment as a singleton: Prefix=dbgIpIn
            // Acquired From Package rmon
            uses rmon_IpIn-group;
        }

        container dbgDot1d-items {

            // Added containment as a singleton: Prefix=dbgDot1d
            // Acquired From Package rmon
            uses rmon_Dot1d-group;
        }

        container dbgEtherStats-items {

            // Added containment as a singleton: Prefix=dbgEtherStats
            // Acquired From Package rmon
            uses rmon_EtherStats-group;
        }

        container dbgDot3Stats-items {

            // Added containment as a singleton: Prefix=dbgDot3Stats
            // Acquired From Package rmon
            uses rmon_Dot3Stats-group;
        }

        container dbgIfHCIn-items {

            // Added containment as a singleton: Prefix=dbgIfHCIn
            // Acquired From Package rmon
            uses rmon_IfHCIn-group;
        }

        container dbgIfHCOut-items {

            // Added containment as a singleton: Prefix=dbgIfHCOut
            // Acquired From Package rmon
            uses rmon_IfHCOut-group;
        }

        container dbgIpv6IfStats-items {

            // Added containment as a singleton: Prefix=dbgIpv6IfStats
            // Acquired From Package rmon
            uses rmon_Ipv6IfStats-group;
        }

        container dbgIfStorm-items {

            // Added containment as a singleton: Prefix=dbgIfStorm
            // Acquired From Package rmon
            uses rmon_IfStorm-group;
        }
    }

    grouping ipqos_PriorFlowCtrl-group {

        // priority mode
        // Type is an MO-Defined-Type
        leaf mode {
            description "mode on/off/auto";

            // Type is an MO-Defined-Type
            type ipqos_PriorFlowCtrlMode;
        }
    }

    grouping l1_PhysIfExtended-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Inherited From l1:EthIfExtended
        // Type is an MO-Defined-Type
        leaf routerMacIpv6Extract {
            description "Disable/enable switchport ipv6 extract";

            // Type is an MO-Defined-Type
            type l1_RouterMacIpv6Extract;
        }

        // Inherited From l1:EthIfExtended
        // Type is an MO-Defined-Type
        leaf switchportBlock {
            description "Disable/enable switchport block on interface";

            // Type is an MO-Defined-Type
            type l1_SwitchportBlock;
        }

        // Inherited From l1:EthIfExtended
        // Type is an MO-Defined-Type
        leaf flowCtrl {
            description "Disable/enable flowcontrol block on interface";

            // Type is an MO-Defined-Type
            type l1_FlowControl;
        }

        // Inherited From l1:EthIfExtended
        // Type is an MO-Defined-Type
        leaf stormCtrlBCastLevel {
            description "storm-control broadcast level";

            // Type is an MO-Defined-Type
            type l1_StormCtrlRate;
        }

        // Inherited From l1:EthIfExtended
        // Type is an MO-Defined-Type
        leaf stormCtrlMCastLevel {
            description "storm-control multicast level";

            // Type is an MO-Defined-Type
            type l1_StormCtrlRate;
        }

        // Inherited From l1:EthIfExtended
        // Type is an MO-Defined-Type
        leaf stormCtrlUCastLevel {
            description "Storm control unicast level";

            // Type is an MO-Defined-Type
            type l1_StormCtrlRate;
        }

        // Inherited From l1:EthIfExtended
        // Type is an MO-Defined-Type
        leaf stormCtrlAct {
            description "Storm control action";

            // Type is an MO-Defined-Type
            type l1_StormCtrlAct;
        }

        // Inherited From l1:EthIfExtended
        // Type is an MO-Defined-Type
        leaf bufferBoost {
            description "Disable/enable buffer boost on interface";

            // Type is an MO-Defined-Type
            type l1_BufferBoost;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping l1_EeeP-group {

        // Administrative state for port energy efficient
        // ethernet (EEE)    @@@ Its by default enabled on every port. No need to
        // @@@ expose in IFC
        // Type is an MO-Defined-Type
        leaf eeeState {
            description "EEE State";

            // Type is an MO-Defined-Type
            type l1_EEEState;
        }

        // Administrative port EEE Lpi threshold    @@@ Its by default enabled on every port. No need to
        // @@@ expose in IFC
        // Type is an MO-Defined-Type
        leaf eeeLpi {
            description "EEE Lpi Threshold";

            // Type is an MO-Defined-Type
            type l1_EEELpi;
        }

        // Administrative port EEE Latency    @@@ Its by default enabled on every port. No need to
        // @@@ expose in IFC
        // Type is an MO-Defined-Type
        leaf eeeLat {
            description "EEE Latency";

            // Type is an MO-Defined-Type
            type l1_EEELatency;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping l1_StormCtrlP-group {

        // Packet Type - Unknwn Ucast/Mcast/Bcast
        // Type is an MO-Defined-Type
        leaf type {
            description "Packet Type";

            // Type is an MO-Defined-Type
            type l1_PktT;
        }

        // Max Rate Allowed
        // Type is an MO-Defined-Type
        leaf rate {
            description "Traffic rate";

            // Type is an MO-Defined-Type
            type l1_StormCtrlRate;
        }

        // Max Burst Rate Allowed
        // Type is an MO-Defined-Type
        leaf burstRate {
            description "Max burst size";

            // Type is an MO-Defined-Type
            type l1_StormCtrlRate;
        }

        // Max Rate Allowed in PPS
        // Type is an MO-Defined-Type
        leaf ratePps {
            description "Tarffic rate";

            // Type is an MO-Defined-Type
            type l1_StormCtrlPps;
        }

        // Max Burst Rate Allowed in PPS
        // Type is an MO-Defined-Type
        leaf burstPps {
            description "Max burst size";

            // Type is an MO-Defined-Type
            type l1_StormCtrlPps;
        }
    }

    grouping l1_LoadP-group {

        // Administrative port load interval 1    @@@ This property gets filled up from stats policy
        // Type is an MO-Defined-Type
        leaf loadIntvl1 {
            description "Load Interval";

            // Type is an MO-Defined-Type
            type l1_LoadIntvl;
        }

        // Administrative port load interval 2    @@@ This property gets filled up from stats policy
        // Type is an MO-Defined-Type
        leaf loadIntvl2 {
            description "Load Interval";

            // Type is an MO-Defined-Type
            type l1_LoadIntvl;
        }

        // Administrative port load interval 3    @@@ This property gets filled up from stats policy
        // Type is an MO-Defined-Type
        leaf loadIntvl3 {
            description "Load Interval";

            // Type is an MO-Defined-Type
            type l1_LoadIntvl;
        }
    }

    grouping l1_VlanMapping-group {
        leaf Enabled {
            type boolean;
            default "false";
        }
        leaf DefaultDrop {
            type boolean;
            default "true";
        }

        // Vlan Translate Table policy
        container vlantranslatetable-items {

            // Added containment as a singleton: Prefix=vlantranslatetable
            // Acquired From Package l1
            uses l1_VlanTranslateTable-group;
        }
    }

    grouping l1_VlanTranslateTable-group {

        // Vlan Translate Table policy    Vlan Translate Entry policy
        container vlan-items {
            list VlanTranslateEntry-list {
                key "vlanid";

                // Added containment: Prefix=vlan
                // Acquired From Package l1
                uses l1_VlanTranslateEntry-group;
            }
        }
    }

    grouping l1_VlanTranslateEntry-group {

        // Type is an MO-Defined-Type
        leaf vlanid {
            description "Vlan Id";

            // Type is an MO-Defined-Type
            type l1_translatevlanid;
        }

        // Type is an MO-Defined-Type
        leaf innervlanid {
            description "Inner Vlan Id";

            // Type is an MO-Defined-Type
            type l1_translatevlanid;
        }

        // Type is an MO-Defined-Type
        leaf translatevlanid {
            description "Translate Vlan Id";

            // Type is an MO-Defined-Type
            type l1_translatevlanid;
        }
    }

    grouping l1_Vrf-group {

        // Vrf Name...
        // Type is an MO-Defined-Type
        leaf name {
            config "false";
            description "Vrf Name";

            // Type is an MO-Defined-Type
            type l3_VrfName;
        }
    }

    grouping ethpm_PhysIf-group {

        // Type is an MO-Defined-Type
        leaf operLinkDebounce {
            description "Link Debounce Interval";

            // Type is an MO-Defined-Type
            type l1_LinkDebounce;
        }
        leaf ifIndex {
            config "false";
            type uint32;
            default "0";
        }

        // Inherited From ethpm:If
        // Type is an MO-Defined-Type
        leaf operAutoNeg {
            config "false";
            description "negotiate auto";

            // Type is an MO-Defined-Type
            type l1_AutoNeg;
        }

        // Inherited From ethpm:If
        // Type is an MO-Defined-Type
        leaf operMtu {
            config "false";
            description "Maximum transmission unit";

            // Type is an MO-Defined-Type
            type l1_Mtu;
        }

        // Inherited From ethpm:If
        // Type is an MO-Defined-Type
        leaf adminSt {
            config "false";
            description "Administrative State";

            // Type is an MO-Defined-Type
            type l1_AdminSt;
        }

        // Inherited From ethpm:If
        // Type is an MO-Defined-Type
        leaf operDescr {
            config "false";
            description "Description";

            // Type is an MO-Defined-Type
            type ethpm_operDescr;
        }

        // Operational state summary
        // Inherited From ethpm:If
        // Type is an MO-Defined-Type
        leaf osSum {
            config "false";
            description "Operational State Summary";

            // Type is an MO-Defined-Type
            type nw_OSSum;
        }

        // Operational port state
        // Inherited From ethpm:If
        // Type is an MO-Defined-Type
        leaf operSt {
            config "false";
            description "Operational State";

            // Type is an MO-Defined-Type
            type l1_OperSt;
        }

        // Operational port status reason
        // Inherited From ethpm:If
        // Type is an MO-Defined-Type
        leaf operStQual {
            config "false";
            description "Operational State Qualifier";

            // Type is an MO-Defined-Type
            type l1_OperStQual;
        }

        // Operational port status syserror code
        // Inherited From ethpm:If
        // Type is an MO-Defined-Type
        leaf operStQualCode {
            config "false";
            description "Operational State Qualifier Code";

            // Type is an MO-Defined-Type
            type l1_OperStQualCode;
        }

        // Operational port err disable reason code
        // Inherited From ethpm:If
        // Type is an MO-Defined-Type
        leaf operErrDisQual {
            config "false";
            description "Operational Error Disable Qualifier";

            // Type is an MO-Defined-Type
            type l1_OperErrDisQual;
        }

        // Operational port speed
        // Inherited From ethpm:If
        // Type is an MO-Defined-Type
        leaf operSpeed {
            config "false";
            description "Operational Speed";

            // Type is an MO-Defined-Type
            type l1_Speed;
        }

        // Operational port mode
        // Inherited From ethpm:If
        // Type is an MO-Defined-Type
        leaf operMode {
            config "false";
            description "Operational Mode";

            // Type is an MO-Defined-Type
            type l1_Mode;
        }

        // Operational duplex
        // Inherited From ethpm:If
        // Type is an MO-Defined-Type
        leaf operDuplex {
            config "false";
            description "Operational Duplex";

            // Type is an MO-Defined-Type
            type l1_Duplex;
        }

        // Operational port flow control
        // Inherited From ethpm:If
        // Type is an MO-Defined-Type
        leaf operFlowCtrl {
            config "false";
            description "Operational Flow Control";

            // Type is an MO-Defined-Type
            type l1_FlowControl;
        }

        // Operational phy port enable state
        // Inherited From ethpm:If
        // Type is an MO-Defined-Type
        leaf operPhyEnSt {
            config "false";
            description "Operational Physical Port Enable State";

            // Type is an MO-Defined-Type
            type l1_OperSt;
        }
        leaf backplaneMac {
            config "false";
            type address_Mac;
        }
        leaf operRouterMac {
            config "false";
            type address_Mac;
        }

        // port Tx type
        // Inherited From ethpm:If
        // Type is an MO-Defined-Type
        leaf txT {
            config "false";
            description "Transmit Type";

            // Type is an MO-Defined-Type
            type l1_TxT;
        }
        leaf lastLinkStChg {
            config "false";
            type uint64;
        }
        leaf lastClear {
            config "false";
            type uint64;
        }
        leaf portCfgWaitFlags {
            config "false";
            type uint32;
        }
        leaf accessVlan {
            config "false";
            type string;
        }
        leaf nativeVlan {
            config "false";
            type string;
        }
        leaf cfgNativeVlan {
            config "false";
            type string;
        }
        leaf cfgAccessVlan {
            config "false";
            type string;
        }
        leaf primaryVlan {
            config "false";
            type string;
        }

        // port oper bitset
        // Inherited From ethpm:If
        // Type is an MO-Defined-Type
        leaf operBitset {
            config "false";
            description "Port Oper Bitset";

            // Type is an MO-Defined-Type
            type ethpm_PortOperBitmap;
        }

        // vdc id
        // Inherited From ethpm:If
        // Type is an MO-Defined-Type
        leaf vdcId {
            config "false";
            description "Vdc Id";

            // Type is an MO-Defined-Type
            type l2_VdcId;
        }
        leaf resetCtr {
            config "false";
            type uint32;
        }
        leaf media {
            config "false";
            type uint32;
        }
        leaf encap {
            config "false";
            type uint32;
        }
        leaf iod {
            config "false";
            type uint64;
        }

        // allowed vlans
        // Inherited From ethpm:If
        // Type is an MO-Defined-Type
        leaf allowedVlans {
            config "false";
            description "Allowed Vlans";

            // Type is an MO-Defined-Type
            type l2_VlanBitmap;
        }

        // operational vlans
        // Inherited From ethpm:If
        // Type is an MO-Defined-Type
        leaf operVlans {
            config "false";
            description "Operational Vlans";

            // Type is an MO-Defined-Type
            type l2_VlanBitmap;
        }

        // errored vlans
        // Inherited From ethpm:If
        // Type is an MO-Defined-Type
        leaf errVlans {
            config "false";
            description "Errored Vlans";

            // Type is an MO-Defined-Type
            type l2_VlanBitmap;
        }

        // autostate exclude vlans
        // Inherited From ethpm:If
        // Type is an MO-Defined-Type
        leaf autostateExcludeVlans {
            config "false";
            description "Autostate Exclude Vlans";

            // Type is an MO-Defined-Type
            type l2_VlanBitmap;
        }

        // bundle index
        // Inherited From ethpm:If
        // Type is an MO-Defined-Type
        leaf bundleIndex {
            config "false";
            description "Bundle Index";

            // Type is an MO-Defined-Type
            type nw_IfId;
        }

        // port oper mdix mode
        // Inherited From ethpm:If
        // Type is an MO-Defined-Type
        leaf operMdix {
            config "false";
            description "Port Oper Mdix Mode";

            // Type is an MO-Defined-Type
            type l1_Mdix;
        }
        leaf currErrIndex {
            config "false";
            type uint32;
        }

        // last seen errors
        // Inherited From ethpm:If
        // Type is an MO-Defined-Type
        leaf lastErrors {
            config "false";
            description "Last Seen Errors";

            // Type is an MO-Defined-Type
            type ethpm_LastErrorsList;
        }
        leaf errDisTimerRunning {
            config "false";
            type boolean;
        }
        leaf bundleBupId {
            config "false";
            type uint32;
        }

        // port per vlan error state
        // Inherited From ethpm:If
        // Type is an MO-Defined-Type
        leaf errVlanStatusHt {
            config "false";
            description "Port Per Vlan Error State";

            // Type is an MO-Defined-Type
            type ethpm_ErrorVlanStatusList;
        }

        // Operational Dce Mode
        // Inherited From ethpm:If
        // Type is an MO-Defined-Type
        leaf operDceMode {
            config "false";
            description "Operational Dce Mode";

            // Type is an MO-Defined-Type
            type l1_DceMode;
        }

        // interface type
        // Inherited From ethpm:If
        // Type is an MO-Defined-Type
        leaf intfT {
            config "false";
            description "Interface Type";

            // Type is an MO-Defined-Type
            type l1_IntfT;
        }

        // port diags type
        // Inherited From ethpm:If
        // Type is an MO-Defined-Type
        leaf diags {
            config "false";
            description "Port Diags Type";

            // Type is an MO-Defined-Type
            type l1_DiagsT;
        }

        // Operational port EEE state
        // Inherited From ethpm:If
        // Type is an MO-Defined-Type
        leaf operEEEState {
            config "false";
            description "Operational Port EEE State";

            // Type is an MO-Defined-Type
            type l1_EEEState;
        }
        leaf operEEETxWkTime {
            config "false";
            type uint32;
        }
        leaf operEEERxWkTime {
            config "false";
            type uint32;
        }

        // port user config flags
        // Inherited From ethpm:If
        // Type is an MO-Defined-Type
        leaf userCfgdFlags {
            config "false";
            description "Port User Config Flags";

            // Type is an MO-Defined-Type
            type l1_userCfgdFlags;
        }
        leaf numOfSI {
            config "false";
            type uint32;
        }
        leaf gport {
            config "false";
            type uint32;
        }

        // configured sub-interface ids
        // Inherited From ethpm:If
        // Type is an MO-Defined-Type
        leaf siList {
            config "false";
            description "Configured Sub-interface Ids";

            // Type is an MO-Defined-Type
            type ethpm_SiBitmap;
        }

        // hw bd id (allocated for l3 ports, port-channels)
        // Inherited From ethpm:If
        // Type is an MO-Defined-Type
        leaf hwBdId {
            config "false";
            description "Hw Bd Id (allocated for L3 Ports, Port-channels)";

            // Type is an MO-Defined-Type
            type l2_DomId;
        }

        // Usage of the port: Fabric, Infra, Epg, Controller, Discovery   @@@ This property is not exposed in IFC
        // Liked from l1:EthIf:usage
        // Inherited From ethpm:If
        // Type is an MO-Defined-Type
        leaf usage {
            config "false";
            description "Port Usage";

            // Type is an MO-Defined-Type
            type l1_PortUsage;
        }

        // This is the class for regualr fcot types.
        container fcot-items {

            // Added containment as a singleton: Prefix=fcot
            // Acquired From Package ethpm
            uses ethpm_Fcot-group;
        }

        // This is the class for X2 fcot types.
        container fcotx2-items {

            // Added containment as a singleton: Prefix=fcotx2
            // Acquired From Package ethpm
            uses ethpm_FcotX2-group;
        }

        container portcap-items {

            // Added containment as a singleton: Prefix=portcap
            // Acquired From Package ethpm
            uses ethpm_PortCap-group;
        }
    }

    grouping ethpm_Fcot-group {
        leaf fcotStatus {
            config "false";
            type uint8;
        }

        // Fcot part number
        // Inherited From ethpm:FcotBase
        // Type is an MO-Defined-Type
        leaf partNumber {
            config "false";
            description "Part Number";

            // Type is an MO-Defined-Type
            type ethpm_SfpPartNumberBytes;
        }

        // Fcot version id
        // Inherited From ethpm:FcotBase
        // Type is an MO-Defined-Type
        leaf versionId {
            config "false";
            description "Version ID";

            // Type is an MO-Defined-Type
            type ethpm_SfpVersionIdBytes;
        }

        // Fcot description
        // Inherited From ethpm:FcotBase
        // Type is an MO-Defined-Type
        leaf description {
            config "false";
            description "Description";

            // Type is an MO-Defined-Type
            type ethpm_SfpDescriptionBytes;
        }
        leaf isFcotPresent {
            config "false";
            type boolean;
        }

        // Fcot state
        // Inherited From ethpm:FcotBase
        // Type is an MO-Defined-Type
        leaf state {
            config "false";
            description "State";

            // Type is an MO-Defined-Type
            type ethpm_FcotState;
        }

        // Fcot flags
        // Inherited From ethpm:FcotBase
        // Type is an MO-Defined-Type
        leaf flags {
            config "false";
            description "Flags";

            // Type is an MO-Defined-Type
            type ethpm_FcotFlags;
        }

        // Fcot type
        // Inherited From ethpm:FcotBase
        // Type is an MO-Defined-Type
        leaf type {
            config "false";
            description "Type";

            // Type is an MO-Defined-Type
            type ethpm_FcotType;
        }
        leaf typeName {
            config "false";
            type string;
        }
        leaf guiName {
            config "false";
            type string;
        }
        leaf guiPN {
            config "false";
            type string;
        }
        leaf guiRev {
            config "false";
            type string;
        }
        leaf guiSN {
            config "false";
            type string;
        }
        leaf guiCiscoPN {
            config "false";
            type string;
        }
        leaf guiCiscoPID {
            config "false";
            type string;
        }
        leaf guiCiscoEID {
            config "false";
            type string;
        }
        leaf xcvrId {
            config "false";
            type uint8;
        }
        leaf xcvrExtId {
            config "false";
            type uint8;
        }
        leaf connectType {
            config "false";
            type uint8;
        }

        // Xcvr code field
        // Inherited From ethpm:AFcot
        // Type is an MO-Defined-Type
        leaf xcvrCode {
            config "false";
            description "Transceiver Code";

            // Type is an MO-Defined-Type
            type ethpm_SfpXcvrCodeBytes;
        }
        leaf encoding {
            config "false";
            type uint8;
        }
        leaf brIn100MHz {
            config "false";
            type uint8;
        }
        leaf baseResvd1 {
            config "false";
            type uint8;
        }
        leaf distInKmFor9u {
            config "false";
            type uint8;
        }
        leaf distIn100mFor9u {
            config "false";
            type uint8;
        }
        leaf distIn10mFor50u {
            config "false";
            type uint8;
        }
        leaf distIn10mFor60u {
            config "false";
            type uint8;
        }
        leaf distIn1mForCu {
            config "false";
            type uint8;
        }
        leaf baseResvd2 {
            config "false";
            type uint8;
        }

        // Vendor name
        // Inherited From ethpm:AFcot
        // Type is an MO-Defined-Type
        leaf vendorName {
            config "false";
            description "Vendor Name";

            // Type is an MO-Defined-Type
            type ethpm_SfpVendorNameBytes;
        }
        leaf baseResvd3 {
            config "false";
            type uint8;
        }

        // IEEE vendor Id
        // Inherited From ethpm:AFcot
        // Type is an MO-Defined-Type
        leaf vendorId {
            config "false";
            description "Vendor ID";

            // Type is an MO-Defined-Type
            type ethpm_SfpVendorIdBytes;
        }

        // Vendor part number
        // Inherited From ethpm:AFcot
        // Type is an MO-Defined-Type
        leaf vendorPn {
            config "false";
            description "Vendor Part Number";

            // Type is an MO-Defined-Type
            type ethpm_VendorPartNumberBytes;
        }

        // Vendor revision number
        // Inherited From ethpm:AFcot
        // Type is an MO-Defined-Type
        leaf vendorRev {
            config "false";
            description "Vendor Revision";

            // Type is an MO-Defined-Type
            type ethpm_SfpVendorRevisionNumberBytes;
        }

        // Reserved field 4
        // Inherited From ethpm:AFcot
        // Type is an MO-Defined-Type
        leaf baseResvd4 {
            config "false";
            description "Base Reserved Field";

            // Type is an MO-Defined-Type
            type ethpm_SfpReserved4Array;
        }
        leaf ccid {
            config "false";
            type uint8;
        }

        // Extended option
        // Inherited From ethpm:AFcot
        // Type is an MO-Defined-Type
        leaf extOption {
            config "false";
            description "Extended Option";

            // Type is an MO-Defined-Type
            type ethpm_SfpExtendedOptionBytes;
        }
        leaf brMaxMargin {
            config "false";
            type uint8;
        }
        leaf brMinMargin {
            config "false";
            type uint8;
        }

        // Vendor serial number
        // Inherited From ethpm:AFcot
        // Type is an MO-Defined-Type
        leaf vendorSn {
            config "false";
            description "TBD";

            // Type is an MO-Defined-Type
            type ethpm_SfpVendorSerialNumberBytes;
        }

        // Date code
        // Inherited From ethpm:AFcot
        // Type is an MO-Defined-Type
        leaf dateCode {
            config "false";
            description "TBD";

            // Type is an MO-Defined-Type
            type ethpm_SfpDateCodeBytes;
        }
        leaf diagMonType {
            config "false";
            type uint8;
        }
        leaf enhOption {
            config "false";
            type uint8;
        }
        leaf sff8472Compl {
            config "false";
            type uint8;
        }
        leaf ccex {
            config "false";
            type uint8;
        }

        // Vendor data
        // Inherited From ethpm:AFcot
        // Type is an MO-Defined-Type
        leaf vendorData {
            config "false";
            description "TBD";

            // Type is an MO-Defined-Type
            type ethpm_X2VendorDataBytes;
        }
        leaf maxSpeed {
            config "false";
            type uint32;
        }
        leaf minSpeed {
            config "false";
            type uint32;
        }
        leaf fcotNum {
            config "false";
            type uint8;
        }
        leaf fcotType {
            config "false";
            type uint8;
        }
        leaf gigEthCC {
            config "false";
            type uint8;
        }
        leaf fCTxType {
            config "false";
            type uint8;
        }
    }

    grouping ethpm_FcotX2-group {
        leaf fcotStatus {
            config "false";
            type uint8;
        }

        // Fcot part number
        // Inherited From ethpm:FcotBase
        // Type is an MO-Defined-Type
        leaf partNumber {
            config "false";
            description "Part Number";

            // Type is an MO-Defined-Type
            type ethpm_SfpPartNumberBytes;
        }

        // Fcot version id
        // Inherited From ethpm:FcotBase
        // Type is an MO-Defined-Type
        leaf versionId {
            config "false";
            description "Version ID";

            // Type is an MO-Defined-Type
            type ethpm_SfpVersionIdBytes;
        }

        // Fcot description
        // Inherited From ethpm:FcotBase
        // Type is an MO-Defined-Type
        leaf description {
            config "false";
            description "Description";

            // Type is an MO-Defined-Type
            type ethpm_SfpDescriptionBytes;
        }
        leaf isFcotPresent {
            config "false";
            type boolean;
        }

        // Fcot state
        // Inherited From ethpm:FcotBase
        // Type is an MO-Defined-Type
        leaf state {
            config "false";
            description "State";

            // Type is an MO-Defined-Type
            type ethpm_FcotState;
        }

        // Fcot flags
        // Inherited From ethpm:FcotBase
        // Type is an MO-Defined-Type
        leaf flags {
            config "false";
            description "Flags";

            // Type is an MO-Defined-Type
            type ethpm_FcotFlags;
        }

        // Fcot type
        // Inherited From ethpm:FcotBase
        // Type is an MO-Defined-Type
        leaf type {
            config "false";
            description "Type";

            // Type is an MO-Defined-Type
            type ethpm_FcotType;
        }
        leaf typeName {
            config "false";
            type string;
        }
        leaf guiName {
            config "false";
            type string;
        }
        leaf guiPN {
            config "false";
            type string;
        }
        leaf guiRev {
            config "false";
            type string;
        }
        leaf guiSN {
            config "false";
            type string;
        }
        leaf guiCiscoPN {
            config "false";
            type string;
        }
        leaf guiCiscoPID {
            config "false";
            type string;
        }
        leaf guiCiscoEID {
            config "false";
            type string;
        }
        leaf xcvrType {
            config "false";
            type uint8;
        }
        leaf connectType {
            config "false";
            type uint8;
        }
        leaf bitEncoding {
            config "false";
            type uint8;
        }

        // Bit rate (Mbps)
        // Inherited From ethpm:AFcotX2
        // Type is an MO-Defined-Type
        leaf bitRateMbps {
            config "false";
            description "TBD";

            // Type is an MO-Defined-Type
            type ethpm_X2BitRateBytes;
        }
        leaf protocolType {
            config "false";
            type uint8;
        }

        // 10G eth code
        // Inherited From ethpm:AFcotX2
        // Type is an MO-Defined-Type
        leaf xgEthCode {
            config "false";
            description "TBD";

            // Type is an MO-Defined-Type
            type ethpm_X2XgEthCodeBytes;
        }

        // Sonet SDH code
        // Inherited From ethpm:AFcotX2
        // Type is an MO-Defined-Type
        leaf sonetSdhCode {
            config "false";
            description "TBD";

            // Type is an MO-Defined-Type
            type ethpm_X2SonetSdhCodeBytes;
        }

        // 10G fc code
        // Inherited From ethpm:AFcotX2
        // Type is an MO-Defined-Type
        leaf xgFcCode {
            config "false";
            description "TBD";

            // Type is an MO-Defined-Type
            type ethpm_X2XbFcCodeBytes;
        }

        // Range
        // Inherited From ethpm:AFcotX2
        // Type is an MO-Defined-Type
        leaf range {
            config "false";
            description "TBD";

            // Type is an MO-Defined-Type
            type ethpm_X2RangeBytes;
        }

        // Fibre type
        // Inherited From ethpm:AFcotX2
        // Type is an MO-Defined-Type
        leaf fibreType {
            config "false";
            description "TBD";

            // Type is an MO-Defined-Type
            type ethpm_X2FibreTypeBytes;
        }

        // Wavelength channel 0
        // Inherited From ethpm:AFcotX2
        // Type is an MO-Defined-Type
        leaf waveLenCh0 {
            config "false";
            description "TBD";

            // Type is an MO-Defined-Type
            type ethpm_X2WavelengthChannelBytes;
        }

        // Wavelength channel 1
        // Inherited From ethpm:AFcotX2
        // Type is an MO-Defined-Type
        leaf waveLenCh1 {
            config "false";
            description "TBD";

            // Type is an MO-Defined-Type
            type ethpm_X2WavelengthChannelBytes;
        }

        // Wavelength channel 2
        // Inherited From ethpm:AFcotX2
        // Type is an MO-Defined-Type
        leaf waveLenCh2 {
            config "false";
            description "TBD";

            // Type is an MO-Defined-Type
            type ethpm_X2WavelengthChannelBytes;
        }

        // Wavelength channel 3
        // Inherited From ethpm:AFcotX2
        // Type is an MO-Defined-Type
        leaf waveLenCh3 {
            config "false";
            description "TBD";

            // Type is an MO-Defined-Type
            type ethpm_X2WavelengthChannelBytes;
        }

        // Package Oui
        // Inherited From ethpm:AFcotX2
        // Type is an MO-Defined-Type
        leaf packageOui {
            config "false";
            description "TBD";

            // Type is an MO-Defined-Type
            type ethpm_X2PackageOuiBytes;
        }

        // Vendor Oui
        // Inherited From ethpm:AFcotX2
        // Type is an MO-Defined-Type
        leaf vendorOui {
            config "false";
            description "TBD";

            // Type is an MO-Defined-Type
            type ethpm_X2VendorOuiBytes;
        }

        // Vendor name
        // Inherited From ethpm:AFcotX2
        // Type is an MO-Defined-Type
        leaf vendorName {
            config "false";
            description "TBD";

            // Type is an MO-Defined-Type
            type ethpm_X2VendorNameBytes;
        }

        // Vendor Part number
        // Inherited From ethpm:AFcotX2
        // Type is an MO-Defined-Type
        leaf vendorPn {
            config "false";
            description "TBD";

            // Type is an MO-Defined-Type
            type ethpm_X2VendorPartNumberBytes;
        }

        // Vendor revision
        // Inherited From ethpm:AFcotX2
        // Type is an MO-Defined-Type
        leaf vendorRev {
            config "false";
            description "TBD";

            // Type is an MO-Defined-Type
            type ethpm_X2VendorRevisionBytes;
        }

        // Vendor serial number
        // Inherited From ethpm:AFcotX2
        // Type is an MO-Defined-Type
        leaf vendorSerNo {
            config "false";
            description "TBD";

            // Type is an MO-Defined-Type
            type ethpm_X2VendorSerialNumberBytes;
        }

        // Date code
        // Inherited From ethpm:AFcotX2
        // Type is an MO-Defined-Type
        leaf dateCode {
            config "false";
            description "TBD";

            // Type is an MO-Defined-Type
            type ethpm_X2DateCodeBytes;
        }

        // Lot code
        // Inherited From ethpm:AFcotX2
        // Type is an MO-Defined-Type
        leaf lotCode {
            config "false";
            description "TBD";

            // Type is an MO-Defined-Type
            type ethpm_X2LotCodeBytes;
        }
        leaf fiveVStressEnv {
            config "false";
            type uint8;
        }
        leaf threeThreeVStressEnv {
            config "false";
            type uint8;
        }
        leaf apsStressEnv {
            config "false";
            type uint8;
        }
        leaf normalApsVolt {
            config "false";
            type uint8;
        }
        leaf diagOptMonCap {
            config "false";
            type uint8;
        }
        leaf lowPwrStartupCap {
            config "false";
            type uint8;
        }
        leaf reserved {
            config "false";
            type uint8;
        }
        leaf checksum {
            config "false";
            type uint8;
        }

        // Cisco PID
        // Inherited From ethpm:AFcotX2
        // Type is an MO-Defined-Type
        leaf ciscoPid {
            config "false";
            description "TBD";

            // Type is an MO-Defined-Type
            type ethpm_X2CiscoPidBytes;
        }

        // Cisco vendor ID
        // Inherited From ethpm:AFcotX2
        // Type is an MO-Defined-Type
        leaf ciscoVid {
            config "false";
            description "TBD";

            // Type is an MO-Defined-Type
            type ethpm_X2CiscoVendorIdBytes;
        }

        // Cisco serial number
        // Inherited From ethpm:AFcotX2
        // Type is an MO-Defined-Type
        leaf ciscoSN {
            config "false";
            description "TBD";

            // Type is an MO-Defined-Type
            type ethpm_X2CiscoSerialNumberBytes;
        }

        // Cisco part number
        // Inherited From ethpm:AFcotX2
        // Type is an MO-Defined-Type
        leaf ciscoPN {
            config "false";
            description "TBD";

            // Type is an MO-Defined-Type
            type ethpm_X2CiscoPartNumberBytes;
        }

        // Cisco revision number
        // Inherited From ethpm:AFcotX2
        // Type is an MO-Defined-Type
        leaf ciscoRev {
            config "false";
            description "TBD";

            // Type is an MO-Defined-Type
            type ethpm_X2CiscoRevisionNumberBytes;
        }

        // Extended vendor specific info
        // Inherited From ethpm:AFcotX2
        // Type is an MO-Defined-Type
        leaf extVendorSpecific {
            config "false";
            description "TBD";

            // Type is an MO-Defined-Type
            type ethpm_X2ExtendedVendorSpecificInfoBytes;
        }
        leaf maxSpeed {
            config "false";
            type uint32;
        }
        leaf minSpeed {
            config "false";
            type uint32;
        }
        leaf fcotNum {
            config "false";
            type uint8;
        }
        leaf fcotType {
            config "false";
            type uint8;
        }
        leaf gigEthCC {
            config "false";
            type uint8;
        }
        leaf fCTxType {
            config "false";
            type uint8;
        }
    }

    grouping ethpm_PortCap-group {

        // If-index
        // Type is an MO-Defined-Type
        leaf id {
            config "false";
            description "If-index";

            // Type is an MO-Defined-Type
            type nw_IfId;
        }

        // Speed bitmask
        // Type is an MO-Defined-Type
        leaf speed {
            config "false";
            description "Speed Bitmask";

            // Type is an MO-Defined-Type
            type ethpm_capSpeed;
        }

        // Duplex bitmask
        // Type is an MO-Defined-Type
        leaf duplex {
            config "false";
            description "Duplex Bitmask";

            // Type is an MO-Defined-Type
            type ethpm_capDuplex;
        }
        leaf trunkEncap {
            config "false";
            type uint8;
        }
        leaf channel {
            config "false";
            type uint8;
        }
        leaf suppression {
            config "false";
            type uint8;
        }
        leaf rxFlowControl {
            config "false";
            type uint8;
        }
        leaf txFlowControl {
            config "false";
            type uint8;
        }
        leaf cosRewrite {
            config "false";
            type uint8;
        }
        leaf tosRewrite {
            config "false";
            type uint8;
        }
        leaf span {
            config "false";
            type uint8;
        }
        leaf udld {
            config "false";
            type uint8;
        }
        leaf autoneg {
            config "false";
            type uint8;
        }
        leaf linkDebounce {
            config "false";
            type uint8;
        }
        leaf linkDebounceTime {
            config "false";
            type uint8;
        }
        leaf fcotCapable {
            config "false";
            type uint8;
        }
        leaf rateMode {
            config "false";
            type uint8;
        }
        leaf mdix {
            config "false";
            type uint8;
        }
        leaf portGroup {
            config "false";
            type uint8;
        }
        leaf ctsCapable {
            config "false";
            type uint8;
        }
        leaf qosRxPrio {
            config "false";
            type uint8;
        }
        leaf qosRxQueue {
            config "false";
            type uint8;
        }
        leaf qosRxThold {
            config "false";
            type uint8;
        }
        leaf qosTxPrio {
            config "false";
            type uint8;
        }
        leaf qosTxQueue {
            config "false";
            type uint8;
        }
        leaf qosTxThold {
            config "false";
            type uint8;
        }

        // Model
        // Type is an MO-Defined-Type
        leaf model {
            config "false";
            description "Model";

            // Type is an MO-Defined-Type
            type ethpm_ModelList;
        }

        // Type
        // Type is an MO-Defined-Type
        leaf type {
            config "false";
            description "Type";

            // Type is an MO-Defined-Type
            type ethpm_TypeList;
        }

        // Port-group members
        // Type is an MO-Defined-Type
        leaf portGrpMbrs {
            config "false";
            description "Port-group Member";

            // Type is an MO-Defined-Type
            type ethpm_PortGroupBitmap;
        }
        leaf protoSupport {
            config "false";
            type uint32;
        }
        leaf portCap {
            config "false";
            type uint32;
        }
        leaf eeeCapVal {
            config "false";
            type uint16;
        }

        // EEE 10G wake times
        // Type is an MO-Defined-Type
        leaf eeeWakeTimes10g {
            config "false";
            description "EEE 10G Wake Times";

            // Type is an MO-Defined-Type
            type ethpm_EeeWakeTimesList;
        }
        leaf eeeFlapFlags {
            config "false";
            type uint16;
        }
        leaf bufferBoost {
            config "false";
            type uint16;
        }
    }

    grouping pc_AggrMbrIf-group {

        // Operational state
        // Type is an MO-Defined-Type
        leaf operSt {
            config "false";
            description "Operational State";

            // Type is an MO-Defined-Type
            type pc_OperSt;
        }

        // Channeling status
        // Type is an MO-Defined-Type
        leaf channelingSt {
            config "false";
            description "Channeling Status";

            // Type is an MO-Defined-Type
            type pc_ChannelingSt;
        }

        // Summarized operational state
        // Type is an MO-Defined-Type
        leaf summOperSt {
            config "false";
            description "Summarized Oper State";

            // Type is an MO-Defined-Type
            type pc_SummOperSt;
        }

        // Member up time
        // Type is an MO-Defined-Type
        leaf uptime {
            config "false";
            description "Member Up Time";

            // Type is an MO-Defined-Type
            type pc_Time;
        }

        // Member port flags
        // Type is an MO-Defined-Type
        leaf flags {
            config "false";
            description "Member Port Flags";

            // Type is an MO-Defined-Type
            type pc_Flags;
        }

        // Bundle port number
        // Type is an MO-Defined-Type
        leaf bdlPortNum {
            config "false";
            description "Bundle Port Number";

            // Type is an MO-Defined-Type
            type pc_BdlPortNum;
        }

        // LTL programmed
        // Type is an MO-Defined-Type
        leaf ltlProgrammed {
            config "false";
            description "LTL Programmed";

            // Type is an MO-Defined-Type
            type pc_LtlProgrammed;
        }

        // From Interface naming:Named
        // Inherited From naming:NamedObject
        // Type is an MO-Defined-Type
        leaf name {
            description "Name";

            // Type is an MO-Defined-Type
            type naming_Name;
        }
    }

    grouping pc_AggrIf-group {

        // Port channel id
        // Type is an MO-Defined-Type
        leaf pcId {
            description "Port Channel Id";

            // Type is an MO-Defined-Type
            type pc_PcId;
        }

        // Channel mode
        // Type is an MO-Defined-Type
        leaf pcMode {
            description "Channel Mode";

            // Type is an MO-Defined-Type
            type pc_Mode;
        }

        // PC interface control properties
        // Type is an MO-Defined-Type
        leaf ctrl {
            description "PC Interface Control Properties";

            // Type is an MO-Defined-Type
            type pc_IfControl;
        }

        // minimum links    @@@ MinLinks in the port channel
        // Type is an MO-Defined-Type
        leaf minLinks {
            description "Minimum Links";

            // Type is an MO-Defined-Type
            type pc_MinLinks;
        }

        // maximum links    @@@ MaxLinks in the port channel
        // Type is an MO-Defined-Type
        leaf maxLinks {
            description "Maximum Links";

            // Type is an MO-Defined-Type
            type pc_MaxLinks;
        }

        // Hash distribution configured - adaptive/fixed
        // Type is an MO-Defined-Type
        leaf hashDist {
            description "Hash Distribution Configured - Adaptive/fixed";

            // Type is an MO-Defined-Type
            type pc_HashDist;
        }

        // Interface ordinal
        // Type is an MO-Defined-Type
        leaf iod {
            config "false";
            description "Interface Ordinal";

            // Type is an MO-Defined-Type
            type pc_Iod;
        }

        // Operational mode
        // Type is an MO-Defined-Type
        leaf operChannelMode {
            config "false";
            description "Operational Mode";

            // Type is an MO-Defined-Type
            type pc_Mode;
        }

        // Last status - successful/failed
        // Type is an MO-Defined-Type
        leaf lastSt {
            config "false";
            description "Last Status - Successful/failed";

            // Type is an MO-Defined-Type
            type pc_LastSt;
        }
        leaf lastStCause {
            config "false";
            type string;
        }

        // Time when last status was set
        // Type is an MO-Defined-Type
        leaf lastTime {
            config "false";
            description "Time when Last Status was Set";

            // Type is an MO-Defined-Type
            type pc_Time;
        }

        // Time of port-channel creation
        // Type is an MO-Defined-Type
        leaf createTime {
            config "false";
            description "Time of Port-channel Creation";

            // Type is an MO-Defined-Type
            type pc_Time;
        }

        // First operational port
        // Type is an MO-Defined-Type
        leaf fop {
            config "false";
            description "First Operational Port";

            // Type is an MO-Defined-Type
            type nw_IfId;
        }

        // Number of active member ports
        // Type is an MO-Defined-Type
        leaf activePorts {
            config "false";
            description "Number of Active Member Ports";

            // Type is an MO-Defined-Type
            type pc_ActivePorts;
        }

        // Time of last member addition
        // Type is an MO-Defined-Type
        leaf lastBundleTime {
            config "false";
            description "Time of Last Member Addition";

            // Type is an MO-Defined-Type
            type pc_Time;
        }

        // Last member added
        // Type is an MO-Defined-Type
        leaf lastBundleMbr {
            config "false";
            description "Last Member Added";

            // Type is an MO-Defined-Type
            type nw_IfId;
        }

        // Time of last member removal
        // Type is an MO-Defined-Type
        leaf lastUnbundleTime {
            config "false";
            description "Time of Last Member Removal";

            // Type is an MO-Defined-Type
            type pc_Time;
        }

        // Last member removed
        // Type is an MO-Defined-Type
        leaf lastUnbundleMbr {
            config "false";
            description "Last Member Removed";

            // Type is an MO-Defined-Type
            type nw_IfId;
        }

        // port-channel suspended due to min-links
        // Type is an MO-Defined-Type
        leaf suspMinlinks {
            config "false";
            description "Port-channel Suspended Due to Min-links";

            // Type is an MO-Defined-Type
            type pc_SuspMinlinks;
        }

        // PIXM-allocated LTL
        // Type is an MO-Defined-Type
        leaf ltl {
            config "false";
            description "PIXM-allocated LTL";

            // Type is an MO-Defined-Type
            type pc_Ltl;
        }

        // ELTM-allocated LIF
        // Type is an MO-Defined-Type
        leaf lif {
            config "false";
            description "ELTM-allocated LIF";

            // Type is an MO-Defined-Type
            type pc_Lif;
        }

        // Max possible active members
        // Type is an MO-Defined-Type
        leaf maxActive {
            config "false";
            description "Max Possible Active Members";

            // Type is an MO-Defined-Type
            type pc_MaxActive;
        }

        // Time when first non-fop port came up
        // Type is an MO-Defined-Type
        leaf loadDeferStartTime {
            config "false";
            description "Time when First Non-fop Port Came Up";

            // Type is an MO-Defined-Type
            type pc_Time;
        }
        leaf isExplicit {
            type boolean;
            default "true";
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Type is an MO-Defined-Type
        leaf adminSt {
            description "Administrative State";

            // Type is an MO-Defined-Type
            type l1_AdminSt;
        }

        // Administrative port speed    @@@ This comes from the host interface
        // @@@ configuration policy
        // Inherited From l1:If
        // Type is an MO-Defined-Type
        leaf speed {
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Administrative port mode    @@@ Internally set by PE
        // Inherited From l1:EthIf
        // Type is an MO-Defined-Type
        leaf mode {
            description "Mode";

            // Type is an MO-Defined-Type
            type l1_Mode;
        }

        // Administrative port layer    @@@ Internally set by PE
        // Inherited From l1:EthIf
        // Modified by Override: pc:AggrIf->layer
        // Type is an MO-Defined-Type
        // Default value handled in local MO type
        leaf layer {
            description "Layer";

            // Type is a Local-MO-Defined-Type
            type l1_Layer_AggrIf_layer;
        }

        // Administrative mdix mode    @@@ Theres no benefit in exposing this property
        // @@@ in IFC. Ask Marketing.
        // Inherited From l1:EthIf
        // Type is an MO-Defined-Type
        leaf mdix {
            description "MDIX";

            // Type is an MO-Defined-Type
            type l1_Mdix;
        }

        // Administrative port delay    @@@ is this exposed in IFC?
        // Inherited From l1:EthIf
        // Type is an MO-Defined-Type
        leaf delay {
            description "Delay";

            // Type is an MO-Defined-Type
            type l1_Delay;
        }

        // Administrative port link debounce interval    @@@ This comes from the interface configuration policy
        // Inherited From l1:EthIf
        // Type is an MO-Defined-Type
        leaf linkDebounce {
            description "Link Debounce Interval";

            // Type is an MO-Defined-Type
            type l1_LinkDebounce;
        }

        // Administrative port dot1q ether-type    @@@ This property is not supported in switch ??
        // Inherited From l1:EthIf
        // Type is an MO-Defined-Type
        leaf dot1qEtherType {
            description "Dot1q Ether Type";

            // Type is an MO-Defined-Type
            type l1_Dot1qEtherType;
        }

        // Administrative port bandwidth    @@@ Comes from QOS Policy
        // Inherited From l1:EthIf
        // Type is an MO-Defined-Type
        leaf bw {
            description "Bandwidth";

            // Type is an MO-Defined-Type
            type l1_Bw;
        }

        // Administrative port medium type    @@@ The fabric & Host connections are P2p.    @@@ No need to expose this property in IFC
        // Inherited From l1:EthIf
        // Type is an MO-Defined-Type
        leaf medium {
            description "Medium";

            // Type is an MO-Defined-Type
            type l1_Medium;
        }

        // Administrative port inherit bandwidth    @@@ It is used for specifying the bandwidth inherited
        // @@@ by the subinterfaces from the parent interface    @@@ It is not exposed in IFC. All the subinterfaces
        // @@@ inherit full parent interface's bandwidth
        // Inherited From l1:EthIf
        // Type is an MO-Defined-Type
        leaf inhBw {
            description "Inherit Bandwidth";

            // Type is an MO-Defined-Type
            type l1_InheritBw;
        }

        // Administrative port span mode    @@@ This comes from the span policy in IFC
        // Inherited From l1:EthIf
        // Type is an MO-Defined-Type
        leaf spanMode {
            description "Span Mode";

            // Type is an MO-Defined-Type
            type l1_SpanMode;
        }

        // Administrative link logging enable    @@@ This come from interface configuration policy
        // Inherited From l1:EthIf
        // Type is an MO-Defined-Type
        leaf linkLog {
            description "Link Logging";

            // Type is an MO-Defined-Type
            type l1_LinkLog;
        }

        // Administrative trunk logging enable    @@@ This come from interface configuration policy
        // Inherited From l1:EthIf
        // Type is an MO-Defined-Type
        leaf trunkLog {
            description "Trunk Logging";

            // Type is an MO-Defined-Type
            type l1_TrunkLog;
        }
        leaf routerMac {
            type address_Mac;
            default "0";
        }

        // Type of the port: Fabric vs Leaf    @@@ This property is not exposed in IFC
        // Inherited From l1:EthIf
        // Type is an MO-Defined-Type
        leaf portT {
            description "Port Type";

            // Type is an MO-Defined-Type
            type eqpt_PortT;
        }

        // Usage of the port: Fabric, Infra, Epg, Controller, Discovery   @@@ This property is not exposed in IFC
        // Inherited From l1:EthIf
        // Type is an MO-Defined-Type
        leaf usage {
            description "Port Usage";

            // Type is an MO-Defined-Type
            type l1_PortUsage;
        }

        // config trunk vlans
        // Inherited From l1:EthIf
        // Type is an MO-Defined-Type
        leaf trunkVlans {
            description "Configed Trunk Vlans";

            // Type is an MO-Defined-Type
            type l1_l1IfTrunkVlans;
        }

        // config access vlan
        // Inherited From l1:EthIf
        // Type is an MO-Defined-Type
        leaf accessVlan {
            description "Configured Access Vlan";

            // Type is an MO-Defined-Type
            type l1_l1IfAccessVlan;
        }

        // Controller Id
        // Inherited From l1:EthIf
        // Type is an MO-Defined-Type
        leaf controllerId {
            description "Controller ID";

            // Type is an MO-Defined-Type
            type aggregate_ControllerIdBitmap;
        }

        // config access vlan
        // Inherited From l1:EthIf
        // Type is an MO-Defined-Type
        leaf nativeVlan {
            description "Configured Native Vlan";

            // Type is an MO-Defined-Type
            type l1_l1IfNativeVlan;
        }

        // port user config flags
        // Inherited From l1:EthIf
        // Type is an MO-Defined-Type
        leaf userCfgdFlags {
            description "Port User Config Flags";

            // Type is an MO-Defined-Type
            type l1_userCfgdFlags;
        }

        container priorflowctrl-items {

            // Added containment as a singleton: Prefix=priorflowctrl
            // Acquired From Package ipqos
            uses ipqos_PriorFlowCtrl-group;
        }

        // EEE policy
        container eeep-items {

            // Added containment as a singleton: Prefix=eeep
            // Acquired From Package l1
            uses l1_EeeP-group;
        }

        // Storm control policy
        container stormctrlp-items {

            // Added containment as a singleton: Prefix=stormctrlp
            // Acquired From Package l1
            uses l1_StormCtrlP-group;
        }

        // Load interval policy
        container loadp-items {

            // Added containment as a singleton: Prefix=loadp
            // Acquired From Package l1
            uses l1_LoadP-group;
        }

        // This MO is temporary. Needs to be removed when
        // "vrf member <vrf-name>" is objectified
        container vrf-items {

            // Added containment as a singleton: Prefix=vrf
            // Acquired From Package l1
            uses l1_Vrf-group;
        }

        // Port-channel interface information holder
        container aggrif-items {

            // Added containment as a singleton: Prefix=aggrif
            // Acquired From Package ethpm
            uses ethpm_AggrIf-group;
        }

        container aggrExtd-items {

            // Added containment as a singleton: Prefix=aggrExtd
            // Acquired From Package pc
            uses pc_AggrIfExtended-group;
        }

        // Vlan Mapping policy
        container vlanmapping-items {

            // Added containment as a singleton: Prefix=vlanmapping
            // Acquired From Package pc
            uses pc_VlanMapping-group;
        }

        container shadowaggr-items {

            // Added containment as a singleton: Prefix=shadowaggr
            // Acquired From Package pc
            uses pc_ShadowAggrIf-group;
        }

        // BndlMbrIf class
        container bndlmbrif-items {
            list BndlMbrIf-list {
                config "false";
                key "id";

                // Added containment: Prefix=bndlmbrif
                // Acquired From Package pc
                uses pc_BndlMbrIf-group;
            }
        }

        // Dom info
        container dom-items {
            list DomDef-list {
                config "false";
                key "domPKey";

                // Added containment: Prefix=dom
                // Acquired From Package fv
                uses fv_DomDef-group;
            }
        }

        // Rel-def target from fexBndlGrpToAggrIf
        // Inherited From pc:AggrIf
        container rtfexBndlGrpToAggrIf-items {

            // Added containment as a singleton: Prefix=rtfexBndlGrpToAggrIf
            // Acquired From Package infra
            uses infra_RtFexBndlGrpToAggrIf_target-group;
        }

        // Rel-def target from accBndlGrpToAggrIf
        // Inherited From pc:AggrIf
        container rtaccBndlGrpToAggrIf-items {

            // Added containment as a singleton: Prefix=rtaccBndlGrpToAggrIf
            // Acquired From Package infra
            uses infra_RtAccBndlGrpToAggrIf_target-group;
        }

        // Rel-def target from extConf
        // Inherited From l1:PhysIf
        // Inherited From pc:AggrIf
        container rtextConf-items {

            // Added containment as a singleton: Prefix=rtextConf
            // Acquired From Package l2
            uses l2_RtExtConf_target-group;
        }

        // Rel-def target from brConf
        // Inherited From l1:PhysIf
        // Inherited From pc:AggrIf
        container rtbrConf-items {

            // Added containment as a singleton: Prefix=rtbrConf
            // Acquired From Package l2
            uses l2_RtBrConf_target-group;
        }

        // Rel-def target from vpcConf
        // Inherited From pc:AggrIf
        container rtvpcConf-items {

            // Added containment as a singleton: Prefix=rtvpcConf
            // Acquired From Package vpc
            uses vpc_RtVpcConf_target-group;
        }

        // Rel-def target from NodePortAtt
        // Inherited From l1:PhysIf
        // Inherited From pc:AggrIf
        container rtfvNodePortAtt-items {

            // Abstract containment of rtfvNodePortAtt derived from l1:EthIf
            list RtFvNodePortAtt-list {
                config "false";
                key "tDn";

                // Added containment: Prefix=rtfvNodePortAtt
                // Acquired From Package fv
                uses fv_RtFvNodePortAtt_target-group;
            }
        }

        // Rel-def from mbrIfs
        container rsmbrIfs-items {

            // Abstract containment of rsmbrIfs derived from pc:AggrIf
            list RsMbrIfs-list {
                key "tDn";

                // Added containment: Prefix=rsmbrIfs
                // Acquired From Package pc
                uses pc_RsMbrIfs_source-group;
            }
        }

        // Rel-def from lacpPolCons
        container rslacpPolCons-items {

            // Added containment as a singleton: Prefix=rslacpPolCons
            // Acquired From Package pc
            uses pc_RsLacpPolCons_source-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        container rtvrfMbr-items {

            // Added containment as a singleton: Prefix=rtvrfMbr
            // Acquired From Package l3
            uses l3_RtVrfMbr_target-group;
        }

        // Rel-def target from physRtdConf
        // Inherited From l1:PhysIf
        // Inherited From pc:AggrIf
        container rtphysRtdConf-items {

            // Added containment as a singleton: Prefix=rtphysRtdConf
            // Acquired From Package l3
            uses l3_RtPhysRtdConf_target-group;
        }

        // Rel-def target from encPhysRtdConf
        // Inherited From l1:PhysIf
        // Inherited From pc:AggrIf
        container rtl3EncPhysRtdConf-items {

            // Abstract containment of rtl3EncPhysRtdConf derived from l1:EthIf
            list RtL3EncPhysRtdConf-list {
                key "tDn";

                // Added containment: Prefix=rtl3EncPhysRtdConf
                // Acquired From Package l3
                uses l3_RtL3EncPhysRtdConf_target-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def target from LsNodeToIf
        // Inherited From l1:PhysIf
        // Inherited From pc:AggrIf
        container rtLsNodeToIf-items {

            // Added containment as a singleton: Prefix=rtLsNodeToIf
            // Acquired From Package leqpt
            uses leqpt_RtLsNodeToIf_target-group;
        }

        container dbgIfIn-items {

            // Added containment as a singleton: Prefix=dbgIfIn
            // Acquired From Package rmon
            uses rmon_IfIn-group;
        }

        container dbgIfOut-items {

            // Added containment as a singleton: Prefix=dbgIfOut
            // Acquired From Package rmon
            uses rmon_IfOut-group;
        }

        container dbgIpIn-items {

            // Added containment as a singleton: Prefix=dbgIpIn
            // Acquired From Package rmon
            uses rmon_IpIn-group;
        }

        container dbgDot1d-items {

            // Added containment as a singleton: Prefix=dbgDot1d
            // Acquired From Package rmon
            uses rmon_Dot1d-group;
        }

        container dbgEtherStats-items {

            // Added containment as a singleton: Prefix=dbgEtherStats
            // Acquired From Package rmon
            uses rmon_EtherStats-group;
        }

        container dbgDot3Stats-items {

            // Added containment as a singleton: Prefix=dbgDot3Stats
            // Acquired From Package rmon
            uses rmon_Dot3Stats-group;
        }

        container dbgIfHCIn-items {

            // Added containment as a singleton: Prefix=dbgIfHCIn
            // Acquired From Package rmon
            uses rmon_IfHCIn-group;
        }

        container dbgIfHCOut-items {

            // Added containment as a singleton: Prefix=dbgIfHCOut
            // Acquired From Package rmon
            uses rmon_IfHCOut-group;
        }

        container dbgIpv6IfStats-items {

            // Added containment as a singleton: Prefix=dbgIpv6IfStats
            // Acquired From Package rmon
            uses rmon_Ipv6IfStats-group;
        }

        container dbgIfStorm-items {

            // Added containment as a singleton: Prefix=dbgIfStorm
            // Acquired From Package rmon
            uses rmon_IfStorm-group;
        }
    }

    grouping ethpm_AggrIf-group {
        leaf numActivePorts {
            config "false";
            type uint16;
        }

        // list of active members
        // Type is an MO-Defined-Type
        leaf activeMbrs {
            config "false";
            description "List of Active Members";

            // Type is an MO-Defined-Type
            type ethpm_ActiveMembersList;
        }
        leaf numMbrUp {
            config "false";
            type uint8;
        }
        leaf operMinLinks {
            config "false";
            type uint8;
        }
        leaf ifIndex {
            config "false";
            type uint32;
            default "0";
        }

        // Inherited From ethpm:If
        // Type is an MO-Defined-Type
        leaf operAutoNeg {
            config "false";
            description "negotiate auto";

            // Type is an MO-Defined-Type
            type l1_AutoNeg;
        }

        // Inherited From ethpm:If
        // Type is an MO-Defined-Type
        leaf operMtu {
            config "false";
            description "Maximum transmission unit";

            // Type is an MO-Defined-Type
            type l1_Mtu;
        }

        // Inherited From ethpm:If
        // Type is an MO-Defined-Type
        leaf adminSt {
            config "false";
            description "Administrative State";

            // Type is an MO-Defined-Type
            type l1_AdminSt;
        }

        // Inherited From ethpm:If
        // Type is an MO-Defined-Type
        leaf operDescr {
            config "false";
            description "Description";

            // Type is an MO-Defined-Type
            type ethpm_operDescr;
        }

        // Operational state summary
        // Inherited From ethpm:If
        // Type is an MO-Defined-Type
        leaf osSum {
            config "false";
            description "Operational State Summary";

            // Type is an MO-Defined-Type
            type nw_OSSum;
        }

        // Operational port state
        // Inherited From ethpm:If
        // Type is an MO-Defined-Type
        leaf operSt {
            config "false";
            description "Operational State";

            // Type is an MO-Defined-Type
            type l1_OperSt;
        }

        // Operational port status reason
        // Inherited From ethpm:If
        // Type is an MO-Defined-Type
        leaf operStQual {
            config "false";
            description "Operational State Qualifier";

            // Type is an MO-Defined-Type
            type l1_OperStQual;
        }

        // Operational port status syserror code
        // Inherited From ethpm:If
        // Type is an MO-Defined-Type
        leaf operStQualCode {
            config "false";
            description "Operational State Qualifier Code";

            // Type is an MO-Defined-Type
            type l1_OperStQualCode;
        }

        // Operational port err disable reason code
        // Inherited From ethpm:If
        // Type is an MO-Defined-Type
        leaf operErrDisQual {
            config "false";
            description "Operational Error Disable Qualifier";

            // Type is an MO-Defined-Type
            type l1_OperErrDisQual;
        }

        // Operational port speed
        // Inherited From ethpm:If
        // Type is an MO-Defined-Type
        leaf operSpeed {
            config "false";
            description "Operational Speed";

            // Type is an MO-Defined-Type
            type l1_Speed;
        }

        // Operational port mode
        // Inherited From ethpm:If
        // Type is an MO-Defined-Type
        leaf operMode {
            config "false";
            description "Operational Mode";

            // Type is an MO-Defined-Type
            type l1_Mode;
        }

        // Operational duplex
        // Inherited From ethpm:If
        // Type is an MO-Defined-Type
        leaf operDuplex {
            config "false";
            description "Operational Duplex";

            // Type is an MO-Defined-Type
            type l1_Duplex;
        }

        // Operational port flow control
        // Inherited From ethpm:If
        // Type is an MO-Defined-Type
        leaf operFlowCtrl {
            config "false";
            description "Operational Flow Control";

            // Type is an MO-Defined-Type
            type l1_FlowControl;
        }

        // Operational phy port enable state
        // Inherited From ethpm:If
        // Type is an MO-Defined-Type
        leaf operPhyEnSt {
            config "false";
            description "Operational Physical Port Enable State";

            // Type is an MO-Defined-Type
            type l1_OperSt;
        }
        leaf backplaneMac {
            config "false";
            type address_Mac;
        }
        leaf operRouterMac {
            config "false";
            type address_Mac;
        }

        // port Tx type
        // Inherited From ethpm:If
        // Type is an MO-Defined-Type
        leaf txT {
            config "false";
            description "Transmit Type";

            // Type is an MO-Defined-Type
            type l1_TxT;
        }
        leaf lastLinkStChg {
            config "false";
            type uint64;
        }
        leaf lastClear {
            config "false";
            type uint64;
        }
        leaf portCfgWaitFlags {
            config "false";
            type uint32;
        }
        leaf accessVlan {
            config "false";
            type string;
        }
        leaf nativeVlan {
            config "false";
            type string;
        }
        leaf cfgNativeVlan {
            config "false";
            type string;
        }
        leaf cfgAccessVlan {
            config "false";
            type string;
        }
        leaf primaryVlan {
            config "false";
            type string;
        }

        // port oper bitset
        // Inherited From ethpm:If
        // Type is an MO-Defined-Type
        leaf operBitset {
            config "false";
            description "Port Oper Bitset";

            // Type is an MO-Defined-Type
            type ethpm_PortOperBitmap;
        }

        // vdc id
        // Inherited From ethpm:If
        // Type is an MO-Defined-Type
        leaf vdcId {
            config "false";
            description "Vdc Id";

            // Type is an MO-Defined-Type
            type l2_VdcId;
        }
        leaf resetCtr {
            config "false";
            type uint32;
        }
        leaf media {
            config "false";
            type uint32;
        }
        leaf encap {
            config "false";
            type uint32;
        }
        leaf iod {
            config "false";
            type uint64;
        }

        // allowed vlans
        // Inherited From ethpm:If
        // Type is an MO-Defined-Type
        leaf allowedVlans {
            config "false";
            description "Allowed Vlans";

            // Type is an MO-Defined-Type
            type l2_VlanBitmap;
        }

        // operational vlans
        // Inherited From ethpm:If
        // Type is an MO-Defined-Type
        leaf operVlans {
            config "false";
            description "Operational Vlans";

            // Type is an MO-Defined-Type
            type l2_VlanBitmap;
        }

        // errored vlans
        // Inherited From ethpm:If
        // Type is an MO-Defined-Type
        leaf errVlans {
            config "false";
            description "Errored Vlans";

            // Type is an MO-Defined-Type
            type l2_VlanBitmap;
        }

        // autostate exclude vlans
        // Inherited From ethpm:If
        // Type is an MO-Defined-Type
        leaf autostateExcludeVlans {
            config "false";
            description "Autostate Exclude Vlans";

            // Type is an MO-Defined-Type
            type l2_VlanBitmap;
        }

        // bundle index
        // Inherited From ethpm:If
        // Type is an MO-Defined-Type
        leaf bundleIndex {
            config "false";
            description "Bundle Index";

            // Type is an MO-Defined-Type
            type nw_IfId;
        }

        // port oper mdix mode
        // Inherited From ethpm:If
        // Type is an MO-Defined-Type
        leaf operMdix {
            config "false";
            description "Port Oper Mdix Mode";

            // Type is an MO-Defined-Type
            type l1_Mdix;
        }
        leaf currErrIndex {
            config "false";
            type uint32;
        }

        // last seen errors
        // Inherited From ethpm:If
        // Type is an MO-Defined-Type
        leaf lastErrors {
            config "false";
            description "Last Seen Errors";

            // Type is an MO-Defined-Type
            type ethpm_LastErrorsList;
        }
        leaf errDisTimerRunning {
            config "false";
            type boolean;
        }
        leaf bundleBupId {
            config "false";
            type uint32;
        }

        // port per vlan error state
        // Inherited From ethpm:If
        // Type is an MO-Defined-Type
        leaf errVlanStatusHt {
            config "false";
            description "Port Per Vlan Error State";

            // Type is an MO-Defined-Type
            type ethpm_ErrorVlanStatusList;
        }

        // Operational Dce Mode
        // Inherited From ethpm:If
        // Type is an MO-Defined-Type
        leaf operDceMode {
            config "false";
            description "Operational Dce Mode";

            // Type is an MO-Defined-Type
            type l1_DceMode;
        }

        // interface type
        // Inherited From ethpm:If
        // Type is an MO-Defined-Type
        leaf intfT {
            config "false";
            description "Interface Type";

            // Type is an MO-Defined-Type
            type l1_IntfT;
        }

        // port diags type
        // Inherited From ethpm:If
        // Type is an MO-Defined-Type
        leaf diags {
            config "false";
            description "Port Diags Type";

            // Type is an MO-Defined-Type
            type l1_DiagsT;
        }

        // Operational port EEE state
        // Inherited From ethpm:If
        // Type is an MO-Defined-Type
        leaf operEEEState {
            config "false";
            description "Operational Port EEE State";

            // Type is an MO-Defined-Type
            type l1_EEEState;
        }
        leaf operEEETxWkTime {
            config "false";
            type uint32;
        }
        leaf operEEERxWkTime {
            config "false";
            type uint32;
        }

        // port user config flags
        // Inherited From ethpm:If
        // Type is an MO-Defined-Type
        leaf userCfgdFlags {
            config "false";
            description "Port User Config Flags";

            // Type is an MO-Defined-Type
            type l1_userCfgdFlags;
        }
        leaf numOfSI {
            config "false";
            type uint32;
        }
        leaf gport {
            config "false";
            type uint32;
        }

        // configured sub-interface ids
        // Inherited From ethpm:If
        // Type is an MO-Defined-Type
        leaf siList {
            config "false";
            description "Configured Sub-interface Ids";

            // Type is an MO-Defined-Type
            type ethpm_SiBitmap;
        }

        // hw bd id (allocated for l3 ports, port-channels)
        // Inherited From ethpm:If
        // Type is an MO-Defined-Type
        leaf hwBdId {
            config "false";
            description "Hw Bd Id (allocated for L3 Ports, Port-channels)";

            // Type is an MO-Defined-Type
            type l2_DomId;
        }

        // Usage of the port: Fabric, Infra, Epg, Controller, Discovery   @@@ This property is not exposed in IFC
        // Liked from l1:EthIf:usage
        // Inherited From ethpm:If
        // Type is an MO-Defined-Type
        leaf usage {
            config "false";
            description "Port Usage";

            // Type is an MO-Defined-Type
            type l1_PortUsage;
        }

        container portcap-items {

            // Added containment as a singleton: Prefix=portcap
            // Acquired From Package ethpm
            uses ethpm_PortCap-group;
        }
    }

    grouping pc_AggrIfExtended-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Inherited From l1:EthIfExtended
        // Type is an MO-Defined-Type
        leaf routerMacIpv6Extract {
            description "Disable/enable switchport ipv6 extract";

            // Type is an MO-Defined-Type
            type l1_RouterMacIpv6Extract;
        }

        // Inherited From l1:EthIfExtended
        // Type is an MO-Defined-Type
        leaf switchportBlock {
            description "Disable/enable switchport block on interface";

            // Type is an MO-Defined-Type
            type l1_SwitchportBlock;
        }

        // Inherited From l1:EthIfExtended
        // Type is an MO-Defined-Type
        leaf flowCtrl {
            description "Disable/enable flowcontrol block on interface";

            // Type is an MO-Defined-Type
            type l1_FlowControl;
        }

        // Inherited From l1:EthIfExtended
        // Type is an MO-Defined-Type
        leaf stormCtrlBCastLevel {
            description "storm-control broadcast level";

            // Type is an MO-Defined-Type
            type l1_StormCtrlRate;
        }

        // Inherited From l1:EthIfExtended
        // Type is an MO-Defined-Type
        leaf stormCtrlMCastLevel {
            description "storm-control multicast level";

            // Type is an MO-Defined-Type
            type l1_StormCtrlRate;
        }

        // Inherited From l1:EthIfExtended
        // Type is an MO-Defined-Type
        leaf stormCtrlUCastLevel {
            description "Storm control unicast level";

            // Type is an MO-Defined-Type
            type l1_StormCtrlRate;
        }

        // Inherited From l1:EthIfExtended
        // Type is an MO-Defined-Type
        leaf stormCtrlAct {
            description "Storm control action";

            // Type is an MO-Defined-Type
            type l1_StormCtrlAct;
        }

        // Inherited From l1:EthIfExtended
        // Type is an MO-Defined-Type
        leaf bufferBoost {
            description "Disable/enable buffer boost on interface";

            // Type is an MO-Defined-Type
            type l1_BufferBoost;
        }

        container shadowaggrextd-items {

            // Added containment as a singleton: Prefix=shadowaggrextd
            // Acquired From Package pc
            uses pc_ShadowAggrIfExtended-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping pc_ShadowAggrIfExtended-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Inherited From l1:EthIfExtended
        // Type is an MO-Defined-Type
        leaf routerMacIpv6Extract {
            description "Disable/enable switchport ipv6 extract";

            // Type is an MO-Defined-Type
            type l1_RouterMacIpv6Extract;
        }

        // Inherited From l1:EthIfExtended
        // Type is an MO-Defined-Type
        leaf switchportBlock {
            description "Disable/enable switchport block on interface";

            // Type is an MO-Defined-Type
            type l1_SwitchportBlock;
        }

        // Inherited From l1:EthIfExtended
        // Type is an MO-Defined-Type
        leaf flowCtrl {
            description "Disable/enable flowcontrol block on interface";

            // Type is an MO-Defined-Type
            type l1_FlowControl;
        }

        // Inherited From l1:EthIfExtended
        // Type is an MO-Defined-Type
        leaf stormCtrlBCastLevel {
            description "storm-control broadcast level";

            // Type is an MO-Defined-Type
            type l1_StormCtrlRate;
        }

        // Inherited From l1:EthIfExtended
        // Type is an MO-Defined-Type
        leaf stormCtrlMCastLevel {
            description "storm-control multicast level";

            // Type is an MO-Defined-Type
            type l1_StormCtrlRate;
        }

        // Inherited From l1:EthIfExtended
        // Type is an MO-Defined-Type
        leaf stormCtrlUCastLevel {
            description "Storm control unicast level";

            // Type is an MO-Defined-Type
            type l1_StormCtrlRate;
        }

        // Inherited From l1:EthIfExtended
        // Type is an MO-Defined-Type
        leaf stormCtrlAct {
            description "Storm control action";

            // Type is an MO-Defined-Type
            type l1_StormCtrlAct;
        }

        // Inherited From l1:EthIfExtended
        // Type is an MO-Defined-Type
        leaf bufferBoost {
            description "Disable/enable buffer boost on interface";

            // Type is an MO-Defined-Type
            type l1_BufferBoost;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping pc_VlanMapping-group {
        leaf Enabled {
            type boolean;
            default "false";
        }
        leaf DefaultDrop {
            type boolean;
            default "true";
        }

        // Vlan Translate Table policy
        container vlantranslatetable-items {

            // Added containment as a singleton: Prefix=vlantranslatetable
            // Acquired From Package pc
            uses pc_VlanTranslateTable-group;
        }
    }

    grouping pc_VlanTranslateTable-group {

        // Vlan Translate Table policy    Vlan Translate Entry policy
        container vlan-items {
            list VlanTranslateEntry-list {
                key "vlanid";

                // Added containment: Prefix=vlan
                // Acquired From Package pc
                uses pc_VlanTranslateEntry-group;
            }
        }
    }

    grouping pc_VlanTranslateEntry-group {

        // Type is an MO-Defined-Type
        leaf vlanid {
            description "Vlan Id";

            // Type is an MO-Defined-Type
            type l1_translatevlanid;
        }

        // Type is an MO-Defined-Type
        leaf innervlanid {
            description "Inner Vlan Id";

            // Type is an MO-Defined-Type
            type l1_translatevlanid;
        }

        // Type is an MO-Defined-Type
        leaf translatevlanid {
            description "Translate Vlan Id";

            // Type is an MO-Defined-Type
            type l1_translatevlanid;
        }
    }

    grouping pc_ShadowAggrIf-group {

        // Port-channel creation Status
        // Type is an MO-Defined-Type
        leaf createSt {
            config "false";
            description "Port-channel Creation Status";

            // Type is an MO-Defined-Type
            type pc_LastSt;
        }
        leaf isExplicit {
            config "false";
            type boolean;
            default "true";
        }
        leaf isCopyDone {
            type boolean;
            default "true";
        }
        leaf numPorts {
            type uint32;
            default "0";
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Type is an MO-Defined-Type
        leaf adminSt {
            description "Administrative State";

            // Type is an MO-Defined-Type
            type l1_AdminSt;
        }

        // Administrative port speed    @@@ This comes from the host interface
        // @@@ configuration policy
        // Inherited From l1:If
        // Type is an MO-Defined-Type
        leaf speed {
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Administrative port mode    @@@ Internally set by PE
        // Inherited From l1:EthIf
        // Type is an MO-Defined-Type
        leaf mode {
            description "Mode";

            // Type is an MO-Defined-Type
            type l1_Mode;
        }

        // Administrative port layer    @@@ Internally set by PE
        // Inherited From l1:EthIf
        // Type is an MO-Defined-Type
        leaf layer {
            description "Layer";

            // Type is an MO-Defined-Type
            type l1_Layer;
        }

        // Administrative mdix mode    @@@ Theres no benefit in exposing this property
        // @@@ in IFC. Ask Marketing.
        // Inherited From l1:EthIf
        // Type is an MO-Defined-Type
        leaf mdix {
            description "MDIX";

            // Type is an MO-Defined-Type
            type l1_Mdix;
        }

        // Administrative port delay    @@@ is this exposed in IFC?
        // Inherited From l1:EthIf
        // Type is an MO-Defined-Type
        leaf delay {
            description "Delay";

            // Type is an MO-Defined-Type
            type l1_Delay;
        }

        // Administrative port link debounce interval    @@@ This comes from the interface configuration policy
        // Inherited From l1:EthIf
        // Type is an MO-Defined-Type
        leaf linkDebounce {
            description "Link Debounce Interval";

            // Type is an MO-Defined-Type
            type l1_LinkDebounce;
        }

        // Administrative port dot1q ether-type    @@@ This property is not supported in switch ??
        // Inherited From l1:EthIf
        // Type is an MO-Defined-Type
        leaf dot1qEtherType {
            description "Dot1q Ether Type";

            // Type is an MO-Defined-Type
            type l1_Dot1qEtherType;
        }

        // Administrative port bandwidth    @@@ Comes from QOS Policy
        // Inherited From l1:EthIf
        // Type is an MO-Defined-Type
        leaf bw {
            description "Bandwidth";

            // Type is an MO-Defined-Type
            type l1_Bw;
        }

        // Administrative port medium type    @@@ The fabric & Host connections are P2p.    @@@ No need to expose this property in IFC
        // Inherited From l1:EthIf
        // Type is an MO-Defined-Type
        leaf medium {
            description "Medium";

            // Type is an MO-Defined-Type
            type l1_Medium;
        }

        // Administrative port inherit bandwidth    @@@ It is used for specifying the bandwidth inherited
        // @@@ by the subinterfaces from the parent interface    @@@ It is not exposed in IFC. All the subinterfaces
        // @@@ inherit full parent interface's bandwidth
        // Inherited From l1:EthIf
        // Type is an MO-Defined-Type
        leaf inhBw {
            description "Inherit Bandwidth";

            // Type is an MO-Defined-Type
            type l1_InheritBw;
        }

        // Administrative port span mode    @@@ This comes from the span policy in IFC
        // Inherited From l1:EthIf
        // Type is an MO-Defined-Type
        leaf spanMode {
            description "Span Mode";

            // Type is an MO-Defined-Type
            type l1_SpanMode;
        }

        // Administrative link logging enable    @@@ This come from interface configuration policy
        // Inherited From l1:EthIf
        // Type is an MO-Defined-Type
        leaf linkLog {
            description "Link Logging";

            // Type is an MO-Defined-Type
            type l1_LinkLog;
        }

        // Administrative trunk logging enable    @@@ This come from interface configuration policy
        // Inherited From l1:EthIf
        // Type is an MO-Defined-Type
        leaf trunkLog {
            description "Trunk Logging";

            // Type is an MO-Defined-Type
            type l1_TrunkLog;
        }
        leaf routerMac {
            type address_Mac;
            default "0";
        }

        // Type of the port: Fabric vs Leaf    @@@ This property is not exposed in IFC
        // Inherited From l1:EthIf
        // Type is an MO-Defined-Type
        leaf portT {
            description "Port Type";

            // Type is an MO-Defined-Type
            type eqpt_PortT;
        }

        // Usage of the port: Fabric, Infra, Epg, Controller, Discovery   @@@ This property is not exposed in IFC
        // Inherited From l1:EthIf
        // Type is an MO-Defined-Type
        leaf usage {
            description "Port Usage";

            // Type is an MO-Defined-Type
            type l1_PortUsage;
        }

        // config trunk vlans
        // Inherited From l1:EthIf
        // Type is an MO-Defined-Type
        leaf trunkVlans {
            description "Configed Trunk Vlans";

            // Type is an MO-Defined-Type
            type l1_l1IfTrunkVlans;
        }

        // config access vlan
        // Inherited From l1:EthIf
        // Type is an MO-Defined-Type
        leaf accessVlan {
            description "Configured Access Vlan";

            // Type is an MO-Defined-Type
            type l1_l1IfAccessVlan;
        }

        // Controller Id
        // Inherited From l1:EthIf
        // Type is an MO-Defined-Type
        leaf controllerId {
            description "Controller ID";

            // Type is an MO-Defined-Type
            type aggregate_ControllerIdBitmap;
        }

        // config access vlan
        // Inherited From l1:EthIf
        // Type is an MO-Defined-Type
        leaf nativeVlan {
            description "Configured Native Vlan";

            // Type is an MO-Defined-Type
            type l1_l1IfNativeVlan;
        }

        // port user config flags
        // Inherited From l1:EthIf
        // Type is an MO-Defined-Type
        leaf userCfgdFlags {
            description "Port User Config Flags";

            // Type is an MO-Defined-Type
            type l1_userCfgdFlags;
        }

        // Dom info
        container dom-items {
            list DomDef-list {
                config "false";
                key "domPKey";

                // Added containment: Prefix=dom
                // Acquired From Package fv
                uses fv_DomDef-group;
            }
        }

        // Rel-def target from extConf
        // Inherited From l1:PhysIf
        // Inherited From pc:AggrIf
        // Inherited From pc:ShadowAggrIf
        container rtextConf-items {

            // Added containment as a singleton: Prefix=rtextConf
            // Acquired From Package l2
            uses l2_RtExtConf_target-group;
        }

        // Rel-def target from brConf
        // Inherited From l1:PhysIf
        // Inherited From pc:AggrIf
        // Inherited From pc:ShadowAggrIf
        container rtbrConf-items {

            // Added containment as a singleton: Prefix=rtbrConf
            // Acquired From Package l2
            uses l2_RtBrConf_target-group;
        }

        // Rel-def target from NodePortAtt
        // Inherited From l1:PhysIf
        // Inherited From pc:AggrIf
        // Inherited From pc:ShadowAggrIf
        container rtfvNodePortAtt-items {

            // Abstract containment of rtfvNodePortAtt derived from l1:EthIf
            list RtFvNodePortAtt-list {
                config "false";
                key "tDn";

                // Added containment: Prefix=rtfvNodePortAtt
                // Acquired From Package fv
                uses fv_RtFvNodePortAtt_target-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        container rtvrfMbr-items {

            // Added containment as a singleton: Prefix=rtvrfMbr
            // Acquired From Package l3
            uses l3_RtVrfMbr_target-group;
        }

        // Rel-def target from physRtdConf
        // Inherited From l1:PhysIf
        // Inherited From pc:AggrIf
        // Inherited From pc:ShadowAggrIf
        container rtphysRtdConf-items {

            // Added containment as a singleton: Prefix=rtphysRtdConf
            // Acquired From Package l3
            uses l3_RtPhysRtdConf_target-group;
        }

        // Rel-def target from encPhysRtdConf
        // Inherited From l1:PhysIf
        // Inherited From pc:AggrIf
        // Inherited From pc:ShadowAggrIf
        container rtl3EncPhysRtdConf-items {

            // Abstract containment of rtl3EncPhysRtdConf derived from l1:EthIf
            list RtL3EncPhysRtdConf-list {
                key "tDn";

                // Added containment: Prefix=rtl3EncPhysRtdConf
                // Acquired From Package l3
                uses l3_RtL3EncPhysRtdConf_target-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def target from LsNodeToIf
        // Inherited From l1:PhysIf
        // Inherited From pc:AggrIf
        // Inherited From pc:ShadowAggrIf
        container rtLsNodeToIf-items {

            // Added containment as a singleton: Prefix=rtLsNodeToIf
            // Acquired From Package leqpt
            uses leqpt_RtLsNodeToIf_target-group;
        }
    }

    grouping pc_BndlMbrIf-group {

        // Type is an MO-Defined-Type
        leaf id {
            config "false";
            description "Interface index";

            // Type is an MO-Defined-Type
            type nw_IfId;
        }
    }

    grouping l3_RtdIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From l3:If
        // Type is an MO-Defined-Type
        leaf adminSt {
            description "Admin State";

            // Type is an MO-Defined-Type
            type l1_AdminSt;
        }

        // Rel-def target from pseudoIf
        // Inherited From mgmt:RtdMgmtIf
        // Inherited From l3:RtdIf
        container rtpseudoIf-items {

            // Added containment as a singleton: Prefix=rtpseudoIf
            // Acquired From Package dhcp
            uses dhcp_RtPseudoIf_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        container rtvrfMbr-items {

            // Added containment as a singleton: Prefix=rtvrfMbr
            // Acquired From Package l3
            uses l3_RtVrfMbr_target-group;
        }

        // Rel-def from physRtdConf
        container rsphysRtdConf-items {

            // Added containment as a singleton: Prefix=rsphysRtdConf
            // Acquired From Package l3
            uses l3_RsPhysRtdConf_source-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping l3_LbRtdIf-group {

        // Administrative link logging enable
        // Type is an MO-Defined-Type
        leaf linkLog {
            description "Administrative Link Logging Enable";

            // Type is an MO-Defined-Type
            type l1_LinkLog;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l3:LbRtdIf->descr
        // Type is an MO-Defined-Type
        leaf descr {
            description "Description";

            // Type is an MO-Defined-Type
            type naming_Descr {
                length "0..254";
            }
        }

        // Administrative state
        // Inherited From l3:If
        // Type is an MO-Defined-Type
        leaf adminSt {
            description "Admin State";

            // Type is an MO-Defined-Type
            type l1_AdminSt;
        }

        // This MO is temporary. Needs to be removed when
        // "vrf member <vrf-name>" is objectified
        container vrf-items {

            // Added containment as a singleton: Prefix=vrf
            // Acquired From Package l1
            uses l1_Vrf-group;
        }

        // loopback interface information holder
        container lbrtdif-items {

            // Added containment as a singleton: Prefix=lbrtdif
            // Acquired From Package ethpm
            uses ethpm_LbRtdIf-group;
        }

        // Rel-def target from pseudoIf
        // Inherited From mgmt:RtdMgmtIf
        // Inherited From l3:RtdIf
        // Inherited From l3:LbRtdIf
        container rtpseudoIf-items {

            // Added containment as a singleton: Prefix=rtpseudoIf
            // Acquired From Package dhcp
            uses dhcp_RtPseudoIf_target-group;
        }

        // Rel-def target from operSourceInterface
        // Inherited From l3:LbRtdIf
        container rtoperSourceInterface-items {

            // Added containment as a singleton: Prefix=rtoperSourceInterface
            // Acquired From Package nvo
            uses nvo_RtOperSourceInterface_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        container rtvrfMbr-items {

            // Added containment as a singleton: Prefix=rtvrfMbr
            // Acquired From Package l3
            uses l3_RtVrfMbr_target-group;
        }

        // Rel-def from protLbIf
        container rsprotLbIf-items {

            // Added containment as a singleton: Prefix=rsprotLbIf
            // Acquired From Package l3
            uses l3_RsProtLbIf_source-group;
        }

        // Rel-def from lbIfToLocale
        container rslbIfToLocale-items {

            // Abstract containment of rslbIfToLocale derived from l3:LbRtdIf
            list RsLbIfToLocale-list {
                key "tDn";

                // Added containment: Prefix=rslbIfToLocale
                // Acquired From Package l3
                uses l3_RsLbIfToLocale_source-group;
            }
        }

        // Rel-def from LbIfToOutRef
        container rslbIfToOutRef-items {

            // Abstract containment of rslbIfToOutRef derived from l3:LbRtdIf
            list RsLbIfToOutRef-list {
                key "tDn";

                // Added containment: Prefix=rslbIfToOutRef
                // Acquired From Package l3
                uses l3_RsLbIfToOutRef_source-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ethpm_LbRtdIf-group {
        leaf ifIndex {
            config "false";
            type uint32;
            default "0";
        }
        leaf iod {
            config "false";
            type uint64;
        }

        // Operational state
        // Type is an MO-Defined-Type
        leaf operSt {
            config "false";
            description "Operational State";

            // Type is an MO-Defined-Type
            type l1_OperSt;
        }

        // Operational MTU
        // Type is an MO-Defined-Type
        leaf operMtu {
            config "false";
            description "Operational MTU";

            // Type is an MO-Defined-Type
            type l1_Mtu;
        }

        // Operational Description
        // Type is an MO-Defined-Type
        leaf operDescr {
            config "false";
            description "Operational Description";

            // Type is an MO-Defined-Type
            type ethpm_operDescr;
        }

        // Operational state reason
        // Type is an MO-Defined-Type
        leaf operStQual {
            config "false";
            description "Operational State Reason";

            // Type is an MO-Defined-Type
            type l1_OperStQual;
        }
        leaf currErrIndex {
            config "false";
            type uint32;
        }

        // Last seen errors
        // Type is an MO-Defined-Type
        leaf lastErrors {
            config "false";
            description "Last Seen Errors";

            // Type is an MO-Defined-Type
            type ethpm_LastErrorsList;
        }

        // Operational state flags
        // Type is an MO-Defined-Type
        leaf operBitset {
            config "false";
            description "Operational State Flags";

            // Type is an MO-Defined-Type
            type ethpm_PortOperBitmap;
        }
    }

    grouping l3_EncRtdIf-group {

        // Interface Mtu    Is it required, check with marketing?
        // Type is an MO-Defined-Type
        leaf mtu {
            description "Interface Mtu";

            // Type is an MO-Defined-Type
            type l1_Mtu;
        }
        leaf mtuInherit {
            type boolean;
            default "true";
        }

        // Interface interface delay    @@@ This is not exposed in IFC
        // Type is an MO-Defined-Type
        leaf delay {
            description "Interface Interface Delay";

            // Type is an MO-Defined-Type
            type l1_Delay;
        }
        leaf encap {
            type string;
        }

        // Interface Bandwidth    Is it required, check with marketing?
        // Type is an MO-Defined-Type
        leaf bw {
            description "Interface Bandwidth";

            // Type is an MO-Defined-Type
            type l1_Bw;
        }

        // Interface link logging enable
        // Type is an MO-Defined-Type
        leaf linkLogEn {
            description "Interface Link Logging Enable";

            // Type is an MO-Defined-Type
            type l1_LinkLog;
        }
        leaf routerMac {
            type address_Mac;
            default "0";
        }
        leaf ifConnDn {
            type string;
        }

        // Interface link logging enable
        // Type is an MO-Defined-Type
        leaf mediumType {
            description "Interface Medium Type";

            // Type is an MO-Defined-Type
            type l1_Medium;
        }

        // Type is an MO-Defined-Type
        leaf routerMacIpv6Extract {
            description "Disable/enable switchport ipv6 extract";

            // Type is an MO-Defined-Type
            type l1_RouterMacIpv6Extract;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l3:EncRtdIf->descr
        // Type is an MO-Defined-Type
        leaf descr {
            description "Description";

            // Type is an MO-Defined-Type
            type naming_Descr {
                length "0..254";
            }
        }

        // Administrative state
        // Inherited From l3:If
        // Modified by Override: l3:EncRtdIf->adminSt
        // Type is an MO-Defined-Type
        leaf adminSt {
            description "Admin State";

            // Type is an MO-Defined-Type
            type l1_AdminSt;
        }

        // This MO is temporary. Needs to be removed when
        // "vrf member <vrf-name>" is objectified
        container vrf-items {

            // Added containment as a singleton: Prefix=vrf
            // Acquired From Package l1
            uses l1_Vrf-group;
        }

        // sub-interface information holder
        container encrtdif-items {

            // Added containment as a singleton: Prefix=encrtdif
            // Acquired From Package ethpm
            uses ethpm_EncRtdIf-group;
        }

        // Rel-def target from pseudoIf
        // Inherited From mgmt:RtdMgmtIf
        // Inherited From l3:RtdIf
        // Inherited From l3:LbRtdIf
        // Inherited From l3:EncRtdIf
        container rtpseudoIf-items {

            // Added containment as a singleton: Prefix=rtpseudoIf
            // Acquired From Package dhcp
            uses dhcp_RtPseudoIf_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        container rtvrfMbr-items {

            // Added containment as a singleton: Prefix=rtvrfMbr
            // Acquired From Package l3
            uses l3_RtVrfMbr_target-group;
        }

        // Rel-def from encPhysRtdConf
        container rsencPhysRtdConf-items {

            // Added containment as a singleton: Prefix=rsencPhysRtdConf
            // Acquired From Package l3
            uses l3_RsEncPhysRtdConf_source-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ethpm_EncRtdIf-group {
        leaf ifIndex {
            config "false";
            type uint32;
            default "0";
        }
        leaf operRouterMac {
            config "false";
            type address_Mac;
        }
        leaf operEncap {
            config "false";
            type uint16;
        }
        leaf lastLinkStChg {
            config "false";
            type uint64;
        }

        // Type is an MO-Defined-Type
        leaf operDescr {
            config "false";
            description "Description";

            // Type is an MO-Defined-Type
            type ethpm_operDescr;
        }
        leaf fsmState {
            config "false";
            type uint8;
        }
        leaf iod {
            config "false";
            type uint64;
        }

        // Operational state
        // Type is an MO-Defined-Type
        leaf operSt {
            config "false";
            description "Operational State";

            // Type is an MO-Defined-Type
            type l1_OperSt;
        }

        // Operational state reason
        // Type is an MO-Defined-Type
        leaf operStQual {
            config "false";
            description "Operational State Reason";

            // Type is an MO-Defined-Type
            type l1_OperStQual;
        }

        // Operational Mtu
        // Type is an MO-Defined-Type
        leaf operMtu {
            config "false";
            description "Operational Mtu";

            // Type is an MO-Defined-Type
            type l1_Mtu;
        }
        leaf currErrIndex {
            config "false";
            type uint32;
        }

        // Last seen errors
        // Type is an MO-Defined-Type
        leaf lastErrors {
            config "false";
            description "Last Seen Errors";

            // Type is an MO-Defined-Type
            type ethpm_LastErrorsList;
        }

        // Operational state flags
        // Type is an MO-Defined-Type
        leaf operBitset {
            config "false";
            description "Operational State Flags";

            // Type is an MO-Defined-Type
            type ethpm_PortOperBitmap;
        }
        leaf siCfgFlags {
            config "false";
            type uint32;
        }

        // hw bd id (allocated for l3 sub-ifs)
        // Type is an MO-Defined-Type
        leaf hwBdId {
            config "false";
            description "Hw Bd Id (allocated for L3 Sub-ifs)";

            // Type is an MO-Defined-Type
            type l2_DomId;
        }
    }

    grouping svi_If-group {

        // VLAN ID associated with the SVI
        // Type is an MO-Defined-Type
        leaf vlanId {
            description "VLAN ID Associated with the SVI";

            // Type is an MO-Defined-Type
            type svi_VlanId;
        }
        leaf mac {
            type address_Mac;
        }

        // Medium type (P2P or Broadcast)   @@@ default value: Not coming from IFC
        // Type is an MO-Defined-Type
        leaf medium {
            description "Medium Type";

            // Type is an MO-Defined-Type
            type svi_Medium;
        }

        // MTU of the SVI    @@@ This comes from qos
        // Type is an MO-Defined-Type
        leaf mtu {
            description "MTU of the SVI";

            // Type is an MO-Defined-Type
            type svi_Mtu;
        }
        leaf mtuInherit {
            type boolean;
            default "true";
        }

        // Delay metric associated with the SVI
        // Type is an MO-Defined-Type
        leaf delay {
            description "Delay";

            // Type is an MO-Defined-Type
            type svi_Delay;
        }

        // Bandwidth metric associated with the SVI
        // Type is an MO-Defined-Type
        leaf bw {
            description "Bandwidth";

            // Type is an MO-Defined-Type
            type svi_Bw;
        }

        // Carrier Delay: hold period for which Carrier transition
        // like L2 interfacing going down is ignored.
        // Type is an MO-Defined-Type
        leaf carDel {
            description "Carrier Delay";

            // Type is an MO-Defined-Type
            type svi_CarrDelay;
        }

        // Load-averaging interval 1    @@@ Infrastrure level policy
        // Type is an MO-Defined-Type
        leaf loadIntvl1 {
            description "Load-averaging Interval 1";

            // Type is an MO-Defined-Type
            type svi_LoadIntvl1;
        }

        // Load-averaging interval 2
        // Type is an MO-Defined-Type
        leaf loadIntvl2 {
            description "Load-averaging Interval 2";

            // Type is an MO-Defined-Type
            type svi_LoadIntvl2;
        }

        // Load-averaging interval 3
        // Type is an MO-Defined-Type
        leaf loadIntvl3 {
            description "Load-averaging Interval 3";

            // Type is an MO-Defined-Type
            type svi_LoadIntvl3;
        }
        leaf inbMgmt {
            type boolean;
        }
        leaf autostate {
            type boolean;
            default "true";
        }
        leaf snmpTrap {
            type boolean;
            default "true";
        }

        // Operational state summary
        // Type is an MO-Defined-Type
        leaf osSum {
            config "false";
            description "SVI Operational State Summary";

            // Type is an MO-Defined-Type
            type nw_OSSum;
        }

        // Operational state of the SVI
        // Type is an MO-Defined-Type
        leaf operSt {
            config "false";
            description "SVI Operational State";

            // Type is an MO-Defined-Type
            type svi_OperSt;
        }

        // Reason for operational state being down
        // Type is an MO-Defined-Type
        leaf operStQual {
            config "false";
            description "Reason for Operational State Being Down";

            // Type is an MO-Defined-Type
            type svi_OperStQual;
        }

        // VLAN Type (e.g. private vlan)
        // Type is an MO-Defined-Type
        leaf vlanT {
            config "false";
            description "VLAN Type";

            // Type is an MO-Defined-Type
            type l2_DomType;
        }

        // Controller Id
        // Type is an MO-Defined-Type
        leaf ctrlrId {
            description "Controller ID";

            // Type is an MO-Defined-Type
            type aggregate_ControllerIdBitmap;
        }
        leaf iod {
            config "false";
            type uint32;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: svi:If->descr
        // Type is an MO-Defined-Type
        leaf descr {
            description "Description";

            // Type is an MO-Defined-Type
            type naming_Descr {
                length "0..254";
            }
        }

        // Administrative state
        // Inherited From l3:If
        // Modified by Override: svi:If->adminSt
        // Type is an MO-Defined-Type
        leaf adminSt {
            description "Admin State";

            // Type is an MO-Defined-Type
            type l1_AdminSt;
        }

        // This MO is temporary. Needs to be removed when
        // "vrf member <vrf-name>" is objectified
        container vrf-items {

            // Added containment as a singleton: Prefix=vrf
            // Acquired From Package l1
            uses l1_Vrf-group;
        }

        container svi-items {

            // Added containment as a singleton: Prefix=svi
            // Acquired From Package svi
            uses svi_OperSvi-group;
        }

        // Rel-def target from pseudoIf
        // Inherited From mgmt:RtdMgmtIf
        // Inherited From l3:RtdIf
        // Inherited From l3:LbRtdIf
        // Inherited From l3:EncRtdIf
        // Inherited From svi:If
        container rtpseudoIf-items {

            // Added containment as a singleton: Prefix=rtpseudoIf
            // Acquired From Package dhcp
            uses dhcp_RtPseudoIf_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping svi_OperSvi-group {
        leaf ifIndex {
            config "false";
            type uint32;
            default "0";
        }
        leaf operDescr {
            config "false";
            type string;
        }
        leaf lastClear {
            config "false";
            type uint64;
        }

        // Operational state summary
        // Type is an MO-Defined-Type
        leaf osSum {
            config "false";
            description "Operational State Summary";

            // Type is an MO-Defined-Type
            type nw_OSSum;
        }

        // Type is an MO-Defined-Type
        leaf adminSt {
            config "false";
            description "Operational State";

            // Type is an MO-Defined-Type
            type l1_AdminSt;
        }

        // Operational port status reason
        // Type is an MO-Defined-Type
        leaf operStQual {
            config "false";
            description "Operational State Qualifier";

            // Type is an MO-Defined-Type
            type svi_OperStQual;
        }

        // Operational port status syserror code
        // Type is an MO-Defined-Type
        leaf operStQualCode {
            config "false";
            description "Operational State Qualifier Code";

            // Type is an MO-Defined-Type
            type l1_OperStQualCode;
        }

        // Operational port err disable reason code
        // Type is an MO-Defined-Type
        leaf operErrDisQual {
            config "false";
            description "Operational Error Disable Qualifier";

            // Type is an MO-Defined-Type
            type l1_OperErrDisQual;
        }

        // Operational Mtu
        // Type is an MO-Defined-Type
        leaf operCarrierDelaySec {
            config "false";
            description "Operational Carrier Delay Seconds";

            // Type is an MO-Defined-Type
            type svi_CarrDelay;
        }

        // Operational Mtu
        // Type is an MO-Defined-Type
        leaf operCarrierDelayMsec {
            config "false";
            description "Operational Carrier Delay milliseconds";

            // Type is an MO-Defined-Type
            type svi_CarrDelay;
        }

        // Operational Mtu
        // Type is an MO-Defined-Type
        leaf operMtu {
            config "false";
            description "Operational Mtu";

            // Type is an MO-Defined-Type
            type svi_Mtu;
        }

        // Type is an MO-Defined-Type
        leaf operBw {
            config "false";
            description "operational Bandwidth";

            // Type is an MO-Defined-Type
            type svi_Bw;
        }

        // Type is an MO-Defined-Type
        leaf operDelay {
            config "false";
            description "operational delay";

            // Type is an MO-Defined-Type
            type svi_Delay;
        }
        leaf operAutoState {
            config "false";
            type boolean;
        }
        leaf operMac {
            config "false";
            type address_Mac;
        }
        leaf iod {
            config "false";
            type uint64;
        }

        // interface type
        // Type is an MO-Defined-Type
        leaf intfT {
            config "false";
            description "Interface Type";

            // Type is an MO-Defined-Type
            type l1_IntfT;
        }

        // Load interval 1
        // Type is an MO-Defined-Type
        leaf operLoadIntvl1 {
            config "false";
            description "Load Interval 1";

            // Type is an MO-Defined-Type
            type svi_LoadIntvl1;
        }

        // Load interval 2
        // Type is an MO-Defined-Type
        leaf operLoadIntvl2 {
            config "false";
            description "Load Interval 2";

            // Type is an MO-Defined-Type
            type svi_LoadIntvl2;
        }

        // Load interval 3
        // Type is an MO-Defined-Type
        leaf operLoadIntvl3 {
            config "false";
            description "Load Interval 3";

            // Type is an MO-Defined-Type
            type svi_LoadIntvl3;
        }
        leaf operLastChgSec {
            config "false";
            type uint64;
        }
        leaf operLastChgUsec {
            config "false";
            type uint64;
        }
    }

    grouping tunnelif_If-group {
        leaf tunSrcAddr {
            type address_Ip;
        }

        // Tunnel source interface
        // Type is an MO-Defined-Type
        leaf tunSrcIntf {
            description "Tunnel Source";

            // Type is an MO-Defined-Type
            type nw_IfId;
        }

        // Tunnel source direct
        // Type is an MO-Defined-Type
        leaf tunSrcDirect {
            description "Tunnel Source";

            // Type is an MO-Defined-Type
            type tunnelif_TunnelSrcDirect;
        }
        leaf tunDestAddr {
            type address_Ip;
        }

        // Tunnel mode
        // Type is an MO-Defined-Type
        leaf tunMode {
            description "Tunnel Mode";

            // Type is an MO-Defined-Type
            type tunnelif_TunnelMode;
        }

        // Tunnel VRF name
        // Type is an MO-Defined-Type
        leaf tunVrf {
            description "Tunnel Transport VRF";

            // Type is an MO-Defined-Type
            type tunnelif_TunnelTransVRF;
        }

        // Tunnel MTU
        // Type is an MO-Defined-Type
        leaf tunMtu {
            description "Tunnel MTU";

            // Type is an MO-Defined-Type
            type tunnelif_TunnelMtu;
        }

        // Tunnel PATH MTU Discovery
        // Type is an MO-Defined-Type
        leaf tunPMTUD {
            description "Tunnel PMTU Discovery";

            // Type is an MO-Defined-Type
            type tunnelif_TunnelPMTUD;
        }

        // Tunnel PMTU min-mtu
        // Type is an MO-Defined-Type
        leaf tunminPMTU {
            description "Tunnel min PMTU";

            // Type is an MO-Defined-Type
            type tunnelif_TunnelminPMTU;
        }

        // Tunnel PMTU ager
        // Type is an MO-Defined-Type
        leaf tunPMTUage {
            description "Tunnel PMTU age";

            // Type is an MO-Defined-Type
            type tunnelif_TunnelPMTUAge;
        }

        // Tunnel Interface Bandwidth
        // Type is an MO-Defined-Type
        leaf tunBW {
            description "Tunnel Bandwidth";

            // Type is an MO-Defined-Type
            type tunnelif_TunnelBW;
        }

        // Tunnel Interface TTL
        // Type is an MO-Defined-Type
        leaf tunTTL {
            description "Tunnel TTL";

            // Type is an MO-Defined-Type
            type tunnelif_TunnelTTL;
        }

        // Administrative port snmp trap state
        // Type is an MO-Defined-Type
        leaf snmpTrapSt {
            description "Snmp Trap State";

            // Type is an MO-Defined-Type
            type tunnelif_SnmpTrapSt;
        }

        // Tunnel operational state
        // Type is an MO-Defined-Type
        leaf tunOperSt {
            config "false";
            description "Tunnel Operational State";

            // Type is an MO-Defined-Type
            type tunnelif_TunnelOperSt;
        }

        // Tunnel operational state down reason
        // Type is an MO-Defined-Type
        leaf tunOperStQual {
            config "false";
            description "Tunnel Operational State Qualifier";

            // Type is an MO-Defined-Type
            type tunnelif_TunnelOperStQual;
        }
        leaf lastStateChgdTs {
            config "false";
            type uint64;
        }
        leaf tunDelInProg {
            config "false";
            type boolean;
        }

        // Tunnel Interface options
        // Type is an MO-Defined-Type
        leaf tunIntfOptions {
            config "false";
            description "Tunnel Interface Options";

            // Type is an MO-Defined-Type
            type tunnelif_TunnelOption;
        }
        leaf tunIod {
            config "false";
            type uint32;
        }
        leaf tunIfIndex {
            config "false";
            type uint32;
        }
        leaf tunIfPmtu {
            config "false";
            type uint32;
        }
        leaf lastCtrRstChgdTs {
            config "false";
            type uint64;
        }
        leaf tunRxPackets {
            config "false";
            type uint64;
        }
        leaf tunRxBytes {
            config "false";
            type uint64;
        }
        leaf tunTxPackets {
            config "false";
            type uint64;
        }
        leaf tunTxBytes {
            config "false";
            type uint64;
        }
        leaf tunSrcIP {
            config "false";
            type address_Ip;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: tunnelif:If->descr
        // Type is an MO-Defined-Type
        leaf descr {
            description "Tunnel Description";

            // Type is an MO-Defined-Type
            type naming_Descr {
                length "0..254";
            }
        }

        // Administrative state
        // Inherited From l3:If
        // Modified by Override: tunnelif:If->adminSt
        // Type is an MO-Defined-Type
        leaf adminSt {
            description "Admin State";

            // Type is an MO-Defined-Type
            type l1_AdminSt;
        }

        // This MO is temporary. Needs to be removed when
        // "vrf member <vrf-name>" is objectified
        container vrf-items {

            // Added containment as a singleton: Prefix=vrf
            // Acquired From Package l1
            uses l1_Vrf-group;
        }

        // Rel-def target from pseudoIf
        // Inherited From mgmt:RtdMgmtIf
        // Inherited From l3:RtdIf
        // Inherited From l3:LbRtdIf
        // Inherited From l3:EncRtdIf
        // Inherited From svi:If
        // Inherited From tunnelif:If
        container rtpseudoIf-items {

            // Added containment as a singleton: Prefix=rtpseudoIf
            // Acquired From Package dhcp
            uses dhcp_RtPseudoIf_target-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ipv4_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per ipv4 instance information. There is
        // only one instance of ipv4 running in the system today
        container inst-items {

            // Added containment as a singleton: Prefix=inst
            // Acquired From Package ipv4
            uses ipv4_Inst-group;
        }
    }

    grouping ipv4_Inst-group {

        // ip source-route enabled by default
        // Type is an MO-Defined-Type
        leaf sourceRoute {
            description "Source-Route";

            // Type is an MO-Defined-Type
            type nw_AdminSt;
        }

        // ip access-list match local enabled by default
        // Type is an MO-Defined-Type
        leaf accessListMatchLocal {
            description "Access-List Match Local";

            // Type is an MO-Defined-Type
            type nw_AdminSt;
        }

        // logging level enabled by default
        // Type is an MO-Defined-Type
        leaf loggingLevel {
            description "Level";

            // Type is an MO-Defined-Type
            type arp_LoggingLevel;
        }

        // Type is an MO-Defined-Type
        leaf defaultLoggingLevel {
            description "Default Logging Level";

            // Type is an MO-Defined-Type
            type arp_LoggingLevel;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Domain (vrf) information
        container dom-items {
            list Dom-list {
                key "name";

                // Added containment: Prefix=dom
                // Acquired From Package ipv4
                uses ipv4_Dom-group;
            }
        }

        // IPv4 Client information
        container client-items {
            list Client-list {
                key "clientName clientProtocol";

                // Added containment: Prefix=client
                // Acquired From Package ipv4
                uses ipv4_Client-group;
            }
        }

        // Load sharing mo
        container iploadsharing-items {

            // Added containment as a singleton: Prefix=iploadsharing
            // Acquired From Package ipv4
            uses ipv4_IPLoadSharing-group;
        }

        container loadstat-items {

            // Added containment as a singleton: Prefix=loadstat
            // Acquired From Package ipv4
            uses ipv4_LoadSharingStat-group;
        }

        container iptrafficstat-items {

            // Added containment as a singleton: Prefix=iptrafficstat
            // Acquired From Package ipv4
            uses ipv4_IpTrafficStat-group;
        }

        container iptrafficerrstat-items {

            // Added containment as a singleton: Prefix=iptrafficerrstat
            // Acquired From Package ipv4
            uses ipv4_IpTrafficErrStat-group;
        }

        container icmptrafficstat-items {

            // Added containment as a singleton: Prefix=icmptrafficstat
            // Acquired From Package ipv4
            uses ipv4_ICMPTrafficStat-group;
        }

        container rfc4293trafficstat-items {

            // Added containment as a singleton: Prefix=rfc4293trafficstat
            // Acquired From Package ipv4
            uses ipv4_RFC4293TrafficStat-group;
        }
    }

    grouping ipv4_Dom-group {

        // Router Id
        // Type is an MO-Defined-Type
        leaf rtrId {
            config "false";
            description "Router ID";

            // Type is an MO-Defined-Type
            type ip_RtrId;
        }

        // ip auto-discard disabled by default
        // Type is an MO-Defined-Type
        leaf autoDiscard {
            description "Auto-Discard";

            // Type is an MO-Defined-Type
            type nw_AdminSt;
        }

        // ip icmp-error source-interface
        // Type is an MO-Defined-Type
        leaf ipIcmpErrorsSrcIntf {
            description "ICMP errors source-interface";

            // Type is an MO-Defined-Type
            type nw_IfId;
        }

        // Inherited From nw:Conn
        // Modified by Override: nw:CpDom->name
        // Type is an MO-Defined-Type
        leaf name {
            description "Name";

            // Type is an MO-Defined-Type
            type naming_Name {
                length "1..64";
            }
        }
        leaf encap {
            type string;
        }

        // ip route static bfd <interface> <nexthop>
        container rtstaticbfd-items {
            list RtStaticBfd-list {
                key "intf nexthop";

                // Added containment: Prefix=rtstaticbfd
                // Acquired From Package ipv4
                uses ipv4_RtStaticBfd-group;
            }
        }

        // This object holds ipv4 information that is operated at a
        // interface level
        container if-items {
            list If-list {
                key "id";

                // Added containment: Prefix=if
                // Acquired From Package ipv4
                uses ipv4_If-group;
            }
        }

        container pstat-items {

            // Added containment as a singleton: Prefix=pstat
            // Acquired From Package ipv4
            uses ipv4_ProcessStat-group;
        }

        // Static route definitions
        container rt-items {
            list Route-list {
                key "prefix";

                // Added containment: Prefix=rt
                // Acquired From Package ipv4
                uses ipv4_Route-group;
            }
        }

        container routestat-items {

            // Added containment as a singleton: Prefix=routestat
            // Acquired From Package ipv4
            uses ipv4_RouteStat-group;
        }
    }

    grouping ipv4_RtStaticBfd-group {

        // interface value.
        // Type is an MO-Defined-Type
        leaf intf {
            description "Interface";

            // Type is an MO-Defined-Type
            type nw_IfId;
        }
        leaf nexthop {
            type address_Ip;
        }
    }

    grouping ipv4_If-group {
        leaf directedBroadcast {
            type enumeration {

                // Disabled
                enum disabled {
                    value 0;
                }

                // Enabled
                enum enabled {
                    value 1;
                }
            }
            default "disabled";
        }
        leaf acl {
            type string {
                length "0..63";
            }
        }

        // IP forward. When interface types: eth, mgmt,
        // or port channel.
        // Type is an MO-Defined-Type
        leaf forward {
            description "IP forward";

            // Type is an MO-Defined-Type
            type nw_AdminSt;
        }

        // IP unnumbered. When interface types: eth, tunnel
        // Type is an MO-Defined-Type
        leaf unnumbered {
            description "IP unnumbered";

            // Type is an MO-Defined-Type
            type nw_IfId;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ip:If
        // Type is an MO-Defined-Type
        leaf ctrl {
            description "Controls";

            // Type is an MO-Defined-Type
            type ip_IfControl;
        }

        // Interface mode
        // Inherited From ip:If
        // Type is an MO-Defined-Type
        leaf mode {
            description "Mode";

            // Type is an MO-Defined-Type
            type ip_IfMode;
        }

        // Donor interface
        // Inherited From ip:If
        // Type is an MO-Defined-Type
        leaf donorIf {
            description "Donor Interface";

            // Type is an MO-Defined-Type
            type nw_IfId;
        }

        // Interface address
        container addr-items {
            list Addr-list {
                key "addr";

                // Added containment: Prefix=addr
                // Acquired From Package ipv4
                uses ipv4_Addr-group;
            }
        }

        container trafficstat-items {

            // Added containment as a singleton: Prefix=trafficstat
            // Acquired From Package ipv4
            uses ipv4_IfTrafficStat-group;
        }

        container stat-items {

            // Added containment as a singleton: Prefix=stat
            // Acquired From Package ipv4
            uses ipv4_IfStat-group;
        }

        // Route map entries
        container rpol-items {

            // Added containment as a singleton: Prefix=rpol
            // Acquired From Package rtmap
            uses rtmap_RmapPolicy-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ipv4_Addr-group {
        leaf seckey {
            type string;
        }
        leaf addr {
            type address_Ip;
        }

        // Type of the address
        // Inherited From ip:Addr
        // Type is an MO-Defined-Type
        leaf type {
            description "Type";

            // Type is an MO-Defined-Type
            type ip_AddrT;
        }

        // Address controls
        // Inherited From ip:Addr
        // Type is an MO-Defined-Type
        leaf ctrl {
            description "Controls";

            // Type is an MO-Defined-Type
            type ip_AddrControl;
        }
        leaf vpcPeer {
            type address_Ip;
        }

        // Ip address preference
        // Inherited From ip:Addr
        // Type is an MO-Defined-Type
        leaf pref {
            description "Preference";

            // Type is an MO-Defined-Type
            type rt_Preference;
        }

        // Route tag
        // Inherited From ip:Addr
        // Type is an MO-Defined-Type
        leaf tag {
            description "Route Tag";

            // Type is an MO-Defined-Type
            type rt_Tag;
        }

        // Operational state
        // Inherited From ip:Addr
        // Type is an MO-Defined-Type
        leaf operSt {
            config "false";
            description "Operational State";

            // Type is an MO-Defined-Type
            type ip_OperSt;
        }

        // Operational state qualifier
        // Inherited From ip:Addr
        // Type is an MO-Defined-Type
        leaf operStQual {
            config "false";
            description "Operational State Qualifier";

            // Type is an MO-Defined-Type
            type ip_AddrOperStQual;
        }
    }

    grouping ipv4_IfTrafficStat-group {
        leaf upktSent {
            config "false";
            type uint64;
        }
        leaf upktRecv {
            config "false";
            type uint64;
        }
        leaf upktFwd {
            config "false";
            type uint64;
        }
        leaf upktOrig {
            config "false";
            type uint64;
        }
        leaf upktConsumed {
            config "false";
            type uint64;
        }
        leaf ubyteSent {
            config "false";
            type uint64;
        }
        leaf ubyteRcv {
            config "false";
            type uint64;
        }
        leaf ubyteFwd {
            config "false";
            type uint64;
        }
        leaf ubyteOrig {
            config "false";
            type uint64;
        }
        leaf ubyteConsumed {
            config "false";
            type uint64;
        }
        leaf mpktSent {
            config "false";
            type uint64;
        }
        leaf mpktRcv {
            config "false";
            type uint64;
        }
        leaf mpktFwd {
            config "false";
            type uint64;
        }
        leaf mpktOrig {
            config "false";
            type uint64;
        }
        leaf mpktConsumed {
            config "false";
            type uint64;
        }
        leaf mbyteSent {
            config "false";
            type uint64;
        }
        leaf mbyteRcv {
            config "false";
            type uint64;
        }
        leaf mbyteFwd {
            config "false";
            type uint64;
        }
        leaf mbyteOrig {
            config "false";
            type uint64;
        }
        leaf mbyteConsumed {
            config "false";
            type uint64;
        }
        leaf bpktSent {
            config "false";
            type uint64;
        }
        leaf bpktRcv {
            config "false";
            type uint64;
        }
        leaf bpktFwd {
            config "false";
            type uint64;
        }
        leaf bpktOrig {
            config "false";
            type uint64;
        }
        leaf bpktConsumed {
            config "false";
            type uint64;
        }
        leaf bbyteSent {
            config "false";
            type uint64;
        }
        leaf bbyteRcv {
            config "false";
            type uint64;
        }
        leaf bbyteFwd {
            config "false";
            type uint64;
        }
        leaf bbyteOrig {
            config "false";
            type uint64;
        }
        leaf bbyteConsumed {
            config "false";
            type uint64;
        }
        leaf lpktSent {
            config "false";
            type uint64;
        }
        leaf lpktRcv {
            config "false";
            type uint64;
        }
        leaf lpktFwd {
            config "false";
            type uint64;
        }
        leaf lpktOrig {
            config "false";
            type uint64;
        }
        leaf lpktConsumed {
            config "false";
            type uint64;
        }
        leaf lbyteSent {
            config "false";
            type uint64;
        }
        leaf lbyteRcv {
            config "false";
            type uint64;
        }
        leaf lbyteFwd {
            config "false";
            type uint64;
        }
        leaf lbyteOrig {
            config "false";
            type uint64;
        }
        leaf lbyteConsumed {
            config "false";
            type uint64;
        }
    }

    grouping ipv4_IfStat-group {
        leaf iodValue {
            config "false";
            type uint64;
        }
        leaf vrfNameOut {
            config "false";
            type string;
        }
        leaf intfName {
            config "false";
            type string;
        }
        leaf protoState {
            config "false";
            type string;
        }
        leaf linkState {
            config "false";
            type string;
        }
        leaf adminState {
            config "false";
            type string;
        }
        leaf priAddr {
            config "false";
            type address_Ipv4;
        }
        leaf priSubnet {
            config "false";
            type string;
        }
        leaf priMasklen {
            config "false";
            type uint8;
        }
        leaf priRoutePref {
            config "false";
            type uint8;
        }
        leaf priTag {
            config "false";
            type uint32;
        }
        leaf secAddr {
            config "false";
            type string;
        }
        leaf secAddrSubnet {
            config "false";
            type string;
        }
        leaf secAddrMasklen {
            config "false";
            type string;
        }
        leaf secAddrRoutePref {
            config "false";
            type string;
        }
        leaf secAddrTag {
            config "false";
            type string;
        }
        leaf numAddr {
            config "false";
            type uint32;
        }
        leaf vaddrClient {
            config "false";
            type string;
        }
        leaf vaddrPrefix {
            config "false";
            type string;
        }
        leaf vaddrSubnet {
            config "false";
            type string;
        }
        leaf vaddrMasklen {
            config "false";
            type string;
        }
        leaf numVaddr {
            config "false";
            type uint64;
        }
        leaf unnumIntf {
            config "false";
            type string;
        }
        leaf ipDisabled {
            config "false";
            type string;
        }
        leaf bcastAddr {
            config "false";
            type address_Ipv4;
        }
        leaf mAddr {
            config "false";
            type string;
        }
        leaf numMaddr {
            config "false";
            type uint32;
        }
        leaf mtu {
            config "false";
            type uint16;
        }
        leaf pref {
            config "false";
            type uint8;
        }
        leaf tag {
            config "false";
            type uint32;
        }

        // Type is an MO-Defined-Type
        leaf proxyArp {
            config "false";
            description "Proxy Arp";

            // Type is a Local-MO-Defined-Type
            type nw_AdminSt_IfStat_proxyArp;
        }

        // Type is an MO-Defined-Type
        leaf localProxyArp {
            config "false";
            description "Local Proxy Arp";

            // Type is a Local-MO-Defined-Type
            type nw_AdminSt_IfStat_localProxyArp;
        }

        // Type is an MO-Defined-Type
        leaf mRouting {
            config "false";
            description "Multicast Routing";

            // Type is a Local-MO-Defined-Type
            type nw_AdminSt_IfStat_mRouting;
        }

        // Type is an MO-Defined-Type
        leaf icmpRedirect {
            config "false";
            description "Icmp Redirect";

            // Type is a Local-MO-Defined-Type
            type nw_AdminSt_IfStat_icmpRedirect;
        }

        // Type is an MO-Defined-Type
        leaf directBcast {
            config "false";
            description "Directed Broadcast";

            // Type is a Local-MO-Defined-Type
            type nw_AdminSt_IfStat_directBcast;
        }

        // Type is an MO-Defined-Type
        leaf ipUnreach {
            config "false";
            description "IP Unreachable";

            // Type is a Local-MO-Defined-Type
            type nw_AdminSt_IfStat_ipUnreach;
        }

        // Type is an MO-Defined-Type
        leaf portUnreach {
            config "false";
            description "Port Unreachable";

            // Type is a Local-MO-Defined-Type
            type nw_AdminSt_IfStat_portUnreach;
        }
        leaf urpfMode {
            config "false";
            type string;
        }
        leaf ipLoadSharing {
            config "false";
            type string;
        }
        leaf aclIn {
            config "false";
            type string;
        }
        leaf aclOut {
            config "false";
            type string;
        }
        leaf statsLastReset {
            config "false";
            type string;
        }
    }

    grouping rtmap_RmapPolicy-group {
        leaf rmapname {
            type string {
                length "0..63";
            }
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping ipv4_ProcessStat-group {
        leaf contextName {
            config "false";
            type string;
        }
        leaf contextId {
            config "false";
            type uint64;
        }
        leaf baseTId {
            config "false";
            type uint64;
        }

        // Type is an MO-Defined-Type
        leaf autoDisc {
            config "false";
            description "Auto Discard";

            // Type is a Local-MO-Defined-Type
            type nw_AdminSt_ProcessStat_autoDisc;
        }

        // Type is an MO-Defined-Type
        leaf autoDiscAdd {
            config "false";
            description "Auto Discard Added";

            // Type is a Local-MO-Defined-Type
            type nw_AdminSt_ProcessStat_autoDiscAdd;
        }

        // Type is an MO-Defined-Type
        leaf nullBcast {
            config "false";
            description "Null BroadCast";

            // Type is a Local-MO-Defined-Type
            type nw_AdminSt_ProcessStat_nullBcast;
        }

        // Type is an MO-Defined-Type
        leaf autoPuntBcast {
            config "false";
            description "Auto Punt Broadcast";

            // Type is a Local-MO-Defined-Type
            type nw_AdminSt_ProcessStat_autoPuntBcast;
        }

        // Type is an MO-Defined-Type
        leaf staticDisc {
            config "false";
            description "Static Discard";

            // Type is a Local-MO-Defined-Type
            type nw_AdminSt_ProcessStat_staticDisc;
        }
        leaf staticDefRoute {
            config "false";
            type uint64;
        }
        leaf ipUnreach {
            config "false";
            type uint64;
        }
        leaf apiVrf {
            config "false";
            type string;
        }
        leaf apiCntxtId {
            config "false";
            type uint64;
        }
        leaf apiBaseTId {
            config "false";
            type uint64;
        }
        leaf apiIpAddr {
            config "false";
            type address_Ipv4;
        }
        leaf apiRtrIdIod {
            config "false";
            type uint64;
        }
        leaf entryIod {
            config "false";
            type string;
        }
        leaf localAddr {
            config "false";
            type string;
        }
    }

    grouping ipv4_Route-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf prefix {
            type address_Ip;
        }

        // Route preference, the administrative distance assigned
        // to this route
        // Inherited From ip:Route
        // Type is an MO-Defined-Type
        leaf pref {
            description "Preference";

            // Type is an MO-Defined-Type
            type rt_Preference;
        }

        // Route tag
        // Inherited From ip:Route
        // Type is an MO-Defined-Type
        leaf tag {
            description "Tag";

            // Type is an MO-Defined-Type
            type rt_Tag;
        }

        // Policy tag
        // Inherited From ip:Route
        // Type is an MO-Defined-Type
        leaf pcTag {
            description "PC Tag";

            // Type is an MO-Defined-Type
            type actrl_PcTag;
        }

        // Route ctrl
        // Inherited From ip:Route
        // Type is an MO-Defined-Type
        leaf ctrl {
            description "Controls";

            // Type is an MO-Defined-Type
            type ip_RtControl;
        }

        // Nexthops for the static route
        container nh-items {
            list Nexthop-list {
                key "nhIf nhAddr nhVrf";

                // Added containment: Prefix=nh
                // Acquired From Package ipv4
                uses ipv4_Nexthop-group;
            }
        }

        // Temporary Nexthop stub created until the Spine proxy
        // IP address is determined.
        container nhs-items {
            list NexthopStub-list {
                key "nhIf nhAddr nhVrf";

                // Added containment: Prefix=nhs
                // Acquired From Package ipv4
                uses ipv4_NexthopStub-group;
            }
        }
    }

    grouping ipv4_Nexthop-group {
        leaf rtname {
            type string;
        }
        leaf tag {
            type uint32;
        }
        leaf pref {
            type uint8;
        }
        leaf object {
            type uint32;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Nexthop interface, force the packet that matches
        // this prefix on this interface
        // Inherited From ip:Nexthop
        // Type is an MO-Defined-Type
        leaf nhIf {
            description "Nexthop Interface";

            // Type is an MO-Defined-Type
            type nw_IfId;
        }
        leaf nhAddr {
            type address_Ip;
        }

        // Nexthop vrf    @@@ This is marked unspecified if the nexthop is in
        // @@@ the same vrf as route
        // Inherited From ip:Nexthop
        // Type is an MO-Defined-Type
        leaf nhVrf {
            description "Nexthop VRF";

            // Type is an MO-Defined-Type
            type l3_VrfName;
        }
        leaf rwEncap {
            type string;
        }

        // Nexthop flags
        // Inherited From ip:Nexthop
        // Type is an MO-Defined-Type
        leaf flags {
            config "false";
            description "Rnh Flags";

            // Type is an MO-Defined-Type
            type ip_NhFlags;
        }

        // Operational state
        // Inherited From ip:Nexthop
        // Type is an MO-Defined-Type
        leaf operSt {
            config "false";
            description "Operational State";

            // Type is an MO-Defined-Type
            type ip_OperSt;
        }

        // Failed state qualifier
        // Inherited From ip:Nexthop
        // Type is an MO-Defined-Type
        leaf operStQual {
            config "false";
            description "Operational State Qualifier";

            // Type is an MO-Defined-Type
            type ip_NhOperStQual;
        }
    }

    grouping ipv4_NexthopStub-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Nexthop interface, force the packet that matches
        // this prefix on this interface
        // Inherited From ip:Nexthop
        // Type is an MO-Defined-Type
        leaf nhIf {
            description "Nexthop Interface";

            // Type is an MO-Defined-Type
            type nw_IfId;
        }
        leaf nhAddr {
            type address_Ip;
        }

        // Nexthop vrf    @@@ This is marked unspecified if the nexthop is in
        // @@@ the same vrf as route
        // Inherited From ip:Nexthop
        // Type is an MO-Defined-Type
        leaf nhVrf {
            description "Nexthop VRF";

            // Type is an MO-Defined-Type
            type l3_VrfName;
        }
        leaf rwEncap {
            type string;
        }

        // Nexthop flags
        // Inherited From ip:Nexthop
        // Type is an MO-Defined-Type
        leaf flags {
            config "false";
            description "Rnh Flags";

            // Type is an MO-Defined-Type
            type ip_NhFlags;
        }

        // Operational state
        // Inherited From ip:Nexthop
        // Type is an MO-Defined-Type
        leaf operSt {
            config "false";
            description "Operational State";

            // Type is an MO-Defined-Type
            type ip_OperSt;
        }

        // Failed state qualifier
        // Inherited From ip:Nexthop
        // Type is an MO-Defined-Type
        leaf operStQual {
            config "false";
            description "Operational State Qualifier";

            // Type is an MO-Defined-Type
            type ip_NhOperStQual;
        }
    }

    grouping ipv4_RouteStat-group {
        leaf contextName {
            config "false";
            type string;
        }
        leaf contextId {
            config "false";
            type uint32;
        }
        leaf prefixMask {
            config "false";
            type string;
        }
        leaf nhPrefixMask {
            config "false";
            type string;
        }
        leaf vrfInfo {
            config "false";
            type string;
        }
        leaf intrInfo {
            config "false";
            type string;
        }
        leaf uribStat {
            config "false";
            type string;
        }
        leaf segId {
            config "false";
            type string;
        }
        leaf tunnelId {
            config "false";
            type string;
        }
        leaf uribEncapType {
            config "false";
            type string;
        }
        leaf nhopUribStat {
            config "false";
            type string;
        }
        leaf trackObjNum {
            config "false";
            type string;
        }
        leaf trackObjState {
            config "false";
            type string;
        }
    }

    grouping ipv4_Client-group {
        leaf clientName {
            type string;
        }
        leaf clientUuid {
            config "false";
            type int32;
        }
        leaf clientPid {
            config "false";
            type int32;
        }
        leaf clientExtPid {
            config "false";
            type uint32;
        }
        leaf clientProtocol {
            type uint8;
        }
        leaf clientIndex {
            config "false";
            type uint16;
        }
        leaf clientContextId {
            config "false";
            type uint32;
        }

        // client mts sap
        // Type is an MO-Defined-Type
        leaf clientMtsSap {
            config "false";
            description "Client Data Mts Sap";

            // Type is an MO-Defined-Type
            type ipv4_ClientMtsSapType;
        }

        // client flag
        // Type is an MO-Defined-Type
        leaf clientFlag {
            config "false";
            description "Client Flag";

            // Type is an MO-Defined-Type
            type ipv4_ClientFlagType;
        }
        leaf clientDataMsgSuccess {
            config "false";
            type uint64;
        }
        leaf clientDataMsgFail {
            config "false";
            type uint64;
        }
        leaf clientRcvFunName {
            config "false";
            type string;
        }
    }

    grouping ipv4_IPLoadSharing-group {

        // load share mode for 'ip load-sharing' cli, there are four modes
        // - 1. {address source-destination}
        // cli: ip load-sharing address source-destination gre-outer
        // concatenation rotate 1 universal-id 2
        // - 2. {address destination port destination}
        // cli: ip load-sharing address source-destination gre
        // concatenation rotate 1 universal-id 2
        // - 3. {address source-destination gre-key}
        // cli: ip load-sharing address destination port destination
        // rotate 1 universal-id 2
        // - 4. {address source-destination port source-destination}
        // cli: ip load-sharing address source-destination port
        // source-destination concatenation
        // Type is an MO-Defined-Type
        leaf loadShareMode {
            description "Load sharing mode";

            // Type is an MO-Defined-Type
            type ip_LoadShareFormat;
        }
        leaf universalID {
            type uint32 {
                range "0..4294967295";
            }
        }

        // whether gre-outer hash is enabled
        // Type is an MO-Defined-Type
        leaf greOuterHash {
            description "GRE Outer Hash";

            // Type is an MO-Defined-Type
            type nw_AdminSt;
        }

        // whether concatenation is enabled
        // Type is an MO-Defined-Type
        leaf concatenation {
            description "Concatenation";

            // Type is an MO-Defined-Type
            type nw_AdminSt;
        }
        leaf rotate {
            type uint16 {
                range "1..63";
            }
            default "32";
        }

        // whether ecmploadsharing is enabled.
        // Not supported on n9k today, defined for future use
        // Type is an MO-Defined-Type
        leaf ecmpLoadSharing {
            description "ECMP load sharing";

            // Type is an MO-Defined-Type
            type nw_AdminSt;
        }
    }

    grouping ipv4_LoadSharingStat-group {
        leaf univerIdRanSeed {
            config "false";
            type uint32;
        }
        leaf ipLoadshareOption {
            config "false";
            type string;
        }

        // Type is an MO-Defined-Type
        leaf hashFlag {
            config "false";
            description "GRE-Outer Hash";

            // Type is an MO-Defined-Type
            type nw_AdminSt;
        }

        // Type is an MO-Defined-Type
        leaf concat {
            config "false";
            description "Concatenation";

            // Type is an MO-Defined-Type
            type nw_AdminSt;
        }
        leaf rotate {
            config "false";
            type uint16 {
                range "1..63";
            }
            default "32";
        }
    }

    grouping ipv4_IpTrafficStat-group {
        leaf vrfNameOut {
            config "false";
            type string;
        }
        leaf received {
            config "false";
            type uint32;
        }
        leaf sent {
            config "false";
            type uint32;
        }
        leaf consumed {
            config "false";
            type uint32;
        }
        leaf fwdUcast {
            config "false";
            type uint32;
        }
        leaf fwdMcast {
            config "false";
            type uint32;
        }
        leaf fwdLabel {
            config "false";
            type uint32;
        }
        leaf ingressMcecFwdPkts {
            config "false";
            type uint32;
        }
        leaf optsEnd {
            config "false";
            type uint32;
        }
        leaf optsNop {
            config "false";
            type uint32;
        }
        leaf optsBsec {
            config "false";
            type uint32;
        }
        leaf optsLsrr {
            config "false";
            type uint32;
        }
        leaf optsTimestamp {
            config "false";
            type uint32;
        }
        leaf optsEsec {
            config "false";
            type uint32;
        }
        leaf optsRecordRoute {
            config "false";
            type uint32;
        }
        leaf optsStrsrcRoute {
            config "false";
            type uint32;
        }
        leaf optsAlert {
            config "false";
            type uint32;
        }
        leaf optsOther {
            config "false";
            type uint32;
        }
        leaf frag {
            config "false";
            type uint32;
        }
        leaf fragmented {
            config "false";
            type uint32;
        }
        leaf outFrag {
            config "false";
            type uint32;
        }
        leaf fragDrop {
            config "false";
            type uint32;
        }
        leaf cantFrag {
            config "false";
            type uint32;
        }
        leaf reasm {
            config "false";
            type uint32;
        }
        leaf fragTO {
            config "false";
            type uint32;
        }
    }

    grouping ipv4_IpTrafficErrStat-group {
        leaf badCsum {
            config "false";
            type uint32;
        }
        leaf tooSmall {
            config "false";
            type uint32;
        }
        leaf badVer {
            config "false";
            type uint32;
        }
        leaf badHLen {
            config "false";
            type uint32;
        }
        leaf badLen {
            config "false";
            type uint32;
        }
        leaf badDest {
            config "false";
            type uint32;
        }
        leaf badTTL {
            config "false";
            type uint32;
        }
        leaf cantFwd {
            config "false";
            type uint32;
        }
        leaf outDrop {
            config "false";
            type uint32;
        }
        leaf badEncap {
            config "false";
            type uint32;
        }
        leaf noRoute {
            config "false";
            type uint32;
        }
        leaf noProto {
            config "false";
            type uint32;
        }
        leaf badOptions {
            config "false";
            type uint32;
        }
        leaf vinciMigPkts {
            config "false";
            type uint32;
        }
        leaf snoopSuccess {
            config "false";
            type uint32;
        }
        leaf sviIodDown {
            config "false";
            type uint32;
        }
        leaf restartPktDrop {
            config "false";
            type uint32;
        }
        leaf mbufErrCount {
            config "false";
            type uint32;
        }
        leaf badCntxtIdDrop {
            config "false";
            type uint32;
        }
        leaf rpfDrop {
            config "false";
            type uint32;
        }
        leaf badGwMacDrop {
            config "false";
            type uint32;
        }
        leaf ipsOptionFail {
            config "false";
            type uint32;
        }
        leaf natInDrop {
            config "false";
            type uint32;
        }
        leaf natOutDrop {
            config "false";
            type uint32;
        }
        leaf ipsMfwdFail {
            config "false";
            type uint32;
        }
        leaf ipsLispDrop {
            config "false";
            type uint32;
        }
        leaf ipsLispDecapDrop {
            config "false";
            type uint32;
        }
        leaf ipsLispEncapDrop {
            config "false";
            type uint32;
        }
        leaf ipsLispEncap {
            config "false";
            type uint32;
        }
        leaf ipsMfwdCopyDrop {
            config "false";
            type uint32;
        }
        leaf ipsRaReassDrop {
            config "false";
            type uint32;
        }
        leaf ipsIcmpRedirProcDrop {
            config "false";
            type uint32;
        }
        leaf ipsIfmgrInitFail {
            config "false";
            type uint32;
        }
        leaf ipsInvalidFilter {
            config "false";
            type uint32;
        }
        leaf ipsInvalidL2msg {
            config "false";
            type uint32;
        }
        leaf aclIngressDrop {
            config "false";
            type uint32;
        }
        leaf aclEgressDrop {
            config "false";
            type uint32;
        }
        leaf aclDirBcastDrop {
            config "false";
            type uint32;
        }
    }

    grouping ipv4_ICMPTrafficStat-group {
        leaf txRedir {
            config "false";
            type uint32;
        }
        leaf txUnreach {
            config "false";
            type uint32;
        }
        leaf txEchoReq {
            config "false";
            type uint32;
        }
        leaf txEchoReply {
            config "false";
            type uint32;
        }
        leaf txMaskReq {
            config "false";
            type uint32;
        }
        leaf txMaskReply {
            config "false";
            type uint32;
        }
        leaf txInfoReq {
            config "false";
            type uint32;
        }
        leaf txInfoReply {
            config "false";
            type uint32;
        }
        leaf txParamProb {
            config "false";
            type uint32;
        }
        leaf txSrcQuench {
            config "false";
            type uint32;
        }
        leaf txTstampReq {
            config "false";
            type uint32;
        }
        leaf txTstampReply {
            config "false";
            type uint32;
        }
        leaf txTstampXceed {
            config "false";
            type uint32;
        }
        leaf txRtrSolicit {
            config "false";
            type uint32;
        }
        leaf txRtrAdvert {
            config "false";
            type uint32;
        }
        leaf outBadLen {
            config "false";
            type uint32;
        }
        leaf outEncapFail {
            config "false";
            type uint32;
        }
        leaf outXmitFail {
            config "false";
            type uint32;
        }
        leaf icmpOrigReq {
            config "false";
            type uint32;
        }
        leaf redirOrigReq {
            config "false";
            type uint32;
        }
        leaf outErr {
            config "false";
            type uint32;
        }
        leaf oldShortIp {
            config "false";
            type uint32;
        }
        leaf oldIcmp {
            config "false";
            type uint32;
        }
        leaf errorDrop {
            config "false";
            type uint32;
        }
        leaf rxRedir {
            config "false";
            type uint32;
        }
        leaf rxUnreach {
            config "false";
            type uint32;
        }
        leaf rxEchoReq {
            config "false";
            type uint32;
        }
        leaf rxEchoReply {
            config "false";
            type uint32;
        }
        leaf rxMaskReq {
            config "false";
            type uint32;
        }
        leaf rxMaskReply {
            config "false";
            type uint32;
        }
        leaf rxInfoReq {
            config "false";
            type uint32;
        }
        leaf rxInfoReply {
            config "false";
            type uint32;
        }
        leaf rxParamProb {
            config "false";
            type uint32;
        }
        leaf rxSrcQuench {
            config "false";
            type uint32;
        }
        leaf rxTstampReq {
            config "false";
            type uint32;
        }
        leaf rxTstampReply {
            config "false";
            type uint32;
        }
        leaf rxTimeXceed {
            config "false";
            type uint32;
        }
        leaf rxRtrSolicit {
            config "false";
            type uint32;
        }
        leaf rxRtrAdvert {
            config "false";
            type uint32;
        }
        leaf rxFormatError {
            config "false";
            type uint32;
        }
        leaf rxCsumError {
            config "false";
            type uint32;
        }
        leaf icmpLispProcessed {
            config "false";
            type uint32;
        }
        leaf icmpNoClients {
            config "false";
            type uint32;
        }
        leaf icmpConsumed {
            config "false";
            type uint32;
        }
        leaf icmpReplies {
            config "false";
            type uint32;
        }
        leaf icmpReplyDropInvldAddr {
            config "false";
            type uint32;
        }
        leaf icmpReplyDropInactAddr {
            config "false";
            type uint32;
        }
        leaf statsLastReset {
            config "false";
            type string;
        }
    }

    grouping ipv4_RFC4293TrafficStat-group {
        leaf inrcv {
            config "false";
            type uint32;
        }
        leaf inoctet {
            config "false";
            type uint32;
        }
        leaf inhdrerr {
            config "false";
            type uint32;
        }
        leaf innoroutes {
            config "false";
            type uint32;
        }
        leaf inaddrerr {
            config "false";
            type uint32;
        }
        leaf innoproto {
            config "false";
            type uint32;
        }
        leaf intruncated {
            config "false";
            type uint32;
        }
        leaf inforwdgrams {
            config "false";
            type uint32;
        }
        leaf reasmreqds {
            config "false";
            type uint32;
        }
        leaf reasmoks {
            config "false";
            type uint32;
        }
        leaf reasmfails {
            config "false";
            type uint32;
        }
        leaf indiscards {
            config "false";
            type uint32;
        }
        leaf indelivers {
            config "false";
            type uint32;
        }
        leaf inMcastPkts {
            config "false";
            type uint32;
        }
        leaf inMcastBytes {
            config "false";
            type uint32;
        }
        leaf inBcastPkts {
            config "false";
            type uint32;
        }
        leaf outRequest {
            config "false";
            type uint32;
        }
        leaf outNoRoutes {
            config "false";
            type uint32;
        }
        leaf outForwdGrams {
            config "false";
            type uint32;
        }
        leaf outDiscards {
            config "false";
            type uint32;
        }
        leaf outFragReqds {
            config "false";
            type uint32;
        }
        leaf outFragOks {
            config "false";
            type uint32;
        }
        leaf outFragFails {
            config "false";
            type uint32;
        }
        leaf outFragCreates {
            config "false";
            type uint32;
        }
        leaf outTransmits {
            config "false";
            type uint32;
        }
        leaf outBytes {
            config "false";
            type uint32;
        }
        leaf outMcastPkts {
            config "false";
            type uint32;
        }
        leaf outMcastBytes {
            config "false";
            type uint32;
        }
        leaf outBcastPkts {
            config "false";
            type uint32;
        }
        leaf outBcastBytes {
            config "false";
            type uint32;
        }
    }

    grouping ipv6_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per ipv6 instance information. There is
        // only one instance of ipv6 running in the system today
        container inst-items {

            // Added containment as a singleton: Prefix=inst
            // Acquired From Package ipv6
            uses ipv6_Inst-group;
        }
    }

    grouping ipv6_Inst-group {

        // ipv6 access-list match local
        // Type is an MO-Defined-Type
        leaf accessListMatchLocal {
            description "Access-List Match Local";

            // Type is an MO-Defined-Type
            type nw_AdminSt;
        }

        // static neighbor outside subnet
        // Type is an MO-Defined-Type
        leaf staticNeighborOutsideSubnet {
            description "Static Neighbor Outside Subnet ";

            // Type is an MO-Defined-Type
            type nw_AdminSt;
        }

        // Queue 1 packet when triggered NS is sent
        // Type is an MO-Defined-Type
        leaf queuePackets {
            description "Queue-packets";

            // Type is an MO-Defined-Type
            type nw_AdminSt;
        }

        // Switch ND packets received on core ports
        // Type is an MO-Defined-Type
        leaf switchPackets {
            description "Switch-packets";

            // Type is an MO-Defined-Type
            type ip_SwitchPktTarget;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Objectification of IPv6 route statistics
        container mtustats-items {

            // Added containment as a singleton: Prefix=mtustats
            // Acquired From Package ipv6
            uses ipv6_IPv6MtuCacheStatGlobal-group;
        }

        // Objectification of IPv6 Client statistics
        container clientstats-items {
            list IPv6Clients-list {
                config "false";
                key "clientName clientProtocol";

                // Added containment: Prefix=clientstats
                // Acquired From Package ipv6
                uses ipv6_IPv6Clients-group;
            }
        }

        // Domain (vrf) information
        container dom-items {
            list Dom-list {
                key "name";

                // Added containment: Prefix=dom
                // Acquired From Package ipv6
                uses ipv6_Dom-group;
            }
        }

        // Objectification of IPv6 Fragments statistics
        container fragstats-items {
            list IPv6Fragments-list {
                key "srcAddr";

                // Added containment: Prefix=fragstats
                // Acquired From Package ipv6
                uses ipv6_IPv6Fragments-group;
            }
        }
        container logs-items {
            list IPv6EventLogs-list {
                key "eventType";

                // Added containment: Prefix=logs
                // Acquired From Package ipv6
                uses ipv6_IPv6EventLogs-group;
            }
        }

        // Holds ipv6 global statistics
        container pktqstats-items {

            // Added containment as a singleton: Prefix=pktqstats
            // Acquired From Package ipv6
            uses ipv6_IPv6InstStat-group;
        }

        // Objectification of IPv6 neighbor statistics
        container ipv6stats-items {
            list IPv6Stat-list {
                key "ftmName";

                // Added containment: Prefix=ipv6stats
                // Acquired From Package ipv6
                uses ipv6_IPv6Stat-group;
            }
        }
    }

    grouping ipv6_IPv6MtuCacheStatGlobal-group {
        leaf outstandingEntries {
            config "false";
            type uint32;
        }
        leaf expiredEntries {
            config "false";
            type uint64;
        }
        leaf purgedEntries {
            config "false";
            type uint64;
        }
        leaf internalErrors {
            config "false";
            type uint64;
        }
        leaf pktTooBig {
            config "false";
            type uint64;
        }
        leaf cacheMisses {
            config "false";
            type uint64;
        }
        leaf cacheUpdates {
            config "false";
            type uint64;
        }
        leaf smallMtuAdv {
            config "false";
            type uint64;
        }
        leaf cacheNoUpdates {
            config "false";
            type uint64;
        }
    }

    grouping ipv6_IPv6Clients-group {
        leaf clientName {
            type string;
        }
        leaf clientStatus {
            config "false";
            type string;
        }
        leaf clientPid {
            config "false";
            type int32;
        }
        leaf clientExtPid {
            config "false";
            type int32;
        }
        leaf clientProtocol {
            config "false";
            type int32;
        }
        leaf clientPibIndex {
            config "false";
            type int32;
        }
        leaf clientUuid {
            config "false";
            type int32;
        }
        leaf clientRoutingVrf {
            config "false";
            type int32;
        }
        leaf clientRoutingFlag {
            config "false";
            type int32;
        }
        leaf clientCtrlMtsSap {
            config "false";
            type int32;
        }
        leaf clientDataMtsSap {
            config "false";
            type int32;
        }
        leaf destUnreachSent {
            config "false";
            type int32;
        }
        leaf destUnreachRcvd {
            config "false";
            type int32;
        }
        leaf adminProhibSent {
            config "false";
            type int32;
        }
        leaf adminProhibRcvd {
            config "false";
            type int32;
        }
        leaf clientIfExtIndex {
            config "false";
            type int32;
        }
        leaf clientRecvFn {
            config "false";
            type string;
        }
        leaf clientRecvHex {
            config "false";
            type string;
        }
    }

    grouping ipv6_Dom-group {

        // Router Id
        // Type is an MO-Defined-Type
        leaf rtrId {
            config "false";
            description "Router ID";

            // Type is an MO-Defined-Type
            type ipv6_RtrId;
        }

        // Inherited From nw:Conn
        // Modified by Override: nw:CpDom->name
        // Type is an MO-Defined-Type
        leaf name {
            description "Name";

            // Type is an MO-Defined-Type
            type naming_Name {
                length "1..64";
            }
        }
        leaf encap {
            type string;
        }

        container mtustats-items {

            // Added containment as a singleton: Prefix=mtustats
            // Acquired From Package ipv6
            uses ipv6_IPv6MtuCacheStat-group;
        }

        // ipv6 route static bfd <interface> <nexthop>
        container rtstaticbfd-items {
            list RtStaticBfd-list {
                key "intf nexthop";

                // Added containment: Prefix=rtstaticbfd
                // Acquired From Package ipv6
                uses ipv6_RtStaticBfd-group;
            }
        }

        // This object holds ipv6 information that is operated at a
        // interface level
        container if-items {
            list If-list {
                key "id";

                // Added containment: Prefix=if
                // Acquired From Package ipv6
                uses ipv6_If-group;
            }
        }

        // Objectification of IPv6 route statistics
        container procstats-items {

            // Added containment as a singleton: Prefix=procstats
            // Acquired From Package ipv6
            uses ipv6_IPv6ProcessStat-group;
        }

        // Static route definitions
        container rt-items {
            list Route-list {
                key "prefix";

                // Added containment: Prefix=rt
                // Acquired From Package ipv6
                uses ipv6_Route-group;
            }
        }

        // Objectification of IPv6 route statistics
        container routestats-items {

            // Added containment as a singleton: Prefix=routestats
            // Acquired From Package ipv6
            uses ipv6_IPv6RouteStat-group;
        }

        // Objectification of IPv6 interface statistics
        container trafficstats-items {

            // Added containment as a singleton: Prefix=trafficstats
            // Acquired From Package ipv6
            uses ipv6_IPv6TrafficStat-group;
        }
    }

    grouping ipv6_IPv6MtuCacheStat-group {
        container addr-items {
            list IPv6MtuCacheDestStat-list {
                config "false";
                key "pathDestination";

                // Added containment: Prefix=addr
                // Acquired From Package ipv6
                uses ipv6_IPv6MtuCacheDestStat-group;
            }
        }
    }

    grouping ipv6_IPv6MtuCacheDestStat-group {
        leaf pathDestination {
            config "false";
            type address_Ipv6;
        }
        leaf pathMtu {
            config "false";
            type uint16;
        }
        leaf outgoingIod {
            config "false";
            type string;
        }
        leaf smallMtuReceived {
            config "false";
            type string;
        }
        leaf bigMtuReeived {
            config "false";
            type string;
        }
        leaf smallMtu {
            config "false";
            type uint16;
        }
        leaf lastMtuUpdate {
            config "false";
            type string;
        }
    }

    grouping ipv6_RtStaticBfd-group {

        // interface value.
        // Type is an MO-Defined-Type
        leaf intf {
            description "Interface";

            // Type is an MO-Defined-Type
            type nw_IfId;
        }
        leaf nexthop {
            type address_Ip;
        }
    }

    grouping ipv6_If-group {

        // Handle ipv6 address use-link-local-address"
        // Type is an MO-Defined-Type
        leaf useLinkLocalAddr {
            description "IPv6 Address Use Link Local Address";

            // Type is an MO-Defined-Type
            type nw_AdminSt;
        }

        // Handle ipv6 forward"
        // Type is an MO-Defined-Type
        leaf forward {
            description "IPv6 forward";

            // Type is an MO-Defined-Type
            type nw_AdminSt;
        }

        // IPv6 Stateless address autoconfig
        // Type is an MO-Defined-Type
        leaf autoconfig {
            description "IPv6 Stateless address autoconfig";

            // Type is an MO-Defined-Type
            type nw_AdminSt;
        }

        // adds default route and the nh would be fetched from RA source address
        // Type is an MO-Defined-Type
        leaf defaultRoute {
            description "Default Route Addition with Nexthop as RA Source Address";

            // Type is an MO-Defined-Type
            type nw_AdminSt;
        }
        leaf llAddr {
            type address_Ip;
        }

        // Operational state
        // Type is an MO-Defined-Type
        leaf lloperSt {
            config "false";
            description "LLaddr Operational State";

            // Type is an MO-Defined-Type
            type ip_OperSt;
        }

        // Operational state qualifier
        // Type is an MO-Defined-Type
        leaf lloperStQual {
            config "false";
            description "LLaddr Operational State Qualifier";

            // Type is an MO-Defined-Type
            type ip_AddrOperStQual;
        }
        leaf operllAddr {
            config "false";
            type address_Ip;
        }

        // To Handle the config fault for this MO
        // Type is an MO-Defined-Type
        leaf configError {
            config "false";
            description "Config error";

            // Type is an MO-Defined-Type
            type ipv6_ConfigErr;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ip:If
        // Type is an MO-Defined-Type
        leaf ctrl {
            description "Controls";

            // Type is an MO-Defined-Type
            type ip_IfControl;
        }

        // Interface mode
        // Inherited From ip:If
        // Type is an MO-Defined-Type
        leaf mode {
            description "Mode";

            // Type is an MO-Defined-Type
            type ip_IfMode;
        }

        // Donor interface
        // Inherited From ip:If
        // Type is an MO-Defined-Type
        leaf donorIf {
            description "Donor Interface";

            // Type is an MO-Defined-Type
            type nw_IfId;
        }

        // Interface address
        container addr-items {
            list Addr-list {
                key "addr";

                // Added containment: Prefix=addr
                // Acquired From Package ipv6
                uses ipv6_Addr-group;
            }
        }

        // Link local Interface address
        container lladdr-items {
            list LLaddr-list {
                key "addr";

                // Added containment: Prefix=lladdr
                // Acquired From Package ipv6
                uses ipv6_LLaddr-group;
            }
        }

        // IPv6 Neighbor Address
        container nghbr-items {
            list Neighbor-list {
                key "addr";

                // Added containment: Prefix=nghbr
                // Acquired From Package ipv6
                uses ipv6_Neighbor-group;
            }
        }

        // Objectification of IPv6 interface statistics
        container ifstats-items {

            // Added containment as a singleton: Prefix=ifstats
            // Acquired From Package ipv6
            uses ipv6_IPv6IfStat-group;
        }

        // Objectification of IPv6 neighbor statistics
        container nbrstats-items {
            list IPv6NeighborStat-list {
                key "ngbrAddr";

                // Added containment: Prefix=nbrstats
                // Acquired From Package ipv6
                uses ipv6_IPv6NeighborStat-group;
            }
        }

        // Route map entries
        container rpol-items {

            // Added containment as a singleton: Prefix=rpol
            // Acquired From Package rtmap
            uses rtmap_RmapPolicy-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ipv6_Addr-group {
        leaf operAddr {
            config "false";
            type address_Ip;
        }
        leaf addr {
            type address_Ip;
        }

        // Type of the address
        // Inherited From ip:Addr
        // Type is an MO-Defined-Type
        leaf type {
            description "Type";

            // Type is an MO-Defined-Type
            type ip_AddrT;
        }

        // Address controls
        // Inherited From ip:Addr
        // Type is an MO-Defined-Type
        leaf ctrl {
            description "Controls";

            // Type is an MO-Defined-Type
            type ip_AddrControl;
        }
        leaf vpcPeer {
            type address_Ip;
        }

        // Ip address preference
        // Inherited From ip:Addr
        // Type is an MO-Defined-Type
        leaf pref {
            description "Preference";

            // Type is an MO-Defined-Type
            type rt_Preference;
        }

        // Route tag
        // Inherited From ip:Addr
        // Type is an MO-Defined-Type
        leaf tag {
            description "Route Tag";

            // Type is an MO-Defined-Type
            type rt_Tag;
        }

        // Operational state
        // Inherited From ip:Addr
        // Type is an MO-Defined-Type
        leaf operSt {
            config "false";
            description "Operational State";

            // Type is an MO-Defined-Type
            type ip_OperSt;
        }

        // Operational state qualifier
        // Inherited From ip:Addr
        // Type is an MO-Defined-Type
        leaf operStQual {
            config "false";
            description "Operational State Qualifier";

            // Type is an MO-Defined-Type
            type ip_AddrOperStQual;
        }
    }

    grouping ipv6_LLaddr-group {
        leaf operAddr {
            config "false";
            type address_Ip;
        }
        leaf addr {
            type address_Ip;
        }

        // Type of the address
        // Inherited From ip:Addr
        // Type is an MO-Defined-Type
        leaf type {
            description "Type";

            // Type is an MO-Defined-Type
            type ip_AddrT;
        }

        // Address controls
        // Inherited From ip:Addr
        // Type is an MO-Defined-Type
        leaf ctrl {
            description "Controls";

            // Type is an MO-Defined-Type
            type ip_AddrControl;
        }
        leaf vpcPeer {
            type address_Ip;
        }

        // Ip address preference
        // Inherited From ip:Addr
        // Type is an MO-Defined-Type
        leaf pref {
            description "Preference";

            // Type is an MO-Defined-Type
            type rt_Preference;
        }

        // Route tag
        // Inherited From ip:Addr
        // Type is an MO-Defined-Type
        leaf tag {
            description "Route Tag";

            // Type is an MO-Defined-Type
            type rt_Tag;
        }

        // Operational state
        // Inherited From ip:Addr
        // Type is an MO-Defined-Type
        leaf operSt {
            config "false";
            description "Operational State";

            // Type is an MO-Defined-Type
            type ip_OperSt;
        }

        // Operational state qualifier
        // Inherited From ip:Addr
        // Type is an MO-Defined-Type
        leaf operStQual {
            config "false";
            description "Operational State Qualifier";

            // Type is an MO-Defined-Type
            type ip_AddrOperStQual;
        }
    }

    grouping ipv6_Neighbor-group {
        leaf neighborMac {
            type address_Mac;
        }

        // To Handle the config fault for this MO
        // Type is an MO-Defined-Type
        leaf configError {
            config "false";
            description "Config error";

            // Type is an MO-Defined-Type
            type ipv6_ConfigErr;
        }
        leaf addr {
            type address_Ip;
        }

        // Type of the address
        // Inherited From ip:Addr
        // Type is an MO-Defined-Type
        leaf type {
            description "Type";

            // Type is an MO-Defined-Type
            type ip_AddrT;
        }

        // Address controls
        // Inherited From ip:Addr
        // Type is an MO-Defined-Type
        leaf ctrl {
            description "Controls";

            // Type is an MO-Defined-Type
            type ip_AddrControl;
        }
        leaf vpcPeer {
            type address_Ip;
        }

        // Ip address preference
        // Inherited From ip:Addr
        // Type is an MO-Defined-Type
        leaf pref {
            description "Preference";

            // Type is an MO-Defined-Type
            type rt_Preference;
        }

        // Route tag
        // Inherited From ip:Addr
        // Type is an MO-Defined-Type
        leaf tag {
            description "Route Tag";

            // Type is an MO-Defined-Type
            type rt_Tag;
        }

        // Operational state
        // Inherited From ip:Addr
        // Type is an MO-Defined-Type
        leaf operSt {
            config "false";
            description "Operational State";

            // Type is an MO-Defined-Type
            type ip_OperSt;
        }

        // Operational state qualifier
        // Inherited From ip:Addr
        // Type is an MO-Defined-Type
        leaf operStQual {
            config "false";
            description "Operational State Qualifier";

            // Type is an MO-Defined-Type
            type ip_AddrOperStQual;
        }
    }

    grouping ipv6_IPv6IfStat-group {
        leaf id {
            type string;
        }
        leaf ifName {
            config "false";
            type string;
        }
        leaf ifProtoState {
            config "false";
            type string;
        }
        leaf ifLinkState {
            config "false";
            type string;
        }
        leaf ifAdminState {
            config "false";
            type string;
        }
        leaf ifIod {
            config "false";
            type uint32;
        }
        leaf ifFwdStatus {
            config "false";
            type boolean;
        }
        leaf ifIpv6Enabled {
            config "false";
            type string;
        }
        leaf ifAddr {
            config "false";
            type string;
        }
        leaf ifAddrSubnet {
            config "false";
            type address_Ip;
        }
        leaf ifAnycastAddr {
            config "false";
            type string;
        }
        leaf ifLLaddr {
            config "false";
            type address_Ip;
        }
        leaf ifLinkLocalConfigStatus {
            config "false";
            type string;
        }
        leaf ifLinkLocalState {
            config "false";
            type string;
        }
        leaf ifVIPAddr {
            config "false";
            type string;
        }
        leaf ifMcastRoutingStatus {
            config "false";
            type string;
        }
        leaf ifReportLLStatus {
            config "false";
            type string;
        }
        leaf ifMcastGroupLocallyJoined {
            config "false";
            type string;
        }
        leaf ifMcastSrcGrpAddr {
            config "false";
            type string;
        }
        leaf ifmtu {
            config "false";
            type uint32;
        }
        leaf ifUcastRevPathFwdMode {
            config "false";
            type string;
        }
        leaf ifUcastRevPathFwdFlag {
            config "false";
            type string;
        }
        leaf ifLoadSharing {
            config "false";
            type string;
        }
        leaf ifStatLastReset {
            config "false";
            type string;
        }
        leaf ifAclInbound {
            config "false";
            type string;
        }
        leaf ifAclOutbound {
            config "false";
            type string;
        }
        leaf ifUnspecifiedSrc {
            config "false";
            type uint32;
        }
        leaf ifTotalPktRxTentativeAddr {
            config "false";
            type uint32;
        }
        leaf ifTotalPktRxInvalidAddrState {
            config "false";
            type uint32;
        }
        leaf ifTotalPktRxDuplicateState {
            config "false";
            type uint32;
        }
        leaf ifAnycastPktTCP {
            config "false";
            type uint32;
        }
        leaf ifDeliverInterfaceDown {
            config "false";
            type uint32;
        }
        leaf rpUcastPktsForwarded {
            config "false";
            type uint32;
        }
        leaf rpUcastPktsOriginated {
            config "false";
            type uint32;
        }
        leaf rpUcastPktsConsumed {
            config "false";
            type uint32;
        }
        leaf rpUcastBytesForwarded {
            config "false";
            type uint32;
        }
        leaf rpUcastBytesOriginated {
            config "false";
            type uint32;
        }
        leaf rpUcastBytesConsumed {
            config "false";
            type uint32;
        }
        leaf rpMcastPktsForwarded {
            config "false";
            type uint32;
        }
        leaf rpMcastPktsOriginated {
            config "false";
            type uint32;
        }
        leaf rpMcastPktsConsumed {
            config "false";
            type uint32;
        }
        leaf rpMcastBytesForwarded {
            config "false";
            type uint32;
        }
        leaf rpMcastBytesOriginated {
            config "false";
            type uint32;
        }
        leaf rpMcastBytesConsumed {
            config "false";
            type uint32;
        }
    }

    grouping ipv6_IPv6NeighborStat-group {
        leaf ngbrAddr {
            type address_Ipv6;
        }
        leaf ngbrMac {
            config "false";
            type address_Mac;
        }
        leaf nghbrInterface {
            config "false";
            type string;
        }
        leaf ngbrPhyInterface {
            config "false";
            type string;
        }
    }

    grouping ipv6_IPv6ProcessStat-group {
        leaf procVRFId {
            config "false";
            type uint32;
        }
        leaf procAutoDiscard {
            config "false";
            type string;
        }
        leaf procAutoDiscardAdded {
            config "false";
            type string;
        }
        leaf procStaticDiscard {
            config "false";
            type string;
        }
        leaf procStaticDefaultCount {
            config "false";
            type uint32;
        }
        leaf procIODList {
            config "false";
            type string;
        }
        leaf procLocalAddrList {
            config "false";
            type string;
        }
    }

    grouping ipv6_Route-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf prefix {
            type address_Ip;
        }

        // Route preference, the administrative distance assigned
        // to this route
        // Inherited From ip:Route
        // Type is an MO-Defined-Type
        leaf pref {
            description "Preference";

            // Type is an MO-Defined-Type
            type rt_Preference;
        }

        // Route tag
        // Inherited From ip:Route
        // Type is an MO-Defined-Type
        leaf tag {
            description "Tag";

            // Type is an MO-Defined-Type
            type rt_Tag;
        }

        // Policy tag
        // Inherited From ip:Route
        // Type is an MO-Defined-Type
        leaf pcTag {
            description "PC Tag";

            // Type is an MO-Defined-Type
            type actrl_PcTag;
        }

        // Route ctrl
        // Inherited From ip:Route
        // Type is an MO-Defined-Type
        leaf ctrl {
            description "Controls";

            // Type is an MO-Defined-Type
            type ip_RtControl;
        }

        // Nexthops for the static route
        container nh-items {
            list Nexthop-list {
                key "nhIf nhAddr nhVrf";

                // Added containment: Prefix=nh
                // Acquired From Package ipv6
                uses ipv6_Nexthop-group;
            }
        }

        // Temporary Nexthop stub created until the Spine proxy
        // IP address is determined.
        container nhs-items {
            list NexthopStub-list {
                key "nhIf nhAddr nhVrf";

                // Added containment: Prefix=nhs
                // Acquired From Package ipv6
                uses ipv6_NexthopStub-group;
            }
        }
    }

    grouping ipv6_Nexthop-group {
        leaf rtname {
            type string;
        }
        leaf tag {
            type uint32;
        }
        leaf pref {
            type uint8;
        }
        leaf object {
            type uint32;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Nexthop interface, force the packet that matches
        // this prefix on this interface
        // Inherited From ip:Nexthop
        // Type is an MO-Defined-Type
        leaf nhIf {
            description "Nexthop Interface";

            // Type is an MO-Defined-Type
            type nw_IfId;
        }
        leaf nhAddr {
            type address_Ip;
        }

        // Nexthop vrf    @@@ This is marked unspecified if the nexthop is in
        // @@@ the same vrf as route
        // Inherited From ip:Nexthop
        // Type is an MO-Defined-Type
        leaf nhVrf {
            description "Nexthop VRF";

            // Type is an MO-Defined-Type
            type l3_VrfName;
        }
        leaf rwEncap {
            type string;
        }

        // Nexthop flags
        // Inherited From ip:Nexthop
        // Type is an MO-Defined-Type
        leaf flags {
            config "false";
            description "Rnh Flags";

            // Type is an MO-Defined-Type
            type ip_NhFlags;
        }

        // Operational state
        // Inherited From ip:Nexthop
        // Type is an MO-Defined-Type
        leaf operSt {
            config "false";
            description "Operational State";

            // Type is an MO-Defined-Type
            type ip_OperSt;
        }

        // Failed state qualifier
        // Inherited From ip:Nexthop
        // Type is an MO-Defined-Type
        leaf operStQual {
            config "false";
            description "Operational State Qualifier";

            // Type is an MO-Defined-Type
            type ip_NhOperStQual;
        }
    }

    grouping ipv6_NexthopStub-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Nexthop interface, force the packet that matches
        // this prefix on this interface
        // Inherited From ip:Nexthop
        // Type is an MO-Defined-Type
        leaf nhIf {
            description "Nexthop Interface";

            // Type is an MO-Defined-Type
            type nw_IfId;
        }
        leaf nhAddr {
            type address_Ip;
        }

        // Nexthop vrf    @@@ This is marked unspecified if the nexthop is in
        // @@@ the same vrf as route
        // Inherited From ip:Nexthop
        // Type is an MO-Defined-Type
        leaf nhVrf {
            description "Nexthop VRF";

            // Type is an MO-Defined-Type
            type l3_VrfName;
        }
        leaf rwEncap {
            type string;
        }

        // Nexthop flags
        // Inherited From ip:Nexthop
        // Type is an MO-Defined-Type
        leaf flags {
            config "false";
            description "Rnh Flags";

            // Type is an MO-Defined-Type
            type ip_NhFlags;
        }

        // Operational state
        // Inherited From ip:Nexthop
        // Type is an MO-Defined-Type
        leaf operSt {
            config "false";
            description "Operational State";

            // Type is an MO-Defined-Type
            type ip_OperSt;
        }

        // Failed state qualifier
        // Inherited From ip:Nexthop
        // Type is an MO-Defined-Type
        leaf operStQual {
            config "false";
            description "Operational State Qualifier";

            // Type is an MO-Defined-Type
            type ip_NhOperStQual;
        }
    }

    grouping ipv6_IPv6RouteStat-group {
        container pfx-items {
            list IPv6RouteStatPfx-list {
                key "rtPrefix rtNextHop";

                // Added containment: Prefix=pfx
                // Acquired From Package ipv6
                uses ipv6_IPv6RouteStatPfx-group;
            }
        }
    }

    grouping ipv6_IPv6RouteStatPfx-group {
        leaf rtPrefix {
            type address_Ip;
        }
        leaf rtNextHop {
            type address_Ip;
        }
        leaf rtRealNextHop {
            config "false";
            type string;
        }
        leaf rtRealNextHopIod {
            config "false";
            type string;
        }
        leaf rtInterface {
            config "false";
            type string;
        }
        leaf rtPreference {
            config "false";
            type uint32;
        }
        leaf rtNhVrfName {
            config "false";
            type string;
        }
        leaf rtResolveTableId {
            config "false";
            type uint32;
        }
        leaf rtTrackObjNum {
            config "false";
            type uint32;
        }
        leaf rtTrackObjState {
            config "false";
            type string;
        }
        leaf rtRnhSentToUrib {
            config "false";
            type string;
        }
        leaf rtBfdEnabled {
            config "false";
            type string;
        }
    }

    grouping ipv6_IPv6TrafficStat-group {
        leaf statLastReset {
            config "false";
            type string;
        }
        leaf ucastFragOriginated {
            config "false";
            type uint64;
        }
        leaf mcastFragOriginated {
            config "false";
            type uint64;
        }
        leaf ucastFragConsumed {
            config "false";
            type uint64;
        }
        leaf mcastFragConsumed {
            config "false";
            type uint64;
        }
        leaf ingressMcecFwdPkts {
            config "false";
            type uint32;
        }
        leaf ingressPktsVinciMigration {
            config "false";
            type uint32;
        }
        leaf errBadVersion {
            config "false";
            type uint64;
        }
        leaf errRouteLookupFailed {
            config "false";
            type uint64;
        }
        leaf errHopLimitExceeded {
            config "false";
            type uint64;
        }
        leaf errIngressIfMgrInitDrops {
            config "false";
            type uint32;
        }
        leaf errRpfDrop {
            config "false";
            type uint32;
        }
        leaf errOptionHeader {
            config "false";
            type uint64;
        }
        leaf errPayloadLenTooSmall {
            config "false";
            type uint64;
        }
        leaf errPMFailed {
            config "false";
            type uint64;
        }
        leaf errMbufError {
            config "false";
            type uint64;
        }
        leaf errEncapError {
            config "false";
            type uint64;
        }
        leaf errPktsDroppedDestIfDown {
            config "false";
            type uint64;
        }
        leaf pktsRecvRx {
            config "false";
            type uint64;
        }
        leaf bytesRecvRx {
            config "false";
            type uint64;
        }
        leaf headerErrorsRx {
            config "false";
            type uint32;
        }
        leaf noRoutesRx {
            config "false";
            type uint32;
        }
        leaf addrErrorRx {
            config "false";
            type uint32;
        }
        leaf unknownProtoRx {
            config "false";
            type uint32;
        }
        leaf truncatedPktsRx {
            config "false";
            type uint32;
        }
        leaf forwardgramsRx {
            config "false";
            type uint64;
        }
        leaf reassemblyRequiredRx {
            config "false";
            type uint32;
        }
        leaf reassemblySuccessfulRx {
            config "false";
            type uint32;
        }
        leaf reassemblyFailedRx {
            config "false";
            type uint32;
        }
        leaf discardedPktsRx {
            config "false";
            type uint32;
        }
        leaf deliveredPktsRx {
            config "false";
            type uint64;
        }
        leaf mcastPktsRx {
            config "false";
            type uint64;
        }
        leaf mcastBytesRx {
            config "false";
            type uint64;
        }
        leaf pktsSentTx {
            config "false";
            type uint64;
        }
        leaf bytesSentTx {
            config "false";
            type uint64;
        }
        leaf sentRequestsTx {
            config "false";
            type uint64;
        }
        leaf noRoutesTx {
            config "false";
            type uint32;
        }
        leaf forwardgramsTx {
            config "false";
            type uint64;
        }
        leaf discardedPktsTx {
            config "false";
            type uint32;
        }
        leaf fragRequiredTx {
            config "false";
            type uint32;
        }
        leaf fragSuccesfulTx {
            config "false";
            type uint32;
        }
        leaf fragFailedTx {
            config "false";
            type uint32;
        }
        leaf fragCreatesTx {
            config "false";
            type uint32;
        }
        leaf transmitsTx {
            config "false";
            type uint64;
        }
        leaf mcastPktsTx {
            config "false";
            type uint64;
        }
        leaf mcastBytesTx {
            config "false";
            type uint64;
        }
        leaf rpUcastPktsForwarded {
            config "false";
            type uint32;
        }
        leaf rpUcastPktsOriginated {
            config "false";
            type uint32;
        }
        leaf rpUcastPktsConsumed {
            config "false";
            type uint32;
        }
        leaf rpUcastBytesForwarded {
            config "false";
            type uint32;
        }
        leaf rpUcastBytesOriginated {
            config "false";
            type uint32;
        }
        leaf rpUcastBytesConsumed {
            config "false";
            type uint32;
        }
        leaf rpMcastPktsForwarded {
            config "false";
            type uint32;
        }
        leaf rpMcastPktsOriginated {
            config "false";
            type uint32;
        }
        leaf rpMcastPktsConsumed {
            config "false";
            type uint32;
        }
        leaf rpMcastBytesForwarded {
            config "false";
            type uint32;
        }
        leaf rpMcastBytesOriginated {
            config "false";
            type uint32;
        }
        leaf rpMcastBytesConsumed {
            config "false";
            type uint32;
        }
    }

    grouping ipv6_IPv6Fragments-group {
        leaf srcAddr {
            type address_Ipv6;
        }
        leaf dstAddr {
            config "false";
            type address_Ipv6;
        }
        leaf fragId {
            config "false";
            type int32;
        }
        leaf fragOffset {
            config "false";
            type int32;
        }
        leaf fragMFlag {
            config "false";
            type int32;
        }
        leaf fragNextHeader {
            config "false";
            type int32;
        }
        leaf fragPayloadLen {
            config "false";
            type int32;
        }
        leaf fragExpirationTime {
            config "false";
            type int32;
        }
    }

    grouping ipv6_IPv6EventLogs-group {

        // Type of Event
        // Type is an MO-Defined-Type
        leaf eventType {
            description "Event Log Type";

            // Type is an MO-Defined-Type
            type ipv6_IPv6EventType;
        }

        // Type of Event LogSize
        // Type is an MO-Defined-Type
        leaf logSize {
            description "Event Log Size";

            // Type is an MO-Defined-Type
            type ipv6_IPv6EventLogSize;
        }
    }

    grouping ipv6_IPv6InstStat-group {
        leaf queuePacket {
            config "false";
            type string;
        }
    }

    grouping ipv6_IPv6Stat-group {
        leaf ftmName {
            type string;
        }
        leaf ftmTimeSecond {
            config "false";
            type uint32;
        }
        leaf ftmTimeNanoSecond {
            config "false";
            type uint32;
        }
        leaf ftCount {
            config "false";
            type uint64;
        }
    }

    grouping l1cap_Prov-group {

        // Subject consuming the capability.
        // Type is an MO-Defined-Type
        leaf subj {
            config "false";
            description "TBD";

            // Type is an MO-Defined-Type
            type l1cap_Subj;
        }

        // Every Consumer has a Subject.
        // Subject represents the entity which consumes the capability.
        // Namespaces which have concrete consumers, define the Subject property
        // and its types
        // Max capability available
        // Inherited From cap:Prov
        // Type is an MO-Defined-Type
        leaf total {
            config "false";
            description "TBD";

            // Type is an MO-Defined-Type
            type cap_Counter;
        }

        // Remaining capability available
        // Inherited From cap:Prov
        // Type is an MO-Defined-Type
        leaf remaining {
            config "false";
            description "TBD";

            // Type is an MO-Defined-Type
            type cap_Counter;
        }

        // utilization indicator in percentages of consiumption
        // Inherited From cap:Prov
        // Type is an MO-Defined-Type
        leaf utilization {
            config "false";
            description "TBD";

            // Type is an MO-Defined-Type
            type cap_StorageHint;
        }

        // Type of the Rule consumed by this consumer.
        // Inherited From cap:Prov
        // Type is an MO-Defined-Type
        leaf type {
            config "false";
            description "TBD";

            // Type is an MO-Defined-Type
            type cap_RuleT;
        }
    }

    grouping ethpm_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This class shall store the global configuration
        // for a running EthPM instance. We have single EthPM
        // in a system
        container inst-items {

            // Added containment as a singleton: Prefix=inst
            // Acquired From Package ethpm
            uses ethpm_Inst-group;
        }
    }

    grouping ethpm_Inst-group {
        leaf vlanTagNative {
            config "false";
            type boolean;
        }

        // System default layer
        // Type is an MO-Defined-Type
        leaf systemDefaultLayer {
            config "false";
            description "System Default Layer";

            // Type is an MO-Defined-Type
            type l1_Layer;
        }

        // System default admin st
        // Type is an MO-Defined-Type
        leaf systemDefaultAdminSt {
            config "false";
            description "System Default Admin St";

            // Type is an MO-Defined-Type
            type l1_AdminSt;
        }

        // System jumbo Mtu
        // Type is an MO-Defined-Type
        leaf systemJumboMtu {
            config "false";
            description "System Jumbo MTU";

            // Type is an MO-Defined-Type
            type l1_Mtu;
        }

        // System logging event
        // Type is an MO-Defined-Type
        leaf logEvent {
            description "Logging Interface events";

            // Type is an MO-Defined-Type
            type l1_LogEventBitmap;
        }

        // System logging level
        // Type is an MO-Defined-Type
        leaf logLevel {
            config "false";
            description "Logging level";

            // Type is an MO-Defined-Type
            type ethpm_SyslogLevel;
        }

        // Total pacer credits
        // Type is an MO-Defined-Type
        leaf pacerTotalCredits {
            config "false";
            description "Pacer Credits";

            // Type is an MO-Defined-Type
            type ethpm_TotalCredits;
        }

        // Access pacer credits
        // Type is an MO-Defined-Type
        leaf pacerAccessCredits {
            config "false";
            description "Access Pacer Credits";

            // Type is an MO-Defined-Type
            type ethpm_AccessCredits;
        }

        // Trunk pacer credits
        // Type is an MO-Defined-Type
        leaf pacerTrunkCredits {
            config "false";
            description "Trunk Pacer Credits";

            // Type is an MO-Defined-Type
            type ethpm_TrunkCredits;
        }

        // Per vlan pacer credits
        // Type is an MO-Defined-Type
        leaf pacerPerVlanCredits {
            config "false";
            description "Per Vlan Pacer Credits";

            // Type is an MO-Defined-Type
            type ethpm_PerVlanCredits;
        }

        // Routed port pacer credits
        // Type is an MO-Defined-Type
        leaf pacerRtdPortCredits {
            config "false";
            description "Routed Port Pacer Credits";

            // Type is an MO-Defined-Type
            type ethpm_RouetdPortCredits;
        }

        // Per sub-interface pacer credits
        // Type is an MO-Defined-Type
        leaf pacerPerSiCredits {
            config "false";
            description "Per SubInterface Pacer Credits";

            // Type is an MO-Defined-Type
            type ethpm_PerSiCredits;
        }

        // fabric port pacer credits
        // Type is an MO-Defined-Type
        leaf pacerFabricPortCredits {
            config "false";
            description "Fabric Port Pacer Credits";

            // Type is an MO-Defined-Type
            type ethpm_FabricPortCredits;
        }

        // Pacer not connected timer value
        // Type is an MO-Defined-Type
        leaf pacerNotConnTimer {
            config "false";
            description "Pacer Timeout";

            // Type is an MO-Defined-Type
            type ethpm_NotConnectedTimer;
        }

        // Pacer not up timer value
        // Type is an MO-Defined-Type
        leaf pacerNotUpTimer {
            config "false";
            description "Pacer not Up Timer Value";

            // Type is an MO-Defined-Type
            type ethpm_NotUpTimer;
        }
        leaf allowUnsupportedSfp {
            type boolean;
            default "true";
        }

        // Interface syslog info
        // Type is an MO-Defined-Type
        leaf ifSyslogInfo {
            config "false";
            description "Interface Syslog Info";

            // Type is an MO-Defined-Type
            type ethpm_SyslogInfo;
        }

        // Admin link-up syslog level
        // Type is an MO-Defined-Type
        leaf adminLinkUpSyslogLevel {
            config "false";
            description "Link Up Syslog Level";

            // Type is an MO-Defined-Type
            type ethpm_SyslogLevel;
        }

        // Admin link-down syslog level
        // Type is an MO-Defined-Type
        leaf adminLinkDownSyslogLevel {
            config "false";
            description "Link Down Syslog Level";

            // Type is an MO-Defined-Type
            type ethpm_SyslogLevel;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        container runtime-items {

            // Added containment as a singleton: Prefix=runtime
            // Acquired From Package ethpm
            uses ethpm_InstRuntime-group;
        }

        // Global Error-disable recovery related configuration
        container errdisrecover-items {

            // Added containment as a singleton: Prefix=errdisrecover
            // Acquired From Package ethpm
            uses ethpm_ErrDisRecover-group;
        }

        // This object stores the runtime state of vlan inside ethpm
        container vlan-items {
            list Vlan-list {
                config "false";
                key "id";

                // Added containment: Prefix=vlan
                // Acquired From Package ethpm
                uses ethpm_Vlan-group;
            }
        }

        // This object stores the runtime state associated
        // with a module inside ethpm
        container module-items {
            list Module-list {
                config "false";
                key "id";

                // Added containment: Prefix=module
                // Acquired From Package ethpm
                uses ethpm_Module-group;
            }
        }
    }

    grouping ethpm_InstRuntime-group {
        leaf staticRMacCfgRefCount {
            config "false";
            type uint32;
        }
        leaf pvlanTrunkCfgRefCount {
            config "false";
            type uint32;
        }
        leaf dot1qRefCount {
            config "false";
            type uint32;
        }
        leaf ethertypeRefCount {
            config "false";
            type uint32;
        }
        leaf l3SatportRefCount {
            config "false";
            type uint32;
        }
        leaf snmpIfTblLastChange {
            config "false";
            type uint64;
        }
        leaf issuPacerRefCount {
            config "false";
            type uint32;
        }
        leaf featurePongState {
            config "false";
            type uint8;
        }
        leaf slowdrainCongCoreConfChkState {
            config "false";
            type uint8;
        }
        leaf slowdrainCongEdgeConfChkState {
            config "false";
            type uint8;
        }
        leaf slowdrainPausConfChkState {
            config "false";
            type uint8;
        }
        leaf slowdrainPausEdgeConfChkState {
            config "false";
            type uint8;
        }
        leaf eeeRefCount {
            config "false";
            type uint32;
        }
        leaf fabpathCfgRefCount {
            config "false";
            type uint32;
        }
        leaf dceSwId {
            config "false";
            type uint32;
        }
        leaf lifLoopbackDone {
            config "false";
            type boolean;
        }
        leaf numBundles {
            config "false";
            type uint32;
        }

        // bundle If list
        // Type is an MO-Defined-Type
        leaf bundleIfList {
            config "false";
            description "Bundle Interface List";

            // Type is an MO-Defined-Type
            type ethpm_IfBundleList1024;
        }

        // Configured loopback interfaces
        // Type is an MO-Defined-Type
        leaf lbIfs {
            config "false";
            description "Loopback Interfaces";

            // Type is an MO-Defined-Type
            type ethpm_LbBitmap;
        }
    }

    grouping ethpm_ErrDisRecover-group {

        // Error disable recovery interval
        // Type is an MO-Defined-Type
        leaf errDisRecovIntvl {
            config "false";
            description "Error Disable Recovery Interval";

            // Type is an MO-Defined-Type
            type ethpm_ErrDisRecovIntvl;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
        container Event-items {
            list Event-list {
                key "event";

                // Added containment: Prefix=Event
                // Acquired From Package ethpm
                uses ethpm_Event-group;
            }
        }

        // Rel-def from ErrDisRecoverPolCons
        container rserrDisRecoverPolCons-items {

            // Added containment as a singleton: Prefix=rserrDisRecoverPolCons
            // Acquired From Package ethpm
            uses ethpm_RsErrDisRecoverPolCons_source-group;
        }
    }

    grouping ethpm_Event-group {

        // Error disable event type
        // Type is an MO-Defined-Type
        leaf event {
            description "Event";

            // Type is an MO-Defined-Type
            type ethpm_ErrDisEvent;
        }
        leaf detect {
            config "false";
            type boolean;
            default "true";
        }
        leaf recover {
            config "false";
            type boolean;
            default "true";
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping ethpm_Vlan-group {

        // vlan id    TODO: how do we add properties to rn
        // for objects owned by process? Currently
        // compilation seems to fails if owner="oper"
        // Type is an MO-Defined-Type
        leaf id {
            config "false";
            description "ID";

            // Type is an MO-Defined-Type
            type l2_DomId;
        }
        leaf numIf {
            config "false";
            type uint32;
        }
        leaf flag {
            config "false";
            type uint32;
        }

        // shut state of vlan
        // Type is an MO-Defined-Type
        leaf shutState {
            config "false";
            description "Shut State";

            // Type is an MO-Defined-Type
            type l1_AdminSt;
        }

        // state of vlan
        // Type is an MO-Defined-Type
        leaf state {
            config "false";
            description "Operational State";

            // Type is an MO-Defined-Type
            type l2_DomAdminSt;
        }
    }

    grouping ethpm_Module-group {
        leaf id {
            config "false";
            type uint8;
        }
        leaf numPortTypes {
            config "false";
            type uint32;
        }
        leaf swCardId {
            config "false";
            type uint16;
        }

        // cfgd ports
        // Type is an MO-Defined-Type
        leaf cfgdPorts {
            config "false";
            description "Configured Ports";

            // Type is an MO-Defined-Type
            type ethpm_PortBitmap;
        }
        leaf flags {
            config "false";
            type uint32;
        }
        leaf runtimeNumPorts {
            config "false";
            type uint8;
        }

        // module type
        // Type is an MO-Defined-Type
        leaf moduleType {
            config "false";
            description "Type";

            // Type is an MO-Defined-Type
            type l1_Module;
        }
        leaf isOffline {
            config "false";
            type boolean;
        }
        leaf lcNodeAddress {
            config "false";
            type uint32;
        }
        leaf portCfgSap {
            config "false";
            type uint16;
        }

        // runtime ports
        // Type is an MO-Defined-Type
        leaf runtimePorts {
            config "false";
            description "Runtime Ports";

            // Type is an MO-Defined-Type
            type ethpm_PortBitmap;
        }
    }

    grouping im_Breakout-group {
        container module-items {
            list Mod-list {
                key "id";

                // Added containment: Prefix=module
                // Acquired From Package im
                uses im_Mod-group;
            }
        }
    }

    grouping im_Mod-group {
        leaf id {
            type uint8 {
                range "1..32";
            }
        }

        // Front-panel port
        container fport-items {
            list FpP-list {
                key "id";

                // Added containment: Prefix=fport
                // Acquired From Package im
                uses im_FpP-group;
            }
        }
    }

    grouping im_FpP-group {
        leaf id {
            type uint8 {
                range "1..72";
            }
        }

        // Breakout Map
        // Type is an MO-Defined-Type
        leaf breakoutMap {
            description "Breakout Map";

            // Type is an MO-Defined-Type
            type im_BreakoutMapT;
        }
    }

    grouping im_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This class shall store the global configuration
        // for a running GIM instance. We have single GIM
        // in a system
        container inst-items {

            // Added containment as a singleton: Prefix=inst
            // Acquired From Package im
            uses im_Inst-group;
        }
    }

    grouping im_Inst-group {

        // Type is an MO-Defined-Type
        leaf mode100M {
            config "false";
            description "Mode 100M";

            // Type is an MO-Defined-Type
            type im_Mode100M;
        }

        // Type is an MO-Defined-Type
        leaf modeHwProfile {
            config "false";
            description "Mode 4C, 2C+4Q";

            // Type is an MO-Defined-Type
            type im_ModeHwProfile;
        }
        leaf numCaps {
            config "false";
            type uint32;
        }

        // default VDC state
        // Type is an MO-Defined-Type
        leaf vdcSt {
            config "false";
            description "Default VDC State";

            // Type is an MO-Defined-Type
            type l1_VdcSt;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This class shall store the software/feature capability
        // information for the GIM instance
        container cap-items {
            list Capability-list {
                config "false";
                key "id";

                // Added containment: Prefix=cap
                // Acquired From Package im
                uses im_Capability-group;
            }
        }

        // This object stores the runtime state associated
        // with a module inside GIM
        container module-items {
            list Module-list {
                config "false";
                key "id";

                // Added containment: Prefix=module
                // Acquired From Package im
                uses im_Module-group;
            }
        }
    }

    grouping im_Capability-group {
        leaf id {
            config "false";
            type uint32;
        }
        leaf capStatus {
            config "false";
            type uint32;
        }
        leaf autoInstCpbl {
            config "false";
            type boolean;
        }
        leaf isInstalled {
            config "false";
            type boolean;
        }
    }

    grouping im_Module-group {
        leaf id {
            config "false";
            type uint8;
        }
        leaf numPorts {
            config "false";
            type uint8;
        }

        // Module type
        // Type is an MO-Defined-Type
        leaf moduleType {
            config "false";
            description "Module Type";

            // Type is an MO-Defined-Type
            type l1_Module;
        }
        leaf swCardId {
            config "false";
            type uint16;
        }
        leaf lcNodeAddress {
            config "false";
            type uint32;
        }
        leaf portCfgSap {
            config "false";
            type uint16;
        }
        leaf isPresent {
            config "false";
            type boolean;
        }
        leaf runtimeFlag {
            config "false";
            type uint8;
        }
        leaf moduleInitiEvalFlag {
            config "false";
            type uint32;
        }
        leaf lcExceptionFlag {
            config "false";
            type uint32;
        }
        leaf lcInsertPldSz {
            config "false";
            type uint32;
        }
        leaf lcInsertPld {
            config "false";
            type uint32;
        }

        // Physical interface
        container phys-items {
            list PhysIf-list {
                config "false";
                key "port";

                // Added containment: Prefix=phys
                // Acquired From Package im
                uses im_PhysIf-group;
            }
        }

        // This object stores the information about
        // different port-types in a module
        container portinfo-items {
            list PortInfo-list {
                config "false";
                key "phyLayer";

                // Added containment: Prefix=portinfo
                // Acquired From Package im
                uses im_PortInfo-group;
            }
        }
    }

    grouping im_PhysIf-group {

        // Operational state summary
        // Type is an MO-Defined-Type
        leaf osSum {
            config "false";
            description "Operational State Summary";

            // Type is an MO-Defined-Type
            type nw_OSSum;
        }

        // Operational port state
        // Type is an MO-Defined-Type
        leaf operSt {
            config "false";
            description "Operational Port State";

            // Type is an MO-Defined-Type
            type l1_OperSt;
        }

        // Operational physical port layer
        // Type is an MO-Defined-Type
        leaf operPhyLayer {
            config "false";
            description "Operational Physical Port Layer";

            // Type is an MO-Defined-Type
            type l1_PhyLayer;
        }
        leaf backplaneMac {
            config "false";
            type address_Mac;
        }
        leaf operRouterMac {
            config "false";
            type address_Mac;
        }
        leaf slot {
            config "false";
            type uint8;
        }
        leaf port {
            config "false";
            type uint8;
        }
        leaf moveStatus {
            config "false";
            type uint32;
        }
    }

    grouping im_PortInfo-group {

        // Physical Layer
        // Type is an MO-Defined-Type
        leaf phyLayer {
            config "false";
            description "Physical Layer";

            // Type is an MO-Defined-Type
            type l1_PhyLayer;
        }
        leaf startNum {
            config "false";
            type uint8;
        }
        leaf numPorts {
            config "false";
            type uint8;
        }
        leaf type {
            config "false";
            type uint8;
        }
    }

    grouping pc_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds per port channel instance information
        container pc-items {

            // Added containment as a singleton: Prefix=pc
            // Acquired From Package pc
            uses pc_Inst-group;
        }
    }

    grouping pc_Inst-group {

        // Load balancing algorithm
        // Type is an MO-Defined-Type
        leaf lbAlgo {
            description "Load Balancing Algorithm";

            // Type is an MO-Defined-Type
            type pc_LoadBalance;
        }

        // Hash distribution type
        // Type is an MO-Defined-Type
        leaf hashDist {
            description "Hash Distribution Type";

            // Type is an MO-Defined-Type
            type pc_PCHashDist;
        }

        // Load defer timeout
        // Type is an MO-Defined-Type
        leaf loadDeferTime {
            description "Load Defer Timeout";

            // Type is an MO-Defined-Type
            type pc_LoadDeferTime;
        }

        // Max number of port-channels
        // Type is an MO-Defined-Type
        leaf maxChannels {
            description "Max Number of Port-channels";

            // Type is an MO-Defined-Type
            type pc_NumChannels;
        }

        // Number of used port-channels
        // Type is an MO-Defined-Type
        leaf usedChannels {
            description "Number of Used Port-channels";

            // Type is an MO-Defined-Type
            type pc_NumChannels;
        }

        // Number of free port-channels
        // Type is an MO-Defined-Type
        leaf freeChannels {
            description "Number of Free Port-channels";

            // Type is an MO-Defined-Type
            type pc_NumChannels;
        }

        // Percentage of used port-channels
        // Type is an MO-Defined-Type
        leaf pcntChannels {
            description "Percentage of Used Port-channels";

            // Type is an MO-Defined-Type
            type pc_PcntChannels;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping l2rib_Entity-group {

        // Global L2RIB instance configuration and operation state.
        // There is only one instance of L2RIB at any time.
        container inst-items {

            // Added containment as a singleton: Prefix=inst
            // Acquired From Package l2rib
            uses l2rib_Inst-group;
        }
    }

    grouping l2rib_Inst-group {

        // L2RIB EVPN Host MAC Mobility Object
        container evpn-items {

            // Added containment as a singleton: Prefix=evpn
            // Acquired From Package l2rib
            uses l2rib_EvpnMACmob-group;
        }
    }

    grouping l2rib_EvpnMACmob-group {
        leaf ddMoves {
            type uint16 {
                range "1..1000";
            }
            default "5";
        }
        leaf ddDuration {
            type uint16 {
                range "2..36000";
            }
            default "180";
        }
        leaf drTimeout {
            type uint16 {
                range "0..1800";
            }
            default "30";
        }
        leaf drRetryCnt {
            type uint16 {
                range "0..3000";
            }
            default "3";
        }
    }

    grouping vlanmgr_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per vlan-mgr instance information. There is only
        // one instance of vlan-mgr running in the system today
        container inst-items {

            // Added containment as a singleton: Prefix=inst
            // Acquired From Package vlanmgr
            uses vlanmgr_Inst-group;
        }
    }

    grouping vlanmgr_Inst-group {

        // Vdc id
        // Type is an MO-Defined-Type
        leaf vdcId {
            config "false";
            description "VDC ID";

            // Type is an MO-Defined-Type
            type l2_VdcId;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // DomainMbrIf class
        container dommbr-items {
            list DomMbrIf-list {
                config "false";
                key "ifIdx";

                // Added containment: Prefix=dommbr
                // Acquired From Package l2
                uses l2_DomMbrIf-group;
            }
        }
    }

    grouping l2_DomMbrIf-group {

        // if-index (Secondary Key)
        // Type is an MO-Defined-Type
        leaf ifIdx {
            config "false";
            description "Interface Index";

            // Type is an MO-Defined-Type
            type nw_IfId;
        }

        // create-flag to track interface creation status
        // Type is an MO-Defined-Type
        leaf createFlag {
            config "false";
            description "Create Flag";

            // Type is an MO-Defined-Type
            type l2_CreateState;
        }

        // bundle_port_state to track port-channel's operational status
        // Type is an MO-Defined-Type
        leaf bundlePortSt {
            config "false";
            description "Bundle Port State";

            // Type is an MO-Defined-Type
            type l1_OperSt;
        }

        // phy-port-state to track port's physical state
        // Type is an MO-Defined-Type
        leaf phyPortState {
            config "false";
            description "Physical Port State";

            // Type is an MO-Defined-Type
            type l1_OperSt;
        }

        // pm-port-state to track port's protocol state
        // Type is an MO-Defined-Type
        leaf pmPortState {
            config "false";
            description "Protocol State";

            // Type is an MO-Defined-Type
            type l1_OperSt;
        }

        // port's access vlan
        // Type is an MO-Defined-Type
        leaf accessVlan {
            config "false";
            description "Access VLAN";

            // Type is an MO-Defined-Type
            type l2_DomId;
        }

        // port's native vlan
        // Type is an MO-Defined-Type
        leaf nativeVlan {
            config "false";
            description "Native VLAN";

            // Type is an MO-Defined-Type
            type l2_DomId;
        }

        // pm-port-mode to track port's mode (access, trunk etc)
        // Type is an MO-Defined-Type
        leaf pmPortMode {
            config "false";
            description "Port Mode";

            // Type is an MO-Defined-Type
            type l1_Mode;
        }

        // allowed-vlan-bitmap used to track vlans that are configured on the interface
        // Type is an MO-Defined-Type
        leaf allowedVlanBmp {
            config "false";
            description "Allowed Vlan Bitmap";

            // Type is an MO-Defined-Type
            type l2_VlanBitmap;
        }

        // up-vlan-bitmap used to track vlans that are up on the interface
        // Type is an MO-Defined-Type
        leaf trunkPortUpVlanBmp {
            config "false";
            description "Trunk Port Up Vlan Bitmap";

            // Type is an MO-Defined-Type
            type l2_VlanBitmap;
        }

        // From Interface naming:Named
        // Inherited From naming:NamedObject
        // Type is an MO-Defined-Type
        leaf name {
            description "Name";

            // Type is an MO-Defined-Type
            type naming_Name;
        }
    }

    grouping nvo_Ep-group {

        // Type is an MO-Defined-Type
        leaf epId {
            description "Network Virtualization Overlay endpoint ID";

            // Type is an MO-Defined-Type
            type nvo_EpIdT;
        }

        // Type is an MO-Defined-Type
        leaf adminSt {
            description "Admin state";

            // Type is an MO-Defined-Type
            type nw_AdminSt;
        }
        leaf descr {
            type string;
        }

        // Type is an MO-Defined-Type
        leaf sourceInterface {
            description "Source Interface";

            // Type is an MO-Defined-Type
            type nw_IfId;
        }
        leaf holdDownTime {
            type uint16 {
                range "1..1000";
            }
            default "180";
        }

        // Type is an MO-Defined-Type
        leaf hostReach {
            description "Host Reachability Protocol";

            // Type is an MO-Defined-Type
            type nvo_HostReachT;
        }
        leaf controllerId {
            type uint32;
            default "0";
        }

        // Type is an MO-Defined-Type
        leaf cfgSrc {
            description "Configuration Source";

            // Type is an MO-Defined-Type
            type nvo_CfgSrcT;
        }

        // Type is an MO-Defined-Type
        leaf encapType {
            description "Encap Type";

            // Type is an MO-Defined-Type
            type nvo_EncapT;
        }
        leaf autoRemapReplicationServers {
            type boolean;
        }

        // Type is an MO-Defined-Type
        leaf operState {
            config "false";
            description "Operational State";

            // Type is an MO-Defined-Type
            type l2_DomOperSt;
        }

        // Type is an MO-Defined-Type
        leaf operEncapType {
            config "false";
            description "Operational encap type";

            // Type is an MO-Defined-Type
            type nvo_EncapT;
        }
        leaf mac {
            config "false";
            type address_Mac;
        }

        // Type is an MO-Defined-Type
        leaf learningMode {
            config "false";
            description "Host learning mode";

            // Type is an MO-Defined-Type
            type nvo_HostLearnModeT;
        }

        // Type is an MO-Defined-Type
        leaf propFaultBitmap {
            config "false";
            description "Error state for Ep MO";

            // Type is an MO-Defined-Type
            type nvo_EpFaultBitmapT;
        }
        leaf holdUpTime {
            config "false";
            type uint16;
        }

        // Type is an MO-Defined-Type
        leaf holdDownTimerExpiryTime {
            config "false";
            description "Time when hold down timer will expire";

            // Type is an MO-Defined-Type
            type nvo_ETimeStamp;
        }

        // Type is an MO-Defined-Type
        leaf holdUpTimerExpiryTime {
            config "false";
            description "Time when hold up timer will expire";

            // Type is an MO-Defined-Type
            type nvo_ETimeStamp;
        }
        leaf vpcVIPNotified {
            config "false";
            type boolean;
        }

        container peers-items {

            // Added containment as a singleton: Prefix=peers
            // Acquired From Package nvo
            uses nvo_Peers-group;
        }

        container nws-items {

            // Added containment as a singleton: Prefix=nws
            // Acquired From Package nvo
            uses nvo_Nws-group;
        }

        // Commented out
        // <mo name="StVni"
        // access="admin,access-connectivity-l2"
        // concrete="yes"
        // configure="yes"
        // label="Static Peer VNI relationship object"
        // >
        // <property name="vni"
        // type="VniT"
        // owner="oper"
        // mod="explicit"
        // label="Virtual Network ID"
        // />
        // </mo>
        // <contains parent="StPeer"
        // child="StVni"
        // />
        // <rn mo="StVni">
        // <item prefix="vni" property="vni"/>
        // </rn>
        container peer_track-items {

            // Added containment as a singleton: Prefix=peer_track
            // Acquired From Package nvo
            uses nvo_PeerTracker-group;
        }

        container cntrs-items {

            // Added containment as a singleton: Prefix=cntrs
            // Acquired From Package nvo
            uses nvo_Counters-group;
        }

        // Rel-def from operSourceInterface
        container rsoperSourceInterface-items {

            // Added containment as a singleton: Prefix=rsoperSourceInterface
            // Acquired From Package nvo
            uses nvo_RsOperSourceInterface_source-group;
        }
    }

    grouping nvo_Peers-group {
        container dy_peer-items {
            list DyPeer-list {
                config "false";
                key "ip";

                // Added containment: Prefix=dy_peer
                // Acquired From Package nvo
                uses nvo_DyPeer-group;
            }
        }

        // Commented out
        // <mo name="DyVni"
        // access="admin,access-connectivity-l2"
        // concrete="yes"
        // configure="no"
        // label="Dynamic Peer VNI relationship object"
        // >
        // <property name="vni"
        // type="VniT"
        // owner="oper"
        // mod="explicit"
        // label="Virtual Network ID"
        // />
        // </mo>
        // <contains parent="DyPeer"
        // child="DyVni"
        // />
        // <rn mo="DyVni">
        // <item prefix="vni" property="vni"/>
        // </rn>
        container st_peer-items {
            list StPeer-list {
                key "ip";

                // Added containment: Prefix=st_peer
                // Acquired From Package nvo
                uses nvo_StPeer-group;
            }
        }
    }

    grouping nvo_DyPeer-group {
        leaf ip {
            config "false";
            type address_Ipv4;
        }

        // Inherited From nvo:GenericPeer
        // Type is an MO-Defined-Type
        leaf state {
            config "false";
            description "NVE Peer state";

            // Type is an MO-Defined-Type
            type nvo_PeerStateT;
        }
        leaf upStateTransitionTs {
            config "false";
            type uint64;
        }
        leaf mac {
            config "false";
            type address_Mac;
        }

        // Inherited From nvo:GenericPeer
        // Type is an MO-Defined-Type
        leaf firstVNI {
            config "false";
            description "First VNI Peer was learnt on";

            // Type is an MO-Defined-Type
            type nvo_VniT;
        }
        leaf createTs {
            config "false";
            type uint64;
        }

        container cntrs-items {

            // Added containment as a singleton: Prefix=cntrs
            // Acquired From Package nvo
            uses nvo_Counters-group;
        }

        // Rel-def from Vni
        container rsvni-items {

            // Abstract containment of rsvni derived from nvo:DyPeer
            list RsVni-list {
                config "false";
                key "tDn";

                // Added containment: Prefix=rsvni
                // Acquired From Package nvo
                uses nvo_RsVni_source-group;
            }
        }
    }

    grouping nvo_Counters-group {
        leaf txUcastpkts {
            config "false";
            type uint64;
        }
        leaf txUcastbytes {
            config "false";
            type uint64;
        }
        leaf txMcastpkts {
            config "false";
            type uint64;
        }
        leaf txMcastbytes {
            config "false";
            type uint64;
        }
        leaf rxUcastpkts {
            config "false";
            type uint64;
        }
        leaf rxUcastbytes {
            config "false";
            type uint64;
        }
        leaf rxMcastpkts {
            config "false";
            type uint64;
        }
        leaf rxMcastbytes {
            config "false";
            type uint64;
        }
    }

    grouping nvo_StPeer-group {
        leaf ip {
            type address_Ipv4;
        }

        // Type is an MO-Defined-Type
        leaf type {
            description "NVO Peer type (mcast/physical)";

            // Type is an MO-Defined-Type
            type tunnel_EpT;
        }
        leaf peerId {
            type uint32;
        }

        // Operational properties
        // Type is an MO-Defined-Type
        leaf propFaultBitmap {
            config "false";
            description "Error state for StIRPeer MO";

            // Type is an MO-Defined-Type
            type nvo_StPeerFaultBitmapT;
        }

        // Inherited From nvo:GenericPeer
        // Type is an MO-Defined-Type
        leaf state {
            config "false";
            description "NVE Peer state";

            // Type is an MO-Defined-Type
            type nvo_PeerStateT;
        }
        leaf upStateTransitionTs {
            config "false";
            type uint64;
        }
        leaf mac {
            config "false";
            type address_Mac;
        }

        // Inherited From nvo:GenericPeer
        // Type is an MO-Defined-Type
        leaf firstVNI {
            config "false";
            description "First VNI Peer was learnt on";

            // Type is an MO-Defined-Type
            type nvo_VniT;
        }
        leaf createTs {
            config "false";
            type uint64;
        }

        container cntrs-items {

            // Added containment as a singleton: Prefix=cntrs
            // Acquired From Package nvo
            uses nvo_Counters-group;
        }
    }

    grouping nvo_Nws-group {
        container vni-items {
            list Nw-list {
                key "vni";

                // Added containment: Prefix=vni
                // Acquired From Package nvo
                uses nvo_Nw-group;
            }
        }
    }

    grouping nvo_Nw-group {

        // Type is an MO-Defined-Type
        leaf vni {
            description "Virtual Network ID";

            // Type is an MO-Defined-Type
            type nvo_VniT;
        }

        // Type is an MO-Defined-Type
        leaf vniRangeMin {
            description "VNI Range min (used only via CLI)";

            // Type is an MO-Defined-Type
            type nvo_VniT;
        }

        // Type is an MO-Defined-Type
        leaf vniRangeMax {
            description "VNI Range max (used only via CLI)";

            // Type is an MO-Defined-Type
            type nvo_VniT;
        }
        leaf suppressARP {
            type boolean;
        }

        // Type is an MO-Defined-Type
        leaf mcastGroup {
            description "Base multicast group address";

            // Type is an MO-Defined-Type
            type mcast_GrpIp;
        }
        leaf isMcastRange {
            type boolean;
        }
        leaf associateVrfFlag {
            type boolean;
        }
        leaf isLegacyMode {
            type boolean;
        }

        // This property is hidden (secure="yes") and used only for internal validation.
        // Following are the expected values -
        // non-CLI/non-Controller DME agents (eg. NetConf/RestConf) - "0"
        // CLI - "cli"
        // Controller - "controller"
        // Type is an MO-Defined-Type
        leaf cfgSrc {
            description "Internal system property. Not intended for external use";

            // Type is an MO-Defined-Type
            type nvo_CfgSrcT;
        }
        leaf dummy {
            type boolean;
        }

        // Operational properties
        // Type is an MO-Defined-Type
        leaf epId {
            config "false";
            description "Network Virtualization Overlay endpoint ID";

            // Type is an MO-Defined-Type
            type nvo_EpIdT;
        }

        // Type is an MO-Defined-Type
        leaf operMcastGroup {
            config "false";
            description "Base multicast group address";

            // Type is an MO-Defined-Type
            type mcast_GrpIp;
        }

        // Type is an MO-Defined-Type
        leaf state {
            config "false";
            description "VNI state";

            // Type is an MO-Defined-Type
            type nvo_VniStateT;
        }

        // Type is an MO-Defined-Type
        leaf mode {
            config "false";
            description "VNI mode";

            // Type is an MO-Defined-Type
            type nvo_HostLearnModeT;
        }

        // Type is an MO-Defined-Type
        leaf type {
            config "false";
            description "VNI type";

            // Type is an MO-Defined-Type
            type nvo_VniTypeT;
        }
        leaf vlanBD {
            config "false";
            type string;
        }

        // Type is an MO-Defined-Type
        leaf propFaultBitmap {
            config "false";
            description "Error state for Nw MO";

            // Type is an MO-Defined-Type
            type nvo_NwFaultBitmapT;
        }

        container IngRepl-items {

            // Added containment as a singleton: Prefix=IngRepl
            // Acquired From Package nvo
            uses nvo_IngRepl-group;
        }

        container cntrs-items {

            // Added containment as a singleton: Prefix=cntrs
            // Acquired From Package nvo
            uses nvo_Counters-group;
        }

        // Rel-def target from Vni
        // Inherited From nvo:Nw
        container rtVni-items {

            // Added containment as a singleton: Prefix=rtVni
            // Acquired From Package nvo
            uses nvo_RtVni_target-group;
        }
    }

    grouping nvo_IngRepl-group {

        // Type is an MO-Defined-Type
        leaf proto {
            description "Vxlan Ingress Replication Protocol";

            // Type is an MO-Defined-Type
            type nvo_IngReplProtoT;
        }

        // This property is required specifically for configuring replication
        // servers from the controller. When its value is replicationServer, it
        // signifies that the static peers downloaded from controller should
        // programmed wth vni hashing. This property directly maps to the
        // replicationMode property in BdEntry MO in the aggregate model.
        // And since this property is to be set only from the controller, it has
        // been defined as hidden. So it will not be visible in REST/Netconf or
        // any other external interface.
        // Type is an MO-Defined-Type
        leaf replMode {
            description "ReplicationMode";

            // Type is an MO-Defined-Type
            type nvo_ReplModeT;
        }

        // Operational properties
        // Type is an MO-Defined-Type
        leaf propFaultBitmap {
            config "false";
            description "Error state for IngRepl MO";

            // Type is an MO-Defined-Type
            type nvo_IrFaultBitmapT;
        }
        container st_ir_peer-items {
            list StIRPeer-list {
                key "ip";

                // Added containment: Prefix=st_ir_peer
                // Acquired From Package nvo
                uses nvo_StIRPeer-group;
            }
        }
        container dyn_ir_peer-items {
            list DyIRPeer-list {
                config "false";
                key "ip";

                // Added containment: Prefix=dyn_ir_peer
                // Acquired From Package nvo
                uses nvo_DyIRPeer-group;
            }
        }
    }

    grouping nvo_StIRPeer-group {
        leaf ip {
            type address_Ipv4;
        }

        // Operational properties
        // Type is an MO-Defined-Type
        leaf propFaultBitmap {
            config "false";
            description "Error state for StIRPeer MO";

            // Type is an MO-Defined-Type
            type nvo_StIRFaultBitmapT;
        }

        // Inherited From nvo:GenericIRPeer
        // Type is an MO-Defined-Type
        leaf state {
            config "false";
            description "NVE Peer state";

            // Type is an MO-Defined-Type
            type nvo_PeerStateT;
        }
        leaf upStateTransitionTs {
            config "false";
            type uint64;
        }
        leaf createTs {
            config "false";
            type uint64;
        }

        container cntrs-items {

            // Added containment as a singleton: Prefix=cntrs
            // Acquired From Package nvo
            uses nvo_Counters-group;
        }
    }

    grouping nvo_DyIRPeer-group {
        leaf ip {
            config "false";
            type address_Ipv4;
        }

        // Inherited From nvo:GenericIRPeer
        // Type is an MO-Defined-Type
        leaf state {
            config "false";
            description "NVE Peer state";

            // Type is an MO-Defined-Type
            type nvo_PeerStateT;
        }
        leaf upStateTransitionTs {
            config "false";
            type uint64;
        }
        leaf createTs {
            config "false";
            type uint64;
        }

        container cntrs-items {

            // Added containment as a singleton: Prefix=cntrs
            // Acquired From Package nvo
            uses nvo_Counters-group;
        }
    }

    grouping nvo_PeerTracker-group {
        leaf innerDestMac {
            type address_Mac;
        }
        leaf remotePeerIP {
            type address_Ipv4;
        }
        leaf innerDestIP {
            type address_Ipv4;
        }

        container peer-items {

            // Added containment as a singleton: Prefix=peer
            // Acquired From Package nvo
            uses nvo_Peer-group;
        }
    }

    grouping nvo_Peer-group {
        leaf ip {
            type address_Ipv4;
        }
    }

    grouping l3_Ctx-group {

        // parameter used by node to enforce filter rules
        // Type is an MO-Defined-Type
        leaf pcEnfPref {
            description "Policy Control Enforcement";

            // Type is an MO-Defined-Type
            type fv_PcEnfPref;
        }

        // Type of the context
        // Type is an MO-Defined-Type
        leaf type {
            description "Type";

            // Type is an MO-Defined-Type
            type l3_CtxT;
        }

        // It represents the classId for the multicast traffic
        // terminating on this context
        // Type is an MO-Defined-Type
        leaf pcTag {
            description "PC Tag";

            // Type is an MO-Defined-Type
            type actrl_PcTag;
        }

        // Local managment class id
        // Type is an MO-Defined-Type
        leaf mgmtPcTag {
            description "Management PC Tag";

            // Type is an MO-Defined-Type
            type actrl_PcTag;
        }

        // Inherited From nw:Conn
        // Modified by Override: nw:FwDom->name
        // Modified by Override: l3:Dom->name
        // Type is an MO-Defined-Type
        leaf name {
            description "Name";

            // Type is an MO-Defined-Type
            type naming_Name {
                length "1..64";
            }
        }

        // Vrf Id. Its a Policyelemnt owned ID used for resource tracking purpose
        // Inherited From l3:Dom
        // Type is an MO-Defined-Type
        leaf resourceId {
            config "false";
            description "VRF ID";

            // Type is an MO-Defined-Type
            type l3_VrfId;
        }

        // vrf id
        // Inherited From l3:Dom
        // Type is an MO-Defined-Type
        leaf id {
            config "false";
            description "VRF ID";

            // Type is an MO-Defined-Type
            type l3_VrfId;
        }
        leaf encap {
            type string;
        }
        leaf descr {
            type string;
        }

        // Scope of the context. It identifies the classId
        // pool and all the epg/bd classIds belonging to
        // this context needs to be allocated from this pool
        // Inherited From l3:Dom
        // Type is an MO-Defined-Type
        leaf scope {
            config "false";
            description "Scope";

            // Type is an MO-Defined-Type
            type actrl_ScopeId;
        }

        // Controller Id
        // Inherited From l3:Dom
        // Type is an MO-Defined-Type
        leaf ctrlrId {
            description "Controller ID";

            // Type is an MO-Defined-Type
            type aggregate_ControllerID;
        }

        // SecurityLabel
        // Inherited From l3:Dom
        // Type is an MO-Defined-Type
        leaf secLbl {
            config "false";
            description "Security Label";

            // Type is an MO-Defined-Type
            type actrl_SecLbl;
        }

        // vrf Admin State
        // Inherited From l3:Dom
        // Type is an MO-Defined-Type
        leaf adminState {
            description "Admin State";

            // Type is an MO-Defined-Type
            type l3_VrfAdminState;
        }

        // vrf Oper State
        // Inherited From l3:Dom
        // Type is an MO-Defined-Type
        leaf operState {
            config "false";
            description "Operational State";

            // Type is an MO-Defined-Type
            type l3_VrfOperState;
        }

        // oper state reason
        // Inherited From l3:Dom
        // Type is an MO-Defined-Type
        leaf operStQual {
            config "false";
            description "Operational State Qualifier";

            // Type is an MO-Defined-Type
            type l3_VrfOperStateQual;
        }

        // old oper state reason
        // Inherited From l3:Dom
        // Type is an MO-Defined-Type
        leaf oldOperStQual {
            config "false";
            description "Old Operational State Qualifier";

            // Type is an MO-Defined-Type
            type l3_VrfOperStateQual;
        }
        leaf gsdbCtx {
            config "false";
            type uint32;
        }
        leaf pending {
            config "false";
            type boolean;
        }
        leaf v4TibValid {
            config "false";
            type boolean;
        }
        leaf v4TibId {
            config "false";
            type uint32;
        }
        leaf v4TibName {
            config "false";
            type string;
        }
        leaf v4TibPending {
            config "false";
            type boolean;
        }

        // ipv4 table Oper State
        // Inherited From l3:Dom
        // Type is an MO-Defined-Type
        leaf v4TibOperState {
            config "false";
            description "IPV4 Table Operational State";

            // Type is an MO-Defined-Type
            type l3_VrfOperState;
        }

        // ipv4 table oper state reason
        // Inherited From l3:Dom
        // Type is an MO-Defined-Type
        leaf v4TibOperStQual {
            config "false";
            description "IPV4 Table Operational State Qualifier";

            // Type is an MO-Defined-Type
            type l3_VrfOperStateQual;
        }

        // ipv4 table old oper state reason
        // Inherited From l3:Dom
        // Type is an MO-Defined-Type
        leaf v4TibOldOperStQual {
            config "false";
            description "IPV4 Old Operational State Qualifier";

            // Type is an MO-Defined-Type
            type l3_VrfOperStateQual;
        }
        leaf v6TibValid {
            config "false";
            type boolean;
        }
        leaf v6TibId {
            config "false";
            type uint32;
        }
        leaf v6TibName {
            config "false";
            type string;
        }
        leaf v6TibPending {
            config "false";
            type boolean;
        }

        // ipv6 table Oper State
        // Inherited From l3:Dom
        // Type is an MO-Defined-Type
        leaf v6TibOperState {
            config "false";
            description "IPV6 Table Operational State";

            // Type is an MO-Defined-Type
            type l3_VrfOperState;
        }

        // ipv6 table oper state reason
        // Inherited From l3:Dom
        // Type is an MO-Defined-Type
        leaf v6TibOperStQual {
            config "false";
            description "IPV6 Table Operational State Qualifer";

            // Type is an MO-Defined-Type
            type l3_VrfOperStateQual;
        }

        // ipv6 table old oper state reason
        // Inherited From l3:Dom
        // Type is an MO-Defined-Type
        leaf v6TibOldOperStQual {
            config "false";
            description "IPV6 Table Operational State Qualifer";

            // Type is an MO-Defined-Type
            type l3_VrfOperStateQual;
        }
        leaf createTs {
            config "false";
            type uint64;
        }
        leaf lastChgdTs {
            config "false";
            type uint64;
        }

        // bgp route distinguisher
        // Inherited From l3:Dom
        // Type is an MO-Defined-Type
        leaf bgpRd {
            config "false";
            description "BGP Route Distinguisher";

            // Type is an MO-Defined-Type
            type l3_BgpRdBytes;
        }
        leaf bgpRdDisp {
            config "false";
            type string;
        }
        leaf prtclBmp {
            config "false";
            type uint32;
        }
        leaf oui {
            config "false";
            type uint32;
        }
        leaf vpnId {
            config "false";
            type uint32;
        }

        // End-Point retention policy identifying the duration
        // of how long information is kept about remote end-point.
        // This is expressed through a set of triggering and
        // aging control parameters
        container epret-items {

            // Added containment as a singleton: Prefix=epret
            // Acquired From Package l2
            uses l2_EpRetPol-group;
        }

        // Prefix list entry definition
        container pfx-items {
            list PfxEntry-list {
                config "false";
                key "addr";

                // Added containment: Prefix=pfx
                // Acquired From Package actrl
                uses actrl_PfxEntry-group;
            }
        }

        // Abstraction of epm database
        container db-items {
            list Db-list {
                config "false";
                key "type";

                // Added containment: Prefix=db
                // Acquired From Package epm
                uses epm_Db-group;
            }
        }

        // Routed management interface
        container mgmt-items {
            list RtdMgmtIf-list {
                key "id";

                // Added containment: Prefix=mgmt
                // Acquired From Package mgmt
                uses mgmt_RtdMgmtIf-group;
            }
        }

        // Rel-def target from tenConn
        // Inherited From l3:Ctx
        container rttenConn-items {

            // Added containment as a singleton: Prefix=rttenConn
            // Acquired From Package actrl
            uses actrl_RtTenConn_target-group;
        }

        // Rel-def from ctxToEpP
        container rsctxToEpP-items {

            // Abstract containment of rsctxToEpP derived from l3:Ctx
            list RsCtxToEpP-list {
                key "tDn";

                // Added containment: Prefix=rsctxToEpP
                // Acquired From Package l3
                uses l3_RsCtxToEpP_source-group;
            }
        }
    }

    grouping actrl_PfxEntry-group {
        leaf addr {
            config "false";
            type address_Ip;
        }

        // Policy tag
        // Type is an MO-Defined-Type
        leaf pcTag {
            config "false";
            description "PC Tag";

            // Type is an MO-Defined-Type
            type actrl_PcTag;
        }

        // Prefix operational state
        // Type is an MO-Defined-Type
        leaf operSt {
            config "false";
            description "Operational State";

            // Type is an MO-Defined-Type
            type actrl_OperSt;
        }

        // Prefix operational state disabled reason
        // Type is an MO-Defined-Type
        leaf operStQual {
            config "false";
            description "Operational State Qualifier";

            // Type is an MO-Defined-Type
            type actrl_OperStQual;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping mgmt_RtdMgmtIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From l3:If
        // Type is an MO-Defined-Type
        leaf adminSt {
            description "Admin State";

            // Type is an MO-Defined-Type
            type l1_AdminSt;
        }

        // Rel-def target from pseudoIf
        // Inherited From mgmt:RtdMgmtIf
        container rtpseudoIf-items {

            // Added containment as a singleton: Prefix=rtpseudoIf
            // Acquired From Package dhcp
            uses dhcp_RtPseudoIf_target-group;
        }

        // Rel-def from rtdMgmtConf
        container rsrtdMgmtConf-items {

            // Added containment as a singleton: Prefix=rsrtdMgmtConf
            // Acquired From Package mgmt
            uses mgmt_RsRtdMgmtConf_source-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping l3_Inst-group {

        // Inherited From nw:Conn
        // Modified by Override: nw:FwDom->name
        // Modified by Override: l3:Dom->name
        // Type is an MO-Defined-Type
        leaf name {
            description "Name";

            // Type is an MO-Defined-Type
            type naming_Name {
                length "1..64";
            }
        }

        // Vrf Id. Its a Policyelemnt owned ID used for resource tracking purpose
        // Inherited From l3:Dom
        // Type is an MO-Defined-Type
        leaf resourceId {
            config "false";
            description "VRF ID";

            // Type is an MO-Defined-Type
            type l3_VrfId;
        }

        // vrf id
        // Inherited From l3:Dom
        // Type is an MO-Defined-Type
        leaf id {
            config "false";
            description "VRF ID";

            // Type is an MO-Defined-Type
            type l3_VrfId;
        }
        leaf encap {
            type string;
        }
        leaf descr {
            type string;
        }

        // Scope of the context. It identifies the classId
        // pool and all the epg/bd classIds belonging to
        // this context needs to be allocated from this pool
        // Inherited From l3:Dom
        // Type is an MO-Defined-Type
        leaf scope {
            config "false";
            description "Scope";

            // Type is an MO-Defined-Type
            type actrl_ScopeId;
        }

        // Controller Id
        // Inherited From l3:Dom
        // Type is an MO-Defined-Type
        leaf ctrlrId {
            description "Controller ID";

            // Type is an MO-Defined-Type
            type aggregate_ControllerID;
        }

        // SecurityLabel
        // Inherited From l3:Dom
        // Type is an MO-Defined-Type
        leaf secLbl {
            config "false";
            description "Security Label";

            // Type is an MO-Defined-Type
            type actrl_SecLbl;
        }

        // vrf Admin State
        // Inherited From l3:Dom
        // Type is an MO-Defined-Type
        leaf adminState {
            description "Admin State";

            // Type is an MO-Defined-Type
            type l3_VrfAdminState;
        }

        // vrf Oper State
        // Inherited From l3:Dom
        // Type is an MO-Defined-Type
        leaf operState {
            config "false";
            description "Operational State";

            // Type is an MO-Defined-Type
            type l3_VrfOperState;
        }

        // oper state reason
        // Inherited From l3:Dom
        // Type is an MO-Defined-Type
        leaf operStQual {
            config "false";
            description "Operational State Qualifier";

            // Type is an MO-Defined-Type
            type l3_VrfOperStateQual;
        }

        // old oper state reason
        // Inherited From l3:Dom
        // Type is an MO-Defined-Type
        leaf oldOperStQual {
            config "false";
            description "Old Operational State Qualifier";

            // Type is an MO-Defined-Type
            type l3_VrfOperStateQual;
        }
        leaf gsdbCtx {
            config "false";
            type uint32;
        }
        leaf pending {
            config "false";
            type boolean;
        }
        leaf v4TibValid {
            config "false";
            type boolean;
        }
        leaf v4TibId {
            config "false";
            type uint32;
        }
        leaf v4TibName {
            config "false";
            type string;
        }
        leaf v4TibPending {
            config "false";
            type boolean;
        }

        // ipv4 table Oper State
        // Inherited From l3:Dom
        // Type is an MO-Defined-Type
        leaf v4TibOperState {
            config "false";
            description "IPV4 Table Operational State";

            // Type is an MO-Defined-Type
            type l3_VrfOperState;
        }

        // ipv4 table oper state reason
        // Inherited From l3:Dom
        // Type is an MO-Defined-Type
        leaf v4TibOperStQual {
            config "false";
            description "IPV4 Table Operational State Qualifier";

            // Type is an MO-Defined-Type
            type l3_VrfOperStateQual;
        }

        // ipv4 table old oper state reason
        // Inherited From l3:Dom
        // Type is an MO-Defined-Type
        leaf v4TibOldOperStQual {
            config "false";
            description "IPV4 Old Operational State Qualifier";

            // Type is an MO-Defined-Type
            type l3_VrfOperStateQual;
        }
        leaf v6TibValid {
            config "false";
            type boolean;
        }
        leaf v6TibId {
            config "false";
            type uint32;
        }
        leaf v6TibName {
            config "false";
            type string;
        }
        leaf v6TibPending {
            config "false";
            type boolean;
        }

        // ipv6 table Oper State
        // Inherited From l3:Dom
        // Type is an MO-Defined-Type
        leaf v6TibOperState {
            config "false";
            description "IPV6 Table Operational State";

            // Type is an MO-Defined-Type
            type l3_VrfOperState;
        }

        // ipv6 table oper state reason
        // Inherited From l3:Dom
        // Type is an MO-Defined-Type
        leaf v6TibOperStQual {
            config "false";
            description "IPV6 Table Operational State Qualifer";

            // Type is an MO-Defined-Type
            type l3_VrfOperStateQual;
        }

        // ipv6 table old oper state reason
        // Inherited From l3:Dom
        // Type is an MO-Defined-Type
        leaf v6TibOldOperStQual {
            config "false";
            description "IPV6 Table Operational State Qualifer";

            // Type is an MO-Defined-Type
            type l3_VrfOperStateQual;
        }
        leaf createTs {
            config "false";
            type uint64;
        }
        leaf lastChgdTs {
            config "false";
            type uint64;
        }

        // bgp route distinguisher
        // Inherited From l3:Dom
        // Type is an MO-Defined-Type
        leaf bgpRd {
            config "false";
            description "BGP Route Distinguisher";

            // Type is an MO-Defined-Type
            type l3_BgpRdBytes;
        }
        leaf bgpRdDisp {
            config "false";
            type string;
        }
        leaf prtclBmp {
            config "false";
            type uint32;
        }
        leaf oui {
            config "false";
            type uint32;
        }
        leaf vpnId {
            config "false";
            type uint32;
        }

        // Ftag tree, fabric multicast tree to direct the tenant flood
        // and multicast traffic over the fabric
        container tree-items {
            list Tree-list {
                config "false";
                key "id";

                // Added containment: Prefix=tree
                // Acquired From Package fmcast
                uses fmcast_Tree-group;
            }
        }

        // Layer3 Domain (aka vrf) container for routing protocols
        container dom-items {
            list Dom-list {
                key "name";

                // Added containment: Prefix=dom
                // Acquired From Package rtctrl
                uses rtctrl_Dom-group;
            }
        }

        // Abstraction of epm database
        container db-items {
            list Db-list {
                config "false";
                key "type";

                // Added containment: Prefix=db
                // Acquired From Package epm
                uses epm_Db-group;
            }
        }

        // Shard chaining policy
        container shchp-items {
            list ShardChP-list {
                config "false";
                key "af";

                // Added containment: Prefix=shchp
                // Acquired From Package topoctrl
                uses topoctrl_ShardChP-group;
            }
        }

        // Routed management interface
        container mgmt-items {
            list RtdMgmtIf-list {
                key "id";

                // Added containment: Prefix=mgmt
                // Acquired From Package mgmt
                uses mgmt_RtdMgmtIf-group;
            }
        }

        // Rel-def from vrfMbr
        container rsvrfMbr-items {

            // Abstract containment of rsvrfMbr derived from l3:Inst
            list RsVrfMbr-list {
                key "tDn";

                // Added containment: Prefix=rsvrfMbr
                // Acquired From Package l3
                uses l3_RsVrfMbr_source-group;
            }
        }
    }

    grouping fmcast_Tree-group {

        // Id
        // Type is an MO-Defined-Type
        leaf id {
            config "false";
            description "Tree Id";

            // Type is an MO-Defined-Type
            type fmcast_Id;
        }

        // Multicast root for this tree, identified by the node
        // ip address
        // Type is an MO-Defined-Type
        leaf root {
            config "false";
            description "Root";

            // Type is an MO-Defined-Type
            type mcast_Root;
        }

        // Administrative state
        // Type is an MO-Defined-Type
        leaf adminSt {
            config "false";
            description "Adminitrative State";

            // Type is an MO-Defined-Type
            type nw_AdminSt;
        }

        // Inherited From nw:Conn
        // Modified by Override: nw:Tree->name
        // Type is an MO-Defined-Type
        leaf name {
            description "Name";

            // Type is an MO-Defined-Type
            type naming_Name {
                length "1..64";
            }
        }
    }

    grouping rtctrl_Dom-group {
        leaf rd {
            type mtx_array_community;
        }
        leaf operRd {
            config "false";
            type mtx_array_community;
        }

        // Inherited From nw:Conn
        // Modified by Override: rtctrl:Dom->name
        // Modified by Override: nw:CpDom->name
        // Type is an MO-Defined-Type
        leaf name {
            description "Name";

            // Type is an MO-Defined-Type
            type naming_Name {
                length "1..64";
            }
        }

        // This object holds per address family bgp vrf information
        container af-items {
            list DomAf-list {
                key "type";

                // Added containment: Prefix=af
                // Acquired From Package rtctrl
                uses rtctrl_DomAf-group;
            }
        }
    }

    grouping rtctrl_DomAf-group {

        // Inherited From nw:Conn
        // Modified by Override: nw:CpDom->name
        // Type is an MO-Defined-Type
        leaf name {
            description "Name";

            // Type is an MO-Defined-Type
            type naming_Name {
                length "1..64";
            }
        }

        // Type
        // Inherited From rtctrl:Af
        // Type is an MO-Defined-Type
        leaf type {
            description "Type";

            // Type is an MO-Defined-Type
            type bgp_AfT;
        }

        // This object holds policy to control vpn af
        // information for a given vrf
        container ctrl-items {
            list AfCtrl-list {
                key "type";

                // Added containment: Prefix=ctrl
                // Acquired From Package rtctrl
                uses rtctrl_AfCtrl-group;
            }
        }
    }

    grouping rtctrl_AfCtrl-group {

        // Inherited From nw:Conn
        // Modified by Override: nw:CpDom->name
        // Type is an MO-Defined-Type
        leaf name {
            description "Name";

            // Type is an MO-Defined-Type
            type naming_Name {
                length "1..64";
            }
        }

        // Type
        // Inherited From rtctrl:Af
        // Type is an MO-Defined-Type
        leaf type {
            description "Type";

            // Type is an MO-Defined-Type
            type bgp_AfT;
        }

        // Route policy holds all route policy entries and route controls
        container rttp-items {
            list RttP-list {
                key "type";

                // Added containment: Prefix=rttp
                // Acquired From Package rtctrl
                uses rtctrl_RttP-group;
            }
        }
    }

    grouping topoctrl_ShardChP-group {

        // Address family for chaining
        // Type is an MO-Defined-Type
        leaf af {
            config "false";
            description "Address Family";

            // Type is an MO-Defined-Type
            type nw_AddrF;
        }

        // Redundancy node, determines the node to go to in case of
        // a local node failure
        // Type is an MO-Defined-Type
        leaf node {
            config "false";
            description "Node";

            // Type is an MO-Defined-Type
            type topoctrl_ShardChNode;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping l3cap_Prov-group {

        // Subject consuming the capability
        // Type is an MO-Defined-Type
        leaf subj {
            config "false";
            description "Subject";

            // Type is an MO-Defined-Type
            type l3cap_Subj;
        }

        // Every Consumer has a Subject.
        // Subject represents the entity which consumes the capability.
        // Namespaces which have concrete consumers, define the Subject property
        // and its types
        // Max capability available
        // Inherited From cap:Prov
        // Type is an MO-Defined-Type
        leaf total {
            config "false";
            description "TBD";

            // Type is an MO-Defined-Type
            type cap_Counter;
        }

        // Remaining capability available
        // Inherited From cap:Prov
        // Type is an MO-Defined-Type
        leaf remaining {
            config "false";
            description "TBD";

            // Type is an MO-Defined-Type
            type cap_Counter;
        }

        // utilization indicator in percentages of consiumption
        // Inherited From cap:Prov
        // Type is an MO-Defined-Type
        leaf utilization {
            config "false";
            description "TBD";

            // Type is an MO-Defined-Type
            type cap_StorageHint;
        }

        // Type of the Rule consumed by this consumer.
        // Inherited From cap:Prov
        // Type is an MO-Defined-Type
        leaf type {
            config "false";
            description "TBD";

            // Type is an MO-Defined-Type
            type cap_RuleT;
        }
    }

    grouping l3vm_Entity-group {
        leaf vrfmemberchangeretainl3cfg {
            type boolean;
            default "true";
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per l3vm instance information. There is only
        // one instance of l3vm running in the system today
        container inst-items {

            // Added containment as a singleton: Prefix=inst
            // Acquired From Package l3vm
            uses l3vm_Inst-group;
        }
    }

    grouping l3vm_Inst-group {
        leaf vrfAllocId {
            config "false";
            type uint32;
        }
        leaf tblAllocId {
            config "false";
            type uint32;
        }
        leaf featureSet {
            config "false";
            type uint32;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // DomainMbrIf class
        container dommbr-items {
            list DomMbrIf-list {
                config "false";
                key "id";

                // Added containment: Prefix=dommbr
                // Acquired From Package l3
                uses l3_DomMbrIf-group;
            }
        }

        // This objects hold runtime information on l3vm tables
        container tbl-items {
            list Tbl-list {
                config "false";
                key "id";

                // Added containment: Prefix=tbl
                // Acquired From Package l3vm
                uses l3vm_Tbl-group;
            }
        }
    }

    grouping l3_DomMbrIf-group {

        // ifindex
        // Type is an MO-Defined-Type
        leaf id {
            config "false";
            description "Interface ID";

            // Type is an MO-Defined-Type
            type nw_IfId;
        }
        leaf iod {
            config "false";
            type uint32;
        }

        // vrfId
        // Type is an MO-Defined-Type
        leaf vrfId {
            config "false";
            description "VRF ID";

            // Type is an MO-Defined-Type
            type l3_VrfId;
        }

        // old vrfId
        // Type is an MO-Defined-Type
        leaf oldVrfId {
            config "false";
            description "Old VRF ID";

            // Type is an MO-Defined-Type
            type l3_VrfId;
        }

        // vrf name
        // Type is an MO-Defined-Type
        leaf vrfName {
            config "false";
            description "VRF Name";

            // Type is an MO-Defined-Type
            type l3_VrfName;
        }

        // old vrf name
        // Type is an MO-Defined-Type
        leaf oldVrfName {
            config "false";
            description "Old VRF Name";

            // Type is an MO-Defined-Type
            type l3_VrfName;
        }
        leaf gsdbCtx {
            config "false";
            type uint32;
        }

        // gsdb context type
        // Type is an MO-Defined-Type
        leaf gsdbCtxType {
            config "false";
            description "GSDB Context Type";

            // Type is an MO-Defined-Type
            type l3_VrfGsdbCtxType;
        }
        leaf bgpExtCommVal {
            config "false";
            type uint8;
        }

        // From Interface naming:Named
        // Inherited From naming:NamedObject
        // Type is an MO-Defined-Type
        leaf name {
            description "Name";

            // Type is an MO-Defined-Type
            type naming_Name;
        }
    }

    grouping l3vm_Tbl-group {
        leaf id {
            config "false";
            type uint32;
        }
        leaf gsdbCtx {
            config "false";
            type uint32;
        }
        leaf rtLmtMax {
            config "false";
            type uint32;
        }
        leaf rtLmtWarn {
            config "false";
            type uint32;
        }
        leaf rtLmtWarnOnly {
            config "false";
            type boolean;
        }
        leaf rtLmtWarnPct {
            config "false";
            type uint8;
        }
        leaf rtLmtReinstPct {
            config "false";
            type uint8;
        }
    }

    grouping urib_Entity4-group {
        leaf uribDmeVersion {
            config "false";
            type uint32;
        }

        // Specific to v4
        container client4-items {
            list Client4-list {
                config "false";
                key "name";

                // Added containment: Prefix=client4
                // Acquired From Package urib
                uses urib_Client4-group;
            }
        }

        // Specific to v4
        container internal4-items {

            // Added containment as a singleton: Prefix=internal4
            // Acquired From Package urib
            uses urib_Internal4-group;
        }
        container internalvrf4-items {
            list InternalVrf4-list {
                config "false";
                key "vrfName";

                // Added containment: Prefix=internalvrf4
                // Acquired From Package urib
                uses urib_InternalVrf4-group;
            }
        }

        // Specific to v4
        container table4-items {
            list Table4-list {
                config "false";
                key "vrfName";

                // Added containment: Prefix=table4
                // Acquired From Package urib
                uses urib_Table4-group;
            }
        }
    }

    grouping urib_Client4-group {
        leaf name {
            config "false";
            type string;
        }
        leaf index {
            config "false";
            type uint64;
        }
        leaf epid {
            config "false";
            type uint32;
        }
        leaf mtsSap {
            config "false";
            type int32;
        }

        // Inherited From urib:ClientBase
        // Type is an MO-Defined-Type
        leaf mruMisses {
            config "false";
            description "MRU cache misses. Internal performance indicator.";

            // Type is an MO-Defined-Type
            type urib_Counter32;
        }

        // Inherited From urib:ClientBase
        // Type is an MO-Defined-Type
        leaf mruHits {
            config "false";
            description "MRU cache hits. Internal performance indicator.";

            // Type is an MO-Defined-Type
            type urib_Counter32;
        }
        leaf staleTime {
            config "false";
            type uint32;
        }

        // Inherited From urib:ClientBase
        // Type is an MO-Defined-Type
        leaf staleTimerRemaining {
            config "false";
            description "Time left before the timer expire";

            // Type is an MO-Defined-Type
            type urib_TimeStr;
        }

        // Some of these messages are received and some are sent by
        // the URIB server. They are prefixed by a r or s respectively
        container message4-items {

            // Added containment as a singleton: Prefix=message4
            // Acquired From Package urib
            uses urib_MsgIO4-group;
        }
        container clientvrf4-items {
            list ClientVrf4-list {
                config "false";
                key "vrfName";

                // Added containment: Prefix=clientvrf4
                // Acquired From Package urib
                uses urib_ClientVrf4-group;
            }
        }
    }

    grouping urib_MsgIO4-group {

        // Type is an MO-Defined-Type
        leaf rRegister {
            config "false";
            description "Client register with URIB";

            // Type is an MO-Defined-Type
            type urib_Counter32;
        }

        // Type is an MO-Defined-Type
        leaf sRegisterAck {
            config "false";
            description "URIB sends ACK following a register";

            // Type is an MO-Defined-Type
            type urib_Counter32;
        }

        // Type is an MO-Defined-Type
        leaf rDeregister {
            config "false";
            description "Client sends deregister to URIB";

            // Type is an MO-Defined-Type
            type urib_Counter32;
        }

        // Type is an MO-Defined-Type
        leaf rAddRoute {
            config "false";
            description "Client sends add route to URIB";

            // Type is an MO-Defined-Type
            type urib_Counter32;
        }

        // Type is an MO-Defined-Type
        leaf sAddRouteAck {
            config "false";
            description "URIB sends add route ACK to client";

            // Type is an MO-Defined-Type
            type urib_Counter32;
        }

        // Type is an MO-Defined-Type
        leaf rDeleteRoute {
            config "false";
            description "Client sends delete route to URIB";

            // Type is an MO-Defined-Type
            type urib_Counter32;
        }

        // Type is an MO-Defined-Type
        leaf sDeleteRouteAck {
            config "false";
            description "URIB sends delete route ACK to client";

            // Type is an MO-Defined-Type
            type urib_Counter32;
        }

        // After a change, URIB sends this to notify a client
        // Type is an MO-Defined-Type
        leaf sNotifyRoute {
            config "false";
            description "URIB sends nodify route to client";

            // Type is an MO-Defined-Type
            type urib_Counter32;
        }

        // Type is an MO-Defined-Type
        leaf rNotifyRouteAck {
            config "false";
            description "Client sends nodify route ACK to URIB";

            // Type is an MO-Defined-Type
            type urib_Counter32;
        }

        // Type is an MO-Defined-Type
        leaf rAddOneRoute {
            config "false";
            description "Client sends add one route to URIB";

            // Type is an MO-Defined-Type
            type urib_Counter32;
        }

        // Type is an MO-Defined-Type
        leaf rDeleteOneRoute {
            config "false";
            description "Client sends delete one route to URIB";

            // Type is an MO-Defined-Type
            type urib_Counter32;
        }

        // Type is an MO-Defined-Type
        leaf rDeleteAllRoute {
            config "false";
            description "Client sends delete all routes to URIB";

            // Type is an MO-Defined-Type
            type urib_Counter32;
        }

        // Type is an MO-Defined-Type
        leaf rAddRnh {
            config "false";
            description "Client sends add RNH to URIB";

            // Type is an MO-Defined-Type
            type urib_Counter32;
        }

        // Type is an MO-Defined-Type
        leaf sAddRnhAck {
            config "false";
            description "URIB sends add RNH ack to client";

            // Type is an MO-Defined-Type
            type urib_Counter32;
        }

        // Type is an MO-Defined-Type
        leaf rDeleteRnh {
            config "false";
            description "Client sends delete RNH to URIB";

            // Type is an MO-Defined-Type
            type urib_Counter32;
        }

        // Type is an MO-Defined-Type
        leaf sDeleteRnhAck {
            config "false";
            description "URIB sends delete RNH ack to client";

            // Type is an MO-Defined-Type
            type urib_Counter32;
        }

        // Type is an MO-Defined-Type
        leaf rDeleteAllRnh {
            config "false";
            description "Client sends delete all RNHs to URIB";

            // Type is an MO-Defined-Type
            type urib_Counter32;
        }

        // Type is an MO-Defined-Type
        leaf sNotifyRnh {
            config "false";
            description "URIB sends notify RNH to client";

            // Type is an MO-Defined-Type
            type urib_Counter32;
        }

        // Type is an MO-Defined-Type
        leaf rNotifyRnhAck {
            config "false";
            description "Client sends notify RNH Ack to URIB";

            // Type is an MO-Defined-Type
            type urib_Counter32;
        }

        // When a client wants to receive route notifications from
        // another client
        // Type is an MO-Defined-Type
        leaf rNotifyRequest {
            config "false";
            description "Client sends notify request to URIB";

            // Type is an MO-Defined-Type
            type urib_Counter32;
        }

        // When a client wants to stop receiving route notifications
        // from another client
        // Type is an MO-Defined-Type
        leaf rDenotifyRequest {
            config "false";
            description "Client sends denotify request to URIB";

            // Type is an MO-Defined-Type
            type urib_Counter32;
        }

        // Type is an MO-Defined-Type
        leaf sRedistNotify {
            config "false";
            description "URIB sends redistribution notify to client";

            // Type is an MO-Defined-Type
            type urib_Counter32;
        }

        // When a client deregister, we notify every client that is
        // redistributing the client being un-registered
        // Type is an MO-Defined-Type
        leaf sRedistDenotify {
            config "false";
            description "URIB sends redistribution denotify to client";

            // Type is an MO-Defined-Type
            type urib_Counter32;
        }

        // When a client asks to be notified when another client
        // declare his convergence
        // Type is an MO-Defined-Type
        leaf rNotifyPibConvRequest {
            config "false";
            description "Client sends PIB convergence request to client";

            // Type is an MO-Defined-Type
            type urib_Counter32;
        }

        // Type is an MO-Defined-Type
        leaf rNotifyPibConv {
            config "false";
            description "Used when a client declare convergence to URIB";

            // Type is an MO-Defined-Type
            type urib_Counter32;
        }

        // Type is an MO-Defined-Type
        leaf sNotifyPibConv {
            config "false";
            description "Used when URIB notify other client of a convergence";

            // Type is an MO-Defined-Type
            type urib_Counter32;
        }

        // A client can either send one notifyPibConv per table or
        // sned a single notifyPibConvAll when every tables are
        // converged
        // Type is an MO-Defined-Type
        leaf rNotifyPibConvAll {
            config "false";
            description "Client sends notify Pib convergence all to URIB";

            // Type is an MO-Defined-Type
            type urib_Counter32;
        }

        // Type is an MO-Defined-Type
        leaf rModifyRoute {
            config "false";
            description "Client sends modify route to URIB";

            // Type is an MO-Defined-Type
            type urib_Counter32;
        }

        // Type is an MO-Defined-Type
        leaf sModifyRouteAck {
            config "false";
            description "URIB sends modify route ACK to client";

            // Type is an MO-Defined-Type
            type urib_Counter32;
        }

        // When URIB needs all the client to re-add all their routes
        // in URIB
        // Type is an MO-Defined-Type
        leaf sRepopulateRoute {
            config "false";
            description "URIB sends repopulate route to client";

            // Type is an MO-Defined-Type
            type urib_Counter32;
        }

        // Used to override the default value
        // Type is an MO-Defined-Type
        leaf rPibSetStaleTime {
            config "false";
            description "Client sends PIB set stale time to URIB";

            // Type is an MO-Defined-Type
            type urib_Counter32;
        }

        // Type is an MO-Defined-Type
        leaf rSetAgedRouteInterval {
            config "false";
            description "Client sends set aged route interval to URIB";

            // Type is an MO-Defined-Type
            type urib_Counter32;
        }

        // Used on switchover only. client should redownload all
        // their route
        // Type is an MO-Defined-Type
        leaf sReinitRepopulateRoute {
            config "false";
            description "URIB sends reinit and repopulate to client";

            // Type is an MO-Defined-Type
            type urib_Counter32;
        }
    }

    grouping urib_ClientVrf4-group {

        // Most of these flags are static and sent on registration
        // Type is an MO-Defined-Type
        leaf flags {
            config "false";
            description "Flags sent by the client";

            // Type is an MO-Defined-Type
            type urib_RoutingVrfFlags4;
        }

        // The bits in this mask refer to the client index.
        // Each client has a bit assigned. See the index
        // property in ClientBase.
        // Type is an MO-Defined-Type
        leaf convergenceSubscribedMask {
            config "false";
            description "Clients whose convergence this client is interested in.";

            // Type is an MO-Defined-Type
            type urib_BitMask64;
        }
        leaf vrfName {
            config "false";
            type string;
        }

        // Inherited From urib:ClientVrfBase
        // Type is an MO-Defined-Type
        leaf routeCount {
            config "false";
            description "Number of routes in this VRF for a specific client";

            // Type is an MO-Defined-Type
            type urib_Counter32;
        }

        // Inherited From urib:ClientVrfBase
        // Type is an MO-Defined-Type
        leaf recursiveNextHopCount {
            config "false";
            description "Number of recursive Next-Hops";

            // Type is an MO-Defined-Type
            type urib_Counter32;
        }

        // Inherited From urib:ClientVrfBase
        // Type is an MO-Defined-Type
        leaf bestPathCount {
            config "false";
            description "Number of best path from this client in this table";

            // Type is an MO-Defined-Type
            type urib_Counter32;
        }

        // A backup path is a path that is not the best. So not installed in FIB
        // Inherited From urib:ClientVrfBase
        // Type is an MO-Defined-Type
        leaf backupPathCount {
            config "false";
            description "Number of backup path from this client in this table";

            // Type is an MO-Defined-Type
            type urib_Counter32;
        }

        // The bits in this mask refer to the client index.
        // Each client has a bit assigned. See the index property in
        // ClientBase. The term 'notifiers' is used in the CLI,
        // Inherited From urib:ClientVrfBase
        // Type is an MO-Defined-Type
        leaf routeChangeSubscribed {
            config "false";
            description "Get a notification whenever a route from these clients change.";

            // Type is an MO-Defined-Type
            type urib_BitMask64;
        }

        // The bits in this mask refer to the client index.
        // Each client has a bit assigned. See the index
        // property in ClientBase
        // Inherited From urib:ClientVrfBase
        // Type is an MO-Defined-Type
        leaf convergenceNotifyMask {
            config "false";
            description "Notify the clients in this mask whenever convergence is set by this client.";

            // Type is an MO-Defined-Type
            type urib_BitMask64;
        }

        // Inherited From urib:ClientVrfBase
        // Type is an MO-Defined-Type
        leaf labelCount {
            config "false";
            description "Number of labels. Internal use.";

            // Type is an MO-Defined-Type
            type urib_Counter32;
        }
    }

    grouping urib_Internal4-group {
        leaf cleanRestart {
            config "false";
            type boolean;
        }

        // Type is an MO-Defined-Type
        leaf servRpm {
            config "false";
            description "Server rpm up or down";

            // Type is an MO-Defined-Type
            type urib_UpDown;
        }

        // Type is an MO-Defined-Type
        leaf servLisp {
            config "false";
            description "Server lisp up or down";

            // Type is an MO-Defined-Type
            type urib_UpDown;
        }
        leaf regRpm {
            config "false";
            type boolean;
        }
        leaf regLisp {
            config "false";
            type boolean;
        }
        leaf mplsVpnMibTrapThresh {
            config "false";
            type uint32;
        }
        leaf ufdmRteMsgVersion {
            config "false";
            type uint32;
        }
        leaf supState {
            config "false";
            type string;
        }
        leaf pssUri {
            config "false";
            type string;
        }

        // Inherited From urib:InternalBase
        // Type is an MO-Defined-Type
        leaf servClisState {
            config "false";
            description "Server for Cli commands up or down";

            // Type is an MO-Defined-Type
            type urib_UpDown;
        }

        // Inherited From urib:InternalBase
        // Type is an MO-Defined-Type
        leaf servL3vmState {
            config "false";
            description "Server l3vm up or down";

            // Type is an MO-Defined-Type
            type urib_UpDown;
        }

        // Inherited From urib:InternalBase
        // Type is an MO-Defined-Type
        leaf servUfdmState {
            config "false";
            description "Server ufdm up or down";

            // Type is an MO-Defined-Type
            type urib_UpDown;
        }
        leaf regClis {
            config "false";
            type boolean;
        }
        leaf regL3vm {
            config "false";
            type boolean;
        }
        leaf regUfdm {
            config "false";
            type boolean;
        }
        leaf shmMin {
            config "false";
            type uint32;
        }
        leaf shmSize {
            config "false";
            type uint32;
        }
        leaf dbgFilterVrfName {
            config "false";
            type string;
        }
        leaf dbgFilterVrfTableId {
            config "false";
            type uint32;
        }
        leaf dbgFilterClientName {
            config "false";
            type string;
        }
        leaf dbgFilterClientIdx {
            config "false";
            type uint32;
        }
        leaf dbgFilterPrefixList {
            config "false";
            type string;
        }
        leaf performanceMode {
            config "false";
            type boolean;
        }
    }

    grouping urib_InternalVrf4-group {
        leaf vrfConverged {
            config "false";
            type boolean;
        }
        leaf repopulateTimerRemaining {
            config "false";
            type string;
        }
        leaf rnhVrfMismatchCount {
            config "false";
            type uint64;
        }
        leaf ufdmRteMsgVersion {
            config "false";
            type uint8;
        }
        leaf vrfName {
            config "false";
            type string;
        }
        leaf tableId {
            config "false";
            type uint32;
        }

        // Inherited From urib:InternalVrfBase
        // Type is an MO-Defined-Type
        leaf state {
            config "false";
            description "State";

            // Type is an MO-Defined-Type
            type urib_TableState;
        }
        leaf l3vmState {
            config "false";
            type string;
        }
        leaf ufdmEnabled {
            config "false";
            type boolean;
        }

        // Inherited From urib:InternalVrfBase
        // Type is an MO-Defined-Type
        leaf emptyTimerRemaining {
            config "false";
            description "Time left on the empty timer. 0 if not running";

            // Type is an MO-Defined-Type
            type urib_TimeStr;
        }
        leaf haClientCount {
            config "false";
            type uint32;
        }
        leaf haClientConvCount {
            config "false";
            type uint32;
        }
        leaf haClientConvList {
            config "false";
            type string;
        }
        leaf haClientUnconvList {
            config "false";
            type string;
        }
        leaf routeLimitMax {
            config "false";
            type uint32;
        }
        leaf routeLimitWarnPct {
            config "false";
            type uint32;
        }
        leaf routeLimitWarn {
            config "false";
            type uint32;
        }
        leaf routeLimitReinstPct {
            config "false";
            type uint32;
        }
        leaf routeLimitReinst {
            config "false";
            type uint32;
        }
        leaf routeLimitReinstPending {
            config "false";
            type boolean;
        }

        // Inherited From urib:InternalVrfBase
        // Type is an MO-Defined-Type
        leaf lastMibTrap {
            config "false";
            description "When was the last mib trap.";

            // Type is an MO-Defined-Type
            type urib_TimeStr;
        }
        leaf maxTrapReset {
            config "false";
            type boolean;
        }
        leaf warnTrapReset {
            config "false";
            type boolean;
        }

        // Inherited From urib:InternalVrfBase
        // Type is an MO-Defined-Type
        leaf addedCount {
            config "false";
            description "Total number of routes added. Not decremented when a route is deleted";

            // Type is an MO-Defined-Type
            type urib_Counter64;
        }

        // Inherited From urib:InternalVrfBase
        // Type is an MO-Defined-Type
        leaf deletedCount {
            config "false";
            description "Total number of routes deleted";

            // Type is an MO-Defined-Type
            type urib_Counter64;
        }
        leaf droppedCount {
            config "false";
            type uint64;
        }
    }

    grouping urib_Table4-group {
        leaf vrfName {
            config "false";
            type string;
        }

        // Inherited From urib:TableBase
        // Type is an MO-Defined-Type
        leaf routeCount {
            config "false";
            description "Total number of route in this table";

            // Type is an MO-Defined-Type
            type urib_Counter32;
        }

        // Inherited From urib:TableBase
        // Type is an MO-Defined-Type
        leaf uniBestCount {
            config "false";
            description "Number of unicast route considered as the best";

            // Type is an MO-Defined-Type
            type urib_Counter32;
        }

        // Inherited From urib:TableBase
        // Type is an MO-Defined-Type
        leaf uniBackupCount {
            config "false";
            description "Number of unicast route not considered as the best";

            // Type is an MO-Defined-Type
            type urib_Counter32;
        }

        // Inherited From urib:TableBase
        // Type is an MO-Defined-Type
        leaf multiBestCount {
            config "false";
            description "Number of multicast route considered as the best";

            // Type is an MO-Defined-Type
            type urib_Counter32;
        }

        // Inherited From urib:TableBase
        // Type is an MO-Defined-Type
        leaf multiBackupCount {
            config "false";
            description "Number of multicast route not considered as the best";

            // Type is an MO-Defined-Type
            type urib_Counter32;
        }
        leaf routePerMaskCount {
            config "false";
            type string;
        }

        // Specific to v4
        container hiddennh4-items {
            list HiddenNextHop4-list {
                config "false";
                key "id";

                // Added containment: Prefix=hiddennh4
                // Acquired From Package urib
                uses urib_HiddenNextHop4-group;
            }
        }

        // Specific to v4
        container route4-items {
            list Route4-list {
                config "false";
                key "prefix";

                // Added containment: Prefix=route4
                // Acquired From Package urib
                uses urib_Route4-group;
            }
        }
    }

    grouping urib_HiddenNextHop4-group {
        leaf id {
            config "false";
            type uint32;
        }
        leaf routeAddress {
            config "false";
            type string;
        }
        leaf routeMask {
            config "false";
            type uint8;
        }
        leaf clientName {
            config "false";
            type string;
        }
        leaf recursiveNhAddress {
            config "false";
            type string;
        }
        leaf recursiveNhMask {
            config "false";
            type uint8;
        }
    }

    grouping urib_Route4-group {
        leaf prefix {
            config "false";
            type string;
        }
        leaf uBestNextHopCount {
            config "false";
            type uint32;
        }
        leaf mBestNextHopCount {
            config "false";
            type uint32;
        }

        // Specific to v4
        container nh4-items {
            list NextHop4-list {
                config "false";
                key "id";

                // Added containment: Prefix=nh4
                // Acquired From Package urib
                uses urib_NextHop4-group;
            }
        }

        // Specific to v4
        container routedetail4-items {

            // Added containment as a singleton: Prefix=routedetail4
            // Acquired From Package urib
            uses urib_RouteDetail4-group;
        }
    }

    grouping urib_NextHop4-group {
        leaf id {
            config "false";
            type uint32;
        }
        leaf prefix {
            config "false";
            type string;
        }
        leaf mask {
            config "false";
            type uint32;
        }
        leaf tableId {
            config "false";
            type uint32;
        }
        leaf interfaceName {
            config "false";
            type string;
        }
        leaf owner {
            config "false";
            type string;
        }
        leaf preference {
            config "false";
            type uint32;
        }
        leaf metric {
            config "false";
            type uint32;
        }

        // Inherited From urib:NextHopBase
        // Type is an MO-Defined-Type
        leaf uptime {
            config "false";
            description "Time since this next hop has been added/modified";

            // Type is an MO-Defined-Type
            type urib_TimeStr;
        }

        // Specific to v4
        container nhdetail4-items {

            // Added containment as a singleton: Prefix=nhdetail4
            // Acquired From Package urib
            uses urib_NextHopDetail4-group;
        }
    }

    grouping urib_NextHopDetail4-group {

        // Type is an MO-Defined-Type
        leaf flags {
            config "false";
            description "Flags";

            // Type is an MO-Defined-Type
            type urib_NhFlags4;
        }

        // Type is an MO-Defined-Type
        leaf nhlfeFlags {
            config "false";
            description "Next-hop Label Forwarding flags";

            // Type is an MO-Defined-Type
            type urib_NhlfeFlags4;
        }

        // Type is an MO-Defined-Type
        leaf tlvType {
            config "false";
            description "Type-Length-Value type";

            // Type is an MO-Defined-Type
            type urib_TlvType4;
        }
        leaf routeType {
            config "false";
            type string;
        }
        leaf tag {
            config "false";
            type uint32;
        }
        leaf segmentId {
            config "false";
            type uint32;
        }
        leaf tunnelId {
            config "false";
            type uint32;
        }

        // Support for VXLAN encap type only with EVPN
        // Inherited From urib:NextHopDetailBase
        // Type is an MO-Defined-Type
        leaf encapType {
            config "false";
            description "Either VXLAN or none";

            // Type is an MO-Defined-Type
            type urib_NextHopEncapType;
        }
        leaf labelStack {
            config "false";
            type string;
        }
        leaf nhlfeOwner {
            config "false";
            type string;
        }

        // Internal use.
        // Urib doesn't know how to interpret client data
        // Inherited From urib:NextHopDetailBase
        // Type is an MO-Defined-Type
        leaf clientData {
            config "false";
            description "Yes if client put data in the next-hop";

            // Type is an MO-Defined-Type
            type urib_YesNo;
        }
        leaf recursiveNextHopPrefix {
            config "false";
            type string;
        }
        leaf xriBgpOrigin {
            config "false";
            type string;
        }
        leaf xriBgpPeer {
            config "false";
            type string;
        }
        leaf tlv {
            config "false";
            type string;
        }
        leaf tlvExtentedCommunity {
            config "false";
            type string;
        }
        leaf tlvAttachExport {
            config "false";
            type string;
        }
    }

    grouping urib_RouteDetail4-group {
        leaf wildcard {
            config "false";
            type boolean;
        }

        // Type is an MO-Defined-Type
        leaf flags {
            config "false";
            description "Route flags";

            // Type is an MO-Defined-Type
            type urib_RouteFlags4;
        }
        leaf attached {
            config "false";
            type boolean;
        }
    }

    grouping urib_Entity6-group {
        leaf uribDmeVersion {
            config "false";
            type uint32;
        }

        // Specific to v6
        container client6-items {
            list Client6-list {
                config "false";
                key "name";

                // Added containment: Prefix=client6
                // Acquired From Package urib
                uses urib_Client6-group;
            }
        }

        // Specific to v6
        container internal6-items {

            // Added containment as a singleton: Prefix=internal6
            // Acquired From Package urib
            uses urib_Internal6-group;
        }
        container internalvrf6-items {
            list InternalVrf6-list {
                config "false";
                key "vrfName";

                // Added containment: Prefix=internalvrf6
                // Acquired From Package urib
                uses urib_InternalVrf6-group;
            }
        }

        // Specific to v6
        container table6-items {
            list Table6-list {
                config "false";
                key "vrfName";

                // Added containment: Prefix=table6
                // Acquired From Package urib
                uses urib_Table6-group;
            }
        }
    }

    grouping urib_Client6-group {

        // Type is an MO-Defined-Type
        leaf updateAckQueueCount {
            config "false";
            description "Number of elements in the update acknowledge queue";

            // Type is an MO-Defined-Type
            type urib_Counter32;
        }

        // Type is an MO-Defined-Type
        leaf readyClientQueueCount {
            config "false";
            description "Number of elements in the ready client queue";

            // Type is an MO-Defined-Type
            type urib_Counter32;
        }

        // Type is an MO-Defined-Type
        leaf bufReqClientQueueCount {
            config "false";
            description "Number of elements in the buffer request client queue";

            // Type is an MO-Defined-Type
            type urib_Counter32;
        }

        // Type is an MO-Defined-Type
        leaf rteBufUsedQueueCount {
            config "false";
            description "Number of elements in the buffer used queue";

            // Type is an MO-Defined-Type
            type urib_Counter32;
        }

        // Type is an MO-Defined-Type
        leaf rnhBufUsedQueueCount {
            config "false";
            description "Number of elements in the rnh buffer used queue";

            // Type is an MO-Defined-Type
            type urib_Counter32;
        }

        // Type is an MO-Defined-Type
        leaf state {
            config "false";
            description "Client state";

            // Type is an MO-Defined-Type
            type urib_Client6State;
        }
        leaf badTableCount {
            config "false";
            type uint32;
        }
        leaf name {
            config "false";
            type string;
        }
        leaf index {
            config "false";
            type uint64;
        }
        leaf epid {
            config "false";
            type uint32;
        }
        leaf mtsSap {
            config "false";
            type int32;
        }

        // Inherited From urib:ClientBase
        // Type is an MO-Defined-Type
        leaf mruMisses {
            config "false";
            description "MRU cache misses. Internal performance indicator.";

            // Type is an MO-Defined-Type
            type urib_Counter32;
        }

        // Inherited From urib:ClientBase
        // Type is an MO-Defined-Type
        leaf mruHits {
            config "false";
            description "MRU cache hits. Internal performance indicator.";

            // Type is an MO-Defined-Type
            type urib_Counter32;
        }
        leaf staleTime {
            config "false";
            type uint32;
        }

        // Inherited From urib:ClientBase
        // Type is an MO-Defined-Type
        leaf staleTimerRemaining {
            config "false";
            description "Time left before the timer expire";

            // Type is an MO-Defined-Type
            type urib_TimeStr;
        }

        // Some of these messages are received and some are sent by
        // the URIB server. They are prefixed by a r or s respectively
        // IPV6
        container message6-items {

            // Added containment as a singleton: Prefix=message6
            // Acquired From Package urib
            uses urib_MsgIO6-group;
        }

        // SPECIFIC TO V6
        container clientvrf6-items {
            list ClientVrf6-list {
                config "false";
                key "vrfName";

                // Added containment: Prefix=clientvrf6
                // Acquired From Package urib
                uses urib_ClientVrf6-group;
            }
        }
    }

    grouping urib_MsgIO6-group {

        // Type is an MO-Defined-Type
        leaf rRegister {
            config "false";
            description "Client register with U6RIB";

            // Type is an MO-Defined-Type
            type urib_Counter32;
        }

        // Type is an MO-Defined-Type
        leaf rDeregister {
            config "false";
            description "Client sends deregister to U6RIB";

            // Type is an MO-Defined-Type
            type urib_Counter32;
        }

        // Type is an MO-Defined-Type
        leaf rAddRoute {
            config "false";
            description "Client sends add route to U6RIB";

            // Type is an MO-Defined-Type
            type urib_Counter32;
        }

        // Type is an MO-Defined-Type
        leaf rDeleteRoute {
            config "false";
            description "Client sends delete route to U6RIB";

            // Type is an MO-Defined-Type
            type urib_Counter32;
        }

        // Type is an MO-Defined-Type
        leaf sAddRouteAck {
            config "false";
            description "U6RIB sends add route ACK to client";

            // Type is an MO-Defined-Type
            type urib_Counter32;
        }

        // Type is an MO-Defined-Type
        leaf sDeleteRouteAck {
            config "false";
            description "U6RIB sends delete route ACK to client";

            // Type is an MO-Defined-Type
            type urib_Counter32;
        }

        // Type is an MO-Defined-Type
        leaf sNotifyRoute {
            config "false";
            description "Client sends nodify route to U6RIB";

            // Type is an MO-Defined-Type
            type urib_Counter32;
        }

        // Type is an MO-Defined-Type
        leaf rNotifyRouteAck {
            config "false";
            description "U6RIB sends nodify route ACK to client";

            // Type is an MO-Defined-Type
            type urib_Counter32;
        }

        // Type is an MO-Defined-Type
        leaf rAddRnh {
            config "false";
            description "Client sends add RNH to U6RIB";

            // Type is an MO-Defined-Type
            type urib_Counter32;
        }

        // Type is an MO-Defined-Type
        leaf rDeleteRnh {
            config "false";
            description "Client sends delete RNH to U6RIB";

            // Type is an MO-Defined-Type
            type urib_Counter32;
        }

        // Type is an MO-Defined-Type
        leaf rDeleteAllRnh {
            config "false";
            description "Client sends delete all RNHs to U6RIB";

            // Type is an MO-Defined-Type
            type urib_Counter32;
        }

        // Type is an MO-Defined-Type
        leaf rDeleteAllRoute {
            config "false";
            description "Client sends delete all routes to U6RIB";

            // Type is an MO-Defined-Type
            type urib_Counter32;
        }

        // Type is an MO-Defined-Type
        leaf sAddRnhAck {
            config "false";
            description "U6RIB sends add RNH ack to client";

            // Type is an MO-Defined-Type
            type urib_Counter32;
        }

        // Type is an MO-Defined-Type
        leaf sDeleteRnhAck {
            config "false";
            description "U6RIB sends delete RNH ack to client";

            // Type is an MO-Defined-Type
            type urib_Counter32;
        }

        // Type is an MO-Defined-Type
        leaf sNotifyRnh {
            config "false";
            description "U6RIB sends notify RNH to client";

            // Type is an MO-Defined-Type
            type urib_Counter32;
        }

        // Type is an MO-Defined-Type
        leaf rNotifyRnhAck {
            config "false";
            description "Client sends notify RNH Ack to U6RIB";

            // Type is an MO-Defined-Type
            type urib_Counter32;
        }

        // When a client wants to receive notifications from
        // another client
        // Type is an MO-Defined-Type
        leaf rNotifyRequest {
            config "false";
            description "Client sends notify request to U6RIB";

            // Type is an MO-Defined-Type
            type urib_Counter32;
        }

        // When a client wants to stop receiving notifications from
        // another client
        // Type is an MO-Defined-Type
        leaf rDenotifyRequest {
            config "false";
            description "Client sends denotify request to U6RIB";

            // Type is an MO-Defined-Type
            type urib_Counter32;
        }

        // When U6RIB needs all the client to re-add all their routes
        // in U6RIB
        // Type is an MO-Defined-Type
        leaf sRepopulateRoute {
            config "false";
            description "U6RIB sends repopulate route to client";

            // Type is an MO-Defined-Type
            type urib_Counter32;
        }

        // When a client asks to be notified when another client
        // declare his convergence
        // Type is an MO-Defined-Type
        leaf rNotifyPibConvRequest {
            config "false";
            description "Client sends PIB convergence request to U6RIB";

            // Type is an MO-Defined-Type
            type urib_Counter32;
        }

        // Type is an MO-Defined-Type
        leaf sNotifyPibConv {
            config "false";
            description "Used when URIB notify other client of a convergence";

            // Type is an MO-Defined-Type
            type urib_Counter32;
        }

        // Type is an MO-Defined-Type
        leaf rNotifyPibConv {
            config "false";
            description "Used when a client declare convergence to URIB";

            // Type is an MO-Defined-Type
            type urib_Counter32;
        }

        // Type is an MO-Defined-Type
        leaf rModifyRoute {
            config "false";
            description "Client sends modify route to U6RIB";

            // Type is an MO-Defined-Type
            type urib_Counter32;
        }

        // Type is an MO-Defined-Type
        leaf sModifyRouteAck {
            config "false";
            description "U6RIB sends modify route ACK to client";

            // Type is an MO-Defined-Type
            type urib_Counter32;
        }

        // A client can either send one notifyPibConv per table or
        // send a single notifyPibConvAll when every tables are
        // converged
        // Type is an MO-Defined-Type
        leaf rNotifyPibConvAll {
            config "false";
            description "Client sends notify Pib convergence all to U6RIB";

            // Type is an MO-Defined-Type
            type urib_Counter32;
        }

        // Used to override the default value
        // Type is an MO-Defined-Type
        leaf rPibSetStaleTime {
            config "false";
            description "Client sends PIB set stale time to U6RIB";

            // Type is an MO-Defined-Type
            type urib_Counter32;
        }

        // Type is an MO-Defined-Type
        leaf rSetAgedRouteInterval {
            config "false";
            description "Client sends set aged route interval to U6RIB";

            // Type is an MO-Defined-Type
            type urib_Counter32;
        }
    }

    grouping urib_ClientVrf6-group {
        leaf changeNotifyNames {
            config "false";
            type string;
        }
        leaf changeNotifyHandles {
            config "false";
            type string;
        }
        leaf changeNotifyAll {
            config "false";
            type boolean;
        }
        leaf changeSubscribedNames {
            config "false";
            type string;
        }
        leaf changeSubscribedHandles {
            config "false";
            type string;
        }
        leaf changeSubscribedIndex {
            config "false";
            type string;
        }

        // Most of these flags are static and sent on registration
        // Type is an MO-Defined-Type
        leaf flags {
            config "false";
            description "Flags sent by the client.";

            // Type is an MO-Defined-Type
            type urib_RoutingVrfFlags6;
        }

        // Type is an MO-Defined-Type
        leaf pendingTimerRemaining {
            config "false";
            description "Timer remaining on the pending timer";

            // Type is an MO-Defined-Type
            type urib_TimeStr;
        }
        leaf vrfName {
            config "false";
            type string;
        }

        // Inherited From urib:ClientVrfBase
        // Type is an MO-Defined-Type
        leaf routeCount {
            config "false";
            description "Number of routes in this VRF for a specific client";

            // Type is an MO-Defined-Type
            type urib_Counter32;
        }

        // Inherited From urib:ClientVrfBase
        // Type is an MO-Defined-Type
        leaf recursiveNextHopCount {
            config "false";
            description "Number of recursive Next-Hops";

            // Type is an MO-Defined-Type
            type urib_Counter32;
        }

        // Inherited From urib:ClientVrfBase
        // Type is an MO-Defined-Type
        leaf bestPathCount {
            config "false";
            description "Number of best path from this client in this table";

            // Type is an MO-Defined-Type
            type urib_Counter32;
        }

        // A backup path is a path that is not the best. So not installed in FIB
        // Inherited From urib:ClientVrfBase
        // Type is an MO-Defined-Type
        leaf backupPathCount {
            config "false";
            description "Number of backup path from this client in this table";

            // Type is an MO-Defined-Type
            type urib_Counter32;
        }

        // The bits in this mask refer to the client index.
        // Each client has a bit assigned. See the index property in
        // ClientBase. The term 'notifiers' is used in the CLI,
        // Inherited From urib:ClientVrfBase
        // Type is an MO-Defined-Type
        leaf routeChangeSubscribed {
            config "false";
            description "Get a notification whenever a route from these clients change.";

            // Type is an MO-Defined-Type
            type urib_BitMask64;
        }

        // The bits in this mask refer to the client index.
        // Each client has a bit assigned. See the index
        // property in ClientBase
        // Inherited From urib:ClientVrfBase
        // Type is an MO-Defined-Type
        leaf convergenceNotifyMask {
            config "false";
            description "Notify the clients in this mask whenever convergence is set by this client.";

            // Type is an MO-Defined-Type
            type urib_BitMask64;
        }

        // Inherited From urib:ClientVrfBase
        // Type is an MO-Defined-Type
        leaf labelCount {
            config "false";
            description "Number of labels. Internal use.";

            // Type is an MO-Defined-Type
            type urib_Counter32;
        }
    }

    grouping urib_Internal6-group {
        leaf supState {
            config "false";
            type string;
        }
        leaf pssUri {
            config "false";
            type string;
        }

        // Inherited From urib:InternalBase
        // Type is an MO-Defined-Type
        leaf servClisState {
            config "false";
            description "Server for Cli commands up or down";

            // Type is an MO-Defined-Type
            type urib_UpDown;
        }

        // Inherited From urib:InternalBase
        // Type is an MO-Defined-Type
        leaf servL3vmState {
            config "false";
            description "Server l3vm up or down";

            // Type is an MO-Defined-Type
            type urib_UpDown;
        }

        // Inherited From urib:InternalBase
        // Type is an MO-Defined-Type
        leaf servUfdmState {
            config "false";
            description "Server ufdm up or down";

            // Type is an MO-Defined-Type
            type urib_UpDown;
        }
        leaf regClis {
            config "false";
            type boolean;
        }
        leaf regL3vm {
            config "false";
            type boolean;
        }
        leaf regUfdm {
            config "false";
            type boolean;
        }
        leaf shmMin {
            config "false";
            type uint32;
        }
        leaf shmSize {
            config "false";
            type uint32;
        }
        leaf dbgFilterVrfName {
            config "false";
            type string;
        }
        leaf dbgFilterVrfTableId {
            config "false";
            type uint32;
        }
        leaf dbgFilterClientName {
            config "false";
            type string;
        }
        leaf dbgFilterClientIdx {
            config "false";
            type uint32;
        }
        leaf dbgFilterPrefixList {
            config "false";
            type string;
        }
        leaf performanceMode {
            config "false";
            type boolean;
        }
    }

    grouping urib_InternalVrf6-group {

        // Type is an MO-Defined-Type
        leaf cleanupTimerRemaining {
            config "false";
            description "Time left on the cleanup timer. 0 if not running";

            // Type is an MO-Defined-Type
            type urib_TimeStr;
        }
        leaf ufdmConnectCheck {
            config "false";
            type boolean;
        }
        leaf convRequested {
            config "false";
            type string;
        }
        leaf vrfName {
            config "false";
            type string;
        }
        leaf tableId {
            config "false";
            type uint32;
        }

        // Inherited From urib:InternalVrfBase
        // Type is an MO-Defined-Type
        leaf state {
            config "false";
            description "State";

            // Type is an MO-Defined-Type
            type urib_TableState;
        }
        leaf l3vmState {
            config "false";
            type string;
        }
        leaf ufdmEnabled {
            config "false";
            type boolean;
        }

        // Inherited From urib:InternalVrfBase
        // Type is an MO-Defined-Type
        leaf emptyTimerRemaining {
            config "false";
            description "Time left on the empty timer. 0 if not running";

            // Type is an MO-Defined-Type
            type urib_TimeStr;
        }
        leaf haClientCount {
            config "false";
            type uint32;
        }
        leaf haClientConvCount {
            config "false";
            type uint32;
        }
        leaf haClientConvList {
            config "false";
            type string;
        }
        leaf haClientUnconvList {
            config "false";
            type string;
        }
        leaf routeLimitMax {
            config "false";
            type uint32;
        }
        leaf routeLimitWarnPct {
            config "false";
            type uint32;
        }
        leaf routeLimitWarn {
            config "false";
            type uint32;
        }
        leaf routeLimitReinstPct {
            config "false";
            type uint32;
        }
        leaf routeLimitReinst {
            config "false";
            type uint32;
        }
        leaf routeLimitReinstPending {
            config "false";
            type boolean;
        }

        // Inherited From urib:InternalVrfBase
        // Type is an MO-Defined-Type
        leaf lastMibTrap {
            config "false";
            description "When was the last mib trap.";

            // Type is an MO-Defined-Type
            type urib_TimeStr;
        }
        leaf maxTrapReset {
            config "false";
            type boolean;
        }
        leaf warnTrapReset {
            config "false";
            type boolean;
        }

        // Inherited From urib:InternalVrfBase
        // Type is an MO-Defined-Type
        leaf addedCount {
            config "false";
            description "Total number of routes added. Not decremented when a route is deleted";

            // Type is an MO-Defined-Type
            type urib_Counter64;
        }

        // Inherited From urib:InternalVrfBase
        // Type is an MO-Defined-Type
        leaf deletedCount {
            config "false";
            description "Total number of routes deleted";

            // Type is an MO-Defined-Type
            type urib_Counter64;
        }
        leaf droppedCount {
            config "false";
            type uint64;
        }
    }

    grouping urib_Table6-group {
        leaf vrfName {
            config "false";
            type string;
        }

        // Inherited From urib:TableBase
        // Type is an MO-Defined-Type
        leaf routeCount {
            config "false";
            description "Total number of route in this table";

            // Type is an MO-Defined-Type
            type urib_Counter32;
        }

        // Inherited From urib:TableBase
        // Type is an MO-Defined-Type
        leaf uniBestCount {
            config "false";
            description "Number of unicast route considered as the best";

            // Type is an MO-Defined-Type
            type urib_Counter32;
        }

        // Inherited From urib:TableBase
        // Type is an MO-Defined-Type
        leaf uniBackupCount {
            config "false";
            description "Number of unicast route not considered as the best";

            // Type is an MO-Defined-Type
            type urib_Counter32;
        }

        // Inherited From urib:TableBase
        // Type is an MO-Defined-Type
        leaf multiBestCount {
            config "false";
            description "Number of multicast route considered as the best";

            // Type is an MO-Defined-Type
            type urib_Counter32;
        }

        // Inherited From urib:TableBase
        // Type is an MO-Defined-Type
        leaf multiBackupCount {
            config "false";
            description "Number of multicast route not considered as the best";

            // Type is an MO-Defined-Type
            type urib_Counter32;
        }
        leaf routePerMaskCount {
            config "false";
            type string;
        }

        // Specific to v6
        container hiddennh6-items {
            list HiddenNextHop6-list {
                config "false";
                key "id";

                // Added containment: Prefix=hiddennh6
                // Acquired From Package urib
                uses urib_HiddenNextHop6-group;
            }
        }

        // Specific to v6
        container route6-items {
            list Route6-list {
                config "false";
                key "prefix";

                // Added containment: Prefix=route6
                // Acquired From Package urib
                uses urib_Route6-group;
            }
        }
    }

    grouping urib_HiddenNextHop6-group {
        leaf id {
            config "false";
            type uint32;
        }
        leaf routeAddress {
            config "false";
            type string;
        }
        leaf routeMask {
            config "false";
            type uint8;
        }
        leaf clientName {
            config "false";
            type string;
        }
        leaf recursiveNhAddress {
            config "false";
            type string;
        }
        leaf recursiveNhMask {
            config "false";
            type uint8;
        }
    }

    grouping urib_Route6-group {
        leaf prefix {
            config "false";
            type string;
        }
        leaf uBestNextHopCount {
            config "false";
            type uint32;
        }
        leaf mBestNextHopCount {
            config "false";
            type uint32;
        }

        // Specific to v6
        container nh6-items {
            list NextHop6-list {
                config "false";
                key "id";

                // Added containment: Prefix=nh6
                // Acquired From Package urib
                uses urib_NextHop6-group;
            }
        }

        // Specific to v6
        container routedetail6-items {

            // Added containment as a singleton: Prefix=routedetail6
            // Acquired From Package urib
            uses urib_RouteDetail6-group;
        }
    }

    grouping urib_NextHop6-group {
        leaf id {
            config "false";
            type uint32;
        }
        leaf prefix {
            config "false";
            type string;
        }
        leaf mask {
            config "false";
            type uint32;
        }
        leaf tableId {
            config "false";
            type uint32;
        }
        leaf interfaceName {
            config "false";
            type string;
        }
        leaf owner {
            config "false";
            type string;
        }
        leaf preference {
            config "false";
            type uint32;
        }
        leaf metric {
            config "false";
            type uint32;
        }

        // Inherited From urib:NextHopBase
        // Type is an MO-Defined-Type
        leaf uptime {
            config "false";
            description "Time since this next hop has been added/modified";

            // Type is an MO-Defined-Type
            type urib_TimeStr;
        }

        // Specific to v6
        container nhdetail6-items {

            // Added containment as a singleton: Prefix=nhdetail6
            // Acquired From Package urib
            uses urib_NextHopDetail6-group;
        }
    }

    grouping urib_NextHopDetail6-group {

        // Type is an MO-Defined-Type
        leaf flags {
            config "false";
            description "Flags";

            // Type is an MO-Defined-Type
            type urib_NhFlags6;
        }

        // Type is an MO-Defined-Type
        leaf nhlfeFlags {
            config "false";
            description "Nexthop Label Forwarding flags";

            // Type is an MO-Defined-Type
            type urib_NhlfeFlags6;
        }

        // Type is an MO-Defined-Type
        leaf tlvType {
            config "false";
            description "Type-Length-Value type";

            // Type is an MO-Defined-Type
            type urib_TlvType6;
        }
        leaf routeType {
            config "false";
            type string;
        }
        leaf tag {
            config "false";
            type uint32;
        }
        leaf segmentId {
            config "false";
            type uint32;
        }
        leaf tunnelId {
            config "false";
            type uint32;
        }

        // Support for VXLAN encap type only with EVPN
        // Inherited From urib:NextHopDetailBase
        // Type is an MO-Defined-Type
        leaf encapType {
            config "false";
            description "Either VXLAN or none";

            // Type is an MO-Defined-Type
            type urib_NextHopEncapType;
        }
        leaf labelStack {
            config "false";
            type string;
        }
        leaf nhlfeOwner {
            config "false";
            type string;
        }

        // Internal use.
        // Urib doesn't know how to interpret client data
        // Inherited From urib:NextHopDetailBase
        // Type is an MO-Defined-Type
        leaf clientData {
            config "false";
            description "Yes if client put data in the next-hop";

            // Type is an MO-Defined-Type
            type urib_YesNo;
        }
        leaf recursiveNextHopPrefix {
            config "false";
            type string;
        }
        leaf xriBgpOrigin {
            config "false";
            type string;
        }
        leaf xriBgpPeer {
            config "false";
            type string;
        }
        leaf tlv {
            config "false";
            type string;
        }
        leaf tlvExtentedCommunity {
            config "false";
            type string;
        }
        leaf tlvAttachExport {
            config "false";
            type string;
        }
    }

    grouping urib_RouteDetail6-group {
        leaf inUfdm {
            config "false";
            type boolean;
        }
        leaf ufdmScheduled {
            config "false";
            type boolean;
        }

        // Type is an MO-Defined-Type
        leaf flags {
            config "false";
            description "Route flags";

            // Type is an MO-Defined-Type
            type urib_RouteFlags6;
        }

        // The bits in this mask refer to the client index.
        // Each client has a bit assigned. See the index property in
        // ClientBase. The term 'redistributed' is used in the CLI,
        // Type is an MO-Defined-Type
        leaf notificationMask {
            config "false";
            description "Who need to be notified when this route change";

            // Type is an MO-Defined-Type
            type urib_BitMask64;
        }
        leaf attached {
            config "false";
            type boolean;
        }
    }

    grouping uribv4_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Domain (vrf) information
        container dom-items {
            list Dom-list {
                key "name";

                // Added containment: Prefix=dom
                // Acquired From Package uribv4
                uses uribv4_Dom-group;
            }
        }
    }

    grouping uribv4_Dom-group {

        // Operational state
        // Type is an MO-Defined-Type
        leaf operSt {
            config "false";
            description "TBD";

            // Type is an MO-Defined-Type
            type rib_DomOperSt;
        }

        // Inherited From nw:Conn
        // Modified by Override: nw:CpDom->name
        // Type is an MO-Defined-Type
        leaf name {
            description "Name";

            // Type is an MO-Defined-Type
            type naming_Name {
                length "1..64";
            }
        }
        container db-items {
            list Db-list {
                key "type";

                // Added containment: Prefix=db
                // Acquired From Package uribv4
                uses uribv4_Db-group;
            }
        }
    }

    grouping uribv4_Db-group {

        // Inherited From nw:Conn
        // Modified by Override: nw:Db->name
        // Type is an MO-Defined-Type
        leaf name {
            description "Name";

            // Type is an MO-Defined-Type
            type naming_Name {
                length "1..64";
            }
        }

        // Type of the repository
        // Inherited From rib:Db
        // Type is an MO-Defined-Type
        leaf type {
            description "Type";

            // Type is an MO-Defined-Type
            type rib_DbT;
        }

        // Route
        container rt-items {
            list Route-list {
                key "prefix";

                // Added containment: Prefix=rt
                // Acquired From Package uribv4
                uses uribv4_Route-group;
            }
        }
    }

    grouping uribv4_Route-group {
        leaf prefix {
            type address_Ip;
        }
        leaf prefixLength {
            config "false";
            type uint8;
        }

        // Inherited From nw:Conn
        // Modified by Override: nw:DbRec->name
        // Type is an MO-Defined-Type
        leaf name {
            description "Name";

            // Type is an MO-Defined-Type
            type naming_Name {
                length "1..64";
            }
        }

        // URIB next-hop database record
        container nh-items {
            list Nexthop-list {
                config "false";
                key "owner addr if vrf";

                // Added containment: Prefix=nh
                // Acquired From Package uribv4
                uses uribv4_Nexthop-group;
            }
        }

        // URIB route ownership record
        container owner-items {
            list RouteOwner-list {
                key "owner";

                // Added containment: Prefix=owner
                // Acquired From Package uribv4
                uses uribv4_RouteOwner-group;
            }
        }
    }

    grouping uribv4_Nexthop-group {

        // Owner
        // Type is an MO-Defined-Type
        leaf owner {
            config "false";
            description "Nexthop Owner";

            // Type is an MO-Defined-Type
            type rib_OwnerT;
        }
        leaf addr {
            config "false";
            type address_Ip;
        }

        // Nexthop interface
        // Type is an MO-Defined-Type
        leaf if {
            config "false";
            description "Nexthop Interface";

            // Type is an MO-Defined-Type
            type nw_IfId;
        }

        // Nexthop vrf
        // Type is an MO-Defined-Type
        leaf vrf {
            config "false";
            description "Nexthop VRF";

            // Type is an MO-Defined-Type
            type l3_VrfName;
        }

        // Preference
        // Type is an MO-Defined-Type
        leaf pref {
            config "false";
            description "Preference";

            // Type is an MO-Defined-Type
            type rib_Pref;
        }

        // Metric
        // Type is an MO-Defined-Type
        leaf metric {
            config "false";
            description "Metric";

            // Type is an MO-Defined-Type
            type rib_Metric;
        }

        // NH route type
        // Type is an MO-Defined-Type
        leaf routeType {
            config "false";
            description "TBD";

            // Type is an MO-Defined-Type
            type rib_RouteT;
        }

        // NH type
        // Type is an MO-Defined-Type
        leaf type {
            config "false";
            description "TBD";

            // Type is an MO-Defined-Type
            type rib_NhT;
        }

        // NH uptime
        // Type is an MO-Defined-Type
        leaf createTs {
            config "false";
            description "TBD";

            // Type is an MO-Defined-Type
            type rib_CreateTs;
        }
        leaf active {
            config "false";
            type boolean;
        }

        // Tag
        // Type is an MO-Defined-Type
        leaf tag {
            config "false";
            description "Tag";

            // Type is an MO-Defined-Type
            type rib_Tag;
        }

        // Inherited From nw:Conn
        // Modified by Override: nw:DbRec->name
        // Type is an MO-Defined-Type
        leaf name {
            description "Name";

            // Type is an MO-Defined-Type
            type naming_Name {
                length "1..64";
            }
        }
    }

    grouping uribv4_RouteOwner-group {

        // Owner's name
        // Type is an MO-Defined-Type
        leaf owner {
            description "TBD";

            // Type is an MO-Defined-Type
            type rib_OwnerT;
        }

        // Inherited From nw:Conn
        // Modified by Override: nw:DbRec->name
        // Type is an MO-Defined-Type
        leaf name {
            description "Name";

            // Type is an MO-Defined-Type
            type naming_Name {
                length "1..64";
            }
        }

        // URIB next-hop database record
        container nh-items {
            list Nexthop-list {
                config "false";
                key "owner addr if vrf";

                // Added containment: Prefix=nh
                // Acquired From Package uribv4
                uses uribv4_Nexthop-group;
            }
        }

        // Rel-def from RouteOwnerToNexthopAtt
        container rsrouteOwnerToNexthopAtt-items {

            // Abstract containment of rsrouteOwnerToNexthopAtt derived from uribv4:RouteOwner
            list RsRouteOwnerToNexthopAtt-list {
                key "tDn";

                // Added containment: Prefix=rsrouteOwnerToNexthopAtt
                // Acquired From Package uribv4
                uses uribv4_RsRouteOwnerToNexthopAtt_source-group;
            }
        }
    }

    grouping uribv6_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Domain (vrf) information
        container dom-items {
            list Dom-list {
                key "name";

                // Added containment: Prefix=dom
                // Acquired From Package uribv6
                uses uribv6_Dom-group;
            }
        }
    }

    grouping uribv6_Dom-group {

        // Operational state
        // Type is an MO-Defined-Type
        leaf operSt {
            config "false";
            description "TBD";

            // Type is an MO-Defined-Type
            type rib_DomOperSt;
        }

        // Inherited From nw:Conn
        // Modified by Override: nw:CpDom->name
        // Type is an MO-Defined-Type
        leaf name {
            description "Name";

            // Type is an MO-Defined-Type
            type naming_Name {
                length "1..64";
            }
        }
        container db-items {
            list Db-list {
                key "type";

                // Added containment: Prefix=db
                // Acquired From Package uribv6
                uses uribv6_Db-group;
            }
        }
    }

    grouping uribv6_Db-group {

        // Inherited From nw:Conn
        // Modified by Override: nw:Db->name
        // Type is an MO-Defined-Type
        leaf name {
            description "Name";

            // Type is an MO-Defined-Type
            type naming_Name {
                length "1..64";
            }
        }

        // Type of the repository
        // Inherited From rib:Db
        // Type is an MO-Defined-Type
        leaf type {
            description "Type";

            // Type is an MO-Defined-Type
            type rib_DbT;
        }

        // Route
        container rt-items {
            list Route-list {
                key "prefix";

                // Added containment: Prefix=rt
                // Acquired From Package uribv6
                uses uribv6_Route-group;
            }
        }
    }

    grouping uribv6_Route-group {

        // Inherited From nw:Conn
        // Modified by Override: nw:DbRec->name
        // Type is an MO-Defined-Type
        leaf name {
            description "Name";

            // Type is an MO-Defined-Type
            type naming_Name {
                length "1..64";
            }
        }
        leaf prefix {
            type address_Ip;
        }
        leaf prefixLength {
            config "false";
            type uint8;
        }

        // URIB next-hop database record
        container nh-items {
            list Nexthop-list {
                config "false";
                key "owner addr if vrf";

                // Added containment: Prefix=nh
                // Acquired From Package uribv6
                uses uribv6_Nexthop-group;
            }
        }

        // URIB route ownership record
        container owner-items {
            list RouteOwner-list {
                key "owner";

                // Added containment: Prefix=owner
                // Acquired From Package uribv6
                uses uribv6_RouteOwner-group;
            }
        }
    }

    grouping uribv6_Nexthop-group {

        // Inherited From nw:Conn
        // Modified by Override: nw:DbRec->name
        // Type is an MO-Defined-Type
        leaf name {
            description "Name";

            // Type is an MO-Defined-Type
            type naming_Name {
                length "1..64";
            }
        }

        // Owner
        // Inherited From rib:Nexthop
        // Type is an MO-Defined-Type
        leaf owner {
            config "false";
            description "Nexthop Owner";

            // Type is an MO-Defined-Type
            type rib_OwnerT;
        }
        leaf addr {
            config "false";
            type address_Ip;
        }

        // Nexthop interface
        // Inherited From rib:Nexthop
        // Type is an MO-Defined-Type
        leaf if {
            config "false";
            description "Nexthop Interface";

            // Type is an MO-Defined-Type
            type nw_IfId;
        }

        // Nexthop vrf
        // Inherited From rib:Nexthop
        // Type is an MO-Defined-Type
        leaf vrf {
            config "false";
            description "Nexthop VRF";

            // Type is an MO-Defined-Type
            type l3_VrfName;
        }

        // Preference
        // Inherited From rib:Nexthop
        // Type is an MO-Defined-Type
        leaf pref {
            config "false";
            description "Preference";

            // Type is an MO-Defined-Type
            type rib_Pref;
        }

        // Metric
        // Inherited From rib:Nexthop
        // Type is an MO-Defined-Type
        leaf metric {
            config "false";
            description "Metric";

            // Type is an MO-Defined-Type
            type rib_Metric;
        }

        // NH route type
        // Inherited From rib:Nexthop
        // Type is an MO-Defined-Type
        leaf routeType {
            config "false";
            description "TBD";

            // Type is an MO-Defined-Type
            type rib_RouteT;
        }

        // NH type
        // Inherited From rib:Nexthop
        // Type is an MO-Defined-Type
        leaf type {
            config "false";
            description "TBD";

            // Type is an MO-Defined-Type
            type rib_NhT;
        }

        // NH uptime
        // Inherited From rib:Nexthop
        // Type is an MO-Defined-Type
        leaf createTs {
            config "false";
            description "TBD";

            // Type is an MO-Defined-Type
            type rib_CreateTs;
        }
        leaf active {
            config "false";
            type boolean;
        }

        // Tag
        // Inherited From rib:Nexthop
        // Type is an MO-Defined-Type
        leaf tag {
            config "false";
            description "Tag";

            // Type is an MO-Defined-Type
            type rib_Tag;
        }
    }

    grouping uribv6_RouteOwner-group {

        // Inherited From nw:Conn
        // Modified by Override: nw:DbRec->name
        // Type is an MO-Defined-Type
        leaf name {
            description "Name";

            // Type is an MO-Defined-Type
            type naming_Name {
                length "1..64";
            }
        }

        // Owner's name
        // Inherited From rib:RouteOwner
        // Type is an MO-Defined-Type
        leaf owner {
            description "TBD";

            // Type is an MO-Defined-Type
            type rib_OwnerT;
        }

        // URIB next-hop database record
        container nh-items {
            list Nexthop-list {
                config "false";
                key "owner addr if vrf";

                // Added containment: Prefix=nh
                // Acquired From Package uribv6
                uses uribv6_Nexthop-group;
            }
        }
    }

    grouping nw_ConnGrp-group {

        // From Interface naming:Described
        // Type is an MO-Defined-Type
        leaf descr {
            description "Description";

            // Type is an MO-Defined-Type
            type naming_Descr;
        }

        // Inherited From nw:Conn
        // Modified by Override: nw:ConnGrp->name
        // Type is an MO-Defined-Type
        leaf name {
            description "Name";

            // Type is an MO-Defined-Type
            type naming_Name {
                length "1..64";
            }
        }

        // Path enpoint
        container path-items {
            list PathEp-list {
                key "id";

                // Added containment: Prefix=path
                // Acquired From Package nw
                uses nw_PathEp-group;
            }
        }
    }

    grouping nw_PathEp-group {

        // Path ID of this endpoint
        // Type is an MO-Defined-Type
        leaf id {
            description "TBD";

            // Type is an MO-Defined-Type
            type nw_IfId;
        }
        leaf nativeEncap {
            type string;
        }
        leaf fabricPathDn {
            type string;
        }

        // From Interface naming:Described
        // Type is an MO-Defined-Type
        leaf descr {
            description "Description";

            // Type is an MO-Defined-Type
            type naming_Descr;
        }

        // Inherited From nw:Conn
        // Modified by Override: nw:Ep->name
        // Type is an MO-Defined-Type
        leaf name {
            description "Name";

            // Type is an MO-Defined-Type
            type naming_Name {
                length "1..64";
            }
        }

        // Rel-def target from epDefToPathEp
        // Inherited From nw:PathEp
        container rtfvEpDefToPathEp-items {

            // Abstract containment of rtfvEpDefToPathEp derived from nw:PathEp
            list RtFvEpDefToPathEp-list {
                config "false";
                key "tDn";

                // Added containment: Prefix=rtfvEpDefToPathEp
                // Acquired From Package fv
                uses fv_RtFvEpDefToPathEp_target-group;
            }
        }

        // Rel-def target from dyPathAtt
        // Inherited From nw:PathEp
        container rtfvDyPathAtt-items {

            // Abstract containment of rtfvDyPathAtt derived from nw:PathEp
            list RtFvDyPathAtt-list {
                config "false";
                key "tDn";

                // Added containment: Prefix=rtfvDyPathAtt
                // Acquired From Package fv
                uses fv_RtFvDyPathAtt_target-group;
            }
        }

        // Rel-def from pathToIf
        container rspathToIf-items {

            // Added containment as a singleton: Prefix=rspathToIf
            // Acquired From Package nw
            uses nw_RsPathToIf_source-group;
        }
    }

    grouping nw_Vdc-group {

        // vdc ID
        // Type is an MO-Defined-Type
        leaf id {
            description "ID";

            // Type is an MO-Defined-Type
            type l2_VdcId;
        }

        // From Interface naming:Named
        // Inherited From naming:NamedObject
        // Type is an MO-Defined-Type
        leaf name {
            description "Name";

            // Type is an MO-Defined-Type
            type naming_Name;
        }
    }

    grouping proc_System-group {

        // Maximum memory allocated for the system
        // Type is an MO-Defined-Type
        leaf maxMemAlloc {
            config "false";
            description "Maximum Memory Allocated";

            // Type is an MO-Defined-Type
            type proc_ProcMem;
        }
        leaf upTs {
            config "false";
            type uint64;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Process entry in the system
        container proc-items {
            list Proc-list {
                config "false";
                key "id";

                // Added containment: Prefix=proc
                // Acquired From Package proc
                uses proc_Proc-group;
            }
        }
    }

    grouping proc_Proc-group {

        // Process id
        // Type is an MO-Defined-Type
        leaf id {
            config "false";
            description "Process ID";

            // Type is an MO-Defined-Type
            type proc_ProcId;
        }

        // State of the process
        // Type is an MO-Defined-Type
        leaf operSt {
            config "false";
            description "Operational State";

            // Type is an MO-Defined-Type
            type proc_OperSt;
        }

        // Start count of the process
        // Type is an MO-Defined-Type
        leaf startCnt {
            config "false";
            description "Start Count";

            // Type is an MO-Defined-Type
            type proc_StartCnt;
        }

        // Program counter
        // Type is an MO-Defined-Type
        leaf pc {
            config "false";
            description "Program Counter";

            // Type is an MO-Defined-Type
            type proc_ProgCntr;
        }

        // Address of bottom of stack for the process
        // Type is an MO-Defined-Type
        leaf stackBase {
            config "false";
            description "Stack Base";

            // Type is an MO-Defined-Type
            type proc_Stack;
        }

        // Stack pointer
        // Type is an MO-Defined-Type
        leaf esp {
            config "false";
            description "Stack Pointer";

            // Type is an MO-Defined-Type
            type proc_Stack;
        }

        // TTY
        // Type is an MO-Defined-Type
        leaf tty {
            config "false";
            description "TTY";

            // Type is an MO-Defined-Type
            type proc_TTY;
        }

        // Maximum memory allocated for a process
        // Type is an MO-Defined-Type
        leaf maxMemAlloc {
            config "false";
            description "Maximum Memory Allocated";

            // Type is an MO-Defined-Type
            type proc_ProcMem;
        }

        // From Interface naming:Named
        // Inherited From naming:NamedObject
        // Type is an MO-Defined-Type
        leaf name {
            description "Name";

            // Type is an MO-Defined-Type
            type naming_Name;
        }
    }

    grouping proc_Entity-group {

        // Maximum memory allocated for the system
        // Type is an MO-Defined-Type
        leaf maxMemAlloc {
            config "false";
            description "Maximum Memory Allocated";

            // Type is an MO-Defined-Type
            type proc_ProcMem;
        }

        // Free memory in the system
        // Type is an MO-Defined-Type
        leaf memFree {
            config "false";
            description "Free Memory";

            // Type is an MO-Defined-Type
            type proc_ProcMem;
        }

        // CPU Usage in the system
        // Type is an MO-Defined-Type
        leaf cpuPct {
            config "false";
            description "CPU Usage";

            // Type is an MO-Defined-Type
            type proc_CpuUsage;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Process entry in the system
        container proc-items {
            list Entry-list {
                key "name";

                // Added containment: Prefix=proc
                // Acquired From Package proc
                uses proc_Entry-group;
            }
        }
    }

    grouping proc_Entry-group {

        // Process id
        // Type is an MO-Defined-Type
        leaf id {
            config "false";
            description "Process ID";

            // Type is an MO-Defined-Type
            type proc_ProcId;
        }

        // State of the process
        // Type is an MO-Defined-Type
        leaf operSt {
            config "false";
            description "Operational State";

            // Type is an MO-Defined-Type
            type proc_OperSt;
        }

        // Start count of the process
        // Type is an MO-Defined-Type
        leaf startCnt {
            config "false";
            description "Start Count";

            // Type is an MO-Defined-Type
            type proc_StartCnt;
        }

        // Program counter
        // Type is an MO-Defined-Type
        leaf pc {
            config "false";
            description "Program Counter";

            // Type is an MO-Defined-Type
            type proc_ProgCntr;
        }

        // Address of botoom of stack for the process
        // Type is an MO-Defined-Type
        leaf stackBase {
            config "false";
            description "Stack Base";

            // Type is an MO-Defined-Type
            type proc_Stack;
        }

        // Stack pointer
        // Type is an MO-Defined-Type
        leaf esp {
            config "false";
            description "Stack Pointer";

            // Type is an MO-Defined-Type
            type proc_Stack;
        }

        // TTY
        // Type is an MO-Defined-Type
        leaf tty {
            config "false";
            description "TTY";

            // Type is an MO-Defined-Type
            type proc_TTY;
        }

        // Maximum memory allocated for a process
        // Type is an MO-Defined-Type
        leaf maxMemAlloc {
            config "false";
            description "Maximum Memory Allocated";

            // Type is an MO-Defined-Type
            type proc_ProcMem;
        }

        // Operational state for a process
        // Type is an MO-Defined-Type
        leaf operState {
            config "false";
            description "Operational State";

            // Type is an MO-Defined-Type
            type proc_OperState;
        }

        // From Interface naming:Named
        // Inherited From naming:NamedObject
        // Modified by Override: proc:Entry->name
        // Type is an MO-Defined-Type
        leaf name {
            description "Name";

            // Type is an MO-Defined-Type
            type naming_Name {
                length "1..64";
            }
        }
    }

    grouping regress_If-group {

        // Enum Property
        // Type is an MO-Defined-Type
        leaf enumProp {
            config "false";
            description "Enum Property";

            // Type is an MO-Defined-Type
            type regress_EnumT;
        }
        leaf strProp {
            config "false";
            type string;
        }
        leaf intProp {
            config "false";
            type uint32;
        }
        leaf boolProp {
            config "false";
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping rpm_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Route control rule for extended community lists
        container rtextcom-items {
            list Rule-list {
                key "name";

                // Added containment: Prefix=rtextcom
                // Acquired From Package rtextcom
                uses rtextcom_Rule-group;
            }
        }

        // Route control rule for access lists
        container accesslist-items {
            list Rule-list {
                key "name";

                // Added containment: Prefix=accesslist
                // Acquired From Package rtlist
                uses rtlist_Rule-group;
            }
        }

        // Route map rule
        container rtmap-items {
            list Rule-list {
                key "name";

                // Added containment: Prefix=rtmap
                // Acquired From Package rtmap
                uses rtmap_Rule-group;
            }
        }

        // Expanded Community List
        container expcommlist-items {
            list ExpandedComList-list {
                key "regex expcommname";

                // Added containment: Prefix=expcommlist
                // Acquired From Package rtmap
                uses rtmap_ExpandedComList-group;
            }
        }

        // Route control rule for V4 prefix lists
        container pfxlistv4-items {
            list RuleV4-list {
                key "name";

                // Added containment: Prefix=pfxlistv4
                // Acquired From Package rtpfx
                uses rtpfx_RuleV4-group;
            }
        }

        // Route control rule for V6 prefix lists
        container pfxlistv6-items {
            list RuleV6-list {
                key "name";

                // Added containment: Prefix=pfxlistv6
                // Acquired From Package rtpfx
                uses rtpfx_RuleV6-group;
            }
        }

        // Route control rule for regular community lists
        container rtregcom-items {
            list Rule-list {
                key "name";

                // Added containment: Prefix=rtregcom
                // Acquired From Package rtregcom
                uses rtregcom_Rule-group;
            }
        }
    }

    grouping rtextcom_Rule-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type of the community list [regular | extended]
        // Inherited From rtcom:Rule
        // Modified by Override: rtextcom:Rule->type
        // Type is an MO-Defined-Type
        leaf type {
            description "Type";

            // Type is an MO-Defined-Type
            type rtcom_ComT;
        }

        // Mode
        // Inherited From rtcom:Rule
        // Type is an MO-Defined-Type
        leaf mode {
            description "Mode";

            // Type is an MO-Defined-Type
            type rtcom_Mode;
        }

        // Extended community list entry
        container ent-items {
            list Entry-list {
                key "order";

                // Added containment: Prefix=ent
                // Acquired From Package rtextcom
                uses rtextcom_Entry-group;
            }
        }

        // Rel-def target from ExtCommAtt
        // Inherited From rtextcom:Rule
        container rtExtCommAtt-items {

            // Added containment as a singleton: Prefix=rtExtCommAtt
            // Acquired From Package rtmap
            uses rtmap_RtExtCommAtt_target-group;
        }
    }

    grouping rtextcom_Entry-group {

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }

        // Item in the community list
        container item-items {
            list Item-list {
                key "scope community";

                // Added containment: Prefix=item
                // Acquired From Package rtextcom
                uses rtextcom_Item-group;
            }
        }
    }

    grouping rtextcom_Item-group {

        // type
        // Type is an MO-Defined-Type
        leaf type {
            description "Type";

            // Type is an MO-Defined-Type
            type rtextcom_Type;
        }

        // Scope
        // Type is an MO-Defined-Type
        leaf scope {
            description "Scope";

            // Type is an MO-Defined-Type
            type rtextcom_Scope;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf community {
            type mtx_array_community;
        }
    }

    grouping rtlist_Rule-group {

        // From Interface naming:Named
        // Inherited From naming:NamedObject
        // Modified by Override: rtlist:Rule->name
        // Modified by Override: pol:Obj->name
        // Modified by Override: nw:FltRule->name
        // Type is an MO-Defined-Type
        leaf name {
            description "Name";

            // Type is an MO-Defined-Type
            type naming_Name {
                length "1..63";
            }
        }

        // From Interface naming:Described
        // Inherited From pol:Instr
        // Type is an MO-Defined-Type
        leaf descr {
            description "Description";

            // Type is an MO-Defined-Type
            type naming_Descr;
        }

        // Prefix list entry definition
        container ent-items {
            list Entry-list {
                key "order";

                // Added containment: Prefix=ent
                // Acquired From Package rtlist
                uses rtlist_Entry-group;
            }
        }

        // Rel-def target from RtAsPathAccAtt
        // Inherited From rtlist:Rule
        container rtrtmapRtAsPathAccAtt-items {

            // Abstract containment of rtrtmapRtAsPathAccAtt derived from rtlist:Rule
            list RtRtmapRtAsPathAccAtt-list {
                key "tDn";

                // Added containment: Prefix=rtrtmapRtAsPathAccAtt
                // Acquired From Package rtmap
                uses rtmap_RtRtmapRtAsPathAccAtt_target-group;
            }
        }
    }

    grouping rtlist_Entry-group {

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }
    }

    grouping rtmap_Rule-group {

        // From Interface naming:Named
        // Inherited From naming:NamedObject
        // Modified by Override: rtmap:Rule->name
        // Modified by Override: pol:Obj->name
        // Modified by Override: nw:FltRule->name
        // Type is an MO-Defined-Type
        leaf name {
            description "Name";

            // Type is an MO-Defined-Type
            type naming_Name {
                length "0..63";
            }
        }

        // From Interface naming:Described
        // Inherited From pol:Instr
        // Type is an MO-Defined-Type
        leaf descr {
            description "Description";

            // Type is an MO-Defined-Type
            type naming_Descr;
        }

        // Route map entries
        container ent-items {
            list Entry-list {
                key "order";

                // Added containment: Prefix=ent
                // Acquired From Package rtmap
                uses rtmap_Entry-group;
            }
        }
    }

    grouping rtmap_Entry-group {

        // Load Sharing v4
        // Type is an MO-Defined-Type
        leaf loadShareV4 {
            description "Load Sharing V4";

            // Type is an MO-Defined-Type
            type rtmap_AdminSt;
        }

        // Load Sharing v6
        // Type is an MO-Defined-Type
        leaf loadShareV6 {
            description "Load Sharing V6";

            // Type is an MO-Defined-Type
            type rtmap_AdminSt;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Modified by Override: rtmap:Entry->descr
        // Type is an MO-Defined-Type
        leaf descr {
            description "descr";

            // Type is an MO-Defined-Type
            type naming_Descr {
                length "0..90";
            }
        }

        // Order
        // Inherited From rtflt:Entry
        // Modified by Override: rtmap:Entry->order
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }

        // Match rule based on regular communities
        container mregcomm-items {

            // Added containment as a singleton: Prefix=mregcomm
            // Acquired From Package rtmap
            uses rtmap_MatchRegComm-group;
        }

        // Match rule based on extended communities
        container mextcomm-items {

            // Added containment as a singleton: Prefix=mextcomm
            // Acquired From Package rtmap
            uses rtmap_MatchExtComm-group;
        }

        // Match rule based on route destinations
        container mrtdst-items {

            // Added containment as a singleton: Prefix=mrtdst
            // Acquired From Package rtmap
            uses rtmap_MatchRtDst-group;
        }

        // Match rule based on IPv6 route destinations
        container mrtdstv6-items {

            // Added containment as a singleton: Prefix=mrtdstv6
            // Acquired From Package rtmap
            uses rtmap_MatchRtDstV6-group;
        }

        // Match rule based on ipv4 multicast attributes
        container mipv4mcast-items {

            // Added containment as a singleton: Prefix=mipv4mcast
            // Acquired From Package rtmap
            uses rtmap_MatchIPv4Mcast-group;
        }

        // Match rule based on ipv6 multicast attributes
        container mipv6mcast-items {

            // Added containment as a singleton: Prefix=mipv6mcast
            // Acquired From Package rtmap
            uses rtmap_MatchIPv6Mcast-group;
        }

        // Match rule based on route nexthops
        container mrtnh-items {

            // Added containment as a singleton: Prefix=mrtnh
            // Acquired From Package rtmap
            uses rtmap_MatchRtNh-group;
        }

        // Match rule based on route nexthops ipv6
        container mrtnhv6-items {

            // Added containment as a singleton: Prefix=mrtnhv6
            // Acquired From Package rtmap
            uses rtmap_MatchRtNhV6-group;
        }

        // Match rule based on route sources
        container mrtsrc-items {

            // Added containment as a singleton: Prefix=mrtsrc
            // Acquired From Package rtmap
            uses rtmap_MatchRtSrc-group;
        }

        // Match rule based on route sources ipv6
        container mrtsrcv6-items {

            // Added containment as a singleton: Prefix=mrtsrcv6
            // Acquired From Package rtmap
            uses rtmap_MatchRtSrcV6-group;
        }

        // Match rule based on route types
        container mrttype-items {
            list MatchRtType-list {
                key "routeT";

                // Added containment: Prefix=mrttype
                // Acquired From Package rtmap
                uses rtmap_MatchRtType-group;
            }
        }

        // Match rule based on route tag
        container mrttag-items {
            list MatchRtTag-list {
                key "tag";

                // Added containment: Prefix=mrttag
                // Acquired From Package rtmap
                uses rtmap_MatchRtTag-group;
            }
        }

        // Match rule based on source protocol
        container msrcprot-items {
            list MatchSrcProto-list {
                key "proto";

                // Added containment: Prefix=msrcprot
                // Acquired From Package rtmap
                uses rtmap_MatchSrcProto-group;
            }
        }

        // Match rule based on pervasive routes
        container mrtpervasive-items {

            // Added containment as a singleton: Prefix=mrtpervasive
            // Acquired From Package rtmap
            uses rtmap_MatchRtPervasive-group;
        }

        // Match rule based on AS Path Access List
        container mrtacclist-items {

            // Added containment as a singleton: Prefix=mrtacclist
            // Acquired From Package rtmap
            uses rtmap_MatchAsPathAccessList-group;
        }

        // Match rule based on route metric
        container mrtmetric-items {
            list MatchRtMetric-list {
                key "measure deviation";

                // Added containment: Prefix=mrtmetric
                // Acquired From Package rtmap
                uses rtmap_MatchRtMetric-group;
            }
        }

        // Match rule based on route asn
        container mrtasn-items {
            list MatchRtAsn-list {
                key "asn";

                // Added containment: Prefix=mrtasn
                // Acquired From Package rtmap
                uses rtmap_MatchRtAsn-group;
            }
        }

        // Match rule based on route Interface
        container mrtif-items {
            list MatchRtIf-list {
                key "id";

                // Added containment: Prefix=mrtif
                // Acquired From Package rtmap
                uses rtmap_MatchRtIf-group;
            }
        }

        // Match rule based on Ospf-area
        container mrtospf-items {
            list MatchRtOspf-list {
                key "area";

                // Added containment: Prefix=mrtospf
                // Acquired From Package rtmap
                uses rtmap_MatchRtOspf-group;
            }
        }

        // Route map Continue
        container scontinue-items {

            // Added containment as a singleton: Prefix=scontinue
            // Acquired From Package rtmap
            uses rtmap_Continue-group;
        }

        // Set rule based on regular communities
        container sregcomm-items {

            // Added containment as a singleton: Prefix=sregcomm
            // Acquired From Package rtmap
            uses rtmap_SetRegComm-group;
        }

        // Set rule based on generic extended communities
        container sextcomm-items {

            // Added containment as a singleton: Prefix=sextcomm
            // Acquired From Package rtmap
            uses rtmap_SetExtComm-group;
        }

        // Set rule based on cost communities
        container sextcommcost-items {
            list SetExtCommCost-list {
                key "commCrit commId commValue";

                // Added containment: Prefix=sextcommcost
                // Acquired From Package rtmap
                uses rtmap_SetExtCommCost-group;
            }
        }

        // Set rule based on community list (for deletion)
        container scommlist-items {

            // Added containment as a singleton: Prefix=scommlist
            // Acquired From Package rtmap
            uses rtmap_SetCommList-group;
        }

        // Set rule based on community list (for deletion)
        container sextcommlist-items {

            // Added containment as a singleton: Prefix=sextcommlist
            // Acquired From Package rtmap
            uses rtmap_SetExtCommList-group;
        }

        // Set rule based on route targets communities
        container srtt-items {

            // Added containment as a singleton: Prefix=srtt
            // Acquired From Package rtmap
            uses rtmap_SetRttComm-group;
        }

        // Set rule based on route distance
        container srtdist-items {

            // Added containment as a singleton: Prefix=srtdist
            // Acquired From Package rtmap
            uses rtmap_SetRtDist-group;
        }

        // Set rule based on route tag
        container srttag-items {

            // Added containment as a singleton: Prefix=srttag
            // Acquired From Package rtmap
            uses rtmap_SetRtTag-group;
        }

        // Set rule based on weight
        container sweight-items {

            // Added containment as a singleton: Prefix=sweight
            // Acquired From Package rtmap
            uses rtmap_SetWeight-group;
        }

        // Set rule based on label-index
        container slblindex-items {

            // Added containment as a singleton: Prefix=slblindex
            // Acquired From Package rtmap
            uses rtmap_SetLabelIndex-group;
        }

        // Set rule based on preference
        container spref-items {

            // Added containment as a singleton: Prefix=spref
            // Acquired From Package rtmap
            uses rtmap_SetPref-group;
        }

        // Set rule based on metric
        container smetric-items {

            // Added containment as a singleton: Prefix=smetric
            // Acquired From Package rtmap
            uses rtmap_SetMetric-group;
        }

        // Set rule based on metric type
        container smetrict-items {

            // Added containment as a singleton: Prefix=smetrict
            // Acquired From Package rtmap
            uses rtmap_SetMetricType-group;
        }

        container sdamp-items {

            // Added containment as a singleton: Prefix=sdamp
            // Acquired From Package rtmap
            uses rtmap_SetDampeningType-group;
        }

        container sprec-items {

            // Added containment as a singleton: Prefix=sprec
            // Acquired From Package rtmap
            uses rtmap_SetPrecedence-group;
        }

        container sprecv6-items {

            // Added containment as a singleton: Prefix=sprecv6
            // Acquired From Package rtmap
            uses rtmap_SetV6Precedence-group;
        }

        // Set rule based on ospf-nssa
        container snssa-items {

            // Added containment as a singleton: Prefix=snssa
            // Acquired From Package rtmap
            uses rtmap_SetOspfNssa-group;
        }

        // Set rule based on ospf forwarding address
        container sfwdaddr-items {

            // Added containment as a singleton: Prefix=sfwdaddr
            // Acquired From Package rtmap
            uses rtmap_SetOspfFwdAddr-group;
        }

        // Set rule based on next hop
        container nh-items {
            list SetNh-list {
                key "addr";

                // Added containment: Prefix=nh
                // Acquired From Package rtmap
                uses rtmap_SetNh-group;
            }
        }

        // Set rule based on next hop peer-address
        container nhpa-items {

            // Added containment as a singleton: Prefix=nhpa
            // Acquired From Package rtmap
            uses rtmap_SetNhPeerAddr-group;
        }

        // Set rule based on as-path prepend
        container setaspathprepend-items {

            // Added containment as a singleton: Prefix=setaspathprepend
            // Acquired From Package rtmap
            uses rtmap_SetPrepend-group;
        }

        // Set Prepend Last As
        container setaspathlastas-items {

            // Added containment as a singleton: Prefix=setaspathlastas
            // Acquired From Package rtmap
            uses rtmap_SetPrependLastAs-group;
        }

        // Set Prepend Tag
        container setaspathtag-items {

            // Added containment as a singleton: Prefix=setaspathtag
            // Acquired From Package rtmap
            uses rtmap_SetAsPathTag-group;
        }

        // Set rule based on origin type
        container origin-items {

            // Added containment as a singleton: Prefix=origin
            // Acquired From Package rtmap
            uses rtmap_SetOrigin-group;
        }
    }

    grouping rtmap_MatchRegComm-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRegComm->type
        // Type is an MO-Defined-Type
        leaf type {
            description "Type";

            // Type is an MO-Defined-Type
            type rtmap_MatchT;
        }

        // criteria
        // Inherited From rtmap:MatchComm
        // Type is an MO-Defined-Type
        leaf criteria {
            description "Criteria";

            // Type is an MO-Defined-Type
            type rtmap_Criteria;
        }

        // Rel-def from RegCommAtt
        container rsregCommAtt-items {

            // Abstract containment of rsregCommAtt derived from rtmap:MatchRegComm
            list RsRegCommAtt-list {
                key "tDn";

                // Added containment: Prefix=rsregCommAtt
                // Acquired From Package rtmap
                uses rtmap_RsRegCommAtt_source-group;
            }
        }
    }

    grouping rtmap_MatchExtComm-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchExtComm->type
        // Type is an MO-Defined-Type
        leaf type {
            description "Type";

            // Type is an MO-Defined-Type
            type rtmap_MatchT;
        }

        // criteria
        // Inherited From rtmap:MatchComm
        // Type is an MO-Defined-Type
        leaf criteria {
            description "Criteria";

            // Type is an MO-Defined-Type
            type rtmap_Criteria;
        }

        // Rel-def from ExtCommAtt
        container rsextCommAtt-items {

            // Abstract containment of rsextCommAtt derived from rtmap:MatchExtComm
            list RsExtCommAtt-list {
                key "tDn";

                // Added containment: Prefix=rsextCommAtt
                // Acquired From Package rtmap
                uses rtmap_RsExtCommAtt_source-group;
            }
        }
    }

    grouping rtmap_MatchRtDst-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtDst->type
        // Type is an MO-Defined-Type
        leaf type {
            description "Type";

            // Type is an MO-Defined-Type
            type rtmap_MatchT;
        }

        // Rel-def from RtDstAtt
        container rsrtDstAtt-items {

            // Abstract containment of rsrtDstAtt derived from rtmap:MatchRtDst
            list RsRtDstAtt-list {
                key "tDn";

                // Added containment: Prefix=rsrtDstAtt
                // Acquired From Package rtmap
                uses rtmap_RsRtDstAtt_source-group;
            }
        }
    }

    grouping rtmap_MatchRtDstV6-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtDstV6->type
        // Type is an MO-Defined-Type
        leaf type {
            description "Type";

            // Type is an MO-Defined-Type
            type rtmap_MatchT;
        }

        // Rel-def from RtDstV6Att
        container rsrtDstV6Att-items {

            // Abstract containment of rsrtDstV6Att derived from rtmap:MatchRtDstV6
            list RsRtDstV6Att-list {
                key "tDn";

                // Added containment: Prefix=rsrtDstV6Att
                // Acquired From Package rtmap
                uses rtmap_RsRtDstV6Att_source-group;
            }
        }
    }

    grouping rtmap_MatchIPv4Mcast-group {

        // From Interface naming:Named
        // Inherited From naming:NamedObject
        // Modified by Override: pol:Obj->name
        // Modified by Override: nw:FltRule->name
        // Modified by Override: rtmap:MatchIPMcast->name
        // Type is an MO-Defined-Type
        leaf name {
            description "Name";

            // Type is an MO-Defined-Type
            type naming_Name {
                length "0..64";
            }
        }

        // From Interface naming:Described
        // Inherited From pol:Instr
        // Modified by Override: rtmap:MatchIPMcast->descr
        // Type is an MO-Defined-Type
        leaf descr {
            config "false";
            description "descr";

            // Type is an MO-Defined-Type
            type naming_Descr {
                length "0..32";
            }
        }

        // Type
        // Inherited From rtmap:Match
        // Modified by Override: rtmap:MatchIPv4Mcast->type
        // Modified by Override: rtmap:MatchIPMcast->type
        // Type is an MO-Defined-Type
        leaf type {
            config "false";
            description "Type";

            // Type is an MO-Defined-Type
            type rtmap_MatchT;
        }
        leaf groupAddr {
            type address_Ip;
        }
        leaf groupStartAddr {
            type address_Ip;
        }
        leaf groupEndAddr {
            type address_Ip;
        }
        leaf rp {
            type address_Ip;
        }

        // rp type ASM/Bidir
        // Inherited From rtmap:MatchIPMcast
        // Type is an MO-Defined-Type
        leaf rpType {
            description "rp type ASM/Bidir";

            // Type is an MO-Defined-Type
            type rtmap_rpTypeT;
        }
        leaf sourceAddr {
            type address_Ip;
        }
    }

    grouping rtmap_MatchIPv6Mcast-group {

        // From Interface naming:Named
        // Inherited From naming:NamedObject
        // Modified by Override: pol:Obj->name
        // Modified by Override: nw:FltRule->name
        // Modified by Override: rtmap:MatchIPMcast->name
        // Type is an MO-Defined-Type
        leaf name {
            description "Name";

            // Type is an MO-Defined-Type
            type naming_Name {
                length "0..64";
            }
        }

        // From Interface naming:Described
        // Inherited From pol:Instr
        // Modified by Override: rtmap:MatchIPMcast->descr
        // Type is an MO-Defined-Type
        leaf descr {
            config "false";
            description "descr";

            // Type is an MO-Defined-Type
            type naming_Descr {
                length "0..32";
            }
        }

        // Type
        // Inherited From rtmap:Match
        // Modified by Override: rtmap:MatchIPv6Mcast->type
        // Modified by Override: rtmap:MatchIPMcast->type
        // Type is an MO-Defined-Type
        leaf type {
            config "false";
            description "Type";

            // Type is an MO-Defined-Type
            type rtmap_MatchT;
        }
        leaf groupAddr {
            type address_Ip;
        }
        leaf groupStartAddr {
            type address_Ip;
        }
        leaf groupEndAddr {
            type address_Ip;
        }
        leaf rp {
            type address_Ip;
        }

        // rp type ASM/Bidir
        // Inherited From rtmap:MatchIPMcast
        // Type is an MO-Defined-Type
        leaf rpType {
            description "rp type ASM/Bidir";

            // Type is an MO-Defined-Type
            type rtmap_rpTypeT;
        }
        leaf sourceAddr {
            type address_Ip;
        }
    }

    grouping rtmap_MatchRtNh-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtNh->type
        // Type is an MO-Defined-Type
        leaf type {
            description "Type";

            // Type is an MO-Defined-Type
            type rtmap_MatchT;
        }

        // Rel-def from RtNhAtt
        container rsrtNhAtt-items {

            // Abstract containment of rsrtNhAtt derived from rtmap:MatchRtNh
            list RsRtNhAtt-list {
                key "tDn";

                // Added containment: Prefix=rsrtNhAtt
                // Acquired From Package rtmap
                uses rtmap_RsRtNhAtt_source-group;
            }
        }
    }

    grouping rtmap_MatchRtNhV6-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtNhV6->type
        // Type is an MO-Defined-Type
        leaf type {
            description "Type";

            // Type is an MO-Defined-Type
            type rtmap_MatchT;
        }

        // Rel-def from RtNhV6Att
        container rsrtNhV6Att-items {

            // Abstract containment of rsrtNhV6Att derived from rtmap:MatchRtNhV6
            list RsRtNhV6Att-list {
                key "tDn";

                // Added containment: Prefix=rsrtNhV6Att
                // Acquired From Package rtmap
                uses rtmap_RsRtNhV6Att_source-group;
            }
        }
    }

    grouping rtmap_MatchRtSrc-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtSrc->type
        // Type is an MO-Defined-Type
        leaf type {
            description "Type";

            // Type is an MO-Defined-Type
            type rtmap_MatchT;
        }

        // Rel-def from RtSrcAtt
        container rsrtSrcAtt-items {

            // Abstract containment of rsrtSrcAtt derived from rtmap:MatchRtSrc
            list RsRtSrcAtt-list {
                key "tDn";

                // Added containment: Prefix=rsrtSrcAtt
                // Acquired From Package rtmap
                uses rtmap_RsRtSrcAtt_source-group;
            }
        }
    }

    grouping rtmap_MatchRtSrcV6-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtSrcV6->type
        // Type is an MO-Defined-Type
        leaf type {
            description "Type";

            // Type is an MO-Defined-Type
            type rtmap_MatchT;
        }

        // Rel-def from RtSrcV6Att
        container rsrtSrcV6Att-items {

            // Abstract containment of rsrtSrcV6Att derived from rtmap:MatchRtSrcV6
            list RsRtSrcV6Att-list {
                key "tDn";

                // Added containment: Prefix=rsrtSrcV6Att
                // Acquired From Package rtmap
                uses rtmap_RsRtSrcV6Att_source-group;
            }
        }
    }

    grouping rtmap_MatchRtType-group {

        // Route types
        // Type is an MO-Defined-Type
        leaf routeT {
            description "Route Type";

            // Type is an MO-Defined-Type
            type rtmap_RouteT;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtType->type
        // Type is an MO-Defined-Type
        leaf type {
            description "Type";

            // Type is an MO-Defined-Type
            type rtmap_MatchT;
        }
    }

    grouping rtmap_MatchRtTag-group {

        // Route tag
        // Type is an MO-Defined-Type
        leaf tag {
            description "Route Tag";

            // Type is an MO-Defined-Type
            type rtmap_RouteTag;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtTag->type
        // Type is an MO-Defined-Type
        leaf type {
            description "Type";

            // Type is an MO-Defined-Type
            type rtmap_MatchT;
        }
    }

    grouping rtmap_MatchSrcProto-group {
        leaf proto {
            type string {
                length "1..32";
            }
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchSrcProto->type
        // Type is an MO-Defined-Type
        leaf type {
            description "Type";

            // Type is an MO-Defined-Type
            type rtmap_MatchT;
        }
    }

    grouping rtmap_MatchRtPervasive-group {

        // Route pervasive
        // Type is an MO-Defined-Type
        leaf pervasive {
            description "Pervasive";

            // Type is an MO-Defined-Type
            type rtmap_RoutePervasive;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtPervasive->type
        // Type is an MO-Defined-Type
        leaf type {
            description "Type";

            // Type is an MO-Defined-Type
            type rtmap_MatchT;
        }
    }

    grouping rtmap_MatchAsPathAccessList-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchAsPathAccessList->type
        // Type is an MO-Defined-Type
        leaf type {
            description "Type";

            // Type is an MO-Defined-Type
            type rtmap_MatchT;
        }

        // Rel-def from RtAsPathAccAtt
        container rsrtAsPathAccAtt-items {

            // Abstract containment of rsrtAsPathAccAtt derived from rtmap:MatchAsPathAccessList
            list RsRtAsPathAccAtt-list {
                key "tDn";

                // Added containment: Prefix=rsrtAsPathAccAtt
                // Acquired From Package rtmap
                uses rtmap_RsRtAsPathAccAtt_source-group;
            }
        }
    }

    grouping rtmap_MatchRtMetric-group {

        // Route metric measure
        // Type is an MO-Defined-Type
        leaf measure {
            description "Route Metric Measure";

            // Type is an MO-Defined-Type
            type rtmap_CommunityVal;
        }

        // Route metric deviation
        // Type is an MO-Defined-Type
        leaf deviation {
            description "Route Metric Deviation";

            // Type is an MO-Defined-Type
            type rtmap_CommunityVal;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtMetric->type
        // Type is an MO-Defined-Type
        leaf type {
            description "Type";

            // Type is an MO-Defined-Type
            type rtmap_MatchT;
        }
    }

    grouping rtmap_MatchRtAsn-group {
        leaf asn {
            type string;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtAsn->type
        // Type is an MO-Defined-Type
        leaf type {
            description "Type";

            // Type is an MO-Defined-Type
            type rtmap_MatchT;
        }
    }

    grouping rtmap_MatchRtIf-group {

        // Route asn
        // Type is an MO-Defined-Type
        leaf id {
            description "Route If";

            // Type is an MO-Defined-Type
            type nw_IfId;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtIf->type
        // Type is an MO-Defined-Type
        leaf type {
            description "Type";

            // Type is an MO-Defined-Type
            type rtmap_MatchT;
        }
    }

    grouping rtmap_MatchRtOspf-group {

        // Route ospf
        // Type is an MO-Defined-Type
        leaf area {
            description "OSPF Area";

            // Type is an MO-Defined-Type
            type rtmap_OSPFArea;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Match
        // Modified by Override: rtmap:MatchRtOspf->type
        // Type is an MO-Defined-Type
        leaf type {
            description "Type";

            // Type is an MO-Defined-Type
            type rtmap_MatchT;
        }
    }

    grouping rtmap_Continue-group {

        // Continue
        // Type is an MO-Defined-Type
        leaf continue {
            description "continue";

            // Type is an MO-Defined-Type
            type rtmap_Order;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:Continue->type
        // Type is an MO-Defined-Type
        leaf type {
            description "Type";

            // Type is an MO-Defined-Type
            type rtmap_SetT;
        }
    }

    grouping rtmap_SetRegComm-group {

        // Add To Existing Community
        // Type is an MO-Defined-Type
        leaf additive {
            description "Add To Existing Community";

            // Type is an MO-Defined-Type
            type rtmap_AdminSt;
        }

        // No Community Attribute
        // Type is an MO-Defined-Type
        leaf noCommAttr {
            description "No Community Attribute";

            // Type is an MO-Defined-Type
            type rtmap_AdminSt;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetRegComm->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }

        // List of community values
        container scomm-items {
            list SetCommItem-list {
                key "community";

                // Added containment: Prefix=scomm
                // Acquired From Package rtmap
                uses rtmap_SetCommItem-group;
            }
        }

        // Item in the community list
        container item-items {
            list Item-list {
                key "community";

                // Added containment: Prefix=item
                // Acquired From Package rtregcom
                uses rtregcom_Item-group;
            }
        }
    }

    grouping rtmap_SetCommItem-group {
        leaf community {
            type mtx_array_community;
        }
    }

    grouping rtregcom_Item-group {

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf community {
            type mtx_array_community;
        }
    }

    grouping rtmap_SetExtComm-group {

        // Add To Existing Community
        // Type is an MO-Defined-Type
        leaf additive {
            description "Add To Existing Community";

            // Type is an MO-Defined-Type
            type rtmap_AdminSt;
        }

        // No Community Attribute
        // Type is an MO-Defined-Type
        leaf noCommAttr {
            description "No Community Attribute";

            // Type is an MO-Defined-Type
            type rtmap_AdminSt;
        }

        // Type is an MO-Defined-Type
        leaf scope {
            description "Scope";

            // Type is an MO-Defined-Type
            type rtextcom_Scope;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetExtComm->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }

        // Item in the community list
        container item-items {
            list Item-list {
                key "scope community";

                // Added containment: Prefix=item
                // Acquired From Package rtextcom
                uses rtextcom_Item-group;
            }
        }

        // List of community values
        container scomm-items {
            list SetCommItem-list {
                key "community";

                // Added containment: Prefix=scomm
                // Acquired From Package rtmap
                uses rtmap_SetCommItem-group;
            }
        }
    }

    grouping rtmap_SetExtCommCost-group {

        // Set criteria for IGP or Pre-bestpath
        // Type is an MO-Defined-Type
        leaf commCrit {
            description "Criteria";

            // Type is an MO-Defined-Type
            type rtmap_SetCriteria;
        }

        // Community Id
        // Type is an MO-Defined-Type
        leaf commId {
            description "Community Id";

            // Type is an MO-Defined-Type
            type rtmap_CommunityId;
        }

        // Community Value
        // Type is an MO-Defined-Type
        leaf commValue {
            description "Community Value";

            // Type is an MO-Defined-Type
            type rtmap_CommunityVal;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetExtCommCost->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }
    }

    grouping rtmap_SetCommList-group {

        // Delete Matching Communities
        // Type is an MO-Defined-Type
        leaf delete {
            description "Delete Matching Communities";

            // Type is an MO-Defined-Type
            type rtmap_AdminSt;
        }

        // From Interface naming:Named
        // Inherited From naming:NamedObject
        // Modified by Override: rtmap:SetCommList->name
        // Modified by Override: pol:Obj->name
        // Modified by Override: nw:FltRule->name
        // Type is an MO-Defined-Type
        leaf name {
            description "Name";

            // Type is an MO-Defined-Type
            type naming_Name {
                length "1..63";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetCommList->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }
    }

    grouping rtmap_SetExtCommList-group {

        // Delete Matching Communities
        // Type is an MO-Defined-Type
        leaf delete {
            description "Delete Matching Ext Communities";

            // Type is an MO-Defined-Type
            type rtmap_AdminSt;
        }

        // From Interface naming:Named
        // Inherited From naming:NamedObject
        // Modified by Override: rtmap:SetExtCommList->name
        // Modified by Override: pol:Obj->name
        // Modified by Override: nw:FltRule->name
        // Type is an MO-Defined-Type
        leaf name {
            description "Name";

            // Type is an MO-Defined-Type
            type naming_Name {
                length "1..63";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetExtCommList->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }
    }

    grouping rtmap_SetRttComm-group {

        // Add To Existing Community
        // Type is an MO-Defined-Type
        leaf additive {
            description "Add To Existing Community";

            // Type is an MO-Defined-Type
            type rtmap_AdminSt;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetRttComm->type
        // Type is an MO-Defined-Type
        leaf type {
            description "Type";

            // Type is an MO-Defined-Type
            type rtmap_SetT;
        }

        // Set criteria
        // Inherited From rtmap:SetComm
        // Type is an MO-Defined-Type
        leaf setCriteria {
            description "Criteria";

            // Type is an MO-Defined-Type
            type rtmap_SetCriteria;
        }

        // Item in the community list
        container item-items {
            list Item-list {
                key "scope community";

                // Added containment: Prefix=item
                // Acquired From Package rtextcom
                uses rtextcom_Item-group;
            }
        }

        // List of community values
        container scomm-items {
            list SetCommItem-list {
                key "community";

                // Added containment: Prefix=scomm
                // Acquired From Package rtmap
                uses rtmap_SetCommItem-group;
            }
        }
    }

    grouping rtmap_SetRtDist-group {

        // Route Administrative Distance for IGP or EBGP
        // Type is an MO-Defined-Type
        leaf dist {
            description "Distance";

            // Type is an MO-Defined-Type
            type rtmap_RouteDist;
        }

        // Route Administrative Distance for Internal
        // Type is an MO-Defined-Type
        leaf distI {
            description "Distance internal";

            // Type is an MO-Defined-Type
            type rtmap_RouteDist;
        }

        // Route Administrative Distance for local
        // Type is an MO-Defined-Type
        leaf distL {
            description "Distance local";

            // Type is an MO-Defined-Type
            type rtmap_RouteDist;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetRtDist->type
        // Type is an MO-Defined-Type
        leaf type {
            description "Type";

            // Type is an MO-Defined-Type
            type rtmap_SetT;
        }
    }

    grouping rtmap_SetRtTag-group {

        // Tag value
        // Type is an MO-Defined-Type
        leaf tag {
            description "Tag";

            // Type is an MO-Defined-Type
            type rtmap_RouteTag;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetRtTag->type
        // Type is an MO-Defined-Type
        leaf type {
            description "Type";

            // Type is an MO-Defined-Type
            type rtmap_SetT;
        }
    }

    grouping rtmap_SetWeight-group {

        // Weight value
        // Type is an MO-Defined-Type
        leaf weight {
            description "Weight";

            // Type is an MO-Defined-Type
            type rtmap_Weight;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetWeight->type
        // Type is an MO-Defined-Type
        leaf type {
            description "Type";

            // Type is an MO-Defined-Type
            type rtmap_SetT;
        }
    }

    grouping rtmap_SetLabelIndex-group {

        // Label Index value
        // Type is an MO-Defined-Type
        leaf index {
            description "Label Index";

            // Type is an MO-Defined-Type
            type rtmap_Index;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetLabelIndex->type
        // Type is an MO-Defined-Type
        leaf type {
            description "Type";

            // Type is an MO-Defined-Type
            type rtmap_SetT;
        }
    }

    grouping rtmap_SetPref-group {

        // Preference value
        // Type is an MO-Defined-Type
        leaf localPref {
            description "Local Preference";

            // Type is an MO-Defined-Type
            type rtmap_LocalPref;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetPref->type
        // Type is an MO-Defined-Type
        leaf type {
            description "Type";

            // Type is an MO-Defined-Type
            type rtmap_SetT;
        }
    }

    grouping rtmap_SetMetric-group {

        // Metric value for bandwidth
        // Type is an MO-Defined-Type
        leaf metric {
            description "Metric";

            // Type is an MO-Defined-Type
            type rtmap_MetricS;
        }

        // Metric value for delay
        // Type is an MO-Defined-Type
        leaf metricD {
            description "Metric delay";

            // Type is an MO-Defined-Type
            type rtmap_MetricD;
        }

        // Metric value for reliability
        // Type is an MO-Defined-Type
        leaf metricR {
            description "Metric rlblty";

            // Type is an MO-Defined-Type
            type rtmap_MetricR;
        }

        // Metric value for load
        // Type is an MO-Defined-Type
        leaf metricL {
            description "Metric load";

            // Type is an MO-Defined-Type
            type rtmap_MetricL;
        }

        // Metric value for mtu
        // Type is an MO-Defined-Type
        leaf metricM {
            description "Metric mtu";

            // Type is an MO-Defined-Type
            type rtmap_MetricM;
        }

        // is BGP config
        // Type is an MO-Defined-Type
        leaf isBGP {
            description "is BGP config";

            // Type is an MO-Defined-Type
            type rtmap_Proto;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetMetric->type
        // Type is an MO-Defined-Type
        leaf type {
            description "Type";

            // Type is an MO-Defined-Type
            type rtmap_SetT;
        }
    }

    grouping rtmap_SetMetricType-group {

        // Metric Type
        // Type is an MO-Defined-Type
        leaf metricT {
            description "Metric Type";

            // Type is an MO-Defined-Type
            type rtmap_MetricT;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetMetricType->type
        // Type is an MO-Defined-Type
        leaf type {
            description "Type";

            // Type is an MO-Defined-Type
            type rtmap_SetT;
        }
    }

    grouping rtmap_SetDampeningType-group {

        // Dampening Halflife
        // Type is an MO-Defined-Type
        leaf halflife {
            description "Dampening Halfife";

            // Type is an MO-Defined-Type
            type rtmap_HalfLife;
        }

        // Dampening Reuse
        // Type is an MO-Defined-Type
        leaf reuse {
            description "Dampening Reuse";

            // Type is an MO-Defined-Type
            type rtmap_Reuse;
        }

        // Dampening Supress
        // Type is an MO-Defined-Type
        leaf supress {
            description "Dampening Supress";

            // Type is an MO-Defined-Type
            type rtmap_Supress;
        }

        // Dampening Duration
        // Type is an MO-Defined-Type
        leaf duration {
            description "Dampening Duration";

            // Type is an MO-Defined-Type
            type rtmap_Duration;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetDampeningType->type
        // Type is an MO-Defined-Type
        leaf type {
            description "Type";

            // Type is an MO-Defined-Type
            type rtmap_SetT;
        }
    }

    grouping rtmap_SetPrecedence-group {

        // Precedence Name
        // Type is an MO-Defined-Type
        leaf precname {
            description "Precedence Name";

            // Type is an MO-Defined-Type
            type rtmap_PrecName;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetPrecedence->type
        // Type is an MO-Defined-Type
        leaf type {
            description "Type";

            // Type is an MO-Defined-Type
            type rtmap_SetT;
        }
    }

    grouping rtmap_SetV6Precedence-group {

        // Precedence Name
        // Type is an MO-Defined-Type
        leaf precname {
            description "Precedence Name";

            // Type is an MO-Defined-Type
            type rtmap_PrecName;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetV6Precedence->type
        // Type is an MO-Defined-Type
        leaf type {
            description "Type";

            // Type is an MO-Defined-Type
            type rtmap_SetT;
        }
    }

    grouping rtmap_SetOspfNssa-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetOspfNssa->type
        // Type is an MO-Defined-Type
        leaf type {
            description "Type";

            // Type is an MO-Defined-Type
            type rtmap_SetT;
        }
    }

    grouping rtmap_SetOspfFwdAddr-group {
        leaf fwdAddr {
            type address_Ip;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetOspfFwdAddr->type
        // Type is an MO-Defined-Type
        leaf type {
            description "Type";

            // Type is an MO-Defined-Type
            type rtmap_SetT;
        }
    }

    grouping rtmap_SetNh-group {
        leaf addr {
            type address_Ip;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetNh->type
        // Type is an MO-Defined-Type
        leaf type {
            description "Type";

            // Type is an MO-Defined-Type
            type rtmap_SetT;
        }
    }

    grouping rtmap_SetNhPeerAddr-group {

        // IPv4 Next hop peer address
        // Type is an MO-Defined-Type
        leaf v4PeerAddr {
            description "Set Next Hop V4 Peer Address";

            // Type is an MO-Defined-Type
            type rtmap_AdminSt;
        }

        // IPv6 Next hop peer address
        // Type is an MO-Defined-Type
        leaf v6PeerAddr {
            description "Set Next Hop V6 Peer Address";

            // Type is an MO-Defined-Type
            type rtmap_AdminSt;
        }

        // IPv4 Next hop Unchanged
        // Type is an MO-Defined-Type
        leaf v4Unchange {
            description "Set IPv4 Next Hop Unchanged";

            // Type is an MO-Defined-Type
            type rtmap_AdminSt;
        }

        // IPv6 Next hop Unchanged
        // Type is an MO-Defined-Type
        leaf v6Unchange {
            description "Set IPv6 Next Hop Unchanged";

            // Type is an MO-Defined-Type
            type rtmap_AdminSt;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetNhPeerAddr->type
        // Type is an MO-Defined-Type
        leaf type {
            description "Type";

            // Type is an MO-Defined-Type
            type rtmap_SetT;
        }
    }

    grouping rtmap_SetPrepend-group {
        leaf as {
            type string;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetPrepend->type
        // Type is an MO-Defined-Type
        leaf type {
            description "Type";

            // Type is an MO-Defined-Type
            type rtmap_SetT;
        }
    }

    grouping rtmap_SetPrependLastAs-group {

        // As Path Last As
        // Type is an MO-Defined-Type
        leaf lastas {
            description "LastAs";

            // Type is an MO-Defined-Type
            type rtmap_RouteLastAs;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetPrependLastAs->type
        // Type is an MO-Defined-Type
        leaf type {
            description "Type";

            // Type is an MO-Defined-Type
            type rtmap_SetT;
        }
    }

    grouping rtmap_SetAsPathTag-group {

        // Set as path
        // Type is an MO-Defined-Type
        leaf tag {
            description "Set as path tag";

            // Type is an MO-Defined-Type
            type rtmap_AdminSt;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetAsPathTag->type
        // Type is an MO-Defined-Type
        leaf type {
            description "Type";

            // Type is an MO-Defined-Type
            type rtmap_SetT;
        }
    }

    grouping rtmap_SetOrigin-group {

        // Metric Type
        // Type is an MO-Defined-Type
        leaf originT {
            description "Origin Type";

            // Type is an MO-Defined-Type
            type rtmap_OriginT;
        }

        // Remote ASN
        // Type is an MO-Defined-Type
        leaf asn {
            description "Autonomous System Number";

            // Type is an MO-Defined-Type
            type rtcom_AS;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type
        // Inherited From rtmap:Set
        // Modified by Override: rtmap:SetOrigin->type
        // Type is an MO-Defined-Type
        leaf type {
            description "Type";

            // Type is an MO-Defined-Type
            type rtmap_SetT;
        }
    }

    grouping rtmap_ExpandedComList-group {
        leaf regex {
            type string {
                length "0..63";
            }
        }
        leaf expcommname {
            type string {
                length "0..63";
            }
        }

        // Deny or Permit
        // Type is an MO-Defined-Type
        leaf action {
            description "Action";

            // Type is an MO-Defined-Type
            type rtmap_Action;
        }

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping rtpfx_RuleV4-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Modified by Override: rtpfx:RuleV4->descr
        // Type is an MO-Defined-Type
        leaf descr {
            description "descr";

            // Type is an MO-Defined-Type
            type naming_Descr {
                length "0..90";
            }
        }

        // Prefix list entry definition
        container ent-items {
            list Entry-list {
                key "order";

                // Added containment: Prefix=ent
                // Acquired From Package rtpfx
                uses rtpfx_Entry-group;
            }
        }

        // Rel-def target from RtDstAtt
        // Inherited From rtpfx:RuleV4
        container rtrtmapRtDstAtt-items {

            // Abstract containment of rtrtmapRtDstAtt derived from rtpfx:Rule
            list RtRtmapRtDstAtt-list {
                key "tDn";

                // Added containment: Prefix=rtrtmapRtDstAtt
                // Acquired From Package rtmap
                uses rtmap_RtRtmapRtDstAtt_target-group;
            }
        }

        // Rel-def target from RtDstV6Att
        // Inherited From rtpfx:RuleV4
        container rtrtmapRtDstV6Att-items {

            // Abstract containment of rtrtmapRtDstV6Att derived from rtpfx:Rule
            list RtRtmapRtDstV6Att-list {
                key "tDn";

                // Added containment: Prefix=rtrtmapRtDstV6Att
                // Acquired From Package rtmap
                uses rtmap_RtRtmapRtDstV6Att_target-group;
            }
        }

        // Rel-def target from RtNhAtt
        // Inherited From rtpfx:RuleV4
        container rtrtmapRtNhAtt-items {

            // Abstract containment of rtrtmapRtNhAtt derived from rtpfx:Rule
            list RtRtmapRtNhAtt-list {
                key "tDn";

                // Added containment: Prefix=rtrtmapRtNhAtt
                // Acquired From Package rtmap
                uses rtmap_RtRtmapRtNhAtt_target-group;
            }
        }

        // Rel-def target from RtNhV6Att
        // Inherited From rtpfx:RuleV4
        container rtrtmapRtNhV6Att-items {

            // Abstract containment of rtrtmapRtNhV6Att derived from rtpfx:Rule
            list RtRtmapRtNhV6Att-list {
                key "tDn";

                // Added containment: Prefix=rtrtmapRtNhV6Att
                // Acquired From Package rtmap
                uses rtmap_RtRtmapRtNhV6Att_target-group;
            }
        }

        // Rel-def target from RtSrcAtt
        // Inherited From rtpfx:RuleV4
        container rtrtmapRtSrcAtt-items {

            // Abstract containment of rtrtmapRtSrcAtt derived from rtpfx:Rule
            list RtRtmapRtSrcAtt-list {
                key "tDn";

                // Added containment: Prefix=rtrtmapRtSrcAtt
                // Acquired From Package rtmap
                uses rtmap_RtRtmapRtSrcAtt_target-group;
            }
        }

        // Rel-def target from RtSrcV6Att
        // Inherited From rtpfx:RuleV4
        container rtrtmapRtSrcV6Att-items {

            // Abstract containment of rtrtmapRtSrcV6Att derived from rtpfx:Rule
            list RtRtmapRtSrcV6Att-list {
                key "tDn";

                // Added containment: Prefix=rtrtmapRtSrcV6Att
                // Acquired From Package rtmap
                uses rtmap_RtRtmapRtSrcV6Att_target-group;
            }
        }
    }

    grouping rtpfx_Entry-group {
        leaf pfx {
            type address_Ip;
        }
        leaf mask {
            type address_Ip;
        }

        // criteria, exact match or inexact match
        // Type is an MO-Defined-Type
        leaf criteria {
            description "Criteria";

            // Type is an MO-Defined-Type
            type rtpfx_Criteria;
        }

        // If the criteria is not an exact match, use a range to
        // describe the prefix list range
        // Type is an MO-Defined-Type
        leaf fromPfxLen {
            description "Start of Prefix Length";

            // Type is an MO-Defined-Type
            type l3_IpPfxLen;
        }

        // Type is an MO-Defined-Type
        leaf toPfxLen {
            description "End of Prefix Length";

            // Type is an MO-Defined-Type
            type l3_IpPfxLen;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
    }

    grouping rtpfx_RuleV6-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Modified by Override: rtpfx:RuleV6->descr
        // Type is an MO-Defined-Type
        leaf descr {
            description "descr";

            // Type is an MO-Defined-Type
            type naming_Descr {
                length "0..90";
            }
        }

        // Prefix list entry definition
        container ent-items {
            list Entry-list {
                key "order";

                // Added containment: Prefix=ent
                // Acquired From Package rtpfx
                uses rtpfx_Entry-group;
            }
        }

        // Rel-def target from RtDstAtt
        // Inherited From rtpfx:RuleV4
        // Inherited From rtpfx:RuleV6
        container rtrtmapRtDstAtt-items {

            // Abstract containment of rtrtmapRtDstAtt derived from rtpfx:Rule
            list RtRtmapRtDstAtt-list {
                key "tDn";

                // Added containment: Prefix=rtrtmapRtDstAtt
                // Acquired From Package rtmap
                uses rtmap_RtRtmapRtDstAtt_target-group;
            }
        }

        // Rel-def target from RtDstV6Att
        // Inherited From rtpfx:RuleV4
        // Inherited From rtpfx:RuleV6
        container rtrtmapRtDstV6Att-items {

            // Abstract containment of rtrtmapRtDstV6Att derived from rtpfx:Rule
            list RtRtmapRtDstV6Att-list {
                key "tDn";

                // Added containment: Prefix=rtrtmapRtDstV6Att
                // Acquired From Package rtmap
                uses rtmap_RtRtmapRtDstV6Att_target-group;
            }
        }

        // Rel-def target from RtNhAtt
        // Inherited From rtpfx:RuleV4
        // Inherited From rtpfx:RuleV6
        container rtrtmapRtNhAtt-items {

            // Abstract containment of rtrtmapRtNhAtt derived from rtpfx:Rule
            list RtRtmapRtNhAtt-list {
                key "tDn";

                // Added containment: Prefix=rtrtmapRtNhAtt
                // Acquired From Package rtmap
                uses rtmap_RtRtmapRtNhAtt_target-group;
            }
        }

        // Rel-def target from RtNhV6Att
        // Inherited From rtpfx:RuleV4
        // Inherited From rtpfx:RuleV6
        container rtrtmapRtNhV6Att-items {

            // Abstract containment of rtrtmapRtNhV6Att derived from rtpfx:Rule
            list RtRtmapRtNhV6Att-list {
                key "tDn";

                // Added containment: Prefix=rtrtmapRtNhV6Att
                // Acquired From Package rtmap
                uses rtmap_RtRtmapRtNhV6Att_target-group;
            }
        }

        // Rel-def target from RtSrcAtt
        // Inherited From rtpfx:RuleV4
        // Inherited From rtpfx:RuleV6
        container rtrtmapRtSrcAtt-items {

            // Abstract containment of rtrtmapRtSrcAtt derived from rtpfx:Rule
            list RtRtmapRtSrcAtt-list {
                key "tDn";

                // Added containment: Prefix=rtrtmapRtSrcAtt
                // Acquired From Package rtmap
                uses rtmap_RtRtmapRtSrcAtt_target-group;
            }
        }

        // Rel-def target from RtSrcV6Att
        // Inherited From rtpfx:RuleV4
        // Inherited From rtpfx:RuleV6
        container rtrtmapRtSrcV6Att-items {

            // Abstract containment of rtrtmapRtSrcV6Att derived from rtpfx:Rule
            list RtRtmapRtSrcV6Att-list {
                key "tDn";

                // Added containment: Prefix=rtrtmapRtSrcV6Att
                // Acquired From Package rtmap
                uses rtmap_RtRtmapRtSrcV6Att_target-group;
            }
        }
    }

    grouping rtregcom_Rule-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type of the community list [regular | extended]
        // Inherited From rtcom:Rule
        // Modified by Override: rtregcom:Rule->type
        // Type is an MO-Defined-Type
        leaf type {
            description "Type";

            // Type is an MO-Defined-Type
            type rtcom_ComT;
        }

        // Mode
        // Inherited From rtcom:Rule
        // Type is an MO-Defined-Type
        leaf mode {
            description "Mode";

            // Type is an MO-Defined-Type
            type rtcom_Mode;
        }

        // Regular community list entry
        container ent-items {
            list Entry-list {
                key "order";

                // Added containment: Prefix=ent
                // Acquired From Package rtregcom
                uses rtregcom_Entry-group;
            }
        }

        // Rel-def target from RegCommAtt
        // Inherited From rtregcom:Rule
        container rtRegCommAtt-items {

            // Added containment as a singleton: Prefix=rtRegCommAtt
            // Acquired From Package rtmap
            uses rtmap_RtRegCommAtt_target-group;
        }
    }

    grouping rtregcom_Entry-group {

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }

        // Item in the community list
        container item-items {
            list Item-list {
                key "community";

                // Added containment: Prefix=item
                // Acquired From Package rtregcom
                uses rtregcom_Item-group;
            }
        }
    }

    grouping srcintf_Entity-group {
        container dns-items {
            list DnsSrcIf-list {
                key "vrf";

                // Added containment: Prefix=dns
                // Acquired From Package srcintf
                uses srcintf_DnsSrcIf-group;
            }
        }
        container tftp-items {
            list Tftp-list {
                key "vrf";

                // Added containment: Prefix=tftp
                // Acquired From Package srcintf
                uses srcintf_Tftp-group;
            }
        }
    }

    grouping srcintf_DnsSrcIf-group {

        // Source interface
        // Inherited From srcintf:SrcIf
        // Modified by Override: srcintf:DnsSrcIf->srcIf
        // Type is an MO-Defined-Type
        leaf srcIf {
            description "Source Interface";

            // Type is an MO-Defined-Type
            type nw_IfId;
        }

        // vrf name
        // Inherited From srcintf:SrcIf
        // Modified by Override: srcintf:DnsSrcIf->vrf
        // Type is an MO-Defined-Type
        leaf vrf {
            description "VRF";

            // Type is an MO-Defined-Type
            type l3_VrfName;
        }
    }

    grouping srcintf_Tftp-group {

        // Source interface
        // Inherited From srcintf:SrcIf
        // Modified by Override: srcintf:Tftp->srcIf
        // Type is an MO-Defined-Type
        leaf srcIf {
            description "Source Interface";

            // Type is an MO-Defined-Type
            type nw_IfId;
        }

        // vrf name
        // Inherited From srcintf:SrcIf
        // Modified by Override: srcintf:Tftp->vrf
        // Type is an MO-Defined-Type
        leaf vrf {
            description "VRF";

            // Type is an MO-Defined-Type
            type l3_VrfName;
        }
    }

    grouping sysmgr_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // System state
        container sys-items {

            // Added containment as a singleton: Prefix=sys
            // Acquired From Package sysmgr
            uses sysmgr_SysSt-group;
        }

        // Holds sysmgr control plane entity information
        container sysCfg-items {

            // Added containment as a singleton: Prefix=sysCfg
            // Acquired From Package sysmgr
            uses sysmgr_SysCfgSt-group;
        }

        // Holder for cores policy
        container core-items {
            list Cores-list {
                config "false";
                key "dest";

                // Added containment: Prefix=core
                // Acquired From Package sysmgrp
                uses sysmgrp_Cores-group;
            }
        }
    }

    grouping sysmgr_SysSt-group {

        // redundancy mode
        // Type is an MO-Defined-Type
        leaf rdMode {
            config "false";
            description "Redundancy Mode";

            // Type is an MO-Defined-Type
            type sysmgr_RdMode;
        }

        // From Interface naming:Named
        // Inherited From naming:NamedObject
        // Type is an MO-Defined-Type
        leaf name {
            description "Name";

            // Type is an MO-Defined-Type
            type naming_Name;
        }

        // Sup state
        container sup-items {
            list SupSt-list {
                config "false";
                key "type";

                // Added containment: Prefix=sup
                // Acquired From Package sysmgr
                uses sysmgr_SupSt-group;
            }
        }

        // Firmware state
        container image-items {
            list FwSt-list {
                config "false";
                key "type";

                // Added containment: Prefix=image
                // Acquired From Package sysmgr
                uses sysmgr_FwSt-group;
            }
        }
    }

    grouping sysmgr_SupSt-group {

        // Local/Remote
        // Type is an MO-Defined-Type
        leaf type {
            config "false";
            description "Type";

            // Type is an MO-Defined-Type
            type sysmgr_SupT;
        }

        // Oper state
        // Type is an MO-Defined-Type
        leaf operSt {
            config "false";
            description "Operational State";

            // Type is an MO-Defined-Type
            type sysmgr_SupSt;
        }

        // Redundancy state
        // Type is an MO-Defined-Type
        leaf rdSt {
            config "false";
            description "Redundancy State";

            // Type is an MO-Defined-Type
            type sysmgr_RdSt;
        }

        // From Interface naming:Named
        // Inherited From naming:NamedObject
        // Type is an MO-Defined-Type
        leaf name {
            description "Name";

            // Type is an MO-Defined-Type
            type naming_Name;
        }
    }

    grouping sysmgr_FwSt-group {

        // Type of the firmware
        // Type is an MO-Defined-Type
        leaf type {
            config "false";
            description "Type";

            // Type is an MO-Defined-Type
            type sysmgr_FwT;
        }

        // Version
        // Type is an MO-Defined-Type
        leaf ver {
            config "false";
            description "Version";

            // Type is an MO-Defined-Type
            type sysmgr_FwVer;
        }

        // The firmware mode in which we are running, either
        // it is recovery or regular mode
        // Type is an MO-Defined-Type
        leaf mode {
            config "false";
            description "Mode";

            // Type is an MO-Defined-Type
            type sysmgr_FwMode;
        }

        // From Interface naming:Named
        // Inherited From naming:NamedObject
        // Type is an MO-Defined-Type
        leaf name {
            description "Name";

            // Type is an MO-Defined-Type
            type naming_Name;
        }
    }

    grouping sysmgr_SysCfgSt-group {

        // configuration mode
        // Type is an MO-Defined-Type
        leaf cfgMode {
            config "false";
            description "Configuration Mode";

            // Type is an MO-Defined-Type
            type sysmgr_CfgMode;
        }

        // operational data mode
        // Type is an MO-Defined-Type
        leaf operDataMode {
            config "false";
            description "Operational Data Mode";

            // Type is an MO-Defined-Type
            type sysmgr_OperDataMode;
        }
    }

    grouping sysmgrp_Cores-group {
        leaf dest {
            config "false";
            type string;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping tcpudp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per tcpudp instance information. There is
        // only one instance of tcpudp running in the system today
        container inst-items {

            // Added containment as a singleton: Prefix=inst
            // Acquired From Package tcpudp
            uses tcpudp_Inst-group;
        }
    }

    grouping tcpudp_Inst-group {

        // Set time to wait on new TCP connections
        // Type is an MO-Defined-Type
        leaf synWaitTime {
            description "Set time to wait on new TCP connections";

            // Type is an MO-Defined-Type
            type tcpudp_SynwaitTime;
        }

        // Enable path-MTU discovery on TCP
        // Type is an MO-Defined-Type
        leaf pathMtuDiscovery {
            description "Enable path-MTU discovery on TCP";

            // Type is an MO-Defined-Type
            type nw_AdminSt;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    grouping terminal_Terminal-group {

        // Line MO is the MO inside which type of line either vty or console
        // would be organize
        container ln-items {

            // Added containment as a singleton: Prefix=ln
            // Acquired From Package terminal
            uses terminal_Line-group;
        }
    }

    grouping terminal_Line-group {

        // Console MO is to consolidate the console specific MO and its
        // properties which is propretary for the vsh session which is
        // spawned via console port
        container cons-items {

            // Added containment as a singleton: Prefix=cons
            // Acquired From Package terminal
            uses terminal_Console-group;
        }

        // VTY MO is to consolidate the VTY specific MO and its
        // properties which is propretary for the vsh session which is
        // spawned via mgmt/telnet ip to box
        container vty-items {

            // Added containment as a singleton: Prefix=vty
            // Acquired From Package terminal
            uses terminal_Vty-group;
        }
    }

    grouping terminal_Console-group {

        // Organizes the exec timeout specific properties
        container execTmeout-items {

            // Added containment as a singleton: Prefix=execTmeout
            // Acquired From Package terminal
            uses terminal_ExecTimeout-group;
        }

        // Organizes the console terminal width specific properties
        container wdth-items {

            // Added containment as a singleton: Prefix=wdth
            // Acquired From Package terminal
            uses terminal_Width-group;
        }

        // Organizes the console terminal length specific properties
        container lgth-items {

            // Added containment as a singleton: Prefix=lgth
            // Acquired From Package terminal
            uses terminal_Length-group;
        }
    }

    grouping terminal_ExecTimeout-group {

        // Inherited From terminal:Timeout
        // Type is an MO-Defined-Type
        leaf timeout {
            description "Timeout";

            // Type is an MO-Defined-Type
            type terminal_TimeoutT;
        }
    }

    grouping terminal_Width-group {

        // Type is an MO-Defined-Type
        leaf termwidth {
            description "terminal width";

            // Type is an MO-Defined-Type
            type terminal_TermSize {
                range "51..511";
            }
        }
    }

    grouping terminal_Length-group {

        // Type is an MO-Defined-Type
        leaf termlength {
            description "terminal length";

            // Type is an MO-Defined-Type
            type terminal_TermSize {
                range "0..511";
            }
        }
    }

    grouping terminal_Vty-group {

        // Organizes the exec timeout specific properties
        container execTmeout-items {

            // Added containment as a singleton: Prefix=execTmeout
            // Acquired From Package terminal
            uses terminal_ExecTimeout-group;
        }

        // Organizes the VTY session's absolute timeout specific properties
        container absTmeout-items {

            // Added containment as a singleton: Prefix=absTmeout
            // Acquired From Package terminal
            uses terminal_AbsTimeout-group;
        }

        // Organizes the VTY session's limit specific properties
        container ssLmt-items {

            // Added containment as a singleton: Prefix=ssLmt
            // Acquired From Package terminal
            uses terminal_SesLmt-group;
        }

        // Organizes the VTY session's logout warning specific properties
        container lgoutWarning-items {

            // Added containment as a singleton: Prefix=lgoutWarning
            // Acquired From Package terminal
            uses terminal_LogoutWarning-group;
        }
    }

    grouping terminal_AbsTimeout-group {

        // Inherited From terminal:Timeout
        // Type is an MO-Defined-Type
        leaf timeout {
            description "Timeout";

            // Type is an MO-Defined-Type
            type terminal_TimeoutT;
        }
    }

    grouping terminal_SesLmt-group {

        // Type is an MO-Defined-Type
        leaf sesLmt {
            description "session limit";

            // Type is an MO-Defined-Type
            type terminal_Limit {
                range "1..64";
            }
        }
    }

    grouping terminal_LogoutWarning-group {

        // Type is an MO-Defined-Type
        leaf lgtWarn {
            description "logout warning";

            // Type is an MO-Defined-Type
            type terminal_Limit {
                range "0..60";
            }
        }
    }

    grouping terminal_TerminalLog-group {
        leaf logShowCommand {
            type boolean;
        }
    }

    grouping test_CRule-group {

        // Prof. Name
        // Type is an MO-Defined-Type
        leaf peChunkName {
            config "false";
            description "Secondary Chunk Name";

            // Type is an MO-Defined-Type
            type naming_Name;
        }

        // Type is an MO-Defined-Type
        leaf testclientChunkName {
            config "false";
            description "Secondary Chunk Name";

            // Type is an MO-Defined-Type
            type naming_Name;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Trigger of this test
        // Inherited From test:Rule
        // Type is an MO-Defined-Type
        leaf trig {
            config "false";
            description "Trigger";

            // Type is an MO-Defined-Type
            type test_Trig;
        }

        // Test frequency
        // Inherited From test:Rule
        // Type is an MO-Defined-Type
        leaf freq {
            config "false";
            description "Frequency";

            // Type is an MO-Defined-Type
            type test_Freq;
        }
    }

    grouping test_CRslt-group {

        // Trigger for this result
        // Inherited From test:Rslt
        // Type is an MO-Defined-Type
        leaf trig {
            config "false";
            description "Trigger";

            // Type is an MO-Defined-Type
            type test_Trig;
        }

        // Test operational status
        // Inherited From test:Rslt
        // Type is an MO-Defined-Type
        leaf operSt {
            config "false";
            description "Operational State";

            // Type is an MO-Defined-Type
            type test_OperSt;
        }

        // Test status qualifier, deprecate this XXX
        // Inherited From test:Rslt
        // Type is an MO-Defined-Type
        leaf qual {
            config "false";
            description "Operational State Qualifier";

            // Type is an MO-Defined-Type
            type test_OperStQual;
        }

        // Test status qualifier
        // Inherited From test:Rslt
        // Type is an MO-Defined-Type
        leaf operStqual {
            config "false";
            description "Operational State Qualifier";

            // Type is an MO-Defined-Type
            type test_OperStQual;
        }
        leaf ts {
            config "false";
            type uint64;
        }

        // Prof. Name
        // Inherited From test:Rslt
        // Type is an MO-Defined-Type
        leaf name {
            config "false";
            description "Name";

            // Type is an MO-Defined-Type
            type naming_Name;
        }
    }

    grouping tunnel_If-group {
        leaf src {
            config "false";
            type address_Ip;
        }
        leaf dest {
            config "false";
            type address_Ip;
        }

        // Tunnel type
        // Type is an MO-Defined-Type
        leaf tType {
            config "false";
            description "Tunnel Type";

            // Type is an MO-Defined-Type
            type tunnel_TunnelQual;
        }

        // Tunnel VRF name
        // Type is an MO-Defined-Type
        leaf vrfName {
            config "false";
            description "VRF";

            // Type is an MO-Defined-Type
            type l3_VrfName;
        }

        // Tunnel MTU
        // Type is an MO-Defined-Type
        leaf cfgdMtu {
            config "false";
            description "MTU";

            // Type is an MO-Defined-Type
            type tunnel_ConfMtu;
        }

        // Tunnel keep-alive period
        // Type is an MO-Defined-Type
        leaf keepAlvIntvl {
            config "false";
            description "Keep Alive Interval";

            // Type is an MO-Defined-Type
            type tunnel_KeepAlvIntvl;
        }

        // Tunnel keep-alive retries
        // Type is an MO-Defined-Type
        leaf keepAlvRetries {
            config "false";
            description "Keep Alive Retries";

            // Type is an MO-Defined-Type
            type tunnel_KeepAlvRetries;
        }

        // Tunnel administrative state
        // Type is an MO-Defined-Type
        leaf adminSt {
            config "false";
            description "Administrative State";

            // Type is an MO-Defined-Type
            type tunnel_AdminSt;
        }

        // Tunnel type
        // Type is an MO-Defined-Type
        leaf type {
            config "false";
            description "Endpoint Type";

            // Type is an MO-Defined-Type
            type tunnel_EpT;
        }

        // Tunnel layer: L2 or L3
        // Type is an MO-Defined-Type
        leaf tLayer {
            config "false";
            description "Layer";

            // Type is an MO-Defined-Type
            type tunnel_LayerT;
        }
        leaf mac {
            config "false";
            type address_Mac;
        }
        leaf iod {
            config "false";
            type uint32;
        }

        // Tunnel operational state
        // Type is an MO-Defined-Type
        leaf operSt {
            config "false";
            description "Operational State";

            // Type is an MO-Defined-Type
            type tunnel_OperSt;
        }

        // Tunnel operational state down reason
        // Type is an MO-Defined-Type
        leaf operStQual {
            config "false";
            description "Operational State Qualifier";

            // Type is an MO-Defined-Type
            type tunnel_OperStQual;
        }
        leaf delInProg {
            config "false";
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // @@@Relationship to policy providing physical configuration of
        // the ports    @@@rel-def
        // name="IfConf"
        // type="named"
        // from="fv:RsCcepConn"
        // to="fabric:HIfPol"
        // cardinality="1-to-1"
        // owner="management"
        // mod="explicit"
        // >
        // </rel-def   DEp represents a dynamically learned end point on the switch.
        // This object is owned by the end point manager
        container dep-items {
            list DEp-list {
                key "mac encap";

                // Added containment: Prefix=dep
                // Acquired From Package fv
                uses fv_DEp-group;
            }
        }

        // VNode represents an opflex capable vnode that is connected
        // to the fabric.
        container vnode-items {
            list VNode-list {
                config "false";
                key "devId";

                // Added containment: Prefix=vnode
                // Acquired From Package fv
                uses fv_VNode-group;
            }
        }

        // IDEp represents a inband learned end point on the switch.
        // This object is owned by the end point manager
        container idep-items {
            list IDEp-list {
                key "mac encap";

                // Added containment: Prefix=idep
                // Acquired From Package opflex
                uses opflex_IDEp-group;
            }
        }

        // Device represents an opflex capable device that is connected
        // to the fabric.
        // This object is owned by the opflexelem
        container odev-items {
            list ODev-list {
                key "devId";

                // Added containment: Prefix=odev
                // Acquired From Package opflex
                uses opflex_ODev-group;
            }
        }

        // Each portIf under tunnel has two sets of banks to
        // count the packets and bytes. This Mo is defined
        // purely for statistics purposes
        container bank-items {
            list Bank-list {
                key "type";

                // Added containment: Prefix=bank
                // Acquired From Package tunnel
                uses tunnel_Bank-group;
            }
        }

        // This object is purely for stats purposes. We count the
        // tunnel stats on a given physical port. These port objects
        // will be created by default whereever the tunnel can exit
        // out. For example, all north bound tunnels will have the
        // fabric ports created under it
        container portif-items {
            list PortIf-list {
                config "false";
                key "id";

                // Added containment: Prefix=portif
                // Acquired From Package tunnel
                uses tunnel_PortIf-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def from tunnelMbrIfs
        container rstunnelMbrIfs-items {

            // Abstract containment of rstunnelMbrIfs derived from tunnel:If
            list RsTunnelMbrIfs-list {
                config "false";
                key "tDn";

                // Added containment: Prefix=rstunnelMbrIfs
                // Acquired From Package tunnel
                uses tunnel_RsTunnelMbrIfs_source-group;
            }
        }

        // Rel-def from tunnelToLooseNode
        container rstunnelToLooseNode-items {

            // Abstract containment of rstunnelToLooseNode derived from tunnel:If
            list RsTunnelToLooseNode-list {
                config "false";
                key "tDn";

                // Added containment: Prefix=rstunnelToLooseNode
                // Acquired From Package tunnel
                uses tunnel_RsTunnelToLooseNode_source-group;
            }
        }
    }

    grouping tunnel_Bank-group {

        // Type
        // Liked from ac:Bank:type
        // Type is an MO-Defined-Type
        leaf type {
            description "Type";

            // Type is an MO-Defined-Type
            type ac_BankT;
        }

        container dbgIngrTep-items {

            // Added containment as a singleton: Prefix=dbgIngrTep
            // Acquired From Package tunnel
            uses tunnel_IngrTep-group;
        }

        container dbgEgrTep-items {

            // Added containment as a singleton: Prefix=dbgEgrTep
            // Acquired From Package tunnel
            uses tunnel_EgrTep-group;
        }
    }

    grouping tunnel_PortIf-group {

        // Type is an MO-Defined-Type
        leaf id {
            config "false";
            description "ID";

            // Type is an MO-Defined-Type
            type nw_IfId;
        }

        // Each portIf under tunnel has two sets of banks to
        // count the packets and bytes. This Mo is defined
        // purely for statistics purposes
        container bank-items {
            list Bank-list {
                key "type";

                // Added containment: Prefix=bank
                // Acquired From Package tunnel
                uses tunnel_Bank-group;
            }
        }
    }

    grouping nbm_NbmFlowsTable-group {

        // Holds NBM configuration
        container flowOp-items {
            list NbmFlowEntity-list {
                key "flowOp srcIP dstIP egressIf";

                // Added containment: Prefix=flowOp
                // Acquired From Package nbm
                uses nbm_NbmFlowEntity-group;
            }
        }

        // Counter MO
        container srcIP-items {
            list NbmOifCounter-list {
                key "srcIP dstIP";

                // Added containment: Prefix=srcIP
                // Acquired From Package nbm
                uses nbm_NbmOifCounter-group;
            }
        }

        // MO FOR IIF CHANGE - UNUSED FOR NOW
        container iif-items {
            list NbmUpdateIif-list {
                key "newIngressIf srcIP dstIP";

                // Added containment: Prefix=iif
                // Acquired From Package nbm
                uses nbm_NbmUpdateIif-group;
            }
        }
    }

    grouping nbm_NbmFlowEntity-group {

        // Properties
        // Type is an MO-Defined-Type
        leaf controllerIP {
            description "Controller IP Address";

            // Type is an MO-Defined-Type
            type nbm_nbmIpAddr;
        }

        // Type is an MO-Defined-Type
        leaf controllerVIP {
            description "Controller Virtual IP Address";

            // Type is an MO-Defined-Type
            type nbm_nbmIpAddr;
        }

        // Type is an MO-Defined-Type
        leaf flowOp {
            description "Operation Type";

            // Type is an MO-Defined-Type
            type nbm_nbmFlowOperEn;
        }

        // Type is an MO-Defined-Type
        leaf srcIP {
            description "source IP Address";

            // Type is an MO-Defined-Type
            type nbm_nbmIpAddr;
        }

        // Type is an MO-Defined-Type
        leaf l4SrcPort {
            description "l4 Source Port";

            // Type is an MO-Defined-Type
            type nbm_nbmL4Port;
        }

        // Type is an MO-Defined-Type
        leaf dstIP {
            description "destination IP Address";

            // Type is an MO-Defined-Type
            type nbm_nbmIpAddr;
        }

        // Type is an MO-Defined-Type
        leaf l4DestPort {
            description "l4 Destination Port";

            // Type is an MO-Defined-Type
            type nbm_nbmL4Port;
        }

        // Type is an MO-Defined-Type
        leaf ingressIf {
            description "ingress Interface";

            // Type is an MO-Defined-Type
            type nbm_nbmIf;
        }

        // Type is an MO-Defined-Type
        leaf egressIf {
            description "egress Interface";

            // Type is an MO-Defined-Type
            type nbm_nbmIf;
        }
        leaf egressIfCount {
            type uint32;
        }
        leaf seqNum {
            type uint32;
        }

        // Type is an MO-Defined-Type
        leaf dscp {
            description "dscp value";

            // Type is an MO-Defined-Type
            type nbm_nbmDscp;
        }

        // Type is an MO-Defined-Type
        leaf bandwidthUnit {
            description "bandwidth units - Mbps, Kbps, or Gbps";

            // Type is an MO-Defined-Type
            type nbm_nbmBwUnitEn;
        }
        leaf bandwidth {
            type uint32;
        }
        leaf queueId {
            type uint8;
        }
        leaf switchIif {
            type uint8;
            default "0";
        }
    }

    grouping nbm_NbmOifCounter-group {

        // Type is an MO-Defined-Type
        leaf srcIP {
            description "source IP Address";

            // Type is an MO-Defined-Type
            type nbm_nbmIpAddr;
        }

        // Type is an MO-Defined-Type
        leaf dstIP {
            description "destination IP Address";

            // Type is an MO-Defined-Type
            type nbm_nbmIpAddr;
        }
        leaf OifCount {
            type uint32;
        }
    }

    grouping nbm_NbmUpdateIif-group {

        // Type is an MO-Defined-Type
        leaf srcIP {
            description "source IP Address";

            // Type is an MO-Defined-Type
            type nbm_nbmIpAddr;
        }

        // Type is an MO-Defined-Type
        leaf dstIP {
            description "destination IP Address";

            // Type is an MO-Defined-Type
            type nbm_nbmIpAddr;
        }

        // Type is an MO-Defined-Type
        leaf newIngressIf {
            description "New Ingress Interface";

            // Type is an MO-Defined-Type
            type nbm_nbmIf;
        }

        // Type is an MO-Defined-Type
        leaf prevIngressIf {
            description "Prev Ingress Interface";

            // Type is an MO-Defined-Type
            type nbm_nbmIf;
        }
        leaf seqNum {
            type uint32;
        }
    }

    grouping nbm_NbmStats-group {

        // Holds NBM configuration
        container srcIP-items {
            list NbmStatsEntity-list {
                key "srcIP dstIP";

                // Added containment: Prefix=srcIP
                // Acquired From Package nbm
                uses nbm_NbmStatsEntity-group;
            }
        }
    }

    grouping nbm_NbmStatsEntity-group {

        // Properties
        // Type is an MO-Defined-Type
        leaf srcIP {
            description "source IP Address";

            // Type is an MO-Defined-Type
            type nbm_nbmIpAddr;
        }

        // Type is an MO-Defined-Type
        leaf dstIP {
            description "destination IP Address";

            // Type is an MO-Defined-Type
            type nbm_nbmIpAddr;
        }
        leaf allowedPkts {
            type uint64;
        }
        leaf allowedBytes {
            type uint64;
        }
        leaf deniedPkts {
            type uint64;
        }
        leaf deniedBytes {
            type uint64;
        }
        leaf totalPkts {
            type uint64;
        }
        leaf totalBytes {
            type uint64;
        }
        leaf tStamp {
            type uint64;
        }
    }

    grouping boot_Boot-group {

        container image-items {

            // Added containment as a singleton: Prefix=image
            // Acquired From Package boot
            uses boot_Image-group;
        }
    }

    grouping boot_Image-group {
        leaf sup1 {
            type string;
        }
        leaf sup2 {
            type string;
        }
        leaf image_err {
            config "false";
            type string;
            default "success";
        }
    }

    grouping eqpt_Ch-group {

        // Role of this chassis
        // Type is an MO-Defined-Type
        leaf role {
            config "false";
            description "Role";

            // Type is an MO-Defined-Type
            type top_NodeRole;
        }

        // Operational status of chassis
        // Type is an MO-Defined-Type
        leaf operSt {
            config "false";
            description "Operational State";

            // Type is an MO-Defined-Type
            type eqpt_ChOperSt;
        }

        // Chassis operational status qualifier
        // Type is an MO-Defined-Type
        leaf operStQual {
            config "false";
            description "Operational State Qualifier";

            // Type is an MO-Defined-Type
            type eqpt_OperStQual;
        }

        // The vendor manufacturing this device.
        // From Interface eqpt:Dev
        // Type is an MO-Defined-Type
        leaf vendor {
            config "false";
            description "Vendor";

            // Type is an MO-Defined-Type
            type eqpt_Vendor;
        }

        // The device model
        // From Interface eqpt:Dev
        // Type is an MO-Defined-Type
        leaf model {
            config "false";
            description "Model";

            // Type is an MO-Defined-Type
            type eqpt_Model;
        }

        // The device revision.
        // From Interface eqpt:Dev
        // Type is an MO-Defined-Type
        leaf rev {
            config "false";
            description "Revision";

            // Type is an MO-Defined-Type
            type eqpt_Revision;
        }

        // The device serial number.
        // From Interface eqpt:Dev
        // Type is an MO-Defined-Type
        leaf ser {
            config "false";
            description "Serial Number";

            // Type is an MO-Defined-Type
            type eqpt_Serial;
        }
        leaf mfgTm {
            config "false";
            type uint64;
            default "0";
        }

        // Identifier for the item
        // Inherited From eqpt:Item
        // Modified by Override: eqpt:Cont->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Ejector policy
        container ejpol-items {
            list EjPol-list {
                config "false";
                key "id";

                // Added containment: Prefix=ejpol
                // Acquired From Package eqpt
                uses eqpt_EjPol-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // supervisor slot
        container supslot-items {
            list SupCSlot-list {
                config "false";
                key "id";

                // Added containment: Prefix=supslot
                // Acquired From Package eqpt
                uses eqpt_SupCSlot-group;
            }
        }

        // line card slot
        container lcslot-items {
            list LCSlot-list {
                config "false";
                key "id";

                // Added containment: Prefix=lcslot
                // Acquired From Package eqpt
                uses eqpt_LCSlot-group;
            }
        }

        // fabric card slot
        container fcslot-items {
            list FCSlot-list {
                config "false";
                key "id";

                // Added containment: Prefix=fcslot
                // Acquired From Package eqpt
                uses eqpt_FCSlot-group;
            }
        }

        // system controller slot
        container scslot-items {
            list SysCSlot-list {
                config "false";
                key "id";

                // Added containment: Prefix=scslot
                // Acquired From Package eqpt
                uses eqpt_SysCSlot-group;
            }
        }

        // power supply slot
        container psuslot-items {
            list PsuSlot-list {
                config "false";
                key "id";

                // Added containment: Prefix=psuslot
                // Acquired From Package eqpt
                uses eqpt_PsuSlot-group;
            }
        }

        // fan tray slot
        container ftslot-items {
            list FtSlot-list {
                config "false";
                key "id";

                // Added containment: Prefix=ftslot
                // Acquired From Package eqpt
                uses eqpt_FtSlot-group;
            }
        }

        // Sprom Backplane Unit block
        container spbp-items {

            // Added containment as a singleton: Prefix=spbp
            // Acquired From Package eqpt
            uses eqpt_SpromBP-group;
        }

        // Board slot
        container bslot-items {

            // Added containment as a singleton: Prefix=bslot
            // Acquired From Package eqpt
            uses eqpt_BSlot-group;
        }

        // Nic slot
        container nslot-items {
            list NSlot-list {
                config "false";
                key "id";

                // Added containment: Prefix=nslot
                // Acquired From Package eqpt
                uses eqpt_NSlot-group;
            }
        }

        // Storage represents the storage of the Controller
        container p-items {
            list Storage-list {
                config "false";
                key "mount fileSystem";

                // Added containment: Prefix=p
                // Acquired From Package eqpt
                uses eqpt_Storage-group;
            }
        }
    }

    grouping eqpt_EjPol-group {

        // Auto shutdown on ejector open
        // Type is an MO-Defined-Type
        leaf autoSh {
            config "false";
            description "Auto Shutdown on Ejector Open";

            // Type is an MO-Defined-Type
            type eqpt_AdSt;
        }

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_IndLed-group {

        // Identifier for the item
        // Inherited From eqpt:Item
        // Modified by Override: eqpt:IndLed->id
        // Type is an MO-Defined-Type
        leaf id {
            config "false";
            description "ID";

            // Type is an MO-Defined-Type
            type eqpt_Id {
                range "1..6";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Color status of an LED
        // Inherited From eqpt:Led
        // Type is an MO-Defined-Type
        leaf color {
            config "false";
            description "Color";

            // Type is an MO-Defined-Type
            type eqpt_Color;
        }

        // Operational status of an LED
        // Inherited From eqpt:Led
        // Type is an MO-Defined-Type
        leaf operSt {
            config "false";
            description "Operational State";

            // Type is an MO-Defined-Type
            type eqpt_LedOpSt;
        }

        // LED type
        // Inherited From eqpt:Led
        // Type is an MO-Defined-Type
        leaf type {
            config "false";
            description "Type";

            // Type is an MO-Defined-Type
            type eqpt_LedType;
        }
    }

    grouping eqpt_LocLed-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Color status of an LED
        // Inherited From eqpt:Led
        // Type is an MO-Defined-Type
        leaf color {
            config "false";
            description "Color";

            // Type is an MO-Defined-Type
            type eqpt_Color;
        }

        // Operational status of an LED
        // Inherited From eqpt:Led
        // Type is an MO-Defined-Type
        leaf operSt {
            config "false";
            description "Operational State";

            // Type is an MO-Defined-Type
            type eqpt_LedOpSt;
        }

        // LED type
        // Inherited From eqpt:Led
        // Type is an MO-Defined-Type
        leaf type {
            config "false";
            description "Type";

            // Type is an MO-Defined-Type
            type eqpt_LedType;
        }

        // Admin status - Used to locate
        // Inherited From eqpt:ALocLed
        // Type is an MO-Defined-Type
        leaf adminSt {
            description "Admin State";

            // Type is an MO-Defined-Type
            type eqpt_AdSt;
        }
    }

    grouping eqpt_SupCSlot-group {

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:SupCSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Sup Card, containing CPU running control plane
        container sup-items {

            // Added containment as a singleton: Prefix=sup
            // Acquired From Package eqpt
            uses eqpt_SupC-group;
        }

        // Card reset record
        container rstrec-items {
            list CardRstRec-list {
                config "false";
                key "ts";

                // Added containment: Prefix=rstrec
                // Acquired From Package syshist
                uses syshist_CardRstRec-group;
            }
        }

        // Remote card reset record
        container remrstrec-items {
            list RemCardRstRec-list {
                config "false";
                key "ts";

                // Added containment: Prefix=remrstrec
                // Acquired From Package syshist
                uses syshist_RemCardRstRec-group;
            }
        }

        // Rel-def target from oosSlot
        // Inherited From eqpt:SupCSlot
        container rtoosSlot-items {

            // Added containment as a singleton: Prefix=rtoosSlot
            // Acquired From Package fabric
            uses fabric_RtOosSlot_target-group;
        }
    }

    grouping eqpt_SupC-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Modified by Override: eqpt:SupC->type
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // Information about each card firmware
        container running-items {

            // Added containment as a singleton: Prefix=running
            // Acquired From Package firmware
            uses firmware_CardRunning-group;
        }

        // Ejector information
        container ej-items {
            list Ejec-list {
                config "false";
                key "id";

                // Added containment: Prefix=ej
                // Acquired From Package eqpt
                uses eqpt_Ejec-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // cpu bound traffic port
        container cpuport-items {
            list CpuP-list {
                config "false";
                key "id";

                // Added containment: Prefix=cpuport
                // Acquired From Package eqpt
                uses eqpt_CpuP-group;
            }
        }

        // internal eobc (ethernet out of band channel) port
        // (all card component management is done via this port)
        container eobc-items {
            list EobcP-list {
                config "false";
                key "id";

                // Added containment: Prefix=eobc
                // Acquired From Package eqpt
                uses eqpt_EobcP-group;
            }
        }

        // internal epc port
        // (internal hi-gig links connecting the external io ports)
        container epc-items {
            list EpcP-list {
                config "false";
                key "id";

                // Added containment: Prefix=epc
                // Acquired From Package eqpt
                uses eqpt_EpcP-group;
            }
        }

        // External management port
        container mgmt-items {
            list MgmtP-list {
                config "false";
                key "id";

                // Added containment: Prefix=mgmt
                // Acquired From Package eqpt
                uses eqpt_MgmtP-group;
            }
        }

        // External (debug) console port
        container console-items {
            list ConsP-list {
                config "false";
                key "id";

                // Added containment: Prefix=console
                // Acquired From Package eqpt
                uses eqpt_ConsP-group;
            }
        }

        // Sensor information
        container sensor-items {
            list Sensor-list {
                config "false";
                key "id";

                // Added containment: Prefix=sensor
                // Acquired From Package eqpt
                uses eqpt_Sensor-group;
            }
        }

        // Sprom Supervisor
        container spsup-items {

            // Added containment as a singleton: Prefix=spsup
            // Acquired From Package eqpt
            uses eqpt_SpromSup-group;
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping firmware_CardRunning-group {

        // Bios version
        // Type is an MO-Defined-Type
        leaf biosVer {
            config "false";
            description "Loader Version";

            // Type is an MO-Defined-Type
            type cap_Version;
        }

        // Expected Component version
        // Type is an MO-Defined-Type
        leaf expectedVer {
            config "false";
            description "Expected Loader Version";

            // Type is an MO-Defined-Type
            type cap_Version;
        }

        // running version Operational State
        // Type is an MO-Defined-Type
        leaf operSt {
            config "false";
            description "Operational State";

            // Type is an MO-Defined-Type
            type firmware_RunningOperSt;
        }

        // Interim version
        // Type is an MO-Defined-Type
        leaf interimVer {
            config "false";
            description "Interim Version";

            // Type is an MO-Defined-Type
            type cap_Version;
        }

        // Running firmware version.
        // Inherited From firmware:ARunning
        // Type is an MO-Defined-Type
        leaf version {
            config "false";
            description "Version";

            // Type is an MO-Defined-Type
            type cap_Version;
        }
        leaf internalLabel {
            type string;
        }

        // Running firmware type.
        // Inherited From firmware:ARunning
        // Type is an MO-Defined-Type
        leaf type {
            config "false";
            description "Type";

            // Type is an MO-Defined-Type
            type firmware_Type;
        }

        // Running firmware mode.
        // Inherited From firmware:ARunning
        // Type is an MO-Defined-Type
        leaf mode {
            config "false";
            description "Mode";

            // Type is an MO-Defined-Type
            type firmware_RunningMode;
        }
        leaf ts {
            config "false";
            type uint64;
        }

        // From Interface naming:Described
        // Inherited From firmware:ARunning
        // Type is an MO-Defined-Type
        leaf descr {
            description "Description";

            // Type is an MO-Defined-Type
            type naming_Descr;
        }
    }

    grouping eqpt_Ejec-group {

        // Status of ejector
        // Type is an MO-Defined-Type
        leaf operSt {
            config "false";
            description "Operational State";

            // Type is an MO-Defined-Type
            type eqpt_EjSt;
        }

        // Identifier for the item
        // Inherited From eqpt:Item
        // Modified by Override: eqpt:Ejec->id
        // Type is an MO-Defined-Type
        leaf id {
            config "false";
            description "ID";

            // Type is an MO-Defined-Type
            type eqpt_Id {
                range "1..2";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_CpuP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Holder of some PE specific information of the port
        container lport-items {

            // Added containment as a singleton: Prefix=lport
            // Acquired From Package eqpt
            uses eqpt_LPort-group;
        }
    }

    grouping eqpt_LPort-group {

        // Interface ID of this endpoint
        // Type is an MO-Defined-Type
        leaf id {
            config "false";
            description "ID";

            // Type is an MO-Defined-Type
            type nw_IfId;
        }
    }

    grouping eqpt_EobcP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Holder of some PE specific information of the port
        container lport-items {

            // Added containment as a singleton: Prefix=lport
            // Acquired From Package eqpt
            uses eqpt_LPort-group;
        }
    }

    grouping eqpt_EpcP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Holder of some PE specific information of the port
        container lport-items {

            // Added containment as a singleton: Prefix=lport
            // Acquired From Package eqpt
            uses eqpt_LPort-group;
        }
    }

    grouping eqpt_MgmtP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // Holder of some PE specific information of the port
        container lport-items {

            // Added containment as a singleton: Prefix=lport
            // Acquired From Package eqpt
            uses eqpt_LPort-group;
        }
    }

    grouping eqpt_ConsP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Holder of some PE specific information of the port
        container lport-items {

            // Added containment as a singleton: Prefix=lport
            // Acquired From Package eqpt
            uses eqpt_LPort-group;
        }
    }

    grouping eqpt_Sensor-group {

        // Type of the sensor
        // Type is an MO-Defined-Type
        leaf type {
            config "false";
            description "Type";

            // Type is an MO-Defined-Type
            type eqpt_SensorT;
        }

        // Major threshold
        // Type is an MO-Defined-Type
        leaf majorThresh {
            config "false";
            description "Major Threshold";

            // Type is an MO-Defined-Type
            type eqpt_TempThresh;
        }

        // Minor threshold
        // Type is an MO-Defined-Type
        leaf minorThresh {
            config "false";
            description "Minor Threshold";

            // Type is an MO-Defined-Type
            type eqpt_TempThresh;
        }

        // oper state
        // Type is an MO-Defined-Type
        leaf operSt {
            config "false";
            description "OperSt";

            // Type is an MO-Defined-Type
            type eqpt_SensorOpSt;
        }

        // Identifier for the item
        // Inherited From eqpt:Item
        // Modified by Override: eqpt:Sensor->id
        // Type is an MO-Defined-Type
        leaf id {
            config "false";
            description "ID";

            // Type is an MO-Defined-Type
            type eqpt_Id {
                range "1..32";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_SpromSup-group {

        // Identifier for the item
        // Inherited From eqpt:Item
        // Modified by Override: eqpt:Sprom->id
        // Type is an MO-Defined-Type
        leaf id {
            config "false";
            description "ID";

            // Type is an MO-Defined-Type
            type eqpt_Id {
                range "1..100";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }

        // Sprom failure reason
        // Inherited From eqpt:Sprom
        // Type is an MO-Defined-Type
        leaf errRsn {
            config "false";
            description "Error Reason";

            // Type is an MO-Defined-Type
            type eqpt_SpErrRsn;
        }
        leaf numBlk {
            config "false";
            type uint16;
        }

        // sprom Common Block
        container spcmn-items {

            // Added containment as a singleton: Prefix=spcmn
            // Acquired From Package eqpt
            uses eqpt_SpCmnBlk-group;
        }

        // Sprom Supervisor block
        container spsupblk-items {

            // Added containment as a singleton: Prefix=spsupblk
            // Acquired From Package eqpt
            uses eqpt_SpromSupBlk-group;
        }

        // sprom Port Data Interface
        container sppd-items {

            // Added containment as a singleton: Prefix=sppd
            // Acquired From Package eqpt
            uses eqpt_SpPd-group;
        }

        // sprom Sensor Data Interface
        container spsd-items {
            list SpSd-list {
                config "false";
                key "id";

                // Added containment: Prefix=spsd
                // Acquired From Package eqpt
                uses eqpt_SpSd-group;
            }
        }

        // Sprom Sensor block
        container spsensorblk-items {

            // Added containment as a singleton: Prefix=spsensorblk
            // Acquired From Package eqpt
            uses eqpt_SpSensorBlk-group;
        }
    }

    grouping eqpt_SpCmnBlk-group {
        leaf size {
            type uint16;
        }
        leaf count {
            type uint16;
        }
        leaf major {
            type uint16;
        }
        leaf minor {
            type uint16;
        }
        leaf oem {
            type string;
        }
        leaf pdNum {
            type string;
        }
        leaf serNum {
            type string;
        }
        leaf prtNum {
            type string;
        }
        leaf pRev {
            type string;
        }
        leaf mfgDev {
            type string;
        }
        leaf hwRevMaj {
            type uint16;
        }
        leaf hwRevMin {
            type uint16;
        }
        leaf mfgBits {
            type uint16;
        }
        leaf engBits {
            type uint16;
        }
        leaf pwrCon {
            type int16;
        }
        leaf ramFl {
            type string;
        }
        leaf clei {
            type string;
        }
        leaf vdrId {
            type string;
        }
        leaf sig {
            type uint16;
        }
        leaf ver {
            type uint16;
        }
        leaf len {
            type uint16;
        }
        leaf cksum {
            type uint16;
        }
    }

    grouping eqpt_SpromSupBlk-group {
        leaf fbits {
            type uint64;
        }
        leaf hwCBits {
            type uint64;
        }
        leaf crdIdx {
            type uint16;
        }
        leaf macB {
            type string;
        }
        leaf macL {
            type uint16;
        }
        leaf eobcN {
            type uint16;
        }
        leaf epldN {
            type uint16;
        }
        leaf epldV {
            type uint16;
        }
        leaf sramSz {
            type uint16;
        }
        leaf maxCPwr {
            type uint16;
        }
        leaf coolRq {
            type uint16;
        }
        leaf ambT {
            type uint16;
        }
        leaf sig {
            type uint16;
        }
        leaf ver {
            type uint16;
        }
        leaf len {
            type uint16;
        }
        leaf cksum {
            type uint16;
        }

        // sprom Sensor Data Interface
        container spsd-items {
            list SpSd-list {
                config "false";
                key "id";

                // Added containment: Prefix=spsd
                // Acquired From Package eqpt
                uses eqpt_SpSd-group;
            }
        }

        // sprom Port Data Interface
        container sppd-items {

            // Added containment as a singleton: Prefix=sppd
            // Acquired From Package eqpt
            uses eqpt_SpPd-group;
        }
    }

    grouping eqpt_SpSd-group {

        // Major Threshold
        // Type is an MO-Defined-Type
        leaf majTh {
            description "Major Threshold";

            // Type is an MO-Defined-Type
            type eqpt_TempThresh;
        }

        // Minor Threshold
        // Type is an MO-Defined-Type
        leaf minTh {
            description "Minor Threshold";

            // Type is an MO-Defined-Type
            type eqpt_TempThresh;
        }

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_SpPd-group {
        leaf prtTy {
            type uint16;
        }
        leaf numPts {
            type uint16;
        }
        leaf sig {
            type uint16;
        }
        leaf ver {
            type uint16;
        }
        leaf len {
            type uint16;
        }
        leaf cksum {
            type uint16;
        }
    }

    grouping eqpt_SpSensorBlk-group {
        leaf sig {
            type uint16;
        }
        leaf ver {
            type uint16;
        }
        leaf len {
            type uint16;
        }
        leaf cksum {
            type uint16;
        }

        // sprom Sensor Data Interface
        container spsd-items {
            list SpSd-list {
                config "false";
                key "id";

                // Added containment: Prefix=spsd
                // Acquired From Package eqpt
                uses eqpt_SpSd-group;
            }
        }
    }

    grouping eqpt_Asic-group {

        // Type of asic
        // Type is an MO-Defined-Type
        leaf type {
            config "false";
            description "Type";

            // Type is an MO-Defined-Type
            type eqpt_AsicT;
        }

        // Asic status
        // Type is an MO-Defined-Type
        leaf operSt {
            config "false";
            description "Operational State";

            // Type is an MO-Defined-Type
            type eqpt_OpSt;
        }

        // Asic numSlices
        // Type is an MO-Defined-Type
        leaf numSlices {
            config "false";
            description "Number of Slices";

            // Type is an MO-Defined-Type
            type eqpt_AsicNumSlices;
        }

        // Asic Capability
        // Type is an MO-Defined-Type
        leaf capabilities {
            config "false";
            description "Capabilities";

            // Type is an MO-Defined-Type
            type eqpt_AsicCapability;
        }

        // Identifier for the item
        // Inherited From eqpt:Item
        // Modified by Override: eqpt:Asic->id
        // Type is an MO-Defined-Type
        leaf id {
            config "false";
            description "ID";

            // Type is an MO-Defined-Type
            type eqpt_Id {
                range "1..10";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_CPU-group {

        // Identifier for the item
        // Inherited From eqpt:Item
        // Modified by Override: eqpt:ACPU->id
        // Type is an MO-Defined-Type
        leaf id {
            config "false";
            description "ID";

            // Type is an MO-Defined-Type
            type eqpt_Id {
                range "1";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Socket designation
        // Inherited From eqpt:ACPU
        // Type is an MO-Defined-Type
        leaf sock {
            config "false";
            description "Socket";

            // Type is an MO-Defined-Type
            type eqpt_Sock;
        }

        // Architecture of the CPU
        // Inherited From eqpt:ACPU
        // Type is an MO-Defined-Type
        leaf arch {
            config "false";
            description "Architecture";

            // Type is a Local-MO-Defined-Type
            type eqpt_Arch_CPU_arch;
        }

        // CPU speed
        // Inherited From eqpt:ACPU
        // Type is an MO-Defined-Type
        leaf speed {
            config "false";
            description "Speed";

            // Type is an MO-Defined-Type
            type eqpt_Speed;
        }

        // Number of cores on the CPU
        // Inherited From eqpt:ACPU
        // Type is an MO-Defined-Type
        leaf cores {
            config "false";
            description "Cores";

            // Type is an MO-Defined-Type
            type eqpt_Cores;
        }

        // Number of cores enabled on the CPU
        // Inherited From eqpt:ACPU
        // Type is an MO-Defined-Type
        leaf coresEn {
            config "false";
            description "Cores Enabled";

            // Type is an MO-Defined-Type
            type eqpt_Cores;
        }
        leaf thrds {
            config "false";
            type uint16;
        }
        container core-items {
            list Core-list {
                config "false";
                key "id";

                // Added containment: Prefix=core
                // Acquired From Package eqpt
                uses eqpt_Core-group;
            }
        }
    }

    grouping eqpt_Core-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_Fpga-group {

        // Type of fpga
        // Type is an MO-Defined-Type
        leaf type {
            config "false";
            description "Type";

            // Type is an MO-Defined-Type
            type eqpt_FpgaT;
        }

        // Fpga status
        // Type is an MO-Defined-Type
        leaf operSt {
            config "false";
            description "Operational State";

            // Type is an MO-Defined-Type
            type eqpt_OpSt;
        }

        // Identifier for the item
        // Inherited From eqpt:Item
        // Modified by Override: eqpt:Fpga->id
        // Type is an MO-Defined-Type
        leaf id {
            config "false";
            description "ID";

            // Type is an MO-Defined-Type
            type eqpt_Id {
                range "1..5";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Information about each equipment component firmware
        container running-items {

            // Added containment as a singleton: Prefix=running
            // Acquired From Package firmware
            uses firmware_CompRunning-group;
        }
    }

    grouping firmware_CompRunning-group {

        // Expected Component version
        // Type is an MO-Defined-Type
        leaf expectedVer {
            config "false";
            description "Expected Component Running Version";

            // Type is an MO-Defined-Type
            type cap_Version;
        }

        // running version Operational State
        // Type is an MO-Defined-Type
        leaf operSt {
            config "false";
            description "Operational State";

            // Type is an MO-Defined-Type
            type firmware_RunningOperSt;
        }

        // Running firmware version.
        // Inherited From firmware:ARunning
        // Type is an MO-Defined-Type
        leaf version {
            config "false";
            description "Version";

            // Type is an MO-Defined-Type
            type cap_Version;
        }
        leaf internalLabel {
            type string;
        }

        // Running firmware type.
        // Inherited From firmware:ARunning
        // Type is an MO-Defined-Type
        leaf type {
            config "false";
            description "Type";

            // Type is an MO-Defined-Type
            type firmware_Type;
        }

        // Running firmware mode.
        // Inherited From firmware:ARunning
        // Type is an MO-Defined-Type
        leaf mode {
            config "false";
            description "Mode";

            // Type is an MO-Defined-Type
            type firmware_RunningMode;
        }
        leaf ts {
            config "false";
            type uint64;
        }

        // From Interface naming:Described
        // Inherited From firmware:ARunning
        // Type is an MO-Defined-Type
        leaf descr {
            description "Description";

            // Type is an MO-Defined-Type
            type naming_Descr;
        }
    }

    grouping eqpt_Dimm-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Modified by Override: eqpt:Dimm->type
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }
    }

    grouping eqpt_Flash-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Modified by Override: eqpt:Flash->type
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }
    }

    grouping eqpt_Obfl-group {

        // Set the obfl log parameters
        // Type is an MO-Defined-Type
        leaf logT {
            config "false";
            description "Log Type";

            // Type is an MO-Defined-Type
            type eqpt_LogType;
        }

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping syshist_CardRstRec-group {
        leaf ts {
            config "false";
            type uint64;
        }

        // Reset reason
        // Inherited From syshist:RstRec
        // Type is an MO-Defined-Type
        leaf reason {
            config "false";
            description "Reset Reason";

            // Type is an MO-Defined-Type
            type syshist_RstRsn;
        }

        // Reset reason qualifier
        // Inherited From syshist:RstRec
        // Type is an MO-Defined-Type
        leaf reasonQual {
            config "false";
            description "Reset Reason Qualifier";

            // Type is an MO-Defined-Type
            type syshist_RstRsnQual;
        }

        // Version with which the reset happened
        // Inherited From syshist:RstRec
        // Type is an MO-Defined-Type
        leaf ver {
            config "false";
            description "Reset Reason";

            // Type is an MO-Defined-Type
            type cap_Version;
        }
    }

    grouping syshist_RemCardRstRec-group {
        leaf ts {
            config "false";
            type uint64;
        }

        // Reset reason
        // Inherited From syshist:RstRec
        // Type is an MO-Defined-Type
        leaf reason {
            config "false";
            description "Reset Reason";

            // Type is an MO-Defined-Type
            type syshist_RstRsn;
        }

        // Reset reason qualifier
        // Inherited From syshist:RstRec
        // Type is an MO-Defined-Type
        leaf reasonQual {
            config "false";
            description "Reset Reason Qualifier";

            // Type is an MO-Defined-Type
            type syshist_RstRsnQual;
        }

        // Version with which the reset happened
        // Inherited From syshist:RstRec
        // Type is an MO-Defined-Type
        leaf ver {
            config "false";
            description "Reset Reason";

            // Type is an MO-Defined-Type
            type cap_Version;
        }
    }

    grouping eqpt_LCSlot-group {
        leaf purgeCfg {
            config "false";
            type boolean;
        }

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:LCSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Line Card (IO card), containing io ports
        container lc-items {

            // Added containment as a singleton: Prefix=lc
            // Acquired From Package eqpt
            uses eqpt_LC-group;
        }

        // Card reset record
        container rstrec-items {
            list CardRstRec-list {
                config "false";
                key "ts";

                // Added containment: Prefix=rstrec
                // Acquired From Package syshist
                uses syshist_CardRstRec-group;
            }
        }

        // Rel-def target from oosSlot
        // Inherited From eqpt:SupCSlot
        // Inherited From eqpt:LCSlot
        container rtoosSlot-items {

            // Added containment as a singleton: Prefix=rtoosSlot
            // Acquired From Package fabric
            uses fabric_RtOosSlot_target-group;
        }
    }

    // Has Polymorphic containment of abstract object eqpt:IoP
    grouping eqpt_LC-group {
        leaf breakoutFactor {
            config "false";
            type uint32;
            default "1";
        }

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Modified by Override: eqpt:LC->type
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // Information about each card firmware
        container running-items {

            // Added containment as a singleton: Prefix=running
            // Acquired From Package firmware
            uses firmware_CardRunning-group;
        }

        // Ejector information
        container ej-items {
            list Ejec-list {
                config "false";
                key "id";

                // Added containment: Prefix=ej
                // Acquired From Package eqpt
                uses eqpt_Ejec-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // internal eobc (ethernet out of band channel) port
        // (all card component management is done via this port)
        container eobc-items {
            list EobcP-list {
                config "false";
                key "id";

                // Added containment: Prefix=eobc
                // Acquired From Package eqpt
                uses eqpt_EobcP-group;
            }
        }

        // Fabric facing external IO port
        // Polymorphic containment of derivative object eqpt:FabP (from eqpt:IoP)
        container fabport-items {

            // Abstract containment of eqpt:FabP derived from eqpt:IoP
            list FabP-list {
                config "false";
                key "id";

                // Added containment: Prefix=fabport
                // Acquired From Package eqpt
                uses eqpt_FabP-group;
            }
        }

        // Leaf (compute, WAN, services) facing external IO port
        // Polymorphic containment of derivative object eqpt:LeafP (from eqpt:IoP)
        container leafport-items {

            // Abstract containment of eqpt:LeafP derived from eqpt:IoP
            list LeafP-list {
                config "false";
                key "id";

                // Added containment: Prefix=leafport
                // Acquired From Package eqpt
                uses eqpt_LeafP-group;
            }
        }

        // Extension chassis port connected to hosts
        // Polymorphic containment of derivative object eqpt:ExtChHP (from eqpt:IoP)
        container hostextport-items {

            // Abstract containment of eqpt:ExtChHP derived from eqpt:IoP
            list ExtChHP-list {
                config "false";
                key "id";

                // Added containment: Prefix=hostextport
                // Acquired From Package eqpt
                uses eqpt_ExtChHP-group;
            }
        }

        // Extension chassis port connected to Leaf
        // Polymorphic containment of derivative object eqpt:ExtChFP (from eqpt:IoP)
        container leafextport-items {

            // Abstract containment of eqpt:ExtChFP derived from eqpt:IoP
            list ExtChFP-list {
                config "false";
                key "id";

                // Added containment: Prefix=leafextport
                // Acquired From Package eqpt
                uses eqpt_ExtChFP-group;
            }
        }

        // Sensor information
        container sensor-items {
            list Sensor-list {
                config "false";
                key "id";

                // Added containment: Prefix=sensor
                // Acquired From Package eqpt
                uses eqpt_Sensor-group;
            }
        }

        // Sprom Linecard
        container splc-items {

            // Added containment as a singleton: Prefix=splc
            // Acquired From Package eqpt
            uses eqpt_SpromLc-group;
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_FabP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }
        leaf speed {
            config "false";
            type uint64;
        }

        // ***************** MOs *******************    MO to send Adj info to dbgrelem from policyelem
        container remotePort-items {
            list RemotePort-list {
                config "false";
                key "lldpAdjEpInstId";

                // Added containment: Prefix=remotePort
                // Acquired From Package dbg
                uses dbg_RemotePort-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // Holder of some PE specific information of the port
        container lport-items {

            // Added containment as a singleton: Prefix=lport
            // Acquired From Package eqpt
            uses eqpt_LPort-group;
        }
    }

    grouping dbg_RemotePort-group {

        // Neighbor port description
        // Type is an MO-Defined-Type
        leaf remotePortDesc {
            config "false";
            description "Description of the Remote Port";

            // Type is an MO-Defined-Type
            type naming_Descr;
        }

        // Neighbor system description
        // Type is an MO-Defined-Type
        leaf remoteSysDesc {
            config "false";
            description "Description of the Remote System";

            // Type is an MO-Defined-Type
            type naming_Descr;
        }
        leaf remoteIp {
            config "false";
            type address_Ip;
        }

        // Local Interface ID of the port
        // Type is an MO-Defined-Type
        leaf LocalIfid {
            config "false";
            description "Interface ID of the Local Port";

            // Type is an MO-Defined-Type
            type nw_IfId;
        }
        leaf lldpAdjEpInstId {
            config "false";
            type string;
        }
    }

    grouping eqpt_LeafP-group {
        leaf ifId {
            config "false";
            type uint32;
            default "0";
        }
        leaf breakoutIfId {
            config "false";
            type uint32;
            default "0";
        }

        // Breakout Map
        // Type is an MO-Defined-Type
        // Default value handled in local MO type
        leaf breakoutMap {
            config "false";
            description "Breakout Map";

            // Type is a Local-MO-Defined-Type
            type im_BreakoutMapT_LeafP_breakoutMap;
        }

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }
        leaf speed {
            config "false";
            type uint64;
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // Holder of some PE specific information of the port
        container lport-items {

            // Added containment as a singleton: Prefix=lport
            // Acquired From Package eqpt
            uses eqpt_LPort-group;
        }
    }

    grouping eqpt_ExtChHP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }
        leaf speed {
            config "false";
            type uint64;
        }

        // Holder of some PE specific information of the port
        container lport-items {

            // Added containment as a singleton: Prefix=lport
            // Acquired From Package eqpt
            uses eqpt_LPort-group;
        }
    }

    grouping eqpt_ExtChFP-group {

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }
        leaf speed {
            config "false";
            type uint64;
        }

        // Holder of some PE specific information of the port
        container lport-items {

            // Added containment as a singleton: Prefix=lport
            // Acquired From Package eqpt
            uses eqpt_LPort-group;
        }
    }

    grouping eqpt_SpromLc-group {

        // Identifier for the item
        // Inherited From eqpt:Item
        // Modified by Override: eqpt:Sprom->id
        // Type is an MO-Defined-Type
        leaf id {
            config "false";
            description "ID";

            // Type is an MO-Defined-Type
            type eqpt_Id {
                range "1..100";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }

        // Sprom failure reason
        // Inherited From eqpt:Sprom
        // Type is an MO-Defined-Type
        leaf errRsn {
            config "false";
            description "Error Reason";

            // Type is an MO-Defined-Type
            type eqpt_SpErrRsn;
        }
        leaf numBlk {
            config "false";
            type uint16;
        }

        // sprom Common Block
        container spcmn-items {

            // Added containment as a singleton: Prefix=spcmn
            // Acquired From Package eqpt
            uses eqpt_SpCmnBlk-group;
        }

        // Sprom Linecard block
        container splcblk-items {

            // Added containment as a singleton: Prefix=splcblk
            // Acquired From Package eqpt
            uses eqpt_SpromLcBlk-group;
        }

        // sprom Port Data Interface
        container sppd-items {

            // Added containment as a singleton: Prefix=sppd
            // Acquired From Package eqpt
            uses eqpt_SpPd-group;
        }

        // sprom Sensor Data Interface
        container spsd-items {
            list SpSd-list {
                config "false";
                key "id";

                // Added containment: Prefix=spsd
                // Acquired From Package eqpt
                uses eqpt_SpSd-group;
            }
        }

        // Sprom Sensor block
        container spsensorblk-items {

            // Added containment as a singleton: Prefix=spsensorblk
            // Acquired From Package eqpt
            uses eqpt_SpSensorBlk-group;
        }
    }

    grouping eqpt_SpromLcBlk-group {
        leaf fbits {
            type uint64;
        }
        leaf hwCBits {
            type uint64;
        }
        leaf crdIdx {
            type uint16;
        }
        leaf macB {
            type string;
        }
        leaf macL {
            type uint16;
        }
        leaf eobcN {
            type uint16;
        }
        leaf epldN {
            type uint16;
        }
        leaf epldV {
            type uint16;
        }
        leaf sramSz {
            type uint16;
        }
        leaf maxCPwr {
            type uint16;
        }
        leaf coolRq {
            type uint16;
        }
        leaf ambT {
            type uint16;
        }
        leaf sig {
            type uint16;
        }
        leaf ver {
            type uint16;
        }
        leaf len {
            type uint16;
        }
        leaf cksum {
            type uint16;
        }

        // sprom Sensor Data Interface
        container spsd-items {
            list SpSd-list {
                config "false";
                key "id";

                // Added containment: Prefix=spsd
                // Acquired From Package eqpt
                uses eqpt_SpSd-group;
            }
        }

        // sprom Port Data Interface
        container sppd-items {

            // Added containment as a singleton: Prefix=sppd
            // Acquired From Package eqpt
            uses eqpt_SpPd-group;
        }
    }

    grouping eqpt_FCSlot-group {

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:FCSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Fabric Card, connecting different io cards
        container fc-items {

            // Added containment as a singleton: Prefix=fc
            // Acquired From Package eqpt
            uses eqpt_FC-group;
        }

        // Card reset record
        container rstrec-items {
            list CardRstRec-list {
                config "false";
                key "ts";

                // Added containment: Prefix=rstrec
                // Acquired From Package syshist
                uses syshist_CardRstRec-group;
            }
        }

        // Rel-def target from oosSlot
        // Inherited From eqpt:SupCSlot
        // Inherited From eqpt:LCSlot
        // Inherited From eqpt:FCSlot
        container rtoosSlot-items {

            // Added containment as a singleton: Prefix=rtoosSlot
            // Acquired From Package fabric
            uses fabric_RtOosSlot_target-group;
        }
    }

    grouping eqpt_FC-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Modified by Override: eqpt:FC->type
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // Information about each card firmware
        container running-items {

            // Added containment as a singleton: Prefix=running
            // Acquired From Package firmware
            uses firmware_CardRunning-group;
        }

        // Ejector information
        container ej-items {
            list Ejec-list {
                config "false";
                key "id";

                // Added containment: Prefix=ej
                // Acquired From Package eqpt
                uses eqpt_Ejec-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // cpu bound traffic port
        container cpuport-items {
            list CpuP-list {
                config "false";
                key "id";

                // Added containment: Prefix=cpuport
                // Acquired From Package eqpt
                uses eqpt_CpuP-group;
            }
        }

        // internal eobc (ethernet out of band channel) port
        // (all card component management is done via this port)
        container eobc-items {
            list EobcP-list {
                config "false";
                key "id";

                // Added containment: Prefix=eobc
                // Acquired From Package eqpt
                uses eqpt_EobcP-group;
            }
        }

        // internal epc port
        // (internal hi-gig links connecting the external io ports)
        container epc-items {
            list EpcP-list {
                config "false";
                key "id";

                // Added containment: Prefix=epc
                // Acquired From Package eqpt
                uses eqpt_EpcP-group;
            }
        }

        // Sensor information
        container sensor-items {
            list Sensor-list {
                config "false";
                key "id";

                // Added containment: Prefix=sensor
                // Acquired From Package eqpt
                uses eqpt_Sensor-group;
            }
        }

        // Sprom Linecard
        container splc-items {

            // Added containment as a singleton: Prefix=splc
            // Acquired From Package eqpt
            uses eqpt_SpromLc-group;
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_SysCSlot-group {

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:SysCSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // System Controller Card
        container sc-items {

            // Added containment as a singleton: Prefix=sc
            // Acquired From Package eqpt
            uses eqpt_SysC-group;
        }

        // Card reset record
        container rstrec-items {
            list CardRstRec-list {
                config "false";
                key "ts";

                // Added containment: Prefix=rstrec
                // Acquired From Package syshist
                uses syshist_CardRstRec-group;
            }
        }

        // Rel-def target from oosSlot
        // Inherited From eqpt:SupCSlot
        // Inherited From eqpt:LCSlot
        // Inherited From eqpt:FCSlot
        // Inherited From eqpt:SysCSlot
        container rtoosSlot-items {

            // Added containment as a singleton: Prefix=rtoosSlot
            // Acquired From Package fabric
            uses fabric_RtOosSlot_target-group;
        }
    }

    grouping eqpt_SysC-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Modified by Override: eqpt:SysC->type
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // Information about each card firmware
        container running-items {

            // Added containment as a singleton: Prefix=running
            // Acquired From Package firmware
            uses firmware_CardRunning-group;
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        // internal eobc (ethernet out of band channel) port
        // (all card component management is done via this port)
        container eobc-items {
            list EobcP-list {
                config "false";
                key "id";

                // Added containment: Prefix=eobc
                // Acquired From Package eqpt
                uses eqpt_EobcP-group;
            }
        }

        // internal epc port
        // (internal hi-gig links connecting the external io ports)
        container epc-items {
            list EpcP-list {
                config "false";
                key "id";

                // Added containment: Prefix=epc
                // Acquired From Package eqpt
                uses eqpt_EpcP-group;
            }
        }

        // Sensor information
        container sensor-items {
            list Sensor-list {
                config "false";
                key "id";

                // Added containment: Prefix=sensor
                // Acquired From Package eqpt
                uses eqpt_Sensor-group;
            }
        }

        // Sprom Linecard
        container splc-items {

            // Added containment as a singleton: Prefix=splc
            // Acquired From Package eqpt
            uses eqpt_SpromLc-group;
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_PsuSlot-group {

        // Identifier for the item
        // Inherited From eqpt:Item
        // Modified by Override: eqpt:PsuSlot->id
        // Modified by Override: eqpt:Cont->id
        // Modified by Override: eqpt:Slot->id
        // Type is an MO-Defined-Type
        leaf id {
            config "false";
            description "ID";

            // Type is an MO-Defined-Type
            type eqpt_Id {
                range "1..10";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:PsuSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // power supply slot
        container psu-items {

            // Added containment as a singleton: Prefix=psu
            // Acquired From Package eqpt
            uses eqpt_Psu-group;
        }

        // Rel-def target from oosSlot
        // Inherited From eqpt:SupCSlot
        // Inherited From eqpt:LCSlot
        // Inherited From eqpt:FCSlot
        // Inherited From eqpt:SysCSlot
        // Inherited From eqpt:ExtChCardSlot
        // Inherited From eqpt:PsuSlot
        container rtoosSlot-items {

            // Added containment as a singleton: Prefix=rtoosSlot
            // Acquired From Package fabric
            uses fabric_RtOosSlot_target-group;
        }
    }

    grouping eqpt_Psu-group {

        // Power supply status
        // Type is an MO-Defined-Type
        leaf operSt {
            config "false";
            description "Operational State";

            // Type is an MO-Defined-Type
            type eqpt_OpSt;
        }

        // Power supply capacity in centi Amps
        // Type is an MO-Defined-Type
        leaf cap {
            config "false";
            description "Capacity";

            // Type is an MO-Defined-Type
            type eqpt_Amps;
        }

        // Actual drawn current in centi Amps
        // Type is an MO-Defined-Type
        leaf drawnCurr {
            config "false";
            description "Capacity";

            // Type is an MO-Defined-Type
            type eqpt_Amps;
        }

        // Power supply voltage source
        // Type is an MO-Defined-Type
        leaf vSrc {
            config "false";
            description "Voltage Source";

            // Type is an MO-Defined-Type
            type eqpt_VSrc;
        }

        // Power supply voltage
        // Type is an MO-Defined-Type
        leaf volt {
            config "false";
            description "Voltage";

            // Type is an MO-Defined-Type
            type eqpt_Volts;
        }
        leaf almReg {
            config "false";
            type uint16;
        }

        // Power supply fan operational status
        // Type is an MO-Defined-Type
        leaf fanOpSt {
            config "false";
            description "Fan Operational State";

            // Type is an MO-Defined-Type
            type eqpt_OpSt;
        }

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Represents a fan in a fan tray
        container fan-items {
            list Fan-list {
                config "false";
                key "id";

                // Added containment: Prefix=fan
                // Acquired From Package eqpt
                uses eqpt_Fan-group;
            }
        }

        // Indicator LED
        container indled-items {
            list IndLed-list {
                config "false";
                key "id";

                // Added containment: Prefix=indled
                // Acquired From Package eqpt
                uses eqpt_IndLed-group;
            }
        }

        // Sprom Power Supply Unit
        container sppsu-items {

            // Added containment as a singleton: Prefix=sppsu
            // Acquired From Package eqpt
            uses eqpt_SpromPsu-group;
        }
    }

    grouping eqpt_Fan-group {

        // Fan operational status
        // Type is an MO-Defined-Type
        leaf operSt {
            config "false";
            description "Operational State";

            // Type is an MO-Defined-Type
            type eqpt_OpSt;
        }

        // Fan direction
        // Type is an MO-Defined-Type
        leaf dir {
            config "false";
            description "Operational State";

            // Type is an MO-Defined-Type
            type eqpt_AirDir;
        }

        // Identifier for the item
        // Inherited From eqpt:Item
        // Modified by Override: eqpt:Fan->id
        // Type is an MO-Defined-Type
        leaf id {
            config "false";
            description "ID";

            // Type is an MO-Defined-Type
            type eqpt_Id {
                range "1..10";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }
    }

    grouping eqpt_SpromPsu-group {

        // Identifier for the item
        // Inherited From eqpt:Item
        // Modified by Override: eqpt:Sprom->id
        // Type is an MO-Defined-Type
        leaf id {
            config "false";
            description "ID";

            // Type is an MO-Defined-Type
            type eqpt_Id {
                range "1..100";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }

        // Sprom failure reason
        // Inherited From eqpt:Sprom
        // Type is an MO-Defined-Type
        leaf errRsn {
            config "false";
            description "Error Reason";

            // Type is an MO-Defined-Type
            type eqpt_SpErrRsn;
        }
        leaf numBlk {
            config "false";
            type uint16;
        }

        // sprom Common Block
        container spcmn-items {

            // Added containment as a singleton: Prefix=spcmn
            // Acquired From Package eqpt
            uses eqpt_SpCmnBlk-group;
        }

        // Sprom Power Supply Unit block
        container sppsublk-items {

            // Added containment as a singleton: Prefix=sppsublk
            // Acquired From Package eqpt
            uses eqpt_SpromPsuBlk-group;
        }
    }

    grouping eqpt_SpromPsuBlk-group {
        leaf fbits {
            type uint64;
        }
        leaf c110v {
            type uint16;
        }
        leaf c220v {
            type uint16;
        }
        leaf smOID {
            type uint16;
        }
        leaf psCMd1 {
            type uint16;
        }
        leaf psCMd2 {
            type uint16;
        }
        leaf psCMd3 {
            type uint16;
        }
        leaf psCMd4 {
            type uint16;
        }
        leaf psCMxMd1 {
            type uint16;
        }
        leaf psCMxMd2 {
            type uint16;
        }
        leaf psCMxMd3 {
            type uint16;
        }
        leaf psCMxMd4 {
            type uint16;
        }
        leaf sig {
            type uint16;
        }
        leaf ver {
            type uint16;
        }
        leaf len {
            type uint16;
        }
        leaf cksum {
            type uint16;
        }
    }

    grouping eqpt_FtSlot-group {

        // Identifier for the item
        // Inherited From eqpt:Item
        // Modified by Override: eqpt:FtSlot->id
        // Modified by Override: eqpt:Cont->id
        // Modified by Override: eqpt:Slot->id
        // Type is an MO-Defined-Type
        leaf id {
            config "false";
            description "ID";

            // Type is an MO-Defined-Type
            type eqpt_Id {
                range "1..6";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:FtSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Represents an inventoried fan tray
        container ft-items {

            // Added containment as a singleton: Prefix=ft
            // Acquired From Package eqpt
            uses eqpt_Ft-group;
        }

        // Rel-def target from oosSlot
        // Inherited From eqpt:SupCSlot
        // Inherited From eqpt:LCSlot
        // Inherited From eqpt:FCSlot
        // Inherited From eqpt:SysCSlot
        // Inherited From eqpt:ExtChCardSlot
        // Inherited From eqpt:PsuSlot
        // Inherited From eqpt:FtSlot
        container rtoosSlot-items {

            // Added containment as a singleton: Prefix=rtoosSlot
            // Acquired From Package fabric
            uses fabric_RtOosSlot_target-group;
        }
    }

    grouping eqpt_Ft-group {

        // Fan tray operational status
        // Type is an MO-Defined-Type
        leaf operSt {
            config "false";
            description "Operational State";

            // Type is an MO-Defined-Type
            type eqpt_OpSt;
        }
        leaf fanletFailString {
            config "false";
            type string;
        }
        leaf fanName {
            config "false";
            type string;
        }

        // Identifier for the item
        // Inherited From eqpt:Item
        // Modified by Override: eqpt:Ft->id
        // Type is an MO-Defined-Type
        leaf id {
            config "false";
            description "ID";

            // Type is an MO-Defined-Type
            type eqpt_Id {
                range "1..4";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Ejector information
        container ej-items {
            list Ejec-list {
                config "false";
                key "id";

                // Added containment: Prefix=ej
                // Acquired From Package eqpt
                uses eqpt_Ejec-group;
            }
        }

        // Represents a fan in a fan tray
        container fan-items {
            list Fan-list {
                config "false";
                key "id";

                // Added containment: Prefix=fan
                // Acquired From Package eqpt
                uses eqpt_Fan-group;
            }
        }

        // Indicator LED
        container indled-items {
            list IndLed-list {
                config "false";
                key "id";

                // Added containment: Prefix=indled
                // Acquired From Package eqpt
                uses eqpt_IndLed-group;
            }
        }

        // Locator LED on chassis components
        container locled-items {
            list LocLed-list {
                config "false";
                key "id";

                // Added containment: Prefix=locled
                // Acquired From Package eqpt
                uses eqpt_LocLed-group;
            }
        }

        container spfan-items {

            // Added containment as a singleton: Prefix=spfan
            // Acquired From Package eqpt
            uses eqpt_SpromFan-group;
        }
    }

    grouping eqpt_SpromFan-group {

        // Identifier for the item
        // Inherited From eqpt:Item
        // Modified by Override: eqpt:Sprom->id
        // Type is an MO-Defined-Type
        leaf id {
            config "false";
            description "ID";

            // Type is an MO-Defined-Type
            type eqpt_Id {
                range "1..100";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }

        // Sprom failure reason
        // Inherited From eqpt:Sprom
        // Type is an MO-Defined-Type
        leaf errRsn {
            config "false";
            description "Error Reason";

            // Type is an MO-Defined-Type
            type eqpt_SpErrRsn;
        }
        leaf numBlk {
            config "false";
            type uint16;
        }

        // sprom Common Block
        container spcmn-items {

            // Added containment as a singleton: Prefix=spcmn
            // Acquired From Package eqpt
            uses eqpt_SpCmnBlk-group;
        }

        // Sprom FAN block
        container spfanblk-items {

            // Added containment as a singleton: Prefix=spfanblk
            // Acquired From Package eqpt
            uses eqpt_SpromFanBlk-group;
        }

        // Fan Serial Number
        container spfansn-items {

            // Added containment as a singleton: Prefix=spfansn
            // Acquired From Package eqpt
            uses eqpt_SpromFanSN-group;
        }
    }

    grouping eqpt_SpromFanBlk-group {
        leaf fbits {
            type uint64;
        }
        leaf hwCBits {
            type uint64;
        }
        leaf stackMIB {
            type uint16;
        }
        leaf coolCap {
            type uint16;
        }
        leaf ambTemp {
            type uint16;
        }
        leaf hpPwrCon {
            type uint16;
        }
        leaf hpCoolCon {
            type uint16;
        }
        leaf sig {
            type uint16;
        }
        leaf ver {
            type uint16;
        }
        leaf len {
            type uint16;
        }
        leaf cksum {
            type uint16;
        }
    }

    grouping eqpt_SpromFanSN-group {

        // Serial Number
        // Type is an MO-Defined-Type
        leaf serNum {
            description "Serial Number";

            // Type is an MO-Defined-Type
            type eqpt_Serial;
        }
        leaf sig {
            type uint16;
        }
        leaf ver {
            type uint16;
        }
        leaf len {
            type uint16;
        }
        leaf cksum {
            type uint16;
        }
    }

    grouping eqpt_SpromBP-group {

        // Identifier for the item
        // Inherited From eqpt:Item
        // Modified by Override: eqpt:Sprom->id
        // Type is an MO-Defined-Type
        leaf id {
            config "false";
            description "ID";

            // Type is an MO-Defined-Type
            type eqpt_Id {
                range "1..100";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Type of the memory
        // Inherited From eqpt:Mem
        // Type is an MO-Defined-Type
        leaf type {
            config "false";
            description "Type";

            // Type is an MO-Defined-Type
            type eqpt_MemT;
        }

        // capacity
        // Inherited From eqpt:Mem
        // Type is an MO-Defined-Type
        leaf cap {
            config "false";
            description "Capacity";

            // Type is an MO-Defined-Type
            type eqpt_Capacity;
        }

        // access: RO/RW
        // Inherited From eqpt:Mem
        // Type is an MO-Defined-Type
        leaf acc {
            config "false";
            description "Access";

            // Type is an MO-Defined-Type
            type eqpt_Acc;
        }

        // Operational status
        // Inherited From eqpt:Mem
        // Type is an MO-Defined-Type
        leaf operSt {
            config "false";
            description "Operational State";

            // Type is an MO-Defined-Type
            type eqpt_OpSt;
        }

        // Sprom failure reason
        // Inherited From eqpt:Sprom
        // Type is an MO-Defined-Type
        leaf errRsn {
            config "false";
            description "Error Reason";

            // Type is an MO-Defined-Type
            type eqpt_SpErrRsn;
        }
        leaf numBlk {
            config "false";
            type uint16;
        }

        // sprom Common Block
        container spcmn-items {

            // Added containment as a singleton: Prefix=spcmn
            // Acquired From Package eqpt
            uses eqpt_SpCmnBlk-group;
        }

        // Sprom BP block
        container spbpblk-items {

            // Added containment as a singleton: Prefix=spbpblk
            // Acquired From Package eqpt
            uses eqpt_SpromBPBlk-group;
        }

        // Backplane sprom WWN
        container bpspwwn-items {

            // Added containment as a singleton: Prefix=bpspwwn
            // Acquired From Package eqpt
            uses eqpt_BpSpWWN-group;
        }

        // Backplane sprom License
        container bpsplic-items {

            // Added containment as a singleton: Prefix=bpsplic
            // Acquired From Package eqpt
            uses eqpt_BpSpLic-group;
        }

        // Backplane Second Serial Number
        container bpspssn-items {

            // Added containment as a singleton: Prefix=bpspssn
            // Acquired From Package eqpt
            uses eqpt_BpSpSSN-group;
        }
    }

    grouping eqpt_SpromBPBlk-group {
        leaf fbits {
            type uint64;
        }
        leaf hwCBits {
            type uint64;
        }
        leaf macB {
            type string;
        }
        leaf macL {
            type uint16;
        }
        leaf stackMIB {
            type uint16;
        }
        leaf oemEprise {
            type uint16;
        }
        leaf oemMIB {
            type uint16;
        }
        leaf coolCoe {
            type uint16;
        }
        leaf maxCPwr {
            type uint16;
        }
        leaf sig {
            type uint16;
        }
        leaf ver {
            type uint16;
        }
        leaf len {
            type uint16;
        }
        leaf cksum {
            type uint16;
        }
    }

    grouping eqpt_BpSpWWN-group {
        leaf uBits {
            type string;
        }
        leaf sig {
            type uint16;
        }
        leaf ver {
            type uint16;
        }
        leaf len {
            type uint16;
        }
        leaf cksum {
            type uint16;
        }
    }

    grouping eqpt_BpSpLic-group {
        leaf uBits {
            type string;
        }
        leaf sig {
            type uint16;
        }
        leaf ver {
            type uint16;
        }
        leaf len {
            type uint16;
        }
        leaf cksum {
            type uint16;
        }
    }

    grouping eqpt_BpSpSSN-group {

        // Serial Number
        // Type is an MO-Defined-Type
        leaf serNum {
            description "Serial Number";

            // Type is an MO-Defined-Type
            type eqpt_Serial;
        }
        leaf sig {
            type uint16;
        }
        leaf ver {
            type uint16;
        }
        leaf len {
            type uint16;
        }
        leaf cksum {
            type uint16;
        }
    }

    grouping eqpt_BSlot-group {

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:BSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Board represents the motherboard of the Controller
        container board-items {

            // Added containment as a singleton: Prefix=board
            // Acquired From Package eqpt
            uses eqpt_Board-group;
        }

        // Rel-def target from oosSlot
        // Inherited From eqpt:SupCSlot
        // Inherited From eqpt:LCSlot
        // Inherited From eqpt:FCSlot
        // Inherited From eqpt:SysCSlot
        // Inherited From eqpt:ExtChCardSlot
        // Inherited From eqpt:PsuSlot
        // Inherited From eqpt:FtSlot
        // Inherited From eqpt:BSlot
        container rtoosSlot-items {

            // Added containment as a singleton: Prefix=rtoosSlot
            // Acquired From Package fabric
            uses fabric_RtOosSlot_target-group;
        }
    }

    grouping eqpt_Board-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // Sensor information
        container sensor-items {
            list Sensor-list {
                config "false";
                key "id";

                // Added containment: Prefix=sensor
                // Acquired From Package eqpt
                uses eqpt_Sensor-group;
            }
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_NSlot-group {

        // Identifier for the item
        // Inherited From eqpt:Item
        // Modified by Override: eqpt:Cont->id
        // Modified by Override: eqpt:Slot->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:NSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Nic represents the NIC Card
        container nic-items {
            list Nic-list {
                config "false";
                key "id";

                // Added containment: Prefix=nic
                // Acquired From Package eqpt
                uses eqpt_Nic-group;
            }
        }

        // Rel-def target from oosSlot
        // Inherited From eqpt:SupCSlot
        // Inherited From eqpt:LCSlot
        // Inherited From eqpt:FCSlot
        // Inherited From eqpt:SysCSlot
        // Inherited From eqpt:ExtChCardSlot
        // Inherited From eqpt:PsuSlot
        // Inherited From eqpt:FtSlot
        // Inherited From eqpt:BSlot
        // Inherited From eqpt:NSlot
        container rtoosSlot-items {

            // Added containment as a singleton: Prefix=rtoosSlot
            // Acquired From Package fabric
            uses fabric_RtOosSlot_target-group;
        }
    }

    grouping eqpt_Nic-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }

        // External Ext Port for Controller
        container eaport-items {
            list ExtAP-list {
                config "false";
                key "id";

                // Added containment: Prefix=eaport
                // Acquired From Package eqpt
                uses eqpt_ExtAP-group;
            }
        }

        // Sensor information
        container sensor-items {
            list Sensor-list {
                config "false";
                key "id";

                // Added containment: Prefix=sensor
                // Acquired From Package eqpt
                uses eqpt_Sensor-group;
            }
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_ExtAP-group {

        // port status
        // Type is an MO-Defined-Type
        leaf operSt {
            config "false";
            description "Operational Status";

            // Type is an MO-Defined-Type
            type eqpt_OpSt;
        }

        // Identifier for the item
        // Inherited From eqpt:Item
        // Modified by Override: eqpt:Cont->id
        // Modified by Override: eqpt:Port->id
        // Type is an MO-Defined-Type
        leaf id {
            config "false";
            description "ID";

            // Type is an MO-Defined-Type
            type eqpt_Id {
                range "1..666";
            }
        }

        // From Interface naming:Described
        // Inherited From eqpt:Cont
        // Type is an MO-Defined-Type
        leaf descr {
            description "Description";

            // Type is an MO-Defined-Type
            type naming_Descr;
        }

        // Type of port
        // Inherited From eqpt:Port
        // Type is an MO-Defined-Type
        leaf type {
            config "false";
            description "Type";

            // Type is an MO-Defined-Type
            type eqpt_PortT;
        }

        // Holder of some PE specific information of the port
        container lport-items {

            // Added containment as a singleton: Prefix=lport
            // Acquired From Package eqpt
            uses eqpt_LPort-group;
        }
    }

    grouping eqpt_Storage-group {

        // Type is an MO-Defined-Type
        leaf fileSystem {
            config "false";
            description "File System";

            // Type is an MO-Defined-Type
            type comp_DelimitedString;
        }

        // Type is an MO-Defined-Type
        leaf blocks {
            config "false";
            description "Blocks";

            // Type is an MO-Defined-Type
            type eqpt_Capacity;
        }

        // Type is an MO-Defined-Type
        leaf used {
            config "false";
            description "Capacity Used";

            // Type is an MO-Defined-Type
            type eqpt_Capacity;
        }

        // Type is an MO-Defined-Type
        leaf available {
            config "false";
            description "Capacity Available";

            // Type is an MO-Defined-Type
            type eqpt_Capacity;
        }
        leaf capUtilized {
            config "false";
            type uint8;
        }

        // Type is an MO-Defined-Type
        leaf mount {
            config "false";
            description "Mounted On";

            // Type is an MO-Defined-Type
            type comp_DelimitedString;
        }

        // port status
        // Type is an MO-Defined-Type
        leaf operSt {
            config "false";
            description "Operational Status";

            // Type is an MO-Defined-Type
            type eqpt_OpSt;
        }
        leaf failReason {
            config "false";
            type string;
        }

        // From Interface naming:Named
        // Inherited From naming:NamedObject
        // Type is an MO-Defined-Type
        leaf name {
            description "Name";

            // Type is an MO-Defined-Type
            type naming_Name;
        }
    }

    grouping eqpt_ExtCh-group {

        // State of the extended chassis
        // Type is an MO-Defined-Type
        leaf extChSt {
            config "false";
            description "State";

            // Type is an MO-Defined-Type
            type eqpt_ExtChSt;
        }

        // Part number of the extended chassis
        // Type is an MO-Defined-Type
        leaf partNum {
            config "false";
            description "TBD";

            // Type is an MO-Defined-Type
            type eqpt_PartNum;
        }

        // MAC address of the extended chassis
        // Type is an MO-Defined-Type
        leaf macAddr {
            config "false";
            description "MAC Address";

            // Type is an MO-Defined-Type
            type eqpt_MacAddr;
        }

        // Number of macs supported
        // Type is an MO-Defined-Type
        leaf numMacs {
            config "false";
            description "MACs Supported";

            // Type is an MO-Defined-Type
            type eqpt_ExtChNumMacs;
        }

        // Number of uplink ports supported
        // Type is an MO-Defined-Type
        leaf numUplinkP {
            config "false";
            description "Number of Uplink Ports";

            // Type is an MO-Defined-Type
            type eqpt_ExtChNumUplinkP;
        }

        // The vendor manufacturing this device.
        // From Interface eqpt:Dev
        // Type is an MO-Defined-Type
        leaf vendor {
            config "false";
            description "Vendor";

            // Type is an MO-Defined-Type
            type eqpt_Vendor;
        }

        // The device model
        // From Interface eqpt:Dev
        // Type is an MO-Defined-Type
        leaf model {
            config "false";
            description "Model";

            // Type is an MO-Defined-Type
            type eqpt_Model;
        }

        // The device revision.
        // From Interface eqpt:Dev
        // Type is an MO-Defined-Type
        leaf rev {
            config "false";
            description "Revision";

            // Type is an MO-Defined-Type
            type eqpt_Revision;
        }

        // The device serial number.
        // From Interface eqpt:Dev
        // Type is an MO-Defined-Type
        leaf ser {
            config "false";
            description "Serial Number";

            // Type is an MO-Defined-Type
            type eqpt_Serial;
        }
        leaf mfgTm {
            config "false";
            type uint64;
            default "0";
        }

        // Identifier for the item
        // Inherited From eqpt:Item
        // Modified by Override: eqpt:ExtCh->id
        // Modified by Override: eqpt:Cont->id
        // Type is an MO-Defined-Type
        leaf id {
            config "false";
            description "ID";

            // Type is an MO-Defined-Type
            type eqpt_Id {
                range "101..199";
            }
        }

        // From Interface naming:Described
        // Inherited From eqpt:Cont
        // Type is an MO-Defined-Type
        leaf descr {
            description "Description";

            // Type is an MO-Defined-Type
            type naming_Descr;
        }

        // Information about extended chassis firmware
        container running-items {

            // Added containment as a singleton: Prefix=running
            // Acquired From Package firmware
            uses firmware_ExtChRunning-group;
        }

        // Locator LED on extended chassis components
        container locled-items {
            list ExtChLocLed-list {
                config "false";
                key "id";

                // Added containment: Prefix=locled
                // Acquired From Package eqpt
                uses eqpt_ExtChLocLed-group;
            }
        }

        // Extended chassis card slot
        container extchslot-items {
            list ExtChCardSlot-list {
                config "false";
                key "id";

                // Added containment: Prefix=extchslot
                // Acquired From Package eqpt
                uses eqpt_ExtChCardSlot-group;
            }
        }

        // power supply slot
        container psuslot-items {
            list PsuSlot-list {
                config "false";
                key "id";

                // Added containment: Prefix=psuslot
                // Acquired From Package eqpt
                uses eqpt_PsuSlot-group;
            }
        }

        // fan tray slot
        container ftslot-items {
            list FtSlot-list {
                config "false";
                key "id";

                // Added containment: Prefix=ftslot
                // Acquired From Package eqpt
                uses eqpt_FtSlot-group;
            }
        }

        // Sprom Backplane Unit block
        container spbp-items {

            // Added containment as a singleton: Prefix=spbp
            // Acquired From Package eqpt
            uses eqpt_SpromBP-group;
        }

        // Sprom Supervisor
        container spsup-items {

            // Added containment as a singleton: Prefix=spsup
            // Acquired From Package eqpt
            uses eqpt_SpromSup-group;
        }
    }

    grouping firmware_ExtChRunning-group {

        // Loader version
        // Type is an MO-Defined-Type
        leaf loaderVer {
            config "false";
            description "Loader Version";

            // Type is an MO-Defined-Type
            type cap_Version;
        }

        // Running firmware version.
        // Inherited From firmware:ARunning
        // Type is an MO-Defined-Type
        leaf version {
            config "false";
            description "Version";

            // Type is an MO-Defined-Type
            type cap_Version;
        }
        leaf internalLabel {
            type string;
        }

        // Running firmware type.
        // Inherited From firmware:ARunning
        // Type is an MO-Defined-Type
        leaf type {
            config "false";
            description "Type";

            // Type is an MO-Defined-Type
            type firmware_Type;
        }

        // Running firmware mode.
        // Inherited From firmware:ARunning
        // Type is an MO-Defined-Type
        leaf mode {
            config "false";
            description "Mode";

            // Type is an MO-Defined-Type
            type firmware_RunningMode;
        }
        leaf ts {
            config "false";
            type uint64;
        }

        // From Interface naming:Described
        // Inherited From firmware:ARunning
        // Type is an MO-Defined-Type
        leaf descr {
            description "Description";

            // Type is an MO-Defined-Type
            type naming_Descr;
        }
    }

    grouping eqpt_ExtChLocLed-group {

        // Identifier for the item
        // Inherited From eqpt:Item
        // Type is an MO-Defined-Type
        leaf id {
            config "false";
            description "ID";

            // Type is an MO-Defined-Type
            type eqpt_Id;
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Color status of an LED
        // Inherited From eqpt:Led
        // Type is an MO-Defined-Type
        leaf color {
            config "false";
            description "Color";

            // Type is an MO-Defined-Type
            type eqpt_Color;
        }

        // Operational status of an LED
        // Inherited From eqpt:Led
        // Type is an MO-Defined-Type
        leaf operSt {
            config "false";
            description "Operational State";

            // Type is an MO-Defined-Type
            type eqpt_LedOpSt;
        }

        // LED type
        // Inherited From eqpt:Led
        // Type is an MO-Defined-Type
        leaf type {
            config "false";
            description "Type";

            // Type is an MO-Defined-Type
            type eqpt_LedType;
        }

        // Admin status - Used to locate
        // Inherited From eqpt:ALocLed
        // Type is an MO-Defined-Type
        leaf adminSt {
            description "Admin State";

            // Type is an MO-Defined-Type
            type eqpt_AdSt;
        }
    }

    grouping eqpt_ExtChCardSlot-group {

        // Identifier for the item
        // Inherited From eqpt:Item
        // Modified by Override: eqpt:ExtChCardSlot->id
        // Modified by Override: eqpt:Cont->id
        // Modified by Override: eqpt:Slot->id
        // Type is an MO-Defined-Type
        leaf id {
            config "false";
            description "ID";

            // Type is an MO-Defined-Type
            type eqpt_Id {
                range "1";
            }
        }

        // From Interface naming:Described
        // Inherited From eqpt:Cont
        // Type is an MO-Defined-Type
        leaf descr {
            description "Description";

            // Type is an MO-Defined-Type
            type naming_Descr;
        }

        // Physical Slot ID
        // Inherited From eqpt:Slot
        // Type is an MO-Defined-Type
        leaf physId {
            config "false";
            description "Physical Slot";

            // Type is an MO-Defined-Type
            type eqpt_Id;
        }

        // type of the slot
        // Inherited From eqpt:Slot
        // Modified by Override: eqpt:ExtChCardSlot->type
        // Type is an MO-Defined-Type
        leaf type {
            config "false";
            description "Type";

            // Type is an MO-Defined-Type
            type eqpt_SlotT;
        }

        // slot status: is it empty or inserted
        // Inherited From eqpt:Slot
        // Type is an MO-Defined-Type
        leaf operSt {
            config "false";
            description "Operational State";

            // Type is an MO-Defined-Type
            type eqpt_SlotOpSt;
        }

        // status of the card currently present in the slot
        // Inherited From eqpt:Slot
        // Type is an MO-Defined-Type
        leaf cardOperSt {
            config "false";
            description "Card Operational State";

            // Type is an MO-Defined-Type
            type eqpt_SlotCardOpSt;
        }

        // location of the slot in the chassis (front/back)
        // Inherited From eqpt:Slot
        // Type is an MO-Defined-Type
        leaf loc {
            config "false";
            description "Location";

            // Type is an MO-Defined-Type
            type eqpt_SlotLoc;
        }

        // Module on extension chassis
        container extchc-items {

            // Added containment as a singleton: Prefix=extchc
            // Acquired From Package eqpt
            uses eqpt_ExtChCard-group;
        }

        // Extended chassis card reset record
        container rstrec-items {
            list ExtChCardRstRec-list {
                config "false";
                key "ts";

                // Added containment: Prefix=rstrec
                // Acquired From Package syshist
                uses syshist_ExtChCardRstRec-group;
            }
        }

        // Rel-def target from oosSlot
        // Inherited From eqpt:SupCSlot
        // Inherited From eqpt:LCSlot
        // Inherited From eqpt:FCSlot
        // Inherited From eqpt:SysCSlot
        // Inherited From eqpt:ExtChCardSlot
        container rtoosSlot-items {

            // Added containment as a singleton: Prefix=rtoosSlot
            // Acquired From Package fabric
            uses fabric_RtOosSlot_target-group;
        }
    }

    grouping eqpt_ExtChCard-group {

        // Module serial number
        // Type is an MO-Defined-Type
        leaf modSerial {
            config "false";
            description "Serial Number";

            // Type is an MO-Defined-Type
            type eqpt_Serial;
        }

        // Module vendor
        // Type is an MO-Defined-Type
        leaf modVendor {
            config "false";
            description "Vendor";

            // Type is an MO-Defined-Type
            type eqpt_Vendor;
        }

        // Module model
        // Type is an MO-Defined-Type
        leaf modModel {
            config "false";
            description "Model";

            // Type is an MO-Defined-Type
            type eqpt_Model;
        }

        // Module Part number
        // Type is an MO-Defined-Type
        leaf partNum {
            config "false";
            description "Module Part Number";

            // Type is an MO-Defined-Type
            type eqpt_PartNum;
        }

        // The vendor manufacturing this device.
        // From Interface eqpt:Dev
        // Type is an MO-Defined-Type
        leaf vendor {
            config "false";
            description "Vendor";

            // Type is an MO-Defined-Type
            type eqpt_Vendor;
        }

        // The device model
        // From Interface eqpt:Dev
        // Type is an MO-Defined-Type
        leaf model {
            config "false";
            description "Model";

            // Type is an MO-Defined-Type
            type eqpt_Model;
        }

        // The device revision.
        // From Interface eqpt:Dev
        // Type is an MO-Defined-Type
        leaf rev {
            config "false";
            description "Revision";

            // Type is an MO-Defined-Type
            type eqpt_Revision;
        }

        // The device serial number.
        // From Interface eqpt:Dev
        // Type is an MO-Defined-Type
        leaf ser {
            config "false";
            description "Serial Number";

            // Type is an MO-Defined-Type
            type eqpt_Serial;
        }

        // Identifier for the item
        // Inherited From eqpt:Item
        // Type is an MO-Defined-Type
        leaf id {
            config "false";
            description "ID";

            // Type is an MO-Defined-Type
            type eqpt_Id;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Hardware version for this fru
        // Inherited From eqpt:Fru
        // Type is an MO-Defined-Type
        leaf hwVer {
            config "false";
            description "Hardware Version";

            // Type is an MO-Defined-Type
            type cap_Version;
        }

        // Type of card
        // Inherited From eqpt:Card
        // Modified by Override: eqpt:ExtChCard->type
        // Type is an MO-Defined-Type
        leaf type {
            config "false";
            description "Type";

            // Type is an MO-Defined-Type
            type eqpt_CardT;
        }

        // Card status
        // Inherited From eqpt:Card
        // Type is an MO-Defined-Type
        leaf operSt {
            config "false";
            description "Operational State";

            // Type is an MO-Defined-Type
            type eqpt_COpSt;
        }

        // Redundancy state
        // Inherited From eqpt:Card
        // Type is an MO-Defined-Type
        leaf rdSt {
            config "false";
            description "Redundancy State";

            // Type is an MO-Defined-Type
            type eqpt_RdSt;
        }

        // Software card ID
        // Inherited From eqpt:Card
        // Type is an MO-Defined-Type
        leaf swCId {
            config "false";
            description "Software Module ID";

            // Type is an MO-Defined-Type
            type eqpt_CardId;
        }

        // Number of ports on the card
        // Inherited From eqpt:Card
        // Type is an MO-Defined-Type
        leaf numP {
            config "false";
            description "Number of Ports";

            // Type is an MO-Defined-Type
            type eqpt_CardNumPorts;
        }

        // mac address base
        // Inherited From eqpt:Card
        // Type is an MO-Defined-Type
        leaf macB {
            config "false";
            description "MAC Address Base";

            // Type is an MO-Defined-Type
            type eqpt_MacAddr;
        }

        // mac address length
        // Inherited From eqpt:Card
        // Type is an MO-Defined-Type
        leaf macL {
            config "false";
            description "MAC Address Length";

            // Type is an MO-Defined-Type
            type eqpt_MacAddrLen;
        }
        leaf upTs {
            config "false";
            type uint64;
        }

        // power state of this card
        // Inherited From eqpt:Card
        // Type is an MO-Defined-Type
        leaf pwrSt {
            config "false";
            description "Power State";

            // Type is an MO-Defined-Type
            type eqpt_PwrState;
        }
        container extchcpu-items {
            list ExtChCPU-list {
                config "false";
                key "id";

                // Added containment: Prefix=extchcpu
                // Acquired From Package eqpt
                uses eqpt_ExtChCPU-group;
            }
        }

        // Extension chassis port connected to hosts
        container hostextport-items {
            list ExtChHP-list {
                config "false";
                key "id";

                // Added containment: Prefix=hostextport
                // Acquired From Package eqpt
                uses eqpt_ExtChHP-group;
            }
        }

        // Extension chassis port connected to Leaf
        container leafextport-items {
            list ExtChFP-list {
                config "false";
                key "id";

                // Added containment: Prefix=leafextport
                // Acquired From Package eqpt
                uses eqpt_ExtChFP-group;
            }
        }

        // Sensor information
        container sensor-items {
            list Sensor-list {
                config "false";
                key "id";

                // Added containment: Prefix=sensor
                // Acquired From Package eqpt
                uses eqpt_Sensor-group;
            }
        }

        // ASIC information container
        container asic-items {
            list Asic-list {
                config "false";
                key "id";

                // Added containment: Prefix=asic
                // Acquired From Package eqpt
                uses eqpt_Asic-group;
            }
        }
        container cpu-items {
            list CPU-list {
                config "false";
                key "id";

                // Added containment: Prefix=cpu
                // Acquired From Package eqpt
                uses eqpt_CPU-group;
            }
        }

        // Fpga container
        container fpga-items {
            list Fpga-list {
                config "false";
                key "id";

                // Added containment: Prefix=fpga
                // Acquired From Package eqpt
                uses eqpt_Fpga-group;
            }
        }

        // Dimm memory unit
        container dimm-items {
            list Dimm-list {
                config "false";
                key "id";

                // Added containment: Prefix=dimm
                // Acquired From Package eqpt
                uses eqpt_Dimm-group;
            }
        }

        // Flash memory unit
        container flash-items {

            // Added containment as a singleton: Prefix=flash
            // Acquired From Package eqpt
            uses eqpt_Flash-group;
        }

        // OBFL (OnBoard Failure Log) information
        container obfl-items {

            // Added containment as a singleton: Prefix=obfl
            // Acquired From Package eqpt
            uses eqpt_Obfl-group;
        }
    }

    grouping eqpt_ExtChCPU-group {

        // Identifier for the item
        // Inherited From eqpt:Item
        // Modified by Override: eqpt:ACPU->id
        // Type is an MO-Defined-Type
        leaf id {
            config "false";
            description "ID";

            // Type is an MO-Defined-Type
            type eqpt_Id {
                range "1";
            }
        }

        // The vendor manufacturing this device.
        // From Interface eqpt:Dev
        // Inherited From eqpt:Comp
        // Type is an MO-Defined-Type
        leaf vendor {
            config "false";
            description "Vendor";

            // Type is an MO-Defined-Type
            type eqpt_Vendor;
        }

        // The device model
        // From Interface eqpt:Dev
        // Inherited From eqpt:Comp
        // Type is an MO-Defined-Type
        leaf model {
            config "false";
            description "Model";

            // Type is an MO-Defined-Type
            type eqpt_Model;
        }

        // The device revision.
        // From Interface eqpt:Dev
        // Inherited From eqpt:Comp
        // Type is an MO-Defined-Type
        leaf rev {
            config "false";
            description "Revision";

            // Type is an MO-Defined-Type
            type eqpt_Revision;
        }

        // The device serial number.
        // From Interface eqpt:Dev
        // Inherited From eqpt:Comp
        // Type is an MO-Defined-Type
        leaf ser {
            config "false";
            description "Serial Number";

            // Type is an MO-Defined-Type
            type eqpt_Serial;
        }
        leaf mfgTm {
            config "false";
            type uint64;
            default "0";
        }

        // From Interface naming:Described
        // Inherited From eqpt:Comp
        // Type is an MO-Defined-Type
        leaf descr {
            description "Description";

            // Type is an MO-Defined-Type
            type naming_Descr;
        }

        // Socket designation
        // Inherited From eqpt:ACPU
        // Type is an MO-Defined-Type
        leaf sock {
            config "false";
            description "Socket";

            // Type is an MO-Defined-Type
            type eqpt_Sock;
        }

        // Architecture of the CPU
        // Inherited From eqpt:ACPU
        // Type is an MO-Defined-Type
        leaf arch {
            config "false";
            description "Architecture";

            // Type is a Local-MO-Defined-Type
            type eqpt_Arch_ExtChCPU_arch;
        }

        // CPU speed
        // Inherited From eqpt:ACPU
        // Type is an MO-Defined-Type
        leaf speed {
            config "false";
            description "Speed";

            // Type is an MO-Defined-Type
            type eqpt_Speed;
        }

        // Number of cores on the CPU
        // Inherited From eqpt:ACPU
        // Type is an MO-Defined-Type
        leaf cores {
            config "false";
            description "Cores";

            // Type is an MO-Defined-Type
            type eqpt_Cores;
        }

        // Number of cores enabled on the CPU
        // Inherited From eqpt:ACPU
        // Type is an MO-Defined-Type
        leaf coresEn {
            config "false";
            description "Cores Enabled";

            // Type is an MO-Defined-Type
            type eqpt_Cores;
        }
        leaf thrds {
            config "false";
            type uint16;
        }
    }

    grouping syshist_ExtChCardRstRec-group {
        leaf ts {
            config "false";
            type uint64;
        }

        // Reset reason
        // Inherited From syshist:RstRec
        // Type is an MO-Defined-Type
        leaf reason {
            config "false";
            description "Reset Reason";

            // Type is an MO-Defined-Type
            type syshist_RstRsn;
        }

        // Reset reason qualifier
        // Inherited From syshist:RstRec
        // Type is an MO-Defined-Type
        leaf reasonQual {
            config "false";
            description "Reset Reason Qualifier";

            // Type is an MO-Defined-Type
            type syshist_RstRsnQual;
        }

        // Version with which the reset happened
        // Inherited From syshist:RstRec
        // Type is an MO-Defined-Type
        leaf ver {
            config "false";
            description "Reset Reason";

            // Type is an MO-Defined-Type
            type cap_Version;
        }
    }

    grouping eqpt_Entity-group {

        // From Interface naming:Named
        // Inherited From naming:NamedObject
        // Modified by Override: pol:Obj->name
        // Type is an MO-Defined-Type
        leaf name {
            description "Name";

            // Type is an MO-Defined-Type
            type naming_Name {
                length "0..64";
            }
        }

        // console policy
        container consolep-items {

            // Added containment as a singleton: Prefix=consolep
            // Acquired From Package eqpt
            uses eqpt_ConsoleP-group;
        }

        // Power supply group policy
        container psgp-items {

            // Added containment as a singleton: Prefix=psgp
            // Acquired From Package eqpt
            uses eqpt_PsgP-group;
        }

        // Policy container for slot
        container slot-items {
            list SlotP-list {
                config "false";
                key "type id";

                // Added containment: Prefix=slot
                // Acquired From Package eqpt
                uses eqpt_SlotP-group;
            }
        }
    }

    grouping eqpt_ConsoleP-group {

        // num of databits per character
        // Type is an MO-Defined-Type
        leaf dataBits {
            config "false";
            description "Data Bits";

            // Type is an MO-Defined-Type
            type eqpt_DataBits;
        }

        // timeout for an inactive session in minutes
        // Type is an MO-Defined-Type
        leaf inactiveIntvl {
            config "false";
            description "Inactive Interval";

            // Type is an MO-Defined-Type
            type eqpt_InactiveIntvl;
        }

        // Terminal parity none, even or odd
        // Type is an MO-Defined-Type
        leaf parity {
            config "false";
            description "Parity";

            // Type is an MO-Defined-Type
            type eqpt_Parity;
        }

        // transmit and receive speed on console port
        // Type is an MO-Defined-Type
        leaf baudRate {
            config "false";
            description "Baud Rate";

            // Type is an MO-Defined-Type
            type eqpt_BaudRate;
        }

        // Async line stopbits
        // Type is an MO-Defined-Type
        leaf stopBits {
            config "false";
            description "Stop Bits";

            // Type is an MO-Defined-Type
            type eqpt_StopBits;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping eqpt_PsgP-group {

        // Admin redundancy mode
        // Type is an MO-Defined-Type
        leaf adminRdnM {
            config "false";
            description "Admin Redundancy Mode";

            // Type is an MO-Defined-Type
            type eqpt_PsRdnM;
        }

        // The power supply redundancy operational mode
        // Type is an MO-Defined-Type
        leaf operRdnM {
            config "false";
            description "Operational Redundancy Mode";

            // Type is an MO-Defined-Type
            type eqpt_PsRdnM;
        }

        // Non redundancy reason
        // Type is an MO-Defined-Type
        leaf nRdnRsn {
            config "false";
            description "Non Redundancy Reason";

            // Type is an MO-Defined-Type
            type eqpt_NRdnRsn;
        }

        // total power capacity in watts. It depends on the
        // redundancy mode and is equal to one of cumCap,
        // psRdCap, gridRdCap, FullRdCap
        // Type is an MO-Defined-Type
        leaf tc {
            config "false";
            description "Total Capacity";

            // Type is an MO-Defined-Type
            type eqpt_Watts;
        }

        // Reserved power in watts
        // Type is an MO-Defined-Type
        leaf rsdPwr {
            config "false";
            description "Reserved Power";

            // Type is an MO-Defined-Type
            type eqpt_Watts;
        }

        // Allocated power in watts
        // Type is an MO-Defined-Type
        leaf alPwr {
            config "false";
            description "Allocated Power";

            // Type is an MO-Defined-Type
            type eqpt_Watts;
        }

        // Available power in watts
        // Type is an MO-Defined-Type
        leaf avPwr {
            config "false";
            description "Available Power";

            // Type is an MO-Defined-Type
            type eqpt_Watts;
        }

        // Available power under various redundancy modes
        // Cumulative power available in non-redundant mode.
        // It is obtained by summing the individual power
        // provided by all present and functioning psu
        // Type is an MO-Defined-Type
        leaf nRdnCap {
            config "false";
            description "N-Redundant Capacity";

            // Type is an MO-Defined-Type
            type eqpt_Watts;
        }

        // power capacity under power supply redundancy, also called
        // N+1 redundancy. It is the sum of lowest N rated psu
        // Type is an MO-Defined-Type
        leaf psRdnCap {
            config "false";
            description "N+1 Redundant Capacity";

            // Type is an MO-Defined-Type
            type eqpt_Watts;
        }

        // power capacity under grid redundancy, also called input
        // src redundancy.  It is calculated as the minimum of grid
        // A and grid B capacity.  It is relevant for psu which
        // can take two independent inputs. For single input psu,
        // grid redundancy is calculated as half of cumulative
        // capacity
        // Type is an MO-Defined-Type
        leaf grdRdnCap {
            config "false";
            description "Grid Redundant Capacity";

            // Type is an MO-Defined-Type
            type eqpt_Watts;
        }

        // Power capacity under full redundancy. It is calculated
        // as the minimum of ps and grid redundancy
        // Type is an MO-Defined-Type
        leaf flRdnCap {
            config "false";
            description "Full Redundant Capacity";

            // Type is an MO-Defined-Type
            type eqpt_Watts;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Rel-def from psuInstPolCons
        container rspsuInstPolCons-items {

            // Added containment as a singleton: Prefix=rspsuInstPolCons
            // Acquired From Package eqpt
            uses eqpt_RsPsuInstPolCons_source-group;
        }
    }

    grouping eqpt_SlotP-group {

        // type of the slot
        // Type is an MO-Defined-Type
        leaf type {
            config "false";
            description "Type";

            // Type is an MO-Defined-Type
            type eqpt_SlotT;
        }

        // logical slot id
        // Type is an MO-Defined-Type
        leaf id {
            description "Logical ID";

            // Type is an MO-Defined-Type
            type eqpt_Id;
        }

        // Controls
        // Type is an MO-Defined-Type
        leaf ctrl {
            config "false";
            description "Controls";

            // Type is an MO-Defined-Type
            type eqpt_SlotControl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping eqptcapacity_Entity-group {

        // From Interface naming:Named
        // Inherited From naming:NamedObject
        // Modified by Override: pol:Obj->name
        // Type is an MO-Defined-Type
        leaf name {
            description "Name";

            // Type is an MO-Defined-Type
            type naming_Name {
                length "0..64";
            }
        }
    }

    grouping eqptdiag_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Diag Group to Diag Test Mappings
        container grptests-items {
            list GrpTests-list {
                config "false";
                key "subjClass model grp";

                // Added containment: Prefix=grptests
                // Acquired From Package eqptdiagp
                uses eqptdiagp_GrpTests-group;
            }
        }

        // Diag rule for bootup and health tests
        container rule-items {
            list Rule-list {
                config "false";
                key "type trig";

                // Added containment: Prefix=rule
                // Acquired From Package eqptdiag
                uses eqptdiag_Rule-group;
            }
        }
    }

    grouping eqptdiagp_GrpTests-group {
        leaf subjClass {
            config "false";
            type string;
        }

        // Model
        // Type is an MO-Defined-Type
        leaf model {
            config "false";
            description "Model of the Subject";

            // Type is an MO-Defined-Type
            type eqpt_Model;
        }

        // Diag group name
        // Type is an MO-Defined-Type
        leaf grp {
            config "false";
            description "Diag Test Group";

            // Type is an MO-Defined-Type
            type eqptdiag_AllGrpsT;
        }

        // Bitmap of tests that are in the diag test group for the givel
        // class and model of the subject
        // Type is an MO-Defined-Type
        leaf testBm {
            config "false";
            description "CLass Name of the Subject";

            // Type is an MO-Defined-Type
            type eqptdiag_TypeBm;
        }

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }
    }

    grouping eqptdiag_Rule-group {

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Trigger of this test
        // Inherited From test:Rule
        // Type is an MO-Defined-Type
        leaf trig {
            config "false";
            description "Trigger";

            // Type is an MO-Defined-Type
            type test_Trig;
        }

        // Test frequency
        // Inherited From test:Rule
        // Type is an MO-Defined-Type
        leaf freq {
            config "false";
            description "Frequency";

            // Type is an MO-Defined-Type
            type test_Freq;
        }

        // Test type
        // Inherited From eqptdiag:ARule
        // Type is an MO-Defined-Type
        leaf type {
            config "false";
            description "TBD";

            // Type is an MO-Defined-Type
            type eqptdiag_Type;
        }

        // Diag subject
        container subj-items {
            list Subj-list {
                config "false";
                key "oDn";

                // Added containment: Prefix=subj
                // Acquired From Package eqptdiag
                uses eqptdiag_Subj-group;
            }
        }
    }

    grouping eqptdiag_Subj-group {

        // Object primary key
        // Inherited From test:Subj
        // Type is an MO-Defined-Type
        leaf oPk {
            config "false";
            description "Object Primary Key";

            // Type is an MO-Defined-Type
            type test_PInstId;
        }

        // Object secondary key
        // Inherited From test:Subj
        // Type is an MO-Defined-Type
        leaf oSk {
            config "false";
            description "Object Secondary Key";

            // Type is an MO-Defined-Type
            type test_PInstId;
        }
        leaf oDn {
            config "false";
            type string;
        }

        // Consolidated operational state of the test
        // on this subject
        // Inherited From test:Subj
        // Type is an MO-Defined-Type
        leaf operSt {
            config "false";
            description "Operational State";

            // Type is an MO-Defined-Type
            type test_OperSt;
        }

        // Operational state qualifier
        // Inherited From test:Subj
        // Type is an MO-Defined-Type
        leaf operStQual {
            config "false";
            description "Operational State Qualifier";

            // Type is an MO-Defined-Type
            type test_OperStQual;
        }

        // Last execution failed operational state qualifier
        // Inherited From test:Subj
        // Type is an MO-Defined-Type
        leaf lastExecFailQual {
            config "false";
            description "Last Execution Failure Qualifier";

            // Type is an MO-Defined-Type
            type test_OperStQual;
        }
        leaf lastExecTs {
            config "false";
            type uint64;
        }
        leaf nextExecTs {
            config "false";
            type uint64;
        }
        leaf lastExecPassTs {
            config "false";
            type uint64;
        }
        leaf firstExecFailTs {
            config "false";
            type uint64;
        }
        leaf lastExecFailTs {
            config "false";
            type uint64;
        }
        leaf numExec {
            config "false";
            type uint32;
        }
        leaf numExecFail {
            config "false";
            type uint32;
        }
        leaf numExecConsFail {
            config "false";
            type uint32;
        }

        // Prof. Name
        // Inherited From test:Subj
        // Type is an MO-Defined-Type
        leaf name {
            config "false";
            description "Name";

            // Type is an MO-Defined-Type
            type naming_Name;
        }

        // Diag result
        container rslt-items {
            list Rslt-list {
                config "false";
                key "ts";

                // Added containment: Prefix=rslt
                // Acquired From Package eqptdiag
                uses eqptdiag_Rslt-group;
            }
        }

        // Port test stats
        container portteststats-items {

            // Added containment as a singleton: Prefix=portteststats
            // Acquired From Package eqptdiag
            uses eqptdiag_PortTestStats-group;
        }
    }

    grouping eqptdiag_Rslt-group {

        // Trigger for this result
        // Inherited From test:Rslt
        // Type is an MO-Defined-Type
        leaf trig {
            config "false";
            description "Trigger";

            // Type is an MO-Defined-Type
            type test_Trig;
        }

        // Test operational status
        // Inherited From test:Rslt
        // Type is an MO-Defined-Type
        leaf operSt {
            config "false";
            description "Operational State";

            // Type is an MO-Defined-Type
            type test_OperSt;
        }

        // Test status qualifier, deprecate this XXX
        // Inherited From test:Rslt
        // Type is an MO-Defined-Type
        leaf qual {
            config "false";
            description "Operational State Qualifier";

            // Type is an MO-Defined-Type
            type test_OperStQual;
        }

        // Test status qualifier
        // Inherited From test:Rslt
        // Type is an MO-Defined-Type
        leaf operStqual {
            config "false";
            description "Operational State Qualifier";

            // Type is an MO-Defined-Type
            type test_OperStQual;
        }
        leaf ts {
            config "false";
            type uint64;
        }

        // Prof. Name
        // Inherited From test:Rslt
        // Type is an MO-Defined-Type
        leaf name {
            config "false";
            description "Name";

            // Type is an MO-Defined-Type
            type naming_Name;
        }
    }

    grouping eqptdiag_PortTestStats-group {

        // Packets Sent
        // Type is an MO-Defined-Type
        leaf pktSent {
            description "Packets Sent";

            // Type is an MO-Defined-Type
            type nw_Counter32;
        }

        // Packets Received
        // Type is an MO-Defined-Type
        leaf pktRcvd {
            description "Packets Received";

            // Type is an MO-Defined-Type
            type nw_Counter32;
        }

        // Packets Dropped
        // Type is an MO-Defined-Type
        leaf pktDrop {
            description "Packets Dropped";

            // Type is an MO-Defined-Type
            type nw_Counter32;
        }
    }

    grouping leqpt_LooseNode-group {

        // A unique identifier for this object
        // Type is an MO-Defined-Type
        leaf id {
            config "false";
            description "TBD";

            // Type is an MO-Defined-Type
            type fabric_LooseNodeId;
        }

        // System description
        // Type is an MO-Defined-Type
        leaf sysDesc {
            config "false";
            description "TBD";

            // Type is an MO-Defined-Type
            type naming_Descr;
        }

        // System Name
        // Type is an MO-Defined-Type
        leaf sysName {
            config "false";
            description "TBD";

            // Type is an MO-Defined-Type
            type naming_Descr;
        }

        // From Interface naming:Named
        // Inherited From naming:NamedObject
        // Type is an MO-Defined-Type
        leaf name {
            description "Name";

            // Type is an MO-Defined-Type
            type naming_Name;
        }

        // Rel-def target from epDefToLooseNode
        // Inherited From leqpt:LooseNode
        container rtfvEpDefToLooseNode-items {

            // Abstract containment of rtfvEpDefToLooseNode derived from leqpt:LooseNode
            list RtFvEpDefToLooseNode-list {
                config "false";
                key "tDn";

                // Added containment: Prefix=rtfvEpDefToLooseNode
                // Acquired From Package fv
                uses fv_RtFvEpDefToLooseNode_target-group;
            }
        }

        // Rel-def target from lsNodeAtt
        // Inherited From leqpt:LooseNode
        container rtfvLsNodeAtt-items {

            // Abstract containment of rtfvLsNodeAtt derived from leqpt:LooseNode
            list RtFvLsNodeAtt-list {
                config "false";
                key "tDn";

                // Added containment: Prefix=rtfvLsNodeAtt
                // Acquired From Package fv
                uses fv_RtFvLsNodeAtt_target-group;
            }
        }

        // Rel-def target from tunnelToLooseNode
        // Inherited From leqpt:LooseNode
        container rttunnelTunnelToLooseNode-items {

            // Abstract containment of rttunnelTunnelToLooseNode derived from leqpt:LooseNode
            list RtTunnelTunnelToLooseNode-list {
                config "false";
                key "tDn";

                // Added containment: Prefix=rttunnelTunnelToLooseNode
                // Acquired From Package tunnel
                uses tunnel_RtTunnelTunnelToLooseNode_target-group;
            }
        }

        // Rel-def from LsNodeToIf
        container rslsNodeToIf-items {

            // Abstract containment of rslsNodeToIf derived from leqpt:LooseNode
            list RsLsNodeToIf-list {
                config "false";
                key "tDn";

                // Added containment: Prefix=rslsNodeToIf
                // Acquired From Package leqpt
                uses leqpt_RsLsNodeToIf_source-group;
            }
        }

        // Rel-def from LsAttLink
        container rslsAttLink-items {

            // Added containment as a singleton: Prefix=rslsAttLink
            // Acquired From Package leqpt
            uses leqpt_RsLsAttLink_source-group;
        }
    }

    grouping platform_Entity-group {
        leaf descr {
            type string;
        }

        // Type is an MO-Defined-Type
        leaf profileMode {
            description "profile portmode ";

            // Type is an MO-Defined-Type
            type platform_HwProfile;
        }

        // Type is an MO-Defined-Type
        leaf profileTuple {
            description "profile portmode 2Tuple";

            // Type is an MO-Defined-Type
            type platform_Tuple;
        }

        // Type is an MO-Defined-Type
        leaf unicastSyslogThreshold {
            description "Unicast syslog-threshold ";

            // Type is an MO-Defined-Type
            type platform_Percentage;
        }

        // Type is an MO-Defined-Type
        leaf lpmMaxLimit {
            description "ucast6 lpm-65-to-127-max-limit";

            // Type is an MO-Defined-Type
            type platform_LpmMaxLimits;
        }

        // Type is an MO-Defined-Type
        leaf unicastMaxLimit {
            description "ucast6 max-limit entries";

            // Type is an MO-Defined-Type
            type platform_UnicastMaxLimit;
        }

        // Type is an MO-Defined-Type
        leaf multicastMaxLimit {
            description "mcast max-limit entries";

            // Type is an MO-Defined-Type
            type platform_MulticastMaxLimit;
        }

        // Type is an MO-Defined-Type
        leaf multicastSyslogThreshold {
            description "multicast syslog-threshold ";

            // Type is an MO-Defined-Type
            type platform_Percentage;
        }

        // Type is an MO-Defined-Type
        leaf IPV6alpmCarveValue {
            description "hardware profile ipv6 alpm carve-value";

            // Type is an MO-Defined-Type
            type platform_IPV6alpmCarveValues;
        }

        // Type is an MO-Defined-Type
        leaf routingMode {
            description "routing mode";

            // Type is an MO-Defined-Type
            type platform_RoutingMode;
        }

        // Type is an MO-Defined-Type
        leaf pcLbAlgo {
            description "pc load-balance internal algorithm";

            // Type is an MO-Defined-Type
            type platform_PcLbAlgo;
        }

        // valif for n3ktoronly
        // Type is an MO-Defined-Type
        leaf urpfStatus {
            description "urpf status";

            // Type is an MO-Defined-Type
            type nw_AdminSt;
        }

        // valid for n9knontahoe
        // Type is an MO-Defined-Type
        leaf qosMinBuffer {
            description "qos min-buffer qos-group";

            // Type is an MO-Defined-Type
            type platform_QosMinBuffer;
        }

        // Container for all the BDs to hold platform data in the system.
        container bd-items {

            // Added containment as a singleton: Prefix=bd
            // Acquired From Package platform
            uses platform_BdEntity-group;
        }

        // Container for all the interfaces in the system.
        container intf-items {

            // Added containment as a singleton: Prefix=intf
            // Acquired From Package platform
            uses platform_Intf-group;
        }

        // Container for all the tcam regions in the system.
        container tcamRegion-items {

            // Added containment as a singleton: Prefix=tcamRegion
            // Acquired From Package platform
            uses platform_TcamRegion-group;
        }
    }

    grouping platform_BdEntity-group {
        leaf descr {
            config "false";
            type string;
        }

        // Layer2 Bridge-domain
        container bd-items {
            list Bd-list {
                key "fabEncap";

                // Added containment: Prefix=bd
                // Acquired From Package platform
                uses platform_Bd-group;
            }
        }
    }

    grouping platform_Bd-group {
        leaf fabEncap {
            type string;
        }

        container eltmBd-items {

            // Added containment as a singleton: Prefix=eltmBd
            // Acquired From Package eltm
            uses eltm_Bd-group;
        }
    }

    grouping eltm_Bd-group {

        // hw bd id (allocated for vlans )
        // Type is an MO-Defined-Type
        leaf hwBdId {
            config "false";
            description "Hw Bd Id (allocated for vlans)";

            // Type is an MO-Defined-Type
            type l2_DomId;
        }
    }

    grouping platform_Intf-group {
        leaf descr {
            config "false";
            type string;
        }

        // This object holds platfrom information at an
        // interface level
        container if-items {
            list If-list {
                key "id";

                // Added containment: Prefix=if
                // Acquired From Package platform
                uses platform_If-group;
            }
        }
    }

    grouping platform_If-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        container eltmIf-items {

            // Added containment as a singleton: Prefix=eltmIf
            // Acquired From Package eltm
            uses eltm_If-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        // Inherited From platform:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        // Inherited From platform:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping eltm_If-group {

        // hw bd id (allocated for l3 ports, port-channels)
        // Type is an MO-Defined-Type
        leaf hwBdId {
            config "false";
            description "Hw Bd Id (allocated for L3 Ports, Port-channels)";

            // Type is an MO-Defined-Type
            type l2_DomId;
        }
    }

    grouping platform_TcamRegion-group {

        // description
        // Type is an MO-Defined-Type
        leaf eRaclSize {
            description "tcam region size";

            // Type is an MO-Defined-Type
            type platform_tcamRegionSize;
        }

        // Type is an MO-Defined-Type
        leaf vpcConvergenceSize {
            description "tcam region size";

            // Type is an MO-Defined-Type
            type platform_tcamRegionSize;
        }

        // Type is an MO-Defined-Type
        leaf raclLiteSize {
            description "tcam region size";

            // Type is an MO-Defined-Type
            type platform_tcamRegionSize;
        }

        // Type is an MO-Defined-Type
        leaf ipv6IfaclSize {
            description "tcam region size";

            // Type is an MO-Defined-Type
            type platform_tcamRegionSize;
        }

        // Type is an MO-Defined-Type
        leaf eIpv6RaclSize {
            description "tcam region size";

            // Type is an MO-Defined-Type
            type platform_tcamRegionSize;
        }

        // Type is an MO-Defined-Type
        leaf ifaclLiteSize {
            description "tcam region size";

            // Type is an MO-Defined-Type
            type platform_tcamRegionSize;
        }

        // Type is an MO-Defined-Type
        leaf vaclSize {
            description "tcam region size";

            // Type is an MO-Defined-Type
            type platform_tcamRegionSize;
        }

        // Type is an MO-Defined-Type
        leaf ifaclSize {
            description "tcam region size";

            // Type is an MO-Defined-Type
            type platform_tcamRegionSize;
        }

        // Type is an MO-Defined-Type
        leaf eVaclSize {
            description "tcam region size";

            // Type is an MO-Defined-Type
            type platform_tcamRegionSize;
        }

        // Type is an MO-Defined-Type
        leaf qosSize {
            description "tcam region size";

            // Type is an MO-Defined-Type
            type platform_tcamRegionSize;
        }

        // Type is an MO-Defined-Type
        leaf raclSize {
            description "tcam region size";

            // Type is an MO-Defined-Type
            type platform_tcamRegionSize;
        }
    }

    grouping satm_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Discovered extended chassis
        container dextch-items {
            list DExtCh-list {
                config "false";
                key "vendor model ser";

                // Added containment: Prefix=dextch
                // Acquired From Package satm
                uses satm_DExtCh-group;
            }
        }

        // Fabric port definition
        container fabp-items {
            list FabP-list {
                key "id";

                // Added containment: Prefix=fabp
                // Acquired From Package satm
                uses satm_FabP-group;
            }
        }
    }

    grouping satm_DExtCh-group {

        // Operational state
        // Type is an MO-Defined-Type
        leaf operSt {
            config "false";
            description "Operational State";

            // Type is an MO-Defined-Type
            type satm_ExtChOperSt;
        }

        // Extended chassis software version
        // Type is an MO-Defined-Type
        leaf ver {
            config "false";
            description "Software Version";

            // Type is an MO-Defined-Type
            type cap_Version;
        }

        // Switch software version
        // Type is an MO-Defined-Type
        leaf swVer {
            config "false";
            description "Switch Software Version";

            // Type is an MO-Defined-Type
            type cap_Version;
        }

        // Interim extended chassis software version
        // Type is an MO-Defined-Type
        leaf intVer {
            config "false";
            description "Interim Software Version";

            // Type is an MO-Defined-Type
            type cap_Version;
        }

        // Interim switch software version
        // Type is an MO-Defined-Type
        leaf swIntVer {
            config "false";
            description "Interim Switch Software Version";

            // Type is an MO-Defined-Type
            type cap_Version;
        }

        // Extended chassis software generation
        // Type is an MO-Defined-Type
        leaf swGen {
            config "false";
            description "Software Generation";

            // Type is an MO-Defined-Type
            type satm_SwGen;
        }

        // Control channel fabric port
        // Type is an MO-Defined-Type
        leaf controlFPort {
            config "false";
            description "Control Channel Fabric Port";

            // Type is an MO-Defined-Type
            type nw_IfId;
        }

        // The vendor manufacturing this device.
        // From Interface eqpt:Dev
        // Type is an MO-Defined-Type
        leaf vendor {
            config "false";
            description "Vendor";

            // Type is an MO-Defined-Type
            type eqpt_Vendor;
        }

        // The device model
        // From Interface eqpt:Dev
        // Type is an MO-Defined-Type
        leaf model {
            config "false";
            description "Model";

            // Type is an MO-Defined-Type
            type eqpt_Model;
        }

        // The device revision.
        // From Interface eqpt:Dev
        // Type is an MO-Defined-Type
        leaf rev {
            config "false";
            description "Revision";

            // Type is an MO-Defined-Type
            type eqpt_Revision;
        }

        // The device serial number.
        // From Interface eqpt:Dev
        // Type is an MO-Defined-Type
        leaf ser {
            config "false";
            description "Serial Number";

            // Type is an MO-Defined-Type
            type eqpt_Serial;
        }

        // Identifier for the item
        // Inherited From eqpt:Item
        // Modified by Override: satm:DExtCh->id
        // Modified by Override: eqpt:Cont->id
        // Type is an MO-Defined-Type
        leaf id {
            config "false";
            description "ID";

            // Type is an MO-Defined-Type
            type eqpt_Id {
                range "101..199";
            }
        }

        // From Interface naming:Described
        // Inherited From eqpt:Cont
        // Type is an MO-Defined-Type
        leaf descr {
            description "Description";

            // Type is an MO-Defined-Type
            type naming_Descr;
        }
    }

    grouping satm_FabP-group {

        // Interface ID of port
        // Type is an MO-Defined-Type
        leaf id {
            description "ID";

            // Type is an MO-Defined-Type
            type nw_IfId;
        }

        // Fabric port operational state
        // Type is an MO-Defined-Type
        leaf operSt {
            config "false";
            description "Operational State";

            // Type is an MO-Defined-Type
            type satm_OperSt;
        }

        // Extended chassis id
        // Type is an MO-Defined-Type
        leaf extChId {
            config "false";
            description "Extended Chassis ID";

            // Type is an MO-Defined-Type
            type eqpt_ExtChId;
        }

        // Fabric port FSM state
        // Type is an MO-Defined-Type
        leaf fsmSt {
            config "false";
            description "Fabric FSM State";

            // Type is an MO-Defined-Type
            type satm_FpFsmSt;
        }
        leaf remoteLinkId {
            config "false";
            type uint16;
        }

        // Fabric port flags
        // Type is an MO-Defined-Type
        leaf flags {
            config "false";
            description "Fabric Port Flags";

            // Type is an MO-Defined-Type
            type satm_FportFlags;
        }

        // Satellite manager host port
        container hostp-items {
            list HostP-list {
                key "id";

                // Added containment: Prefix=hostp
                // Acquired From Package satm
                uses satm_HostP-group;
            }
        }

        // Remote fcot definition
        container remotefcot-items {

            // Added containment as a singleton: Prefix=remotefcot
            // Acquired From Package satm
            uses satm_RemoteFcot-group;
        }

        // Remote X2 fcot definition
        container remotefcotx2-items {

            // Added containment as a singleton: Prefix=remotefcotx2
            // Acquired From Package satm
            uses satm_RemoteFcotX2-group;
        }
    }

    grouping satm_HostP-group {

        // Interface ID of port
        // Type is an MO-Defined-Type
        leaf id {
            description "ID";

            // Type is an MO-Defined-Type
            type nw_IfId;
        }

        // Operational state
        // Type is an MO-Defined-Type
        leaf operSt {
            config "false";
            description "Operational State";

            // Type is an MO-Defined-Type
            type satm_HpOperSt;
        }

        // Fabric port
        // Type is an MO-Defined-Type
        leaf fabricPort {
            config "false";
            description "Fabric Port";

            // Type is an MO-Defined-Type
            type nw_IfId;
        }
    }

    grouping satm_RemoteFcot-group {
        leaf fcotStatus {
            config "false";
            type uint8;
        }

        // Fcot part number
        // Inherited From ethpm:FcotBase
        // Type is an MO-Defined-Type
        leaf partNumber {
            config "false";
            description "Part Number";

            // Type is an MO-Defined-Type
            type ethpm_SfpPartNumberBytes;
        }

        // Fcot version id
        // Inherited From ethpm:FcotBase
        // Type is an MO-Defined-Type
        leaf versionId {
            config "false";
            description "Version ID";

            // Type is an MO-Defined-Type
            type ethpm_SfpVersionIdBytes;
        }

        // Fcot description
        // Inherited From ethpm:FcotBase
        // Type is an MO-Defined-Type
        leaf description {
            config "false";
            description "Description";

            // Type is an MO-Defined-Type
            type ethpm_SfpDescriptionBytes;
        }
        leaf isFcotPresent {
            config "false";
            type boolean;
        }

        // Fcot state
        // Inherited From ethpm:FcotBase
        // Type is an MO-Defined-Type
        leaf state {
            config "false";
            description "State";

            // Type is an MO-Defined-Type
            type ethpm_FcotState;
        }

        // Fcot flags
        // Inherited From ethpm:FcotBase
        // Type is an MO-Defined-Type
        leaf flags {
            config "false";
            description "Flags";

            // Type is an MO-Defined-Type
            type ethpm_FcotFlags;
        }

        // Fcot type
        // Inherited From ethpm:FcotBase
        // Type is an MO-Defined-Type
        leaf type {
            config "false";
            description "Type";

            // Type is an MO-Defined-Type
            type ethpm_FcotType;
        }
        leaf typeName {
            config "false";
            type string;
        }
        leaf guiName {
            config "false";
            type string;
        }
        leaf guiPN {
            config "false";
            type string;
        }
        leaf guiRev {
            config "false";
            type string;
        }
        leaf guiSN {
            config "false";
            type string;
        }
        leaf guiCiscoPN {
            config "false";
            type string;
        }
        leaf guiCiscoPID {
            config "false";
            type string;
        }
        leaf guiCiscoEID {
            config "false";
            type string;
        }
        leaf xcvrId {
            config "false";
            type uint8;
        }
        leaf xcvrExtId {
            config "false";
            type uint8;
        }
        leaf connectType {
            config "false";
            type uint8;
        }

        // Xcvr code field
        // Inherited From ethpm:AFcot
        // Type is an MO-Defined-Type
        leaf xcvrCode {
            config "false";
            description "Transceiver Code";

            // Type is an MO-Defined-Type
            type ethpm_SfpXcvrCodeBytes;
        }
        leaf encoding {
            config "false";
            type uint8;
        }
        leaf brIn100MHz {
            config "false";
            type uint8;
        }
        leaf baseResvd1 {
            config "false";
            type uint8;
        }
        leaf distInKmFor9u {
            config "false";
            type uint8;
        }
        leaf distIn100mFor9u {
            config "false";
            type uint8;
        }
        leaf distIn10mFor50u {
            config "false";
            type uint8;
        }
        leaf distIn10mFor60u {
            config "false";
            type uint8;
        }
        leaf distIn1mForCu {
            config "false";
            type uint8;
        }
        leaf baseResvd2 {
            config "false";
            type uint8;
        }

        // Vendor name
        // Inherited From ethpm:AFcot
        // Type is an MO-Defined-Type
        leaf vendorName {
            config "false";
            description "Vendor Name";

            // Type is an MO-Defined-Type
            type ethpm_SfpVendorNameBytes;
        }
        leaf baseResvd3 {
            config "false";
            type uint8;
        }

        // IEEE vendor Id
        // Inherited From ethpm:AFcot
        // Type is an MO-Defined-Type
        leaf vendorId {
            config "false";
            description "Vendor ID";

            // Type is an MO-Defined-Type
            type ethpm_SfpVendorIdBytes;
        }

        // Vendor part number
        // Inherited From ethpm:AFcot
        // Type is an MO-Defined-Type
        leaf vendorPn {
            config "false";
            description "Vendor Part Number";

            // Type is an MO-Defined-Type
            type ethpm_VendorPartNumberBytes;
        }

        // Vendor revision number
        // Inherited From ethpm:AFcot
        // Type is an MO-Defined-Type
        leaf vendorRev {
            config "false";
            description "Vendor Revision";

            // Type is an MO-Defined-Type
            type ethpm_SfpVendorRevisionNumberBytes;
        }

        // Reserved field 4
        // Inherited From ethpm:AFcot
        // Type is an MO-Defined-Type
        leaf baseResvd4 {
            config "false";
            description "Base Reserved Field";

            // Type is an MO-Defined-Type
            type ethpm_SfpReserved4Array;
        }
        leaf ccid {
            config "false";
            type uint8;
        }

        // Extended option
        // Inherited From ethpm:AFcot
        // Type is an MO-Defined-Type
        leaf extOption {
            config "false";
            description "Extended Option";

            // Type is an MO-Defined-Type
            type ethpm_SfpExtendedOptionBytes;
        }
        leaf brMaxMargin {
            config "false";
            type uint8;
        }
        leaf brMinMargin {
            config "false";
            type uint8;
        }

        // Vendor serial number
        // Inherited From ethpm:AFcot
        // Type is an MO-Defined-Type
        leaf vendorSn {
            config "false";
            description "TBD";

            // Type is an MO-Defined-Type
            type ethpm_SfpVendorSerialNumberBytes;
        }

        // Date code
        // Inherited From ethpm:AFcot
        // Type is an MO-Defined-Type
        leaf dateCode {
            config "false";
            description "TBD";

            // Type is an MO-Defined-Type
            type ethpm_SfpDateCodeBytes;
        }
        leaf diagMonType {
            config "false";
            type uint8;
        }
        leaf enhOption {
            config "false";
            type uint8;
        }
        leaf sff8472Compl {
            config "false";
            type uint8;
        }
        leaf ccex {
            config "false";
            type uint8;
        }

        // Vendor data
        // Inherited From ethpm:AFcot
        // Type is an MO-Defined-Type
        leaf vendorData {
            config "false";
            description "TBD";

            // Type is an MO-Defined-Type
            type ethpm_X2VendorDataBytes;
        }
        leaf maxSpeed {
            config "false";
            type uint32;
        }
        leaf minSpeed {
            config "false";
            type uint32;
        }
        leaf fcotNum {
            config "false";
            type uint8;
        }
        leaf fcotType {
            config "false";
            type uint8;
        }
        leaf gigEthCC {
            config "false";
            type uint8;
        }
        leaf fCTxType {
            config "false";
            type uint8;
        }
    }

    grouping satm_RemoteFcotX2-group {
        leaf fcotStatus {
            config "false";
            type uint8;
        }

        // Fcot part number
        // Inherited From ethpm:FcotBase
        // Type is an MO-Defined-Type
        leaf partNumber {
            config "false";
            description "Part Number";

            // Type is an MO-Defined-Type
            type ethpm_SfpPartNumberBytes;
        }

        // Fcot version id
        // Inherited From ethpm:FcotBase
        // Type is an MO-Defined-Type
        leaf versionId {
            config "false";
            description "Version ID";

            // Type is an MO-Defined-Type
            type ethpm_SfpVersionIdBytes;
        }

        // Fcot description
        // Inherited From ethpm:FcotBase
        // Type is an MO-Defined-Type
        leaf description {
            config "false";
            description "Description";

            // Type is an MO-Defined-Type
            type ethpm_SfpDescriptionBytes;
        }
        leaf isFcotPresent {
            config "false";
            type boolean;
        }

        // Fcot state
        // Inherited From ethpm:FcotBase
        // Type is an MO-Defined-Type
        leaf state {
            config "false";
            description "State";

            // Type is an MO-Defined-Type
            type ethpm_FcotState;
        }

        // Fcot flags
        // Inherited From ethpm:FcotBase
        // Type is an MO-Defined-Type
        leaf flags {
            config "false";
            description "Flags";

            // Type is an MO-Defined-Type
            type ethpm_FcotFlags;
        }

        // Fcot type
        // Inherited From ethpm:FcotBase
        // Type is an MO-Defined-Type
        leaf type {
            config "false";
            description "Type";

            // Type is an MO-Defined-Type
            type ethpm_FcotType;
        }
        leaf typeName {
            config "false";
            type string;
        }
        leaf guiName {
            config "false";
            type string;
        }
        leaf guiPN {
            config "false";
            type string;
        }
        leaf guiRev {
            config "false";
            type string;
        }
        leaf guiSN {
            config "false";
            type string;
        }
        leaf guiCiscoPN {
            config "false";
            type string;
        }
        leaf guiCiscoPID {
            config "false";
            type string;
        }
        leaf guiCiscoEID {
            config "false";
            type string;
        }
        leaf xcvrType {
            config "false";
            type uint8;
        }
        leaf connectType {
            config "false";
            type uint8;
        }
        leaf bitEncoding {
            config "false";
            type uint8;
        }

        // Bit rate (Mbps)
        // Inherited From ethpm:AFcotX2
        // Type is an MO-Defined-Type
        leaf bitRateMbps {
            config "false";
            description "TBD";

            // Type is an MO-Defined-Type
            type ethpm_X2BitRateBytes;
        }
        leaf protocolType {
            config "false";
            type uint8;
        }

        // 10G eth code
        // Inherited From ethpm:AFcotX2
        // Type is an MO-Defined-Type
        leaf xgEthCode {
            config "false";
            description "TBD";

            // Type is an MO-Defined-Type
            type ethpm_X2XgEthCodeBytes;
        }

        // Sonet SDH code
        // Inherited From ethpm:AFcotX2
        // Type is an MO-Defined-Type
        leaf sonetSdhCode {
            config "false";
            description "TBD";

            // Type is an MO-Defined-Type
            type ethpm_X2SonetSdhCodeBytes;
        }

        // 10G fc code
        // Inherited From ethpm:AFcotX2
        // Type is an MO-Defined-Type
        leaf xgFcCode {
            config "false";
            description "TBD";

            // Type is an MO-Defined-Type
            type ethpm_X2XbFcCodeBytes;
        }

        // Range
        // Inherited From ethpm:AFcotX2
        // Type is an MO-Defined-Type
        leaf range {
            config "false";
            description "TBD";

            // Type is an MO-Defined-Type
            type ethpm_X2RangeBytes;
        }

        // Fibre type
        // Inherited From ethpm:AFcotX2
        // Type is an MO-Defined-Type
        leaf fibreType {
            config "false";
            description "TBD";

            // Type is an MO-Defined-Type
            type ethpm_X2FibreTypeBytes;
        }

        // Wavelength channel 0
        // Inherited From ethpm:AFcotX2
        // Type is an MO-Defined-Type
        leaf waveLenCh0 {
            config "false";
            description "TBD";

            // Type is an MO-Defined-Type
            type ethpm_X2WavelengthChannelBytes;
        }

        // Wavelength channel 1
        // Inherited From ethpm:AFcotX2
        // Type is an MO-Defined-Type
        leaf waveLenCh1 {
            config "false";
            description "TBD";

            // Type is an MO-Defined-Type
            type ethpm_X2WavelengthChannelBytes;
        }

        // Wavelength channel 2
        // Inherited From ethpm:AFcotX2
        // Type is an MO-Defined-Type
        leaf waveLenCh2 {
            config "false";
            description "TBD";

            // Type is an MO-Defined-Type
            type ethpm_X2WavelengthChannelBytes;
        }

        // Wavelength channel 3
        // Inherited From ethpm:AFcotX2
        // Type is an MO-Defined-Type
        leaf waveLenCh3 {
            config "false";
            description "TBD";

            // Type is an MO-Defined-Type
            type ethpm_X2WavelengthChannelBytes;
        }

        // Package Oui
        // Inherited From ethpm:AFcotX2
        // Type is an MO-Defined-Type
        leaf packageOui {
            config "false";
            description "TBD";

            // Type is an MO-Defined-Type
            type ethpm_X2PackageOuiBytes;
        }

        // Vendor Oui
        // Inherited From ethpm:AFcotX2
        // Type is an MO-Defined-Type
        leaf vendorOui {
            config "false";
            description "TBD";

            // Type is an MO-Defined-Type
            type ethpm_X2VendorOuiBytes;
        }

        // Vendor name
        // Inherited From ethpm:AFcotX2
        // Type is an MO-Defined-Type
        leaf vendorName {
            config "false";
            description "TBD";

            // Type is an MO-Defined-Type
            type ethpm_X2VendorNameBytes;
        }

        // Vendor Part number
        // Inherited From ethpm:AFcotX2
        // Type is an MO-Defined-Type
        leaf vendorPn {
            config "false";
            description "TBD";

            // Type is an MO-Defined-Type
            type ethpm_X2VendorPartNumberBytes;
        }

        // Vendor revision
        // Inherited From ethpm:AFcotX2
        // Type is an MO-Defined-Type
        leaf vendorRev {
            config "false";
            description "TBD";

            // Type is an MO-Defined-Type
            type ethpm_X2VendorRevisionBytes;
        }

        // Vendor serial number
        // Inherited From ethpm:AFcotX2
        // Type is an MO-Defined-Type
        leaf vendorSerNo {
            config "false";
            description "TBD";

            // Type is an MO-Defined-Type
            type ethpm_X2VendorSerialNumberBytes;
        }

        // Date code
        // Inherited From ethpm:AFcotX2
        // Type is an MO-Defined-Type
        leaf dateCode {
            config "false";
            description "TBD";

            // Type is an MO-Defined-Type
            type ethpm_X2DateCodeBytes;
        }

        // Lot code
        // Inherited From ethpm:AFcotX2
        // Type is an MO-Defined-Type
        leaf lotCode {
            config "false";
            description "TBD";

            // Type is an MO-Defined-Type
            type ethpm_X2LotCodeBytes;
        }
        leaf fiveVStressEnv {
            config "false";
            type uint8;
        }
        leaf threeThreeVStressEnv {
            config "false";
            type uint8;
        }
        leaf apsStressEnv {
            config "false";
            type uint8;
        }
        leaf normalApsVolt {
            config "false";
            type uint8;
        }
        leaf diagOptMonCap {
            config "false";
            type uint8;
        }
        leaf lowPwrStartupCap {
            config "false";
            type uint8;
        }
        leaf reserved {
            config "false";
            type uint8;
        }
        leaf checksum {
            config "false";
            type uint8;
        }

        // Cisco PID
        // Inherited From ethpm:AFcotX2
        // Type is an MO-Defined-Type
        leaf ciscoPid {
            config "false";
            description "TBD";

            // Type is an MO-Defined-Type
            type ethpm_X2CiscoPidBytes;
        }

        // Cisco vendor ID
        // Inherited From ethpm:AFcotX2
        // Type is an MO-Defined-Type
        leaf ciscoVid {
            config "false";
            description "TBD";

            // Type is an MO-Defined-Type
            type ethpm_X2CiscoVendorIdBytes;
        }

        // Cisco serial number
        // Inherited From ethpm:AFcotX2
        // Type is an MO-Defined-Type
        leaf ciscoSN {
            config "false";
            description "TBD";

            // Type is an MO-Defined-Type
            type ethpm_X2CiscoSerialNumberBytes;
        }

        // Cisco part number
        // Inherited From ethpm:AFcotX2
        // Type is an MO-Defined-Type
        leaf ciscoPN {
            config "false";
            description "TBD";

            // Type is an MO-Defined-Type
            type ethpm_X2CiscoPartNumberBytes;
        }

        // Cisco revision number
        // Inherited From ethpm:AFcotX2
        // Type is an MO-Defined-Type
        leaf ciscoRev {
            config "false";
            description "TBD";

            // Type is an MO-Defined-Type
            type ethpm_X2CiscoRevisionNumberBytes;
        }

        // Extended vendor specific info
        // Inherited From ethpm:AFcotX2
        // Type is an MO-Defined-Type
        leaf extVendorSpecific {
            config "false";
            description "TBD";

            // Type is an MO-Defined-Type
            type ethpm_X2ExtendedVendorSpecificInfoBytes;
        }
        leaf maxSpeed {
            config "false";
            type uint32;
        }
        leaf minSpeed {
            config "false";
            type uint32;
        }
        leaf fcotNum {
            config "false";
            type uint8;
        }
        leaf fcotType {
            config "false";
            type uint8;
        }
        leaf gigEthCC {
            config "false";
            type uint8;
        }
        leaf fCTxType {
            config "false";
            type uint8;
        }
    }

    grouping adjacency_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        container inst-items {

            // Added containment as a singleton: Prefix=inst
            // Acquired From Package adjacency
            uses adjacency_Inst-group;
        }
    }

    grouping adjacency_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
        container dom-items {
            list Dom-list {
                key "name";

                // Added containment: Prefix=dom
                // Acquired From Package adjacency
                uses adjacency_Dom-group;
            }
        }
    }

    grouping adjacency_Dom-group {

        // Inherited From nw:Conn
        // Modified by Override: nw:CpDom->name
        // Type is an MO-Defined-Type
        leaf name {
            description "Name";

            // Type is an MO-Defined-Type
            type naming_Name {
                length "1..64";
            }
        }
        container db-items {
            list Db-list {
                key "type";

                // Added containment: Prefix=db
                // Acquired From Package adjacency
                uses adjacency_Db-group;
            }
        }
    }

    grouping adjacency_Db-group {

        // Type is an MO-Defined-Type
        leaf type {
            description "Type";

            // Type is an MO-Defined-Type
            type adjacency_DbT;
        }

        // Inherited From nw:Conn
        // Modified by Override: nw:Db->name
        // Type is an MO-Defined-Type
        leaf name {
            description "Name";

            // Type is an MO-Defined-Type
            type naming_Name {
                length "1..64";
            }
        }
        container if-items {
            list If-list {
                config "false";
                key "ifId";

                // Added containment: Prefix=if
                // Acquired From Package adjacency
                uses adjacency_If-group;
            }
        }
    }

    grouping adjacency_If-group {

        // Type is an MO-Defined-Type
        leaf ifId {
            config "false";
            description "Logical Interface ID";

            // Type is an MO-Defined-Type
            type nw_IfId;
        }
        container ip-items {
            list AdjEp-list {
                key "ip";

                // Added containment: Prefix=ip
                // Acquired From Package adjacency
                uses adjacency_AdjEp-group;
            }
        }
    }

    grouping adjacency_AdjEp-group {
        leaf ip {
            type address_Ip;
        }
        leaf mac {
            config "false";
            type address_Mac;
        }

        // Type is an MO-Defined-Type
        leaf operSt {
            config "false";
            description "Operational State";

            // Type is an MO-Defined-Type
            type adjacency_AdjOperSt;
        }

        // Type is an MO-Defined-Type
        leaf physIfId {
            config "false";
            description "Physical Interface ID";

            // Type is an MO-Defined-Type
            type nw_IfId;
        }
        leaf source {
            config "false";
            type string;
        }

        // Flags that this ep has
        // Type is an MO-Defined-Type
        leaf flags {
            config "false";
            description "Flags";

            // Type is an MO-Defined-Type
            type adjacency_AdjFlags;
        }

        // Inherited From nw:Conn
        // Modified by Override: nw:Ep->name
        // Type is an MO-Defined-Type
        leaf name {
            description "Name";

            // Type is an MO-Defined-Type
            type naming_Name {
                length "1..64";
            }
        }
    }

    grouping arp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds per arp instance information. There is
        // only one instance of arp running in the system today
        container inst-items {

            // Added containment as a singleton: Prefix=inst
            // Acquired From Package arp
            uses arp_Inst-group;
        }
    }

    grouping arp_Inst-group {

        // Timeout
        // Type is an MO-Defined-Type
        leaf timeout {
            description "Timeout";

            // Type is an MO-Defined-Type
            type arp_Timeout;
        }

        // Suppression Timeout
        // Type is an MO-Defined-Type
        leaf suppression_timeout {
            description "Timeout";

            // Type is an MO-Defined-Type
            type arp_SuppressionTimeout;
        }

        // Off list Timeout
        // Type is an MO-Defined-Type
        leaf offListTimeout {
            description "Off-list timeout";

            // Type is an MO-Defined-Type
            type arp_OffListTimeout;
        }

        // RARP fabric forwarding
        // Type is an MO-Defined-Type
        leaf rarpFabricFwding {
            description "RARP Fabric Forwarding";

            // Type is an MO-Defined-Type
            type nw_AdminSt;
        }

        // RARP Fabric Fwding Rate
        // Type is an MO-Defined-Type
        leaf rarpFabricFwdingRate {
            description "RARP Fabric Forwarding Rate";

            // Type is an MO-Defined-Type
            type arp_RarpForwadingRate;
        }

        // ARP Cache Limit
        // Type is an MO-Defined-Type
        leaf cacheLimit {
            description "Cache Limit";

            // Type is an MO-Defined-Type
            type arp_ArpCacheLimit;
        }

        // ARP Cache SysLog Rate
        // Type is an MO-Defined-Type
        leaf cacheSyslogRate {
            description "Cache Syslog Rate";

            // Type is an MO-Defined-Type
            type arp_ArpCacheSyslogRate;
        }

        // ARP Logging Level
        // Type is an MO-Defined-Type
        leaf loggingLevel {
            description "Logging Level";

            // Type is an MO-Defined-Type
            type arp_LoggingLevel;
        }

        // Adjacency Manager Logging Level
        // Type is an MO-Defined-Type
        leaf adjLoggingLevel {
            description "Adjacency Events Logging Level";

            // Type is an MO-Defined-Type
            type arp_LoggingLevel;
        }

        // Type is an MO-Defined-Type
        leaf ipAdjRouteDistance {
            description "IP Adjacency Route Distance";

            // Type is an MO-Defined-Type
            type arp_AdjRouteDist;
        }

        // Enable / Disable allow-static-arp-outside-subnet
        // Type is an MO-Defined-Type
        leaf allowStaticArpOutsideSubnet {
            description "Allow static ARP outside subnet";

            // Type is an MO-Defined-Type
            type nw_AdminSt;
        }

        // Config error in this MO
        // Type is an MO-Defined-Type
        leaf configErr {
            config "false";
            description "Config error Inst";

            // Type is an MO-Defined-Type
            type arp_ConfigErrInst;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Holds GlobalStats information
        container globalstats-items {

            // Added containment as a singleton: Prefix=globalstats
            // Acquired From Package arp
            uses arp_GlobalStats-group;
        }

        // This object holds per ARP domain (vrf) information
        container dom-items {
            list Dom-list {
                key "name";

                // Added containment: Prefix=dom
                // Acquired From Package arp
                uses arp_Dom-group;
            }
        }

        // IpV4 Glean throttling MO
        container ipgleanthrottle-items {

            // Added containment as a singleton: Prefix=ipgleanthrottle
            // Acquired From Package arp
            uses arp_Ipv4Throttle-group;
        }

        // This object holds the size of the Log Tables for
        // various types of ARP events
        container evtLogs-items {
            list EventLogs-list {
                key "eventType";

                // Added containment: Prefix=evtLogs
                // Acquired From Package arp
                uses arp_EventLogs-group;
            }
        }

        // This object holds IP ARP Sync for VPC
        container vpc-items {

            // Added containment as a singleton: Prefix=vpc
            // Acquired From Package arp
            uses arp_Vpc-group;
        }

        // Holds Suppression-cache table oper data
        container db-items {
            list DbSupCache-list {
                key "type";

                // Added containment: Prefix=db
                // Acquired From Package arp
                uses arp_DbSupCache-group;
            }
        }
    }

    grouping arp_GlobalStats-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Holds controller-statistics information
        container controllerstats-items {

            // Added containment as a singleton: Prefix=controllerstats
            // Acquired From Package arp
            uses arp_ControllerStats-group;
        }

        // Holds VPC related statistics information
        container vpcstats-items {

            // Added containment as a singleton: Prefix=vpcstats
            // Acquired From Package arp
            uses arp_VpcStats-group;
        }

        // Holds Tunnel statistics information
        container tunnelstats-items {

            // Added containment as a singleton: Prefix=tunnelstats
            // Acquired From Package arp
            uses arp_TunnelStats-group;
        }

        // Holds Suppression-cache related statistics
        container supcachestats-items {

            // Added containment as a singleton: Prefix=supcachestats
            // Acquired From Package arp
            uses arp_SupCacheStats-group;
        }

        // Holds open-flow error statistics
        container ofastats-items {

            // Added containment as a singleton: Prefix=ofastats
            // Acquired From Package arp
            uses arp_OfaStats-group;
        }
    }

    grouping arp_ControllerStats-group {
        leaf adjAddCount {
            config "false";
            type uint64;
        }
        leaf adjDelCount {
            config "false";
            type uint64;
        }
        leaf adjAddErrorCount {
            config "false";
            type uint64;
        }
        leaf adjDelErrorCount {
            config "false";
            type uint64;
        }
    }

    grouping arp_VpcStats-group {
        leaf cfsPullDropSinceOff {
            config "false";
            type uint64;
        }
        leaf cfsPushDropSinceOff {
            config "false";
            type uint64;
        }
        leaf sendIgnorePullReqCfsoe {
            config "false";
            type uint64;
        }
        leaf sendIgnorePushMsgCfsoe {
            config "false";
            type uint64;
        }
        leaf imFailCFSPayload {
            config "false";
            type uint64;
        }
        leaf mcecmFailCFSPayload {
            config "false";
            type uint64;
        }
        leaf invalidMctPcCFSPayload {
            config "false";
            type uint64;
        }
        leaf ptLookFailCFSPayload {
            config "false";
            type uint64;
        }
        leaf cfsRspFailInvalidMct {
            config "false";
            type uint64;
        }
        leaf cfsRspFailCfsPayload {
            config "false";
            type uint64;
        }
        leaf retrieveVpcFailPushMsg {
            config "false";
            type uint64;
        }
        leaf retIfindexFrmVpcFail {
            config "false";
            type uint64;
        }
        leaf retIfindexFrmVpcFailSync {
            config "false";
            type uint64;
        }
        leaf rspSentCfsoe {
            config "false";
            type uint64;
        }
        leaf rspRecvCfsoe {
            config "false";
            type uint64;
        }
        leaf rspRecvCfsoeErr {
            config "false";
            type uint64;
        }
        leaf recvCfsoe {
            config "false";
            type uint64;
        }
        leaf sentFailCfsoe {
            config "false";
            type uint64;
        }
        leaf mcecmSendApiFailCfsoe {
            config "false";
            type uint64;
        }
        leaf sendCfsoe {
            config "false";
            type uint64;
        }

        // Holds VPC SYNC related statistics
        container syncstats-items {

            // Added containment as a singleton: Prefix=syncstats
            // Acquired From Package arp
            uses arp_VpcSyncStats-group;
        }
    }

    grouping arp_VpcSyncStats-group {
        leaf ptAddFailOfflist {
            config "false";
            type uint64;
        }
        leaf mallocFailOfflistDb {
            config "false";
            type uint64;
        }
        leaf timerCreateFailOfflistDb {
            config "false";
            type uint64;
        }
        leaf adjAddFailOfflistDb {
            config "false";
            type uint64;
        }
        leaf ptLookupFailOfflistDb {
            config "false";
            type uint64;
        }
        leaf vlanMismatchOfflistDb {
            config "false";
            type uint64;
        }
        leaf invalidSviOfflistDb {
            config "false";
            type uint64;
        }
        leaf sviDownOfflistDb {
            config "false";
            type uint64;
        }
        leaf mctDownOfflistDb {
            config "false";
            type uint64;
        }
        leaf ctxTypeInvalidOfflistDb {
            config "false";
            type uint64;
        }
        leaf vrfInvalidOfflistDb {
            config "false";
            type uint64;
        }
        leaf invalidIpOfflistDb {
            config "false";
            type uint64;
        }
        leaf ipSanityFailOfflistDb {
            config "false";
            type uint64;
        }
        leaf macSanityFailOfflistDb {
            config "false";
            type uint64;
        }
        leaf ownRouterMacOfflistDb {
            config "false";
            type uint64;
        }
        leaf ownIpOfflistDb {
            config "false";
            type uint64;
        }
        leaf ownvIpOfflistDb {
            config "false";
            type uint64;
        }
        leaf adjCreateFailOfflistDb {
            config "false";
            type uint64;
        }
        leaf subnetMismatchOfflistDb {
            config "false";
            type uint64;
        }
        leaf dupEntryOfflistDb {
            config "false";
            type uint64;
        }
        leaf ipNotEnOfflistDb {
            config "false";
            type uint64;
        }
        leaf totDropOfflistDb {
            config "false";
            type uint64;
        }
        leaf totDontDropOfflistDb {
            config "false";
            type uint64;
        }
        leaf totAdjAddOfflistDb {
            config "false";
            type uint64;
        }
        leaf totAdjDelOfflistDb {
            config "false";
            type uint64;
        }
        leaf totAdjIgnoredOfflistDb {
            config "false";
            type uint64;
        }
        leaf totAdjFrmPeerToAdd {
            config "false";
            type uint64;
        }
        leaf totAdjFrmPeerToDel {
            config "false";
            type uint64;
        }
        leaf totAdjSentPeriodically {
            config "false";
            type uint64;
        }
        leaf totAdjPeerToAdd {
            config "false";
            type uint64;
        }
        leaf totAdjPeerToDel {
            config "false";
            type uint64;
        }
        leaf totPeriodicSyncAdj {
            config "false";
            type uint64;
        }
        leaf totAdjAddFailDuringSyncSend {
            config "false";
            type uint64;
        }
        leaf totDropDuringSyncInvalidSvi {
            config "false";
            type uint64;
        }
        leaf totDropSyncSviDown {
            config "false";
            type uint64;
        }
        leaf totDropSyncInvalidCtxt {
            config "false";
            type uint64;
        }
        leaf totDropSyncNullAdj {
            config "false";
            type uint64;
        }
        leaf totDropSyncNullIp {
            config "false";
            type uint64;
        }
        leaf totSyncAdjAddL2SupCache {
            config "false";
            type uint64;
        }
    }

    grouping arp_TunnelStats-group {
        leaf totTunnelRcvd {
            config "false";
            type uint64;
        }
        leaf rxForIngressVpc {
            config "false";
            type uint64;
        }
        leaf rxIngressforGpc {
            config "false";
            type uint64;
        }
        leaf rxIngressOrphanVpc {
            config "false";
            type uint64;
        }
        leaf rxIngressOrphanVpcPlus {
            config "false";
            type uint64;
        }
        leaf totPackSent {
            config "false";
            type uint64;
        }
        leaf pktSentArpSnoop {
            config "false";
            type uint64;
        }
        leaf pktSentNonlocalVip {
            config "false";
            type uint64;
        }
        leaf pktSentPeerGway {
            config "false";
            type uint64;
        }
        leaf txIngressVpc {
            config "false";
            type uint64;
        }
        leaf txIngressGpc {
            config "false";
            type uint64;
        }
        leaf txIngressOrphanVpc {
            config "false";
            type uint64;
        }
        leaf txIngressOrphanVpcPlus {
            config "false";
            type uint64;
        }
        leaf totRecvDropped {
            config "false";
            type uint64;
        }
        leaf totSendDropped {
            config "false";
            type uint64;
        }
        leaf sendFailDrop {
            config "false";
            type uint64;
        }
        leaf rcvdInvalidVer {
            config "false";
            type uint64;
        }
        leaf rcvdInvalidPayloadType {
            config "false";
            type uint64;
        }
        leaf rcvdMctIf {
            config "false";
            type uint64;
        }
        leaf rcvdInvalidIngressPort {
            config "false";
            type uint64;
        }
        leaf dropSentInvalidPort {
            config "false";
            type uint64;
        }
        leaf dropRecvInvalidGpcCore {
            config "false";
            type uint64;
        }
        leaf dropRecvInvalidGpcPeer {
            config "false";
            type uint64;
        }
        leaf dropRecvFailRetrieveGpc {
            config "false";
            type uint64;
        }
        leaf dropSendFailRetrieveGpc {
            config "false";
            type uint64;
        }
        leaf failRetrieveVpcId {
            config "false";
            type uint64;
        }
        leaf imApiFail {
            config "false";
            type uint64;
        }
        leaf invalidContext {
            config "false";
            type uint64;
        }
        leaf dropMctDown {
            config "false";
            type uint64;
        }
        leaf recvDropMbufFail {
            config "false";
            type uint64;
        }
        leaf sendDropMbufFail {
            config "false";
            type uint64;
        }
        leaf tunnelFailed {
            config "false";
            type uint64;
        }
        leaf tunnelFailCENetwork {
            config "false";
            type uint64;
        }
        leaf mcecmKeyNotFound {
            config "false";
            type uint64;
        }
    }

    grouping arp_SupCacheStats-group {
        leaf requests {
            config "false";
            type uint64;
        }
        leaf requestsL2 {
            config "false";
            type uint64;
        }
        leaf gratuitous {
            config "false";
            type uint64;
        }
        leaf gratuitousL2 {
            config "false";
            type uint64;
        }
        leaf fwdRequestsL3 {
            config "false";
            type uint64;
        }
        leaf fwdRepliesL3 {
            config "false";
            type uint64;
        }
        leaf fwdRequestOnCorePort {
            config "false";
            type uint64;
        }
        leaf fwdReplyOnCorePort {
            config "false";
            type uint64;
        }
        leaf sentDrop {
            config "false";
            type uint64;
        }
        leaf sentReqL2 {
            config "false";
            type uint64;
        }
        leaf sentReplyL2 {
            config "false";
            type uint64;
        }
        leaf sentReqCoreL2 {
            config "false";
            type uint64;
        }
        leaf sentReplyCoreL2 {
            config "false";
            type uint64;
        }
        leaf sentDropL2 {
            config "false";
            type uint64;
        }
        leaf recvReqL3 {
            config "false";
            type uint64;
        }
        leaf recvReplyL3 {
            config "false";
            type uint64;
        }
        leaf recvLocalReqL3 {
            config "false";
            type uint64;
        }
        leaf recvLocalReplyL3 {
            config "false";
            type uint64;
        }
        leaf recvGratArp {
            config "false";
            type uint64;
        }
        leaf recvDrop {
            config "false";
            type uint64;
        }
        leaf recvRequestL2 {
            config "false";
            type uint64;
        }
        leaf recvReplyL2 {
            config "false";
            type uint64;
        }
        leaf recvGratArpL2 {
            config "false";
            type uint64;
        }
        leaf recvDropL2 {
            config "false";
            type uint64;
        }
        leaf localEntryAdds {
            config "false";
            type uint64;
        }
        leaf localEntryDel {
            config "false";
            type uint64;
        }
    }

    grouping arp_OfaStats-group {
        leaf dpAdjErrDel {
            config "false";
            type uint64;
        }
        leaf cpMacMismatchErrDel {
            config "false";
            type uint64;
        }
        leaf cpNullMacErrDel {
            config "false";
            type uint64;
        }
        leaf cpNoAdjErrDel {
            config "false";
            type uint64;
        }
        leaf cpCpNhMismatchErrDel {
            config "false";
            type uint64;
        }
        leaf cpAdjDelFailureErr {
            config "false";
            type uint64;
        }
        leaf cpNullMacErrAdd {
            config "false";
            type uint64;
        }
        leaf cpDpMacMismatchErrAdd {
            config "false";
            type uint64;
        }
        leaf cpCpMacMismatchErrAdd {
            config "false";
            type uint64;
        }
        leaf cpAddFirstErr {
            config "false";
            type uint64;
        }
        leaf dpOverwriteCpErr {
            config "false";
            type uint64;
        }
        leaf dpCpNhMismatchErrAdd {
            config "false";
            type uint64;
        }
        leaf cpCpNhMismatchErrAdd {
            config "false";
            type uint64;
        }
        leaf cpDpNhMismatchErrAdd {
            config "false";
            type uint64;
        }
        leaf cpAdjAddFailureErr {
            config "false";
            type uint64;
        }
        leaf barrierResponseErr {
            config "false";
            type uint64;
        }
    }

    grouping arp_Dom-group {
        leaf encap {
            type string;
        }

        // Inherited From nw:Conn
        // Modified by Override: nw:CpDom->name
        // Type is an MO-Defined-Type
        leaf name {
            description "Name";

            // Type is an MO-Defined-Type
            type naming_Name {
                length "1..64";
            }
        }

        // ARP databases
        container db-items {
            list Db-list {
                key "type";

                // Added containment: Prefix=db
                // Acquired From Package arp
                uses arp_Db-group;
            }
        }

        // This object holds the arp dom related tx statistics
        container domstatstx-items {

            // Added containment as a singleton: Prefix=domstatstx
            // Acquired From Package arp
            uses arp_DomStatsTx-group;
        }

        // This object holds the arp dom related rx statistics
        container domstatsrx-items {

            // Added containment as a singleton: Prefix=domstatsrx
            // Acquired From Package arp
            uses arp_DomStatsRx-group;
        }

        // This object holds the arp dom related adj statistics
        container domstatsadj-items {

            // Added containment as a singleton: Prefix=domstatsadj
            // Acquired From Package arp
            uses arp_DomStatsAdj-group;
        }

        // This object holds the arp dom related misc statistics
        container domstatsmisc-items {

            // Added containment as a singleton: Prefix=domstatsmisc
            // Acquired From Package arp
            uses arp_DomStatsMisc-group;
        }

        // This object holds arp information that is operated at a
        // interface level
        container if-items {
            list If-list {
                key "id";

                // Added containment: Prefix=if
                // Acquired From Package arp
                uses arp_If-group;
            }
        }
    }

    grouping arp_Db-group {

        // Type of the repository
        // Type is an MO-Defined-Type
        leaf type {
            description "Type";

            // Type is an MO-Defined-Type
            type arp_DbT;
        }

        // Inherited From nw:Conn
        // Modified by Override: nw:Db->name
        // Type is an MO-Defined-Type
        leaf name {
            description "Name";

            // Type is an MO-Defined-Type
            type naming_Name {
                length "1..64";
            }
        }

        // Arp adjacency definitions
        container adj-items {
            list AdjEp-list {
                config "false";
                key "ifId ip";

                // Added containment: Prefix=adj
                // Acquired From Package arp
                uses arp_AdjEp-group;
            }
        }
    }

    grouping arp_AdjEp-group {
        leaf ip {
            type address_Ip;
        }
        leaf mac {
            config "false";
            type address_Mac;
        }
        leaf upTS {
            config "false";
            type uint64;
        }

        // Logical interface that this ep is associated with
        // Type is an MO-Defined-Type
        leaf ifId {
            config "false";
            description "Logical Interface ID";

            // Type is an MO-Defined-Type
            type nw_IfId;
        }

        // Operational state
        // Type is an MO-Defined-Type
        leaf operSt {
            config "false";
            description "Operational State";

            // Type is an MO-Defined-Type
            type arp_AdjOperSt;
        }

        // Physical interface that this ep is associated with
        // Type is an MO-Defined-Type
        leaf physIfId {
            config "false";
            description "Physical Interface ID";

            // Type is an MO-Defined-Type
            type nw_IfId;
        }

        // Flags that this ep has
        // Type is an MO-Defined-Type
        leaf flags {
            config "false";
            description "Flags";

            // Type is an MO-Defined-Type
            type arp_AdjFlags;
        }

        // Inherited From nw:Conn
        // Modified by Override: nw:Ep->name
        // Type is an MO-Defined-Type
        leaf name {
            description "Name";

            // Type is an MO-Defined-Type
            type naming_Name {
                length "1..64";
            }
        }
    }

    grouping arp_DomStatsTx-group {

        // ARP_PKT_SEND_COUNT
        // Type is an MO-Defined-Type
        leaf pktSent {
            config "false";
            description "Arp Pkt Send Count";

            // Type is an MO-Defined-Type
            type nw_Counter32;
        }

        // ARP_PKT_SEND_REQ_COUNT
        // Type is an MO-Defined-Type
        leaf pktSentReq {
            config "false";
            description "Arp Pkt Send Req Count";

            // Type is an MO-Defined-Type
            type nw_Counter32;
        }

        // ARP_PKT_SEND_REPLY_COUNT
        // Type is an MO-Defined-Type
        leaf pktSentRsp {
            config "false";
            description "Arp Pkt Send Reply Count";

            // Type is an MO-Defined-Type
            type nw_Counter32;
        }

        // ARP_PKT_SEND_REQ_COUNT_L2
        // Type is an MO-Defined-Type
        leaf pktSentReqL2 {
            config "false";
            description "Arp Pkt Send Req Count L2";

            // Type is an MO-Defined-Type
            type nw_Counter32;
        }

        // ARP_PKT_SEND_REPLY_COUNT_L2
        // Type is an MO-Defined-Type
        leaf pktSentRspL2 {
            config "false";
            description "Arp Pkt Send Reply Count L2";

            // Type is an MO-Defined-Type
            type nw_Counter32;
        }

        // ARP_PKT_SEND_GRAT_REQ_COUNT
        // Type is an MO-Defined-Type
        leaf pktSentGratReq {
            config "false";
            description "Arp Pkt Send Grat Req Count";

            // Type is an MO-Defined-Type
            type nw_Counter32;
        }

        // ARP_PKT_SEND_TUNNEL_COUNT
        // Type is an MO-Defined-Type
        leaf pktSentTunnel {
            config "false";
            description "Arp Pkt Send Tunnel Count";

            // Type is an MO-Defined-Type
            type nw_Counter32;
        }

        // ARP_PKT_SEND_DROP_COUNT
        // Type is an MO-Defined-Type
        leaf pktSentDrop {
            config "false";
            description "Arp Pkt Send Drop Count";

            // Type is an MO-Defined-Type
            type nw_Counter32;
        }

        // ARP_PKT_SEND_FAIL_INVALID_PKT_COUNT
        // Type is an MO-Defined-Type
        leaf pktSentFailInvPkt {
            config "false";
            description "Arp Pkt Send Fail Invalid Pkt Count";

            // Type is an MO-Defined-Type
            type nw_Counter32;
        }

        // ARP_PKT_SEND_FAIL_MBUF_OP_COUNT
        // Type is an MO-Defined-Type
        leaf pktSentFailMbufOp {
            config "false";
            description "Arp Pkt Send Fail Mbuf Op Count";

            // Type is an MO-Defined-Type
            type nw_Counter32;
        }

        // ARP_PKT_SEND_FAIL_NO_IFINDEX_COUNT
        // Type is an MO-Defined-Type
        leaf pktSentFailNoIfindex {
            config "false";
            description "Arp Pkt Send Fail no Ifindex Count";

            // Type is an MO-Defined-Type
            type nw_Counter32;
        }

        // ARP_PKT_SEND_FAIL_NO_VLAN_FOR_SVI_COUNT
        // Type is an MO-Defined-Type
        leaf pktSentFailNoVlanForSvi {
            config "false";
            description "Arp Pkt Send Fail no Vlan for Svi Count";

            // Type is an MO-Defined-Type
            type nw_Counter32;
        }

        // ARP_PKT_SEND_FAIL_UNSUPPORTED_INT_COUNT
        // Type is an MO-Defined-Type
        leaf pktSentFailUnsupportedInt {
            config "false";
            description "Arp Pkt Send Fail Unsupported Int Count";

            // Type is an MO-Defined-Type
            type nw_Counter32;
        }

        // ARP_PKT_SEND_FAIL_IM_DOWN_COUNT
        // Type is an MO-Defined-Type
        leaf pktSentFailImDown {
            config "false";
            description "Arp Pkt Send Fail Im Down Count";

            // Type is an MO-Defined-Type
            type nw_Counter32;
        }

        // ARP_PKT_SEND_FAIL_INVALID_SRC_IP_COUNT
        // Type is an MO-Defined-Type
        leaf pktSentFailInvSrcIp {
            config "false";
            description "Arp Pkt Send Fail Invalid Src Ip Count";

            // Type is an MO-Defined-Type
            type nw_Counter32;
        }

        // ARP_PKT_SEND_FAIL_INVALID_DEST_IP_COUNT
        // Type is an MO-Defined-Type
        leaf pktSentFailInvDstIp {
            config "false";
            description "Arp Pkt Send Fail Invalid Dst Ip Count";

            // Type is an MO-Defined-Type
            type nw_Counter32;
        }

        // ARP_PKT_SEND_FAIL_OWN_IP_COUNT
        // Type is an MO-Defined-Type
        leaf pktSentFailOwnIp {
            config "false";
            description "Arp Pkt Send Fail own Ip Count";

            // Type is an MO-Defined-Type
            type nw_Counter32;
        }

        // ARP_PKT_SEND_FAIL_CONTEXT_NOT_CREATED_COUNT
        // Type is an MO-Defined-Type
        leaf pktSentFailCtxtNotCreated {
            config "false";
            description "Arp Pkt Send Fail Context not Created Count";

            // Type is an MO-Defined-Type
            type nw_Counter32;
        }

        // ARP_PKT_SEND_FAIL_BAD_CONTEXT_ID_COUNT
        // Type is an MO-Defined-Type
        leaf pktSentFailBadCtxtId {
            config "false";
            description "Arp Pkt Send Fail Bad Context Id Count";

            // Type is an MO-Defined-Type
            type nw_Counter32;
        }

        // ARP_PKT_SEND_FAIL_UNATTACHED_IP_COUNT
        // Type is an MO-Defined-Type
        leaf pktSentFailUnattachedIp {
            config "false";
            description "Arp Pkt Send Fail Unattached Ip Count";

            // Type is an MO-Defined-Type
            type nw_Counter32;
        }

        // ARP_PKT_SEND_FAIL_ADJ_ADD_FAILURE_COUNT
        // Type is an MO-Defined-Type
        leaf pktSentFailAdjAddFailure {
            config "false";
            description "Arp Pkt Send Fail Adj Add Failure Count";

            // Type is an MO-Defined-Type
            type nw_Counter32;
        }

        // ARP_PKT_SEND_FAIL_NO_SRC_IP_COUNT
        // Type is an MO-Defined-Type
        leaf pktSentFailNoSrcIp {
            config "false";
            description "Arp Pkt Send Fail no Src Ip Count";

            // Type is an MO-Defined-Type
            type nw_Counter32;
        }

        // ARP_PKT_SEND_FAIL_NO_MAC_COUNT
        // Type is an MO-Defined-Type
        leaf pktSentFailNoMac {
            config "false";
            description "Arp Pkt Send Fail no Mac Count";

            // Type is an MO-Defined-Type
            type nw_Counter32;
        }

        // ARP_PKT_SEND_FAIL_CLIENT_ENQUEUE_FAILED_COUNT
        // Type is an MO-Defined-Type
        leaf pktSentFailClientEnqFailed {
            config "false";
            description "Arp Pkt Send Fail Client Enqueue Failed Count";

            // Type is an MO-Defined-Type
            type nw_Counter32;
        }

        // ARP_PKT_SEND_FAIL_PROXY_DEST_NOT_REACHABLE_COUNT
        // Type is an MO-Defined-Type
        leaf pktSentFailProxyDstNotRchbl {
            config "false";
            description "Arp Pkt Send Fail Proxy Dest not Reachable Count";

            // Type is an MO-Defined-Type
            type nw_Counter32;
        }

        // ARP_PKT_SEND_FAIL_INVALID_LOCAL_PROXY_COUNT
        // Type is an MO-Defined-Type
        leaf pktSentFailInvLocalProxy {
            config "false";
            description "Arp Pkt Send Fail Invalid Local Proxy Count";

            // Type is an MO-Defined-Type
            type nw_Counter32;
        }

        // ARP_PKT_SEND_FAIL_INVALID_PROXY_COUNT
        // Type is an MO-Defined-Type
        leaf pktSentFailInvProxy {
            config "false";
            description "Arp Pkt Send Fail Invalid Proxy Count";

            // Type is an MO-Defined-Type
            type nw_Counter32;
        }

        // ARP_PKT_SEND_FAIL_VIP_GROUP_NOT_ACTIVE_COUNT
        // Type is an MO-Defined-Type
        leaf pktSentFailVipGroupNotActive {
            config "false";
            description "Arp Pkt Send Fail Vip Group not Active Count";

            // Type is an MO-Defined-Type
            type nw_Counter32;
        }
    }

    grouping arp_DomStatsRx-group {

        // ARP_PKT_RECV_COUNT
        // Type is an MO-Defined-Type
        leaf pktRcvd {
            config "false";
            description "Arp Pkt Recv Count";

            // Type is an MO-Defined-Type
            type nw_Counter32;
        }

        // ARP_PKT_RECV_REQ_COUNT
        // Type is an MO-Defined-Type
        leaf pktRcvdReq {
            config "false";
            description "Arp Pkt Recv Req Count";

            // Type is an MO-Defined-Type
            type nw_Counter32;
        }

        // ARP_PKT_RECV_REPLY_COUNT
        // Type is an MO-Defined-Type
        leaf pktRcvdRsp {
            config "false";
            description "Arp Pkt Recv Reply Count";

            // Type is an MO-Defined-Type
            type nw_Counter32;
        }

        // ARP_PKT_RECV_PROXY_ARP_COUNT
        // Type is an MO-Defined-Type
        leaf pktRcvdProxyArp {
            config "false";
            description "Arp Pkt Recv Proxy Arp Count";

            // Type is an MO-Defined-Type
            type nw_Counter32;
        }

        // ARP_PKT_RECV_LOCAL_PROXY_ARP_COUNT
        // Type is an MO-Defined-Type
        leaf pktRcvdLocalProxyArp {
            config "false";
            description "Arp Pkt Recv Local Proxy Arp Count";

            // Type is an MO-Defined-Type
            type nw_Counter32;
        }

        // ARP_PKT_RECV_REQ_COUNT_L2
        // Type is an MO-Defined-Type
        leaf pktRcvdReqL2 {
            config "false";
            description "Arp Pkt Recv Req Count L2";

            // Type is an MO-Defined-Type
            type nw_Counter32;
        }

        // ARP_PKT_RECV_REPLY_COUNT_L2
        // Type is an MO-Defined-Type
        leaf pktRcvdRspL2 {
            config "false";
            description "Arp Pkt Recv Reply Count L2";

            // Type is an MO-Defined-Type
            type nw_Counter32;
        }

        // ARP_PKT_RECV_TUNNEL_COUNT
        // Type is an MO-Defined-Type
        leaf pktRcvdTunnel {
            config "false";
            description "Arp Pkt Recv Tunnel Count";

            // Type is an MO-Defined-Type
            type nw_Counter32;
        }

        // ARP_PKT_RECV_FASTPATH_COUNT
        // Type is an MO-Defined-Type
        leaf pktRcvdFastpath {
            config "false";
            description "Arp Pkt Recv Fastpath Count";

            // Type is an MO-Defined-Type
            type nw_Counter32;
        }

        // ARP_PKT_RECV_SNOOP_COUNT
        // Type is an MO-Defined-Type
        leaf pktRcvdSnoop {
            config "false";
            description "Arp Pkt Recv Snoop Count";

            // Type is an MO-Defined-Type
            type nw_Counter32;
        }

        // ARP_PKT_RECV_DROP_COUNT
        // Type is an MO-Defined-Type
        leaf pktRcvdDrp {
            config "false";
            description "Arp Pkt Recv Drop Count";

            // Type is an MO-Defined-Type
            type nw_Counter32;
        }

        // ARP_PKT_RECV_MBUF_OP_COUNT
        // Type is an MO-Defined-Type
        leaf pktRcvdMbufOp {
            config "false";
            description "Arp Pkt Recv Mbuf Op Count";

            // Type is an MO-Defined-Type
            type nw_Counter32;
        }

        // ARP_PKT_RECV_DROP_BAD_IF_COUNT
        // Type is an MO-Defined-Type
        leaf pktRcvdDrpBadIf {
            config "false";
            description "Arp Pkt Recv Drop Bad if Count";

            // Type is an MO-Defined-Type
            type nw_Counter32;
        }

        // ARP_PKT_RECV_DROP_BAD_LEN_COUNT
        // Type is an MO-Defined-Type
        leaf pktRcvdDrpBadLen {
            config "false";
            description "Arp Pkt Recv Drop Bad Len Count";

            // Type is an MO-Defined-Type
            type nw_Counter32;
        }

        // ARP_PKT_RECV_DROP_BAD_PROTO_COUNT
        // Type is an MO-Defined-Type
        leaf pktRcvdDrpBadProto {
            config "false";
            description "Arp Pkt Recv Drop Bad Proto Count";

            // Type is an MO-Defined-Type
            type nw_Counter32;
        }

        // ARP_PKT_RECV_DROP_BAD_L2ADDR_LEN_COUNT
        // Type is an MO-Defined-Type
        leaf pktRcvdDrpBadL2AddrLen {
            config "false";
            description "Arp Pkt Recv Drop Bad L2Addr Len Count";

            // Type is an MO-Defined-Type
            type nw_Counter32;
        }

        // ARP_PKT_RECV_DROP_BAD_L3ADDR_LEN_COUNT
        // Type is an MO-Defined-Type
        leaf pktRcvdDrpBadL3AddrLen {
            config "false";
            description "Arp Pkt Recv Drop Bad L3Addr Len Count";

            // Type is an MO-Defined-Type
            type nw_Counter32;
        }

        // ARP_PKT_RECV_DROP_INVAL_SRC_IP_COUNT
        // Type is an MO-Defined-Type
        leaf pktRcvdDrpInvalSrcIp {
            config "false";
            description "Arp Pkt Recv Drop Inval Src Ip Count";

            // Type is an MO-Defined-Type
            type nw_Counter32;
        }

        // ARP_PKT_RECV_DROP_DIR_BCAST_COUNT
        // Type is an MO-Defined-Type
        leaf pktRcvdDrpDirBcast {
            config "false";
            description "Arp Pkt Recv Drop Dir Bcast Count";

            // Type is an MO-Defined-Type
            type nw_Counter32;
        }

        // ARP_PKT_RECV_DROP_INVAL_DST_IP_COUNT
        // Type is an MO-Defined-Type
        leaf pktRcvdDrpInvalDstIp {
            config "false";
            description "Arp Pkt Recv Drop Inval Dst Ip Count";

            // Type is an MO-Defined-Type
            type nw_Counter32;
        }

        // ARP_PKT_RECV_DROP_BAD_SRC_MAC_COUNT
        // Type is an MO-Defined-Type
        leaf pktRcvdDrpBadSrcMac {
            config "false";
            description "Arp Pkt Recv Drop Bad Src Mac Count";

            // Type is an MO-Defined-Type
            type nw_Counter32;
        }

        // ARP_PKT_RECV_DROP_OWN_SRC_MAC_COUNT
        // Type is an MO-Defined-Type
        leaf pktRcvdDrpOwnSrcMac {
            config "false";
            description "Arp Pkt Recv Drop own Src Mac Count";

            // Type is an MO-Defined-Type
            type nw_Counter32;
        }

        // ARP_PKT_RECV_DROP_OWN_SRC_IP_COUNT
        // Type is an MO-Defined-Type
        leaf pktRcvdDrpOwnSrcIp {
            config "false";
            description "Arp Pkt Recv Drop own Src Ip Count";

            // Type is an MO-Defined-Type
            type nw_Counter32;
        }

        // ARP_PKT_RECV_DROP_ARP_IF_NO_MEM_COUNT
        // Type is an MO-Defined-Type
        leaf pktRcvdDrpArpIfNoMem {
            config "false";
            description "Arp Pkt Recv Drop Arp if no Mem Count";

            // Type is an MO-Defined-Type
            type nw_Counter32;
        }

        // ARP_PKT_RECV_DROP_NOT_FOR_US_COUNT
        // Type is an MO-Defined-Type
        leaf pktRcvdDrpNotForUs {
            config "false";
            description "Arp Pkt Recv Drop not for us Count";

            // Type is an MO-Defined-Type
            type nw_Counter32;
        }

        // ARP_PKT_RECV_LEARN_AND_DROP_NOT_FOR_US_COUNT
        // Type is an MO-Defined-Type
        leaf pktRcvdLearnAndDropNotForUs {
            config "false";
            description "Arp Pkt Recv Learn and Drop not for us Count";

            // Type is an MO-Defined-Type
            type nw_Counter32;
        }

        // ARP_PKT_RECV_DROP_SUBNET_MISMATCH_COUNT
        // Type is an MO-Defined-Type
        leaf pktRcvdDrpSubnetMismatch {
            config "false";
            description "Arp Pkt Recv Drop Subnet Mismatch Count";

            // Type is an MO-Defined-Type
            type nw_Counter32;
        }

        // ARP_PKT_RECV_DROP_NOT_INITIALIZED_COUNT
        // Type is an MO-Defined-Type
        leaf pktRcvdDrpNotInit {
            config "false";
            description "Arp Pkt Recv Drop not Initialized Count";

            // Type is an MO-Defined-Type
            type nw_Counter32;
        }

        // ARP_PKT_RECV_DROP_BAD_CONTEXT_COUNT
        // Type is an MO-Defined-Type
        leaf pktRcvdDrpBadCtxt {
            config "false";
            description "Arp Pkt Recv Drop Bad Context Count";

            // Type is an MO-Defined-Type
            type nw_Counter32;
        }

        // ARP_PKT_RECV_DROP_CONTEXT_NOT_CREATED_COUNT
        // Type is an MO-Defined-Type
        leaf pktRcvdDrpCtxtNotCreated {
            config "false";
            description "Arp Pkt Recv Drop Context not Created Count";

            // Type is an MO-Defined-Type
            type nw_Counter32;
        }

        // ARP_PKT_RECV_DROP_L2_LOCAL_PROXY_ARP_COUNT
        // Type is an MO-Defined-Type
        leaf pktRcvdDrpL2LocalProxyArp {
            config "false";
            description "Arp Pkt Recv Drop L2 Local Proxy Arp Count";

            // Type is an MO-Defined-Type
            type nw_Counter32;
        }

        // ARP_PKT_RECV_DROP_L2_PURE_L2_PKT_COUNT
        // Type is an MO-Defined-Type
        leaf pktRcvdDrpL2PureL2Pkt {
            config "false";
            description "Arp Pkt Recv Drop L2 Pure L2 Pkt Count";

            // Type is an MO-Defined-Type
            type nw_Counter32;
        }

        // ARP_PKT_RECV_DROP_L2_PORT_UNTRUSTED_COUNT
        // Type is an MO-Defined-Type
        leaf pktRcvdDrpL2PrtUntrusted {
            config "false";
            description "Arp Pkt Recv Drop L2 Port Untrusted Count";

            // Type is an MO-Defined-Type
            type nw_Counter32;
        }

        // ARP_PKT_RECV_DROP_STANDBY_FHRP_VIP_COUNT
        // Type is an MO-Defined-Type
        leaf pktRcvdDrpStdbyFhrpVip {
            config "false";
            description "Arp Pkt Recv Drop Standby Fhrp Vip Count";

            // Type is an MO-Defined-Type
            type nw_Counter32;
        }

        // ARP_PKT_RECV_DROP_GRAT_ON_PROXY_ARP_COUNT
        // Type is an MO-Defined-Type
        leaf pktRcvdDrpGratOnProxyArp {
            config "false";
            description "Arp Pkt Recv Drop Grat on Proxy Arp Count";

            // Type is an MO-Defined-Type
            type nw_Counter32;
        }

        // ARP_PKT_RECV_DROP_ARP_REQUEST_IGNORE_COUNT
        // Type is an MO-Defined-Type
        leaf pktRcvdDrpArpRequestIgnore {
            config "false";
            description "Arp Pkt Recv Drop Arp Request Ignore Count";

            // Type is an MO-Defined-Type
            type nw_Counter32;
        }

        // ARP_PKT_RECV_DROP_L2FM_QUERY_FAIL_COUNT
        // Type is an MO-Defined-Type
        leaf pktRcvdDrpL2FmQueryFail {
            config "false";
            description "Arp Pkt Recv Drop L2Fm Query Fail Count";

            // Type is an MO-Defined-Type
            type nw_Counter32;
        }

        // ARP_PKT_RECV_DROP_TUNNEL_FAIL_COUNT
        // Type is an MO-Defined-Type
        leaf pktRcvdDrpTunnelFail {
            config "false";
            description "Arp Pkt Recv Drop Tunnel Fail Count";

            // Type is an MO-Defined-Type
            type nw_Counter32;
        }
    }

    grouping arp_DomStatsAdj-group {

        // ARP_ADJ_ADD_COUNT
        // Type is an MO-Defined-Type
        leaf adjAdd {
            config "false";
            description "Arp Adj Add Count";

            // Type is an MO-Defined-Type
            type nw_Counter32;
        }

        // ARP_ADJ_DEL_COUNT
        // Type is an MO-Defined-Type
        leaf adjDel {
            config "false";
            description "Arp Adj Del Count";

            // Type is an MO-Defined-Type
            type nw_Counter32;
        }

        // ARP_ADJ_TIMEOUT_COUNT
        // Type is an MO-Defined-Type
        leaf adjTimeout {
            config "false";
            description "Arp Adj Timeout Count";

            // Type is an MO-Defined-Type
            type nw_Counter32;
        }

        // ARP_RESOLVED_ADJS_COUNT
        // Type is an MO-Defined-Type
        leaf resolved {
            config "false";
            description "Arp Resolved Adjs Count";

            // Type is an MO-Defined-Type
            type nw_Counter64;
        }

        // ARP_INCOMPLETE_ADJS_COUNT
        // Type is an MO-Defined-Type
        leaf incomplete {
            config "false";
            description "Arp Incomplete Adjs Count";

            // Type is an MO-Defined-Type
            type nw_Counter64;
        }

        // ARP_TOTAL_ADJS_COUNT
        // Type is an MO-Defined-Type
        leaf total {
            config "false";
            description "Arp Total Adjs Count";

            // Type is an MO-Defined-Type
            type nw_Counter64;
        }
    }

    grouping arp_DomStatsMisc-group {

        // ARP_CLIENT_MSG_COUNT
        // Type is an MO-Defined-Type
        leaf clientMsg {
            config "false";
            description "Arp Client Msg Count";

            // Type is an MO-Defined-Type
            type nw_Counter32;
        }

        // ARP_CLIENT_MSG_FAIL_COUNT
        // Type is an MO-Defined-Type
        leaf clientMsgFail {
            config "false";
            description "Arp Client Msg Fail Count";

            // Type is an MO-Defined-Type
            type nw_Counter32;
        }

        // ARP_IF_TIMEOUT_MSG_FAIL_COUNT
        // Type is an MO-Defined-Type
        leaf ifTimeoutMsgFail {
            config "false";
            description "Arp if Timeout Msg Fail Count";

            // Type is an MO-Defined-Type
            type nw_Counter32;
        }

        // ARP_IF_STATUS_MSG_FAIL_COUNT
        // Type is an MO-Defined-Type
        leaf ifStatusMsgFail {
            config "false";
            description "Arp if Status Msg Fail Count";

            // Type is an MO-Defined-Type
            type nw_Counter32;
        }
    }

    grouping arp_If-group {

        // Timeout
        // Type is an MO-Defined-Type
        leaf timeout {
            description "ARP Timeout";

            // Type is an MO-Defined-Type
            type arp_Timeout;
        }

        // Gratuitous ARP request
        // Type is an MO-Defined-Type
        leaf gratuitousRequest {
            description "Gratuitous ARP Request";

            // Type is an MO-Defined-Type
            type nw_AdminSt;
        }

        // Gratuitous ARP Update
        // Type is an MO-Defined-Type
        leaf gratuitousUpdate {
            description "Gratuitous ARP Update";

            // Type is an MO-Defined-Type
            type nw_AdminSt;
        }

        // Gratuitous ARP HSRP Duplicate
        // Type is an MO-Defined-Type
        leaf gratuitousHsrpDup {
            description "Gratuitous ARP HSRP Duplicate";

            // Type is an MO-Defined-Type
            type nw_AdminSt;
        }

        // Proxy ARP
        // Type is an MO-Defined-Type
        leaf proxyArp {
            description "Proxy ARP";

            // Type is an MO-Defined-Type
            type nw_AdminSt;
        }

        // Local Proxy ARP
        // Type is an MO-Defined-Type
        leaf localProxyArp {
            description "Local Proxy ARP";

            // Type is an MO-Defined-Type
            type nw_AdminSt;
        }

        // Config error in this MO
        // Type is an MO-Defined-Type
        leaf configError {
            config "false";
            description "Config error";

            // Type is an MO-Defined-Type
            type arp_ConfigErr;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Static arp adjacency definitions
        container sadj-items {
            list StAdjEp-list {
                key "ip";

                // Added containment: Prefix=sadj
                // Acquired From Package arp
                uses arp_StAdjEp-group;
            }
        }

        // This object holds the arp if related tx statistics
        container ifstatstx-items {

            // Added containment as a singleton: Prefix=ifstatstx
            // Acquired From Package arp
            uses arp_IfStatsTx-group;
        }

        // This object holds the arp if related rx statistics
        container ifstatsrx-items {

            // Added containment as a singleton: Prefix=ifstatsrx
            // Acquired From Package arp
            uses arp_IfStatsRx-group;
        }

        // This object holds the arp if related adj statistics
        container ifstatsadj-items {

            // Added containment as a singleton: Prefix=ifstatsadj
            // Acquired From Package arp
            uses arp_IfStatsAdj-group;
        }

        // This object holds the arp if related misc statistics
        container ifstatsmisc-items {

            // Added containment as a singleton: Prefix=ifstatsmisc
            // Acquired From Package arp
            uses arp_IfStatsMisc-group;
        }

        // This object holds the arp related Multihoming(MH) statistics
        container ifstatsmh-items {

            // Added containment as a singleton: Prefix=ifstatsmh
            // Acquired From Package arp
            uses arp_IfStatsMH-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping arp_StAdjEp-group {

        // Operational state
        // Type is an MO-Defined-Type
        leaf operSt {
            config "false";
            description "Operational State";

            // Type is an MO-Defined-Type
            type arp_StAdjOperSt;
        }

        // Operational state qualifier
        // Type is an MO-Defined-Type
        leaf operStQual {
            config "false";
            description "Operational State Qualifier";

            // Type is an MO-Defined-Type
            type arp_StAdjOperStQual;
        }

        // Inherited From nw:Conn
        // Modified by Override: nw:Ep->name
        // Type is an MO-Defined-Type
        leaf name {
            description "Name";

            // Type is an MO-Defined-Type
            type naming_Name {
                length "1..64";
            }
        }
        leaf ip {
            type address_Ip;
        }
        leaf mac {
            type address_Mac;
        }
        leaf upTS {
            config "false";
            type uint64;
        }

        // Rel-def target from CtrlrAdjEpToStAdjEp
        // Inherited From arp:StAdjEp
        container rtCtrlrAdjEpToStAdjEp-items {

            // Added containment as a singleton: Prefix=rtCtrlrAdjEpToStAdjEp
            // Acquired From Package lldp
            uses lldp_RtCtrlrAdjEpToStAdjEp_target-group;
        }

        // Rel-def target from EpDefRefToStAdjEp
        // Inherited From arp:StAdjEp
        container rtfvEpDefRefToStAdjEp-items {

            // Abstract containment of rtfvEpDefRefToStAdjEp derived from arp:StAdjEp
            list RtFvEpDefRefToStAdjEp-list {
                config "false";
                key "tDn";

                // Added containment: Prefix=rtfvEpDefRefToStAdjEp
                // Acquired From Package fv
                uses fv_RtFvEpDefRefToStAdjEp_target-group;
            }
        }
    }

    grouping arp_IfStatsTx-group {

        // ARP_PKT_SEND_COUNT
        // Type is an MO-Defined-Type
        leaf pktSent {
            config "false";
            description "Arp Pkt Send Count";

            // Type is an MO-Defined-Type
            type nw_Counter32;
        }

        // ARP_PKT_SEND_REQ_COUNT
        // Type is an MO-Defined-Type
        leaf pktSentReq {
            config "false";
            description "Arp Pkt Send Req Count";

            // Type is an MO-Defined-Type
            type nw_Counter32;
        }

        // ARP_PKT_SEND_REPLY_COUNT
        // Type is an MO-Defined-Type
        leaf pktSentRsp {
            config "false";
            description "Arp Pkt Send Reply Count";

            // Type is an MO-Defined-Type
            type nw_Counter32;
        }

        // ARP_PKT_SEND_REQ_COUNT_L2
        // Type is an MO-Defined-Type
        leaf pktSentReqL2 {
            config "false";
            description "Arp Pkt Send Req Count L2";

            // Type is an MO-Defined-Type
            type nw_Counter32;
        }

        // ARP_PKT_SEND_REPLY_COUNT_L2
        // Type is an MO-Defined-Type
        leaf pktSentRspL2 {
            config "false";
            description "Arp Pkt Send Reply Count L2";

            // Type is an MO-Defined-Type
            type nw_Counter32;
        }

        // ARP_PKT_SEND_GRAT_REQ_COUNT
        // Type is an MO-Defined-Type
        leaf pktSentGratReq {
            config "false";
            description "Arp Pkt Send Grat Req Count";

            // Type is an MO-Defined-Type
            type nw_Counter32;
        }

        // ARP_PKT_SEND_TUNNEL_COUNT
        // Type is an MO-Defined-Type
        leaf pktSentTunnel {
            config "false";
            description "Arp Pkt Send Tunnel Count";

            // Type is an MO-Defined-Type
            type nw_Counter32;
        }

        // ARP_PKT_SEND_DROP_COUNT
        // Type is an MO-Defined-Type
        leaf pktSentDrop {
            config "false";
            description "Arp Pkt Send Drop Count";

            // Type is an MO-Defined-Type
            type nw_Counter32;
        }

        // ARP_PKT_SEND_SRVRPORT_COUNT
        // Type is an MO-Defined-Type
        leaf pktSendSrvPort {
            config "false";
            description "Arp Pkt Send server port Count";

            // Type is an MO-Defined-Type
            type nw_Counter32;
        }

        // ARP_PKT_SEND_FBRCPORT_COUNT
        // Type is an MO-Defined-Type
        leaf pktSendFbrcPort {
            config "false";
            description "Arp Pkt Send Fabric port Count";

            // Type is an MO-Defined-Type
            type nw_Counter32;
        }

        // ARP_PKT_SEND_FIXUP_CORE_COUNT
        // Type is an MO-Defined-Type
        leaf pktSendFixupCore {
            config "false";
            description "Arp Pkt Send Fixup core Count";

            // Type is an MO-Defined-Type
            type nw_Counter32;
        }

        // ARP_PKT_SEND_FIXUP_SERVER_COUNT
        // Type is an MO-Defined-Type
        leaf pktSendFixupServer {
            config "false";
            description "Arp Pkt Send Fixup Server Count";

            // Type is an MO-Defined-Type
            type nw_Counter32;
        }

        // ARP_PKT_SEND_FIXUP_RARP_COUNT
        // Type is an MO-Defined-Type
        leaf pktSendFixupRarp {
            config "false";
            description "Arp Pkt Send Fixup Rarp Count";

            // Type is an MO-Defined-Type
            type nw_Counter32;
        }

        // ARP_PKT_SEND_ANYCAST_GLEAN_COUNT
        // Type is an MO-Defined-Type
        leaf pktSendAnyCastGlean {
            config "false";
            description "Arp Pkt Send Anycast Glean Count";

            // Type is an MO-Defined-Type
            type nw_Counter32;
        }

        // ARP_PKT_SEND_FAIL_INVALID_PKT_COUNT
        // Type is an MO-Defined-Type
        leaf pktSentFailInvPkt {
            config "false";
            description "Arp Pkt Send Fail Invalid Pkt Count";

            // Type is an MO-Defined-Type
            type nw_Counter32;
        }

        // ARP_PKT_SEND_FAIL_MBUF_OP_COUNT
        // Type is an MO-Defined-Type
        leaf pktSentFailMbufOp {
            config "false";
            description "Arp Pkt Send Fail Mbuf Op Count";

            // Type is an MO-Defined-Type
            type nw_Counter32;
        }

        // ARP_PKT_SEND_FAIL_NO_IFINDEX_COUNT
        // Type is an MO-Defined-Type
        leaf pktSentFailNoIfindex {
            config "false";
            description "Arp Pkt Send Fail no Ifindex Count";

            // Type is an MO-Defined-Type
            type nw_Counter32;
        }

        // ARP_PKT_SEND_FAIL_NO_VLAN_FOR_SVI_COUNT
        // Type is an MO-Defined-Type
        leaf pktSentFailNoVlanForSvi {
            config "false";
            description "Arp Pkt Send Fail no Vlan for Svi Count";

            // Type is an MO-Defined-Type
            type nw_Counter32;
        }

        // ARP_PKT_SEND_FAIL_UNSUPPORTED_INT_COUNT
        // Type is an MO-Defined-Type
        leaf pktSentFailUnsupportedInt {
            config "false";
            description "Arp Pkt Send Fail Unsupported Int Count";

            // Type is an MO-Defined-Type
            type nw_Counter32;
        }

        // ARP_PKT_SEND_FAIL_IM_DOWN_COUNT
        // Type is an MO-Defined-Type
        leaf pktSentFailImDown {
            config "false";
            description "Arp Pkt Send Fail Im Down Count";

            // Type is an MO-Defined-Type
            type nw_Counter32;
        }

        // ARP_PKT_SEND_FAIL_INVALID_SRC_IP_COUNT
        // Type is an MO-Defined-Type
        leaf pktSentFailInvSrcIp {
            config "false";
            description "Arp Pkt Send Fail Invalid Src Ip Count";

            // Type is an MO-Defined-Type
            type nw_Counter32;
        }

        // ARP_PKT_SEND_FAIL_INVALID_DEST_IP_COUNT
        // Type is an MO-Defined-Type
        leaf pktSentFailInvDstIp {
            config "false";
            description "Arp Pkt Send Fail Invalid Dst Ip Count";

            // Type is an MO-Defined-Type
            type nw_Counter32;
        }

        // ARP_PKT_SEND_FAIL_OWN_IP_COUNT
        // Type is an MO-Defined-Type
        leaf pktSentFailOwnIp {
            config "false";
            description "Arp Pkt Send Fail own Ip Count";

            // Type is an MO-Defined-Type
            type nw_Counter32;
        }

        // ARP_PKT_SEND_FAIL_CONTEXT_NOT_CREATED_COUNT
        // Type is an MO-Defined-Type
        leaf pktSentFailCtxtNotCreated {
            config "false";
            description "Arp Pkt Send Fail Context not Created Count";

            // Type is an MO-Defined-Type
            type nw_Counter32;
        }

        // ARP_PKT_SEND_FAIL_BAD_CONTEXT_ID_COUNT
        // Type is an MO-Defined-Type
        leaf pktSentFailBadCtxtId {
            config "false";
            description "Arp Pkt Send Fail Bad Context Id Count";

            // Type is an MO-Defined-Type
            type nw_Counter32;
        }

        // ARP_PKT_SEND_FAIL_UNATTACHED_IP_COUNT
        // Type is an MO-Defined-Type
        leaf pktSentFailUnattachedIp {
            config "false";
            description "Arp Pkt Send Fail Unattached Ip Count";

            // Type is an MO-Defined-Type
            type nw_Counter32;
        }

        // ARP_PKT_SEND_FAIL_ADJ_ADD_FAILURE_COUNT
        // Type is an MO-Defined-Type
        leaf pktSentFailAdjAddFailure {
            config "false";
            description "Arp Pkt Send Fail Adj Add Failure Count";

            // Type is an MO-Defined-Type
            type nw_Counter32;
        }

        // ARP_PKT_SEND_FAIL_NO_SRC_IP_COUNT
        // Type is an MO-Defined-Type
        leaf pktSentFailNoSrcIp {
            config "false";
            description "Arp Pkt Send Fail no Src Ip Count";

            // Type is an MO-Defined-Type
            type nw_Counter32;
        }

        // ARP_PKT_SEND_FAIL_NO_MAC_COUNT
        // Type is an MO-Defined-Type
        leaf pktSentFailNoMac {
            config "false";
            description "Arp Pkt Send Fail no Mac Count";

            // Type is an MO-Defined-Type
            type nw_Counter32;
        }

        // ARP_PKT_SEND_FAIL_CLIENT_ENQUEUE_FAILED_COUNT
        // Type is an MO-Defined-Type
        leaf pktSentFailClientEnqFailed {
            config "false";
            description "Arp Pkt Send Fail Client Enqueue Failed Count";

            // Type is an MO-Defined-Type
            type nw_Counter32;
        }

        // ARP_PKT_SEND_FAIL_PROXY_DEST_NOT_REACHABLE_COUNT
        // Type is an MO-Defined-Type
        leaf pktSentFailProxyDstNotRchbl {
            config "false";
            description "Arp Pkt Send Fail Proxy Dest not Reachable Count";

            // Type is an MO-Defined-Type
            type nw_Counter32;
        }

        // ARP_PKT_SKIP_RESPONSE_ENHANCED_PROXY_DEST_NOT_REACHABLE_COUNT
        // Type is an MO-Defined-Type
        leaf pktSkipRespEnhancedProxyDestNotReach {
            config "false";
            description "Arp Pkt Skip response enhanced proxy dest not reachable count";

            // Type is an MO-Defined-Type
            type nw_Counter32;
        }

        // ARP_PKT_SKIP_RESPONSE_ENHANCED_PROXY_L2PORT_TRACK_COUNT
        // Type is an MO-Defined-Type
        leaf pktSkipRespEnhancedProxyL2portTrack {
            config "false";
            description "Arp Pkt Skip response enhanced proxy L2 port track Count";

            // Type is an MO-Defined-Type
            type nw_Counter32;
        }

        // ARP_PKT_SEND_FAIL_INVALID_LOCAL_PROXY_COUNT
        // Type is an MO-Defined-Type
        leaf pktSentFailInvLocalProxy {
            config "false";
            description "Arp Pkt Send Fail Invalid Local Proxy Count";

            // Type is an MO-Defined-Type
            type nw_Counter32;
        }

        // ARP_PKT_SEND_FAIL_INVALID_PROXY_COUNT
        // Type is an MO-Defined-Type
        leaf pktSentFailInvProxy {
            config "false";
            description "Arp Pkt Send Fail Invalid Proxy Count";

            // Type is an MO-Defined-Type
            type nw_Counter32;
        }

        // ARP_PKT_SEND_FAIL_VIP_GROUP_NOT_ACTIVE_COUNT
        // Type is an MO-Defined-Type
        leaf pktSentFailVipGroupNotActive {
            config "false";
            description "Arp Pkt Send Fail Vip Group not Active Count";

            // Type is an MO-Defined-Type
            type nw_Counter32;
        }
    }

    grouping arp_IfStatsRx-group {

        // ARP_PKT_RECV_COUNT
        // Type is an MO-Defined-Type
        leaf pktRcvd {
            config "false";
            description "Arp Pkt Recv Count";

            // Type is an MO-Defined-Type
            type nw_Counter32;
        }

        // ARP_PKT_RECV_REQ_COUNT
        // Type is an MO-Defined-Type
        leaf pktRcvdReq {
            config "false";
            description "Arp Pkt Recv Req Count";

            // Type is an MO-Defined-Type
            type nw_Counter32;
        }

        // ARP_PKT_RECV_REPLY_COUNT
        // Type is an MO-Defined-Type
        leaf pktRcvdRsp {
            config "false";
            description "Arp Pkt Recv Reply Count";

            // Type is an MO-Defined-Type
            type nw_Counter32;
        }

        // ARP_PKT_RECV_PROXY_ARP_COUNT
        // Type is an MO-Defined-Type
        leaf pktRcvdProxyArp {
            config "false";
            description "Arp Pkt Recv Proxy Arp Count";

            // Type is an MO-Defined-Type
            type nw_Counter32;
        }

        // ARP_PKT_RECV_LOCAL_PROXY_ARP_COUNT
        // Type is an MO-Defined-Type
        leaf pktRcvdLocalProxyArp {
            config "false";
            description "Arp Pkt Recv Local Proxy Arp Count";

            // Type is an MO-Defined-Type
            type nw_Counter32;
        }

        // ARP_PKT_RECV_ENHANCED_PROXY_ARP_COUNT
        // Type is an MO-Defined-Type
        leaf pktRcvdEnhancedProxyArp {
            config "false";
            description "Arp Pkt Recv Enhanced Proxy Arp Count";

            // Type is an MO-Defined-Type
            type nw_Counter32;
        }

        // ARP_PKT_RECV_ENHANCED_PROXY_ANYCAST_ARP_COUNT
        // Type is an MO-Defined-Type
        leaf pktRcvdEnhancedProxyAnycastArp {
            config "false";
            description "Arp Pkt Recv Enhanced Proxy Anycast Arp Count";

            // Type is an MO-Defined-Type
            type nw_Counter32;
        }

        // ARP_PKT_RECV_ENHANCED_PROXY_L2PORT_TRACK_ARP_COUNT
        // Type is an MO-Defined-Type
        leaf pktRcvdEnhancedProxyL2portTrackArp {
            config "false";
            description "Arp Pkt Recv Enhanced Proxy L2 port track Arp Count";

            // Type is an MO-Defined-Type
            type nw_Counter32;
        }

        // ARP_PKT_RECV_SRVRPORT_COUNT
        // Type is an MO-Defined-Type
        leaf pktRcvdServerPort {
            config "false";
            description "Arp Pkt Recv Server port Count";

            // Type is an MO-Defined-Type
            type nw_Counter32;
        }

        // ARP_PKT_RECV_REQ_COUNT_L2
        // Type is an MO-Defined-Type
        leaf pktRcvdReqL2 {
            config "false";
            description "Arp Pkt Recv Req Count L2";

            // Type is an MO-Defined-Type
            type nw_Counter32;
        }

        // ARP_PKT_RECV_REPLY_COUNT_L2
        // Type is an MO-Defined-Type
        leaf pktRcvdRspL2 {
            config "false";
            description "Arp Pkt Recv Reply Count L2";

            // Type is an MO-Defined-Type
            type nw_Counter32;
        }

        // ARP_PKT_RECV_TUNNEL_COUNT
        // Type is an MO-Defined-Type
        leaf pktRcvdTunnel {
            config "false";
            description "Arp Pkt Recv Tunnel Count";

            // Type is an MO-Defined-Type
            type nw_Counter32;
        }

        // ARP_PKT_RECV_FASTPATH_COUNT
        // Type is an MO-Defined-Type
        leaf pktRcvdFastpath {
            config "false";
            description "Arp Pkt Recv Fastpath Count";

            // Type is an MO-Defined-Type
            type nw_Counter32;
        }

        // ARP_PKT_RECV_SNOOP_COUNT
        // Type is an MO-Defined-Type
        leaf pktRcvdSnoop {
            config "false";
            description "Arp Pkt Recv Snoop Count";

            // Type is an MO-Defined-Type
            type nw_Counter32;
        }

        // ARP_PKT_RECV_DROP_COUNT
        // Type is an MO-Defined-Type
        leaf pktRcvdDrp {
            config "false";
            description "Arp Pkt Recv Drop Count";

            // Type is an MO-Defined-Type
            type nw_Counter32;
        }

        // ARP_PKT_RECV_MBUF_OP_COUNT
        // Type is an MO-Defined-Type
        leaf pktRcvdMbufOp {
            config "false";
            description "Arp Pkt Recv Mbuf Op Count";

            // Type is an MO-Defined-Type
            type nw_Counter32;
        }

        // ARP_PKT_RECV_DROP_BAD_IF_COUNT
        // Type is an MO-Defined-Type
        leaf pktRcvdDrpBadIf {
            config "false";
            description "Arp Pkt Recv Drop Bad if Count";

            // Type is an MO-Defined-Type
            type nw_Counter32;
        }

        // ARP_PKT_RECV_DROP_BAD_LEN_COUNT
        // Type is an MO-Defined-Type
        leaf pktRcvdDrpBadLen {
            config "false";
            description "Arp Pkt Recv Drop Bad Len Count";

            // Type is an MO-Defined-Type
            type nw_Counter32;
        }

        // ARP_PKT_RECV_DROP_BAD_PROTO_COUNT
        // Type is an MO-Defined-Type
        leaf pktRcvdDrpBadProto {
            config "false";
            description "Arp Pkt Recv Drop Bad Proto Count";

            // Type is an MO-Defined-Type
            type nw_Counter32;
        }

        // ARP_PKT_RECV_DROP_BAD_HRD_TYPE
        // Type is an MO-Defined-Type
        leaf pktRcvdDropBadHrd {
            config "false";
            description "Arp Pkt Recv Drop Bad Hardware Type Count";

            // Type is an MO-Defined-Type
            type nw_Counter32;
        }

        // ARP_PKT_RECV_DROP_BAD_L2ADDR_LEN_COUNT
        // Type is an MO-Defined-Type
        leaf pktRcvdDrpBadL2AddrLen {
            config "false";
            description "Arp Pkt Recv Drop Bad L2Addr Len Count";

            // Type is an MO-Defined-Type
            type nw_Counter32;
        }

        // ARP_PKT_RECV_DROP_BAD_L3ADDR_LEN_COUNT
        // Type is an MO-Defined-Type
        leaf pktRcvdDrpBadL3AddrLen {
            config "false";
            description "Arp Pkt Recv Drop Bad L3Addr Len Count";

            // Type is an MO-Defined-Type
            type nw_Counter32;
        }

        // ARP_PKT_RECV_DROP_INVAL_SRC_IP_COUNT
        // Type is an MO-Defined-Type
        leaf pktRcvdDrpInvalSrcIp {
            config "false";
            description "Arp Pkt Recv Drop Inval Src Ip Count";

            // Type is an MO-Defined-Type
            type nw_Counter32;
        }

        // ARP_PKT_RECV_DROP_DIR_BCAST_COUNT
        // Type is an MO-Defined-Type
        leaf pktRcvdDrpDirBcast {
            config "false";
            description "Arp Pkt Recv Drop Dir Bcast Count";

            // Type is an MO-Defined-Type
            type nw_Counter32;
        }

        // ARP_PKT_RECV_DROP_INVAL_DST_IP_COUNT
        // Type is an MO-Defined-Type
        leaf pktRcvdDrpInvalDstIp {
            config "false";
            description "Arp Pkt Recv Drop Inval Dst Ip Count";

            // Type is an MO-Defined-Type
            type nw_Counter32;
        }

        // ARP_PKT_RECV_DROP_BAD_SRC_MAC_COUNT
        // Type is an MO-Defined-Type
        leaf pktRcvdDrpBadSrcMac {
            config "false";
            description "Arp Pkt Recv Drop Bad Src Mac Count";

            // Type is an MO-Defined-Type
            type nw_Counter32;
        }

        // ARP_PKT_RECV_DROP_OWN_SRC_MAC_COUNT
        // Type is an MO-Defined-Type
        leaf pktRcvdDrpOwnSrcMac {
            config "false";
            description "Arp Pkt Recv Drop own Src Mac Count";

            // Type is an MO-Defined-Type
            type nw_Counter32;
        }

        // ARP_PKT_RECV_DROP_OWN_SRC_IP_COUNT
        // Type is an MO-Defined-Type
        leaf pktRcvdDrpOwnSrcIp {
            config "false";
            description "Arp Pkt Recv Drop own Src Ip Count";

            // Type is an MO-Defined-Type
            type nw_Counter32;
        }

        // ARP_PKT_RECV_DROP_ARP_IF_NO_MEM_COUNT
        // Type is an MO-Defined-Type
        leaf pktRcvdDrpArpIfNoMem {
            config "false";
            description "Arp Pkt Recv Drop Arp if no Mem Count";

            // Type is an MO-Defined-Type
            type nw_Counter32;
        }

        // ARP_PKT_RECV_DROP_NOT_FOR_US_COUNT
        // Type is an MO-Defined-Type
        leaf pktRcvdDrpNotForUs {
            config "false";
            description "Arp Pkt Recv Drop not for us Count";

            // Type is an MO-Defined-Type
            type nw_Counter32;
        }

        // ARP_PKT_RECV_LEARN_AND_DROP_NOT_FOR_US_COUNT
        // Type is an MO-Defined-Type
        leaf pktRcvdLearnAndDropNotForUs {
            config "false";
            description "Arp Pkt Recv Learn and Drop not for us Count";

            // Type is an MO-Defined-Type
            type nw_Counter32;
        }

        // ARP_PKT_RECV_DROP_SUBNET_MISMATCH_COUNT
        // Type is an MO-Defined-Type
        leaf pktRcvdDrpSubnetMismatch {
            config "false";
            description "Arp Pkt Recv Drop Subnet Mismatch Count";

            // Type is an MO-Defined-Type
            type nw_Counter32;
        }

        // ARP_PKT_RECV_DROP_NOT_INITIALIZED_COUNT
        // Type is an MO-Defined-Type
        leaf pktRcvdDrpNotInit {
            config "false";
            description "Arp Pkt Recv Drop not Initialized Count";

            // Type is an MO-Defined-Type
            type nw_Counter32;
        }

        // ARP_PKT_RECV_DROP_BAD_CONTEXT_COUNT
        // Type is an MO-Defined-Type
        leaf pktRcvdDrpBadCtxt {
            config "false";
            description "Arp Pkt Recv Drop Bad Context Count";

            // Type is an MO-Defined-Type
            type nw_Counter32;
        }

        // ARP_PKT_RECV_DROP_CONTEXT_NOT_CREATED_COUNT
        // Type is an MO-Defined-Type
        leaf pktRcvdDrpCtxtNotCreated {
            config "false";
            description "Arp Pkt Recv Drop Context not Created Count";

            // Type is an MO-Defined-Type
            type nw_Counter32;
        }

        // ARP_PKT_RECV_DROP_L2_LOCAL_PROXY_ARP_COUNT
        // Type is an MO-Defined-Type
        leaf pktRcvdDrpL2LocalProxyArp {
            config "false";
            description "Arp Pkt Recv Drop L2 Local Proxy Arp Count";

            // Type is an MO-Defined-Type
            type nw_Counter32;
        }

        // ARP_PKT_RECV_DROP_L2_PURE_L2_PKT_COUNT
        // Type is an MO-Defined-Type
        leaf pktRcvdDrpL2PureL2Pkt {
            config "false";
            description "Arp Pkt Recv Drop L2 Pure L2 Pkt Count";

            // Type is an MO-Defined-Type
            type nw_Counter32;
        }

        // ARP_PKT_RECV_DROP_L2_PORT_UNTRUSTED_COUNT
        // Type is an MO-Defined-Type
        leaf pktRcvdDrpL2PrtUntrusted {
            config "false";
            description "Arp Pkt Recv Drop L2 Port Untrusted Count";

            // Type is an MO-Defined-Type
            type nw_Counter32;
        }

        // ARP_PKT_RECV_DROP_STANDBY_FHRP_VIP_COUNT
        // Type is an MO-Defined-Type
        leaf pktRcvdDrpStdbyFhrpVip {
            config "false";
            description "Arp Pkt Recv Drop Standby Fhrp Vip Count";

            // Type is an MO-Defined-Type
            type nw_Counter32;
        }

        // ARP_PKT_RECV_DROP_GRAT_ON_PROXY_ARP_COUNT
        // Type is an MO-Defined-Type
        leaf pktRcvdDrpGratOnProxyArp {
            config "false";
            description "Arp Pkt Recv Drop Grat on Proxy Arp Count";

            // Type is an MO-Defined-Type
            type nw_Counter32;
        }

        // ARP_PKT_RECV_DROP_ARP_REQUEST_IGNORE_COUNT
        // Type is an MO-Defined-Type
        leaf pktRcvdDrpArpRequestIgnore {
            config "false";
            description "Arp Pkt Recv Drop Arp Request Ignore Count";

            // Type is an MO-Defined-Type
            type nw_Counter32;
        }

        // ARP_PKT_RECV_DROP_L2FM_QUERY_FAIL_COUNT
        // Type is an MO-Defined-Type
        leaf pktRcvdDrpL2FmQueryFail {
            config "false";
            description "Arp Pkt Recv Drop L2Fm Query Fail Count";

            // Type is an MO-Defined-Type
            type nw_Counter32;
        }

        // ARP_PKT_RECV_DROP_TUNNEL_FAIL_COUNT
        // Type is an MO-Defined-Type
        leaf pktRcvdDrpTunnelFail {
            config "false";
            description "Arp Pkt Recv Drop Tunnel Fail Count";

            // Type is an MO-Defined-Type
            type nw_Counter32;
        }

        // ARP_PKT_RECV_DROP_RSP_ON_HSRP_STANDBY_HSRP_ACTIVE_VMAC
        // Type is an MO-Defined-Type
        leaf pktRcvdDrpRspOnHsrpStbyActiveVmac {
            config "false";
            description "Arp Pkt Recv Drop Rsp on Hsrp standby with hasrp active vmac Count";

            // Type is an MO-Defined-Type
            type nw_Counter32;
        }

        // ARP_PKT_RECV_FAIL_IM_DOWN_COUNT
        // Type is an MO-Defined-Type
        leaf pktRcvdFailImDown {
            config "false";
            description "Arp Pkt Recv Fail Im Down Count";

            // Type is an MO-Defined-Type
            type nw_Counter32;
        }
    }

    grouping arp_IfStatsAdj-group {

        // ARP_ADJ_ADD_COUNT
        // Type is an MO-Defined-Type
        leaf adjAdd {
            config "false";
            description "Arp Adj Add Count";

            // Type is an MO-Defined-Type
            type nw_Counter32;
        }

        // ARP_ADJ_DEL_COUNT
        // Type is an MO-Defined-Type
        leaf adjDel {
            config "false";
            description "Arp Adj Del Count";

            // Type is an MO-Defined-Type
            type nw_Counter32;
        }

        // ARP_ADJ_TIMEOUT_COUNT
        // Type is an MO-Defined-Type
        leaf adjTimeout {
            config "false";
            description "Arp Adj Timeout Count";

            // Type is an MO-Defined-Type
            type nw_Counter32;
        }
    }

    grouping arp_IfStatsMisc-group {

        // ARP_CLIENT_MSG_COUNT
        // Type is an MO-Defined-Type
        leaf clientMsg {
            config "false";
            description "Arp Client Msg Count";

            // Type is an MO-Defined-Type
            type nw_Counter32;
        }

        // ARP_CLIENT_MSG_FAIL_COUNT
        // Type is an MO-Defined-Type
        leaf clientMsgFail {
            config "false";
            description "Arp Client Msg Fail Count";

            // Type is an MO-Defined-Type
            type nw_Counter32;
        }

        // ARP_IF_TIMEOUT_MSG_FAIL_COUNT
        // Type is an MO-Defined-Type
        leaf ifTimeoutMsgFail {
            config "false";
            description "Arp if Timeout Msg Fail Count";

            // Type is an MO-Defined-Type
            type nw_Counter32;
        }

        // ARP_IF_STATUS_MSG_FAIL_COUNT
        // Type is an MO-Defined-Type
        leaf ifStatusMsgFail {
            config "false";
            description "Arp if Status Msg Fail Count";

            // Type is an MO-Defined-Type
            type nw_Counter32;
        }
    }

    grouping arp_IfStatsMH-group {

        // ARP_MH_PS_RECV_ADD_FROM_L2RIB
        // Type is an MO-Defined-Type
        leaf recvaddfrml2rib {
            config "false";
            description "Arp received PS add from l2rib";

            // Type is an MO-Defined-Type
            type nw_Counter32;
        }

        // ARP_MH_PS_PROCESS_ADD_FROM_L2RIB
        // Type is an MO-Defined-Type
        leaf processaddfrml2rib {
            config "false";
            description "Arp processed PS add from l2rib";

            // Type is an MO-Defined-Type
            type nw_Counter32;
        }

        // ARP_MH_PS_RECV_DEL_FROM_L2RIB
        // Type is an MO-Defined-Type
        leaf recvdelfrml2rib {
            config "false";
            description "Arp received PS del from l2rib";

            // Type is an MO-Defined-Type
            type nw_Counter32;
        }

        // ARP_MH_PS_PROCESS_DEL_FROM_L2RIB
        // Type is an MO-Defined-Type
        leaf processdelfrml2rib {
            config "false";
            description "Arp processed PS del from l2rib";

            // Type is an MO-Defined-Type
            type nw_Counter32;
        }

        // ARP_MH_PS_RECV_PC_SHUT_FROM_L2RIB
        // Type is an MO-Defined-Type
        leaf recvpcshutfrml2rib {
            config "false";
            description "Arp received PC Shut from l2rib";

            // Type is an MO-Defined-Type
            type nw_Counter32;
        }

        // ARP_MH_PS_PROCESS_PC_SHUT_FROM_L2RIB
        // Type is an MO-Defined-Type
        leaf processpcshutfrml2rib {
            config "false";
            description "Arp processed PC Shut from l2rib";

            // Type is an MO-Defined-Type
            type nw_Counter32;
        }

        // ARP_MH_PS_RECV_REMOTE_UPD_FROM_L2RIB
        // Type is an MO-Defined-Type
        leaf recvremoteupdfrml2rib {
            config "false";
            description "Arp received remote update from l2rib";

            // Type is an MO-Defined-Type
            type nw_Counter32;
        }

        // ARP_MH_PS_PROCESS_REMOTE_UPD_FROM_L2RIB
        // Type is an MO-Defined-Type
        leaf processremoteupdfrml2rib {
            config "false";
            description "Arp processed remote update from l2rib";

            // Type is an MO-Defined-Type
            type nw_Counter32;
        }

        // ARP_MH_PS_ADD_ERR_INVALID_FLAGS
        // Type is an MO-Defined-Type
        leaf psadderrinvalidflags {
            config "false";
            description "Arp MH add error invalid flag";

            // Type is an MO-Defined-Type
            type nw_Counter32;
        }

        // ARP_MH_PS_DEL_ERR_INVALID_FLAGS
        // Type is an MO-Defined-Type
        leaf psdelerrinvalidflags {
            config "false";
            description "Arp MH del error invalid flag";

            // Type is an MO-Defined-Type
            type nw_Counter32;
        }

        // ARP_MH_PS_ADD_ERR_INVALID_CURR_STATE
        // Type is an MO-Defined-Type
        leaf psadderrinvalidcurrstate {
            config "false";
            description "Arp MH add error current state";

            // Type is an MO-Defined-Type
            type nw_Counter32;
        }

        // ARP_MH_PS_DEL_ERR_INVALID_CURR_STATE
        // Type is an MO-Defined-Type
        leaf psdelerrinvalidcurrstate {
            config "false";
            description "Arp MH del error current state";

            // Type is an MO-Defined-Type
            type nw_Counter32;
        }

        // ARP_MH_PS_DEL_ERR_MAC_MISMATCH
        // Type is an MO-Defined-Type
        leaf psdelerrmacmismatch {
            config "false";
            description "Arp MH error PS del mac mismatch";

            // Type is an MO-Defined-Type
            type nw_Counter32;
        }

        // ARP_MH_PS_DEL_ERR_SEC_DEL_FROM_L2RIB
        // Type is an MO-Defined-Type
        leaf psdelerrsecdelfrml2rib {
            config "false";
            description "Arp MH error PS Sec del from l2rib";

            // Type is an MO-Defined-Type
            type nw_Counter32;
        }

        // ARP_MH_PS_DEL_ERR_FOR_TL_ROUTE
        // Type is an MO-Defined-Type
        leaf psdelerrfortlroute {
            config "false";
            description "Arp MH error PS del for TL route";

            // Type is an MO-Defined-Type
            type nw_Counter32;
        }

        // ARP_MH_TL_DEL_ERR_FOR_PSRO_ROUTE
        // Type is an MO-Defined-Type
        leaf tldelerrforpsroroute {
            config "false";
            description "Arp MH error TL del for PS RO route";

            // Type is an MO-Defined-Type
            type nw_Counter32;
        }
    }

    grouping arp_Ipv4Throttle-group {

        // Enable / Disable glean throttling
        // Type is an MO-Defined-Type
        leaf adminSt {
            description "Glean throttle state";

            // Type is an MO-Defined-Type
            type nw_AdminSt;
        }

        // Threshold for syslog for number of packets hitting the entry
        // Type is an MO-Defined-Type
        leaf syslog {
            description "Glean throttle syslog for number of packets";

            // Type is an MO-Defined-Type
            type arp_SyslogCnt;
        }

        // Max throttle packets count. Crossing this threshold,
        // packet will not be throttled for a particular adjacency
        // Type is an MO-Defined-Type
        leaf maxPacket {
            description "Glean throttle packet count";

            // Type is an MO-Defined-Type
            type arp_MaxPacket;
        }

        // Timeout for throttle setting for a particular adjacency
        // Type is an MO-Defined-Type
        leaf timeout {
            description "Ipv4 glean throttle timeout";

            // Type is an MO-Defined-Type
            type arp_ThrottleTimeout;
        }
    }

    grouping arp_EventLogs-group {

        // Event LogType
        // Type is an MO-Defined-Type
        leaf eventType {
            description "Sync Event Log Type";

            // Type is an MO-Defined-Type
            type arp_EventType;
        }

        // Event LogSize
        // Type is an MO-Defined-Type
        leaf logSize {
            description "Sync Event Log Size";

            // Type is an MO-Defined-Type
            type arp_EventLogSize;
        }
    }

    grouping arp_Vpc-group {

        // This objects hold per vpc domain information. There is only
        // one vpc domain that is configurable in the system
        container dom-items {

            // Added containment as a singleton: Prefix=dom
            // Acquired From Package arp
            uses arp_VpcDom-group;
        }
    }

    grouping arp_VpcDom-group {

        // Enable/Disable IP ARP SYNC
        // Type is an MO-Defined-Type
        leaf arpSync {
            description "IP ARP Sync";

            // Type is an MO-Defined-Type
            type nw_AdminSt;
        }
    }

    grouping arp_DbSupCache-group {

        // Type of the repository
        // Type is an MO-Defined-Type
        leaf type {
            description "Type";

            // Type is an MO-Defined-Type
            type arp_DbT;
        }

        // Inherited From nw:Conn
        // Modified by Override: nw:Db->name
        // Type is an MO-Defined-Type
        leaf name {
            description "Name";

            // Type is an MO-Defined-Type
            type naming_Name {
                length "1..64";
            }
        }

        // Holds Suppression-cache vlan related information
        container vlan-items {
            list SupCacheVlan-list {
                key "id";

                // Added containment: Prefix=vlan
                // Acquired From Package arp
                uses arp_SupCacheVlan-group;
            }
        }
    }

    grouping arp_SupCacheVlan-group {

        // vlan id
        // Type is an MO-Defined-Type
        leaf id {
            description "VLAN id";

            // Type is an MO-Defined-Type
            type stp_VlanId;
        }

        // Suppression ARP Mode
        // Type is an MO-Defined-Type
        leaf suppressArpMode {
            config "false";
            description "Suppression ARP mode";

            // Type is an MO-Defined-Type
            type arp_SuppressArpMode;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Holds suppression-cache entry information
        container ip-items {
            list SupCacheEntry-list {
                key "ip";

                // Added containment: Prefix=ip
                // Acquired From Package arp
                uses arp_SupCacheEntry-group;
            }
        }
    }

    grouping arp_SupCacheEntry-group {
        leaf ip {
            type address_Ip;
        }

        // IRP Entry flags
        // Type is an MO-Defined-Type
        leaf flags {
            config "false";
            description "Address";

            // Type is an MO-Defined-Type
            type arp_SupCacheFlag;
        }
        leaf mac {
            config "false";
            type address_Mac;
        }
        leaf upTS {
            config "false";
            type uint64;
        }

        // Physical Interface ID
        // Type is an MO-Defined-Type
        leaf phyid {
            config "false";
            description "Physical Interface ID";

            // Type is an MO-Defined-Type
            type nw_IfId;
        }
        leaf remotevtepaddr {
            config "false";
            type string;
        }
    }

    grouping bfd_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per bfd instance information.
        container inst-items {

            // Added containment as a singleton: Prefix=inst
            // Acquired From Package bfd
            uses bfd_Inst-group;
        }
    }

    grouping bfd_Inst-group {

        // Loopback interface to be used for bfd echo frames
        // Type is an MO-Defined-Type
        leaf echoIf {
            description "Echo Interface";

            // Type is an MO-Defined-Type
            type nw_IfId;
        }

        // Startup timer interval.
        // Type is an MO-Defined-Type
        leaf startupIntvl {
            description "Startup Interval";

            // Type is an MO-Defined-Type
            type bfd_StartupIntvl;
        }

        // Slow mode timer interval. This is the interval at which
        // BFD control packets are sent.
        // Type is an MO-Defined-Type
        leaf slowIntvl {
            description "Slow Interval";

            // Type is an MO-Defined-Type
            type bfd_SlowIntvl;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds bfd interface information
        container if-items {
            list If-list {
                key "id";

                // Added containment: Prefix=if
                // Acquired From Package bfd
                uses bfd_If-group;
            }
        }

        container aux-items {

            // Added containment as a singleton: Prefix=aux
            // Acquired From Package bfd
            uses bfd_InstHaCtx-group;
        }

        // This objects hold per address family bfd instance information
        container af-items {
            list InstAf-list {
                key "type";

                // Added containment: Prefix=af
                // Acquired From Package bfd
                uses bfd_InstAf-group;
            }
        }

        // This object holds keepalive policy information
        container ka-items {

            // Added containment as a singleton: Prefix=ka
            // Acquired From Package bfd
            uses bfd_KaP-group;
        }

        // This object holds bfd session information
        container session-items {
            list Sess-list {
                config "false";
                key "discr";

                // Added containment: Prefix=session
                // Acquired From Package bfd
                uses bfd_Sess-group;
            }
        }
    }

    grouping bfd_If-group {

        // Enable/disable echo mode for interface
        // Type is an MO-Defined-Type
        leaf echoAdminSt {
            description "Echo Mode Admin State";

            // Type is an MO-Defined-Type
            type nw_AdminSt;
        }

        // Interface controls
        // Type is an MO-Defined-Type
        leaf ctrl {
            description "Controls";

            // Type is an MO-Defined-Type
            type bfd_IfControl;
        }

        // BFD track-member-link
        // Type is an MO-Defined-Type
        leaf trkMbrLnk {
            description "Track Member Link Enable Disable";

            // Type is an MO-Defined-Type
            type bfd_TrkMbrLnk;
        }

        // BFD Start Time
        // Type is an MO-Defined-Type
        leaf stTm {
            description "Start timeout";

            // Type is an MO-Defined-Type
            type bfd_StTm;
        }
        leaf dst {
            type address_Ipv4;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds authentication policy information
        container auth-items {

            // Added containment as a singleton: Prefix=auth
            // Acquired From Package bfd
            uses bfd_AuthP-group;
        }

        // This object holds per address family bfd interface information
        container af-items {
            list IfAf-list {
                key "type";

                // Added containment: Prefix=af
                // Acquired From Package bfd
                uses bfd_IfAf-group;
            }
        }

        // Neighbor MacEntry
        container nbr-items {
            list Nbr-list {
                key "srcip destip";

                // Added containment: Prefix=nbr
                // Acquired From Package bfd
                uses bfd_Nbr-group;
            }
        }

        // This object holds keepalive policy information
        container ka-items {

            // Added containment as a singleton: Prefix=ka
            // Acquired From Package bfd
            uses bfd_KaP-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping bfd_AuthP-group {

        // Authentication type
        // Type is an MO-Defined-Type
        leaf type {
            description "Authentication Type";

            // Type is an MO-Defined-Type
            type bfd_AuthT;
        }

        // Authentication key id
        // Type is an MO-Defined-Type
        leaf keyId {
            description "Authentication Key ID";

            // Type is an MO-Defined-Type
            type bfd_AuthKeyId;
        }

        // Authentication Hex key Size
        // Type is an MO-Defined-Type
        leaf hexKeySize {
            description "Authentication Hex Key Size";

            // Type is an MO-Defined-Type
            type bfd_AuthHexKeySize;
        }

        // Authentication hex key
        // Type is an MO-Defined-Type
        leaf hexKey {
            description "Authentication Hex Key";

            // Type is an MO-Defined-Type
            type bfd_AuthHexKey;
        }

        // Authentication key
        // Type is an MO-Defined-Type
        leaf key {
            description "Authentication Key";

            // Type is an MO-Defined-Type
            type bfd_AuthKey;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping bfd_IfAf-group {

        // Enable/disable sessions for interface address family
        // Type is an MO-Defined-Type
        leaf adminSt {
            description "Admin State";

            // Type is an MO-Defined-Type
            type nw_AdminSt;
        }

        // Enable/disable echo mode for interface address family
        // Type is an MO-Defined-Type
        leaf echoAdminSt {
            description "Echo Mode Admin State";

            // Type is an MO-Defined-Type
            type nw_AdminSt;
        }

        // Interface controls
        // Type is an MO-Defined-Type
        leaf ctrl {
            description "Controls";

            // Type is an MO-Defined-Type
            type bfd_IfControl;
        }

        // Inherited From nw:Conn
        // Modified by Override: nw:CpDom->name
        // Type is an MO-Defined-Type
        leaf name {
            description "Name";

            // Type is an MO-Defined-Type
            type naming_Name {
                length "1..64";
            }
        }

        // Type
        // Inherited From bfd:Af
        // Type is an MO-Defined-Type
        leaf type {
            description "Type";

            // Type is an MO-Defined-Type
            type bfd_AfT;
        }

        // This object holds authentication policy information
        container auth-items {

            // Added containment as a singleton: Prefix=auth
            // Acquired From Package bfd
            uses bfd_AuthP-group;
        }

        // This object holds keepalive policy information
        container ka-items {

            // Added containment as a singleton: Prefix=ka
            // Acquired From Package bfd
            uses bfd_KaP-group;
        }
    }

    grouping bfd_KaP-group {

        // Desired minimum tx interval. This is the minimum interval,
        // in ms, that the system would like to use when transmitting
        // BFD control packets.
        // Type is an MO-Defined-Type
        leaf minTxIntvl {
            description "Desired Minimum TX Interval";

            // Type is an MO-Defined-Type
            type bfd_MinTxIntvl;
        }

        // Required minimum rx interval. This is the minimum interval,
        // in ms, between received BFD control packets that this
        // system is capable of supporting.
        // Type is an MO-Defined-Type
        leaf minRxIntvl {
            description "Required Minimum RX Interval";

            // Type is an MO-Defined-Type
            type bfd_MinRxIntvl;
        }

        // Detection multiplier. This is the desired detection time
        // multiplier for BFD packets on the local system.
        // Type is an MO-Defined-Type
        leaf detectMult {
            description "Detection Multiplier";

            // Type is an MO-Defined-Type
            type bfd_DetectMult;
        }

        // Echo rx interval. This is the minimum interval, in ms,
        // between received BFD echo packets that this system is
        // capable of supporting.
        // Type is an MO-Defined-Type
        leaf echoRxIntvl {
            description "Echo Rx Interval";

            // Type is an MO-Defined-Type
            type bfd_EchoRxIntvl;
        }
    }

    grouping bfd_Nbr-group {
        leaf srcip {
            type address_Ip;
        }
        leaf destip {
            type address_Ip;
        }
    }

    grouping bfd_InstHaCtx-group {

        // Current session index
        // Type is an MO-Defined-Type
        leaf sessId {
            config "false";
            description "Current session index";

            // Type is an MO-Defined-Type
            type bfd_CurSessIndex;
        }

        // Instance flags
        // Type is an MO-Defined-Type
        leaf flags {
            config "false";
            description "Instance Flags";

            // Type is an MO-Defined-Type
            type bfd_InstFlags;
        }

        // From Interface naming:Named
        // Inherited From naming:NamedObject
        // Type is an MO-Defined-Type
        leaf name {
            description "Name";

            // Type is an MO-Defined-Type
            type naming_Name;
        }
    }

    grouping bfd_InstAf-group {

        // Slow mode timer interval. This is the interval at which
        // BFD control packets are sent.
        // Type is an MO-Defined-Type
        leaf slowIntvl {
            description "Slow Interval";

            // Type is an MO-Defined-Type
            type bfd_SlowIntvl;
        }

        // Inherited From nw:Conn
        // Modified by Override: nw:CpDom->name
        // Type is an MO-Defined-Type
        leaf name {
            description "Name";

            // Type is an MO-Defined-Type
            type naming_Name {
                length "1..64";
            }
        }

        // Type
        // Inherited From bfd:Af
        // Type is an MO-Defined-Type
        leaf type {
            description "Type";

            // Type is an MO-Defined-Type
            type bfd_AfT;
        }

        // This object holds keepalive policy information
        container ka-items {

            // Added containment as a singleton: Prefix=ka
            // Acquired From Package bfd
            uses bfd_KaP-group;
        }
    }

    grouping bfd_Sess-group {

        // Local session identifier
        // Type is an MO-Defined-Type
        leaf discr {
            config "false";
            description "Local Session Identifier";

            // Type is an MO-Defined-Type
            type bfd_Discr;
        }

        // Remote session identifier
        // Type is an MO-Defined-Type
        leaf remoteDiscr {
            config "false";
            description "Remote Session Identifier";

            // Type is an MO-Defined-Type
            type bfd_Discr;
        }

        // Async mode source port
        // Type is an MO-Defined-Type
        leaf asyncPort {
            config "false";
            description "Async Source Port";

            // Type is an MO-Defined-Type
            type l4_Port;
        }

        // Echo mode source port
        // Type is an MO-Defined-Type
        leaf echoPort {
            config "false";
            description "Echo Source Port";

            // Type is an MO-Defined-Type
            type l4_Port;
        }
        leaf localMac {
            config "false";
            type address_Mac;
        }
        leaf remoteMac {
            config "false";
            type address_Mac;
        }

        // Interface id
        // Type is an MO-Defined-Type
        leaf ifId {
            config "false";
            description "Interface ID";

            // Type is an MO-Defined-Type
            type nw_IfId;
        }

        // Interface ordinal
        // Type is an MO-Defined-Type
        leaf iod {
            config "false";
            description "Interface ordinal";

            // Type is an MO-Defined-Type
            type nw_Iod;
        }

        // L3 context name
        // Type is an MO-Defined-Type
        leaf vrfName {
            config "false";
            description "L3 Context Name";

            // Type is an MO-Defined-Type
            type l3_VrfName;
        }
        leaf srcAddr {
            config "false";
            type address_Ip;
        }
        leaf destAddr {
            config "false";
            type address_Ip;
        }

        // Local value of tx interval
        // Type is an MO-Defined-Type
        leaf localTxIntvl {
            config "false";
            description "Local Value of Tx Interval";

            // Type is an MO-Defined-Type
            type bfd_MinTxIntvl;
        }

        // Local value of rx interval
        // Type is an MO-Defined-Type
        leaf localRxIntvl {
            config "false";
            description "Local Value of Rx Interval";

            // Type is an MO-Defined-Type
            type bfd_MinRxIntvl;
        }

        // Local value of detection multiplier
        // Type is an MO-Defined-Type
        leaf localDetectMult {
            config "false";
            description "Local value of Detection Multiplier";

            // Type is an MO-Defined-Type
            type bfd_DetectMult;
        }

        // Active value of tx interval
        // Type is an MO-Defined-Type
        leaf txIntvl {
            config "false";
            description "Active Value of Tx Interval";

            // Type is an MO-Defined-Type
            type bfd_MinTxIntvl;
        }

        // Active value of echo tx interval
        // Type is an MO-Defined-Type
        leaf echoTxIntvl {
            config "false";
            description "Active Value of Echo Tx Interval";

            // Type is an MO-Defined-Type
            type bfd_MinTxIntvl;
        }

        // Active value of rx interval
        // Type is an MO-Defined-Type
        leaf rxIntvl {
            config "false";
            description "Active Value of Rx Interval";

            // Type is an MO-Defined-Type
            type bfd_MinRxIntvl;
        }

        // Active value of slow interval
        // Type is an MO-Defined-Type
        leaf slowIntvl {
            config "false";
            description "Active value of Slow Interval";

            // Type is an MO-Defined-Type
            type bfd_SlowIntvl;
        }

        // Active value of detection multiplier
        // Type is an MO-Defined-Type
        leaf detectMult {
            config "false";
            description "Active value of Detection Multiplier";

            // Type is an MO-Defined-Type
            type bfd_DetectMult;
        }

        // Active value of auth type
        // Type is an MO-Defined-Type
        leaf authType {
            config "false";
            description "Active value of Auth Type";

            // Type is an MO-Defined-Type
            type bfd_AuthT;
        }

        // Authentication sequence number
        // Type is an MO-Defined-Type
        leaf authSeqno {
            config "false";
            description "Authentication Sequence Number";

            // Type is an MO-Defined-Type
            type bfd_AuthSeqno;
        }

        // Oper (protocol) state
        // Type is an MO-Defined-Type
        leaf operSt {
            config "false";
            description "Oper State";

            // Type is an MO-Defined-Type
            type bfd_OperSt;
        }

        // Remote oper state
        // Type is an MO-Defined-Type
        leaf remoteOperSt {
            config "false";
            description "Remote Oper State";

            // Type is an MO-Defined-Type
            type bfd_OperSt;
        }

        // Protocol diag code
        // Type is an MO-Defined-Type
        leaf diag {
            config "false";
            description "Protocol Diag";

            // Type is an MO-Defined-Type
            type bfd_DiagCode;
        }

        // Packet flags
        // Type is an MO-Defined-Type
        leaf flags {
            config "false";
            description "Packet Flags";

            // Type is an MO-Defined-Type
            type bfd_PktFlags;
        }
        leaf lastTransTime {
            config "false";
            type uint64;
        }

        // Last diag code
        // Type is an MO-Defined-Type
        leaf lastDiag {
            config "false";
            description "Last Diag";

            // Type is an MO-Defined-Type
            type bfd_DiagCode;
        }
        leaf lastDownTime {
            config "false";
            type uint64;
        }

        // This object holds bfd session stats information
        container stats-items {

            // Added containment as a singleton: Prefix=stats
            // Acquired From Package bfd
            uses bfd_SessStats-group;
        }

        // This object holds bfd last packet information. This signifies
        // peer view of the session.
        container peerv-items {

            // Added containment as a singleton: Prefix=peerv
            // Acquired From Package bfd
            uses bfd_PeerV-group;
        }

        // This object holds app information per bfd session
        container app-items {
            list SessApp-list {
                config "false";
                key "id";

                // Added containment: Prefix=app
                // Acquired From Package bfd
                uses bfd_SessApp-group;
            }
        }

        // Rel-def from mbrSess
        container rsmbrSess-items {

            // Abstract containment of rsmbrSess derived from bfd:Sess
            list RsMbrSess-list {
                config "false";
                key "tDn";

                // Added containment: Prefix=rsmbrSess
                // Acquired From Package bfd
                uses bfd_RsMbrSess_source-group;
            }
        }
    }

    grouping bfd_SessStats-group {

        // Packets received
        // Type is an MO-Defined-Type
        leaf rxCnt {
            config "false";
            description "Packets Received";

            // Type is an MO-Defined-Type
            type nw_Counter64;
        }

        // Average interval between received packets
        // Type is an MO-Defined-Type
        leaf rxAvg {
            config "false";
            description "Packets Average Receive Interval";

            // Type is an MO-Defined-Type
            type bfd_PktInterval;
        }

        // Minimum interval between received packets
        // Type is an MO-Defined-Type
        leaf rxMin {
            config "false";
            description "Packets Minimum Receive Interval";

            // Type is an MO-Defined-Type
            type bfd_PktInterval;
        }

        // Maximum interval between received packets
        // Type is an MO-Defined-Type
        leaf rxMax {
            config "false";
            description "Packets Maximum Receive Interval";

            // Type is an MO-Defined-Type
            type bfd_PktInterval;
        }
        leaf lastRxPkt {
            config "false";
            type uint64;
        }

        // Packets transmitted
        // Type is an MO-Defined-Type
        leaf txCnt {
            config "false";
            description "Packets Transmitted";

            // Type is an MO-Defined-Type
            type nw_Counter64;
        }

        // Average interval between transmitted packets
        // Type is an MO-Defined-Type
        leaf txAvg {
            config "false";
            description "Packets Average Transmit Interval";

            // Type is an MO-Defined-Type
            type bfd_PktInterval;
        }

        // Minimum interval between transmitted packets
        // Type is an MO-Defined-Type
        leaf txMin {
            config "false";
            description "Packets Minimum Transmit Interval";

            // Type is an MO-Defined-Type
            type bfd_PktInterval;
        }

        // Maximum interval between transmitted packets
        // Type is an MO-Defined-Type
        leaf txMax {
            config "false";
            description "Packets Maximum Transmit Interval";

            // Type is an MO-Defined-Type
            type bfd_PktInterval;
        }
        leaf lastTxPkt {
            config "false";
            type uint64;
        }

        // Number of times session has gone into up state
        // Type is an MO-Defined-Type
        leaf upCnt {
            config "false";
            description "Up Count";

            // Type is an MO-Defined-Type
            type nw_Counter32;
        }

        // Number of times session has gone into down state
        // Type is an MO-Defined-Type
        leaf downCnt {
            config "false";
            description "Down Count";

            // Type is an MO-Defined-Type
            type nw_Counter32;
        }
    }

    grouping bfd_PeerV-group {

        // Diag Code in last packet
        // Type is an MO-Defined-Type
        leaf diag {
            config "false";
            description "Diag Code in Last Packet";

            // Type is an MO-Defined-Type
            type bfd_DiagCode;
        }

        // Protocol state in last packet
        // Type is an MO-Defined-Type
        leaf operSt {
            config "false";
            description "Protocol State in Last Packet";

            // Type is an MO-Defined-Type
            type bfd_OperSt;
        }

        // Flags in last packet
        // Type is an MO-Defined-Type
        leaf flags {
            config "false";
            description "Flags in Last Packet";

            // Type is an MO-Defined-Type
            type bfd_PktFlags;
        }

        // Detect multiplier in last packet
        // Type is an MO-Defined-Type
        leaf detectMult {
            config "false";
            description "Detect Multiplier in Last Packet";

            // Type is an MO-Defined-Type
            type bfd_DetectMult;
        }

        // My discriminator in last packet
        // Type is an MO-Defined-Type
        leaf myDisc {
            config "false";
            description "My Discriminator in Last Packet";

            // Type is an MO-Defined-Type
            type bfd_Discr;
        }

        // Your discriminator in last packet
        // Type is an MO-Defined-Type
        leaf yourDisc {
            config "false";
            description "Your Discriminator in Last Packet";

            // Type is an MO-Defined-Type
            type bfd_Discr;
        }

        // Min tx interval in last packet
        // Type is an MO-Defined-Type
        leaf minTx {
            config "false";
            description "Min Tx Interval in Last Packet";

            // Type is an MO-Defined-Type
            type bfd_MinTxIntvl;
        }

        // Min rx interval in last packet
        // Type is an MO-Defined-Type
        leaf minRx {
            config "false";
            description "Min Rx Interval in Last Packet";

            // Type is an MO-Defined-Type
            type bfd_MinRxIntvl;
        }

        // Min echo interval in last packet
        // Type is an MO-Defined-Type
        leaf minEcho {
            config "false";
            description "Min Echo Interval in Last Packet";

            // Type is an MO-Defined-Type
            type bfd_MinRxIntvl;
        }
    }

    grouping bfd_SessApp-group {

        // Application ID
        // Type is an MO-Defined-Type
        leaf id {
            config "false";
            description "Application ID";

            // Type is an MO-Defined-Type
            type bfd_AppId;
        }
        leaf name {
            config "false";
            type string;
        }

        // Application sap ID
        // Type is an MO-Defined-Type
        leaf sapId {
            config "false";
            description "Application SAP ID";

            // Type is an MO-Defined-Type
            type bfd_SapId;
        }
        leaf descr {
            config "false";
            type string;
        }

        // Application session flags
        // Type is an MO-Defined-Type
        leaf flags {
            config "false";
            description "Application Session Flags";

            // Type is an MO-Defined-Type
            type bfd_AppFlags;
        }

        // Application private data
        // Type is an MO-Defined-Type
        leaf data {
            config "false";
            description "Application Private Data";

            // Type is an MO-Defined-Type
            type bfd_AppData;
        }
        leaf autoExpTime {
            config "false";
            type uint64;
        }
    }

    grouping eigrp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects holds per EIGRP instance information.
        container inst-items {
            list Inst-list {
                key "name";

                // Added containment: Prefix=inst
                // Acquired From Package eigrp
                uses eigrp_Inst-group;
            }
        }
    }

    grouping eigrp_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds per eigrp domain (vrf) information
        container dom-items {
            list Dom-list {
                key "name";

                // Added containment: Prefix=dom
                // Acquired From Package eigrp
                uses eigrp_Dom-group;
            }
        }
    }

    grouping eigrp_Dom-group {

        // Inherited From nw:Conn
        // Modified by Override: nw:CpDom->name
        // Type is an MO-Defined-Type
        leaf name {
            description "Name";

            // Type is an MO-Defined-Type
            type naming_Name {
                length "1..64";
            }
        }

        // This object holds per address family EIGRP information
        container af-items {
            list DomAf-list {
                config "false";
                key "type";

                // Added containment: Prefix=af
                // Acquired From Package eigrp
                uses eigrp_DomAf-group;
            }
        }

        // This object holds interface information
        container if-items {
            list If-list {
                key "id";

                // Added containment: Prefix=if
                // Acquired From Package eigrp
                uses eigrp_If-group;
            }
        }
    }

    grouping eigrp_DomAf-group {

        // Autonomous system number
        // Type is an MO-Defined-Type
        leaf asn {
            config "false";
            description "Autonomous System Number";

            // Type is an MO-Defined-Type
            type rtcom_AS;
        }

        // Router id for this domain, if this is not specified
        // the router-id is automatically picked up
        // Type is an MO-Defined-Type
        leaf rtrId {
            config "false";
            description "Router ID";

            // Type is an MO-Defined-Type
            type ip_RtrId;
        }

        // Administrative distance preference for Internal Routes
        // Type is an MO-Defined-Type
        leaf intDist {
            config "false";
            description "Internal Distance";

            // Type is an MO-Defined-Type
            type eigrp_Dist;
        }

        // Administrative distance preference for External Routes
        // Type is an MO-Defined-Type
        leaf extDist {
            config "false";
            description "External Distance";

            // Type is an MO-Defined-Type
            type eigrp_Dist;
        }

        // Maximum ECMP Paths
        // Type is an MO-Defined-Type
        leaf maxPaths {
            config "false";
            description "Maximum ECMP Paths";

            // Type is an MO-Defined-Type
            type eigrp_MaxPaths;
        }

        // Active interval
        // Type is an MO-Defined-Type
        leaf actIntvl {
            config "false";
            description "Active timer";

            // Type is an MO-Defined-Type
            type eigrp_ActIntvl;
        }

        // Inherited From nw:Conn
        // Modified by Override: nw:CpDom->name
        // Type is an MO-Defined-Type
        leaf name {
            description "Name";

            // Type is an MO-Defined-Type
            type naming_Name {
                length "1..64";
            }
        }

        // Type
        // Inherited From eigrp:Af
        // Type is an MO-Defined-Type
        leaf type {
            config "false";
            description "Type";

            // Type is an MO-Defined-Type
            type eigrp_AfT;
        }

        // EIGRP databases
        container db-items {
            list Db-list {
                config "false";
                key "type";

                // Added containment: Prefix=db
                // Acquired From Package eigrp
                uses eigrp_Db-group;
            }
        }

        // This object holds stub options
        container stub-items {

            // Added containment as a singleton: Prefix=stub
            // Acquired From Package eigrp
            uses eigrp_StubP-group;
        }

        // This object holds EIGRP Dom AF statistics
        // operational information.
        container stats-items {

            // Added containment as a singleton: Prefix=stats
            // Acquired From Package eigrp
            uses eigrp_DomAfStats-group;
        }

        // Inter protocol route leak policy. This defines distribution
        // of routes from one protocol to another protocol
        container interleak-items {
            list InterLeakP-list {
                key "proto inst";

                // Added containment: Prefix=interleak
                // Acquired From Package eigrp
                uses eigrp_InterLeakP-group;
            }
        }
    }

    grouping eigrp_Db-group {

        // Type of the repository
        // Type is an MO-Defined-Type
        leaf type {
            config "false";
            description "Type";

            // Type is an MO-Defined-Type
            type eigrp_DbT;
        }

        // Inherited From nw:Conn
        // Modified by Override: nw:Db->name
        // Type is an MO-Defined-Type
        leaf name {
            description "Name";

            // Type is an MO-Defined-Type
            type naming_Name {
                length "1..64";
            }
        }

        // This object holds eigrp route information
        container rt-items {
            list Route-list {
                config "false";
                key "pfx";

                // Added containment: Prefix=rt
                // Acquired From Package eigrp
                uses eigrp_Route-group;
            }
        }
    }

    grouping eigrp_Route-group {
        leaf pfx {
            config "false";
            type address_Ip;
        }

        // State of the route
        // Type is an MO-Defined-Type
        leaf operSt {
            config "false";
            description "Operational State";

            // Type is an MO-Defined-Type
            type eigrp_RtOperSt;
        }

        // Feasible Distance
        // Type is an MO-Defined-Type
        leaf fDist {
            config "false";
            description "Feasible Distance";

            // Type is an MO-Defined-Type
            type eigrp_FDist;
        }

        // Active State Qualifier
        // Type is an MO-Defined-Type
        leaf actStQual {
            config "false";
            description "Query Origin Qualifier";

            // Type is an MO-Defined-Type
            type nw_OSSumQual;
        }

        // Route change Qualifier
        // Type is an MO-Defined-Type
        leaf chgQual {
            config "false";
            description "Last route state transition Qualifier";

            // Type is an MO-Defined-Type
            type nw_OSSumQual;
        }
        leaf lastActTs {
            config "false";
            type uint64;
        }

        // Number of Stuck-in-active queries sent for the active route
        // Type is an MO-Defined-Type
        leaf siaQueryCnt {
            config "false";
            description "Number of Stuck-in-active queries sent for the active route";

            // Type is an MO-Defined-Type
            type nw_Counter32;
        }

        // Route Flags
        // Type is an MO-Defined-Type
        leaf flags {
            config "false";
            description "Route Flags";

            // Type is an MO-Defined-Type
            type eigrp_RtFlags;
        }

        // Inherited From nw:Conn
        // Modified by Override: nw:DbRec->name
        // Type is an MO-Defined-Type
        leaf name {
            description "Name";

            // Type is an MO-Defined-Type
            type naming_Name {
                length "1..64";
            }
        }

        // This object holds the eigrp nexthop information
        container nh-items {
            list Nexthop-list {
                config "false";
                key "informer if";

                // Added containment: Prefix=nh
                // Acquired From Package eigrp
                uses eigrp_Nexthop-group;
            }
        }
    }

    grouping eigrp_Nexthop-group {
        leaf informer {
            config "false";
            type address_Ip;
        }

        // Interface
        // Type is an MO-Defined-Type
        leaf if {
            config "false";
            description "Interface";

            // Type is an MO-Defined-Type
            type nw_IfId;
        }
        leaf addr {
            config "false";
            type address_Ip;
        }

        // Origin of the route/nexthop
        // Type is an MO-Defined-Type
        leaf origin {
            config "false";
            description "Originator";

            // Type is an MO-Defined-Type
            type eigrp_NhOrigin;
        }

        // Feasible Distance
        // Type is an MO-Defined-Type
        leaf fDist {
            config "false";
            description "Feasible Distance";

            // Type is an MO-Defined-Type
            type eigrp_FDist;
        }

        // Reported Distance
        // Type is an MO-Defined-Type
        leaf repDist {
            config "false";
            description "Reported Distance";

            // Type is an MO-Defined-Type
            type eigrp_RepDist;
        }

        // Nexthop change qualifier
        // Type is an MO-Defined-Type
        leaf chgQual {
            config "false";
            description "Change Qualifier";

            // Type is an MO-Defined-Type
            type nw_OSSumQual;
        }

        // Minimum Bandwidth
        // Type is an MO-Defined-Type
        leaf minBw {
            config "false";
            description "Minimum Bandwidth";

            // Type is an MO-Defined-Type
            type eigrp_Bw;
        }

        // Total Delay
        // Type is an MO-Defined-Type
        leaf delay {
            config "false";
            description "Total Delay";

            // Type is an MO-Defined-Type
            type eigrp_Delay;
        }

        // Minimum MTU
        // Type is an MO-Defined-Type
        leaf minMTU {
            config "false";
            description "Minimum MTU";

            // Type is an MO-Defined-Type
            type eigrp_MTU;
        }

        // Hop Count
        // Type is an MO-Defined-Type
        leaf hops {
            config "false";
            description "Hop Count";

            // Type is an MO-Defined-Type
            type eigrp_Hops;
        }

        // Load as a fraction of 255
        // Type is an MO-Defined-Type
        leaf load {
            config "false";
            description "Load as a fraction of 255";

            // Type is an MO-Defined-Type
            type eigrp_Load;
        }

        // Reliability as a fraction of 255
        // Type is an MO-Defined-Type
        leaf reliability {
            config "false";
            description "Reliability as a fraction of 255";

            // Type is an MO-Defined-Type
            type eigrp_Reliability;
        }

        // Internal Tag
        // Type is an MO-Defined-Type
        leaf tag {
            config "false";
            description "Internal Tag";

            // Type is an MO-Defined-Type
            type eigrp_Tag;
        }

        // Nexthop Flags
        // Type is an MO-Defined-Type
        leaf flags {
            config "false";
            description "Nexthop Flags";

            // Type is an MO-Defined-Type
            type eigrp_NhFlags;
        }

        // URIB state information
        // Type is an MO-Defined-Type
        leaf uribSt {
            config "false";
            description "URIB state";

            // Type is an MO-Defined-Type
            type eigrp_UribSt;
        }

        // Inherited From nw:Conn
        // Modified by Override: nw:DbRec->name
        // Type is an MO-Defined-Type
        leaf name {
            description "Name";

            // Type is an MO-Defined-Type
            type naming_Name {
                length "1..64";
            }
        }

        // This object holds the eigrp nexthop extended community
        // information
        container extcomm-items {
            list ExtCommNhRec-list {
                config "false";
                key "comm";

                // Added containment: Prefix=extcomm
                // Acquired From Package eigrp
                uses eigrp_ExtCommNhRec-group;
            }
        }

        // This object holds the eigrp nexthop information related to
        // inter protocol leak policy
        container extrec-items {

            // Added containment as a singleton: Prefix=extrec
            // Acquired From Package eigrp
            uses eigrp_ExtProtNhRec-group;
        }
    }

    grouping eigrp_ExtCommNhRec-group {
        leaf comm {
            config "false";
            type mtx_array_community;
        }
    }

    grouping eigrp_ExtProtNhRec-group {

        // External protocol originator
        // Type is an MO-Defined-Type
        leaf origin {
            config "false";
            description "Originator";

            // Type is an MO-Defined-Type
            type eigrp_ExtProtNhOrigin;
        }

        // External Tag
        // Type is an MO-Defined-Type
        leaf tag {
            config "false";
            description "External Tag";

            // Type is an MO-Defined-Type
            type eigrp_Tag;
        }

        // External Autonomous system number
        // Type is an MO-Defined-Type
        leaf asn {
            config "false";
            description "External Autonomous System Number";

            // Type is an MO-Defined-Type
            type rtcom_AS;
        }

        // Originating Router id
        // Type is an MO-Defined-Type
        leaf origRtrId {
            config "false";
            description "Originating Router ID";

            // Type is an MO-Defined-Type
            type ip_RtrId;
        }

        // Metric for the external route
        // Type is an MO-Defined-Type
        leaf metric {
            config "false";
            description "External route metric";

            // Type is an MO-Defined-Type
            type eigrp_Metric;
        }

        // External protocol nexthop flags
        // Type is an MO-Defined-Type
        leaf flags {
            config "false";
            description "External protocol nexthop flags";

            // Type is an MO-Defined-Type
            type eigrp_ExtNhFlags;
        }

        // Inherited From nw:Conn
        // Modified by Override: nw:DbRec->name
        // Type is an MO-Defined-Type
        leaf name {
            description "Name";

            // Type is an MO-Defined-Type
            type naming_Name {
                length "1..64";
            }
        }
    }

    grouping eigrp_StubP-group {

        // Stub route advertisement controls
        // Type is an MO-Defined-Type
        leaf rtAdvCtrl {
            config "false";
            description "Route Advertisement Controls";

            // Type is an MO-Defined-Type
            type eigrp_StubRtAdvControl;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping eigrp_DomAfStats-group {

        // Number of Active Interfaces
        // Type is an MO-Defined-Type
        leaf numIntf {
            config "false";
            description "Number of Active Interfaces";

            // Type is an MO-Defined-Type
            type nw_Counter32;
        }

        // Number of Passive Interfaces
        // Type is an MO-Defined-Type
        leaf numPassiveIntf {
            config "false";
            description "Number of Passive Interfaces";

            // Type is an MO-Defined-Type
            type nw_Counter32;
        }

        // Number of Neighbors
        // Type is an MO-Defined-Type
        leaf numNbrs {
            config "false";
            description "Number of Neighbors";

            // Type is an MO-Defined-Type
            type nw_Counter32;
        }

        // Count of hellos sent
        // Type is an MO-Defined-Type
        leaf helloSent {
            config "false";
            description "Count of hellos sent";

            // Type is an MO-Defined-Type
            type nw_Counter32;
        }

        // Count of hellos received
        // Type is an MO-Defined-Type
        leaf helloRcvd {
            config "false";
            description "Count of hellos received";

            // Type is an MO-Defined-Type
            type nw_Counter32;
        }

        // Count of queries sent
        // Type is an MO-Defined-Type
        leaf qrySent {
            config "false";
            description "Count of queries sent";

            // Type is an MO-Defined-Type
            type nw_Counter32;
        }

        // Count of queries received
        // Type is an MO-Defined-Type
        leaf qryRcvd {
            config "false";
            description "Count of queries received";

            // Type is an MO-Defined-Type
            type nw_Counter32;
        }

        // Count of updates sent
        // Type is an MO-Defined-Type
        leaf updSent {
            config "false";
            description "Count of updates sent";

            // Type is an MO-Defined-Type
            type nw_Counter32;
        }

        // Count of updates received
        // Type is an MO-Defined-Type
        leaf updRcvd {
            config "false";
            description "Count of updates received";

            // Type is an MO-Defined-Type
            type nw_Counter32;
        }

        // Count of replies sent
        // Type is an MO-Defined-Type
        leaf repSent {
            config "false";
            description "Count of replies sent";

            // Type is an MO-Defined-Type
            type nw_Counter32;
        }

        // Count of replies received
        // Type is an MO-Defined-Type
        leaf repRcvd {
            config "false";
            description "Count of replies received";

            // Type is an MO-Defined-Type
            type nw_Counter32;
        }

        // Count of acks sent
        // Type is an MO-Defined-Type
        leaf ackSent {
            config "false";
            description "Count of acks sent";

            // Type is an MO-Defined-Type
            type nw_Counter32;
        }

        // Count of acks received
        // Type is an MO-Defined-Type
        leaf ackRcvd {
            config "false";
            description "Count of acks received";

            // Type is an MO-Defined-Type
            type nw_Counter32;
        }

        // Count of SIA queries sent
        // Type is an MO-Defined-Type
        leaf siaQrySent {
            config "false";
            description "Count of SIA queries sent";

            // Type is an MO-Defined-Type
            type nw_Counter32;
        }

        // Count of SIA queries received
        // Type is an MO-Defined-Type
        leaf siaQryRcvd {
            config "false";
            description "Count of SIA queries received";

            // Type is an MO-Defined-Type
            type nw_Counter32;
        }

        // Count of SIA replies sent
        // Type is an MO-Defined-Type
        leaf siaRepSent {
            config "false";
            description "Count of SIA replies sent";

            // Type is an MO-Defined-Type
            type nw_Counter32;
        }

        // Count of SIA replies received
        // Type is an MO-Defined-Type
        leaf siaRepRcvd {
            config "false";
            description "Count of SIA replies received";

            // Type is an MO-Defined-Type
            type nw_Counter32;
        }
        leaf maxQDepth {
            config "false";
            type uint32;
        }

        // Count of input Queue drops
        // Type is an MO-Defined-Type
        leaf inQDrops {
            config "false";
            description "Count of input Queue drops";

            // Type is an MO-Defined-Type
            type nw_Counter32;
        }

        // Head Serial Number of the thread
        // Type is an MO-Defined-Type
        leaf headSer {
            config "false";
            description "Head Serial Number";

            // Type is an MO-Defined-Type
            type nw_Counter64;
        }

        // Next Serial Number on the thread
        // Type is an MO-Defined-Type
        leaf nextSer {
            config "false";
            description "Next Serial Number";

            // Type is an MO-Defined-Type
            type nw_Counter64;
        }

        // Count of Routes in the topology
        // Type is an MO-Defined-Type
        leaf rtCnt {
            config "false";
            description "Count of Routes";

            // Type is an MO-Defined-Type
            type nw_Counter32;
        }

        // Count of pending replies
        // Type is an MO-Defined-Type
        leaf pendReplies {
            config "false";
            description "Count of pending replies";

            // Type is an MO-Defined-Type
            type nw_Counter32;
        }

        // Count of dummies in the thread
        // Type is an MO-Defined-Type
        leaf xmitDummies {
            config "false";
            description "Count of dummies";

            // Type is an MO-Defined-Type
            type nw_Counter32;
        }
    }

    grouping eigrp_InterLeakP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Modified by Override: rtleak:InterLeakP->scope
        // Type is an MO-Defined-Type
        leaf scope {
            description "Scope";

            // Type is an MO-Defined-Type
            type rtleak_Scope;
        }
        leaf rtMap {
            type string;
        }

        // Protocol from where the routes are leaked
        // Inherited From rtleak:InterLeakP
        // Type is an MO-Defined-Type
        leaf proto {
            description "Protocol";

            // Type is an MO-Defined-Type
            type rtleak_Proto;
        }

        // Routing protocol instance, the routing instance of the
        // protocol from where the routes are being leaked
        // Inherited From rtleak:InterLeakP
        // Type is an MO-Defined-Type
        leaf inst {
            description "Instance";

            // Type is an MO-Defined-Type
            type rtleak_Inst;
        }

        // Leak BGP routes from this Autonomous System (AS)    <1-4294967295>|<1-65535>[.<0-65535>]  Autonomous system number
        // Inherited From rtleak:InterLeakP
        // Type is an MO-Defined-Type
        leaf asn {
            description "Autonomous System Number";

            // Type is an MO-Defined-Type
            type rtleak_Asn {
            }
        }
    }

    grouping eigrp_If-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds per address family interface information
        container af-items {
            list IfAf-list {
                config "false";
                key "type";

                // Added containment: Prefix=af
                // Acquired From Package eigrp
                uses eigrp_IfAf-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping eigrp_IfAf-group {

        // Controls
        // Type is an MO-Defined-Type
        leaf ctrl {
            config "false";
            description "Controls";

            // Type is an MO-Defined-Type
            type eigrp_IfAfControl;
        }

        // Hello interval, interval between hello packets that
        // EIGRP sends on the interface
        // Type is an MO-Defined-Type
        leaf helloIntvl {
            config "false";
            description "Hello Interval";

            // Type is an MO-Defined-Type
            type eigrp_HelloIntvl;
        }

        // Hold time, interval during which at least one
        // hello packet must be received from a neighbor before
        // the router declares that neighbor as down
        // Type is an MO-Defined-Type
        leaf holdIntvl {
            config "false";
            description "Hold Interval";

            // Type is an MO-Defined-Type
            type eigrp_HoldIntvl;
        }

        // Inherited From nw:Conn
        // Modified by Override: nw:CpDom->name
        // Type is an MO-Defined-Type
        leaf name {
            description "Name";

            // Type is an MO-Defined-Type
            type naming_Name {
                length "1..64";
            }
        }

        // Type
        // Inherited From eigrp:Af
        // Type is an MO-Defined-Type
        leaf type {
            config "false";
            description "Type";

            // Type is an MO-Defined-Type
            type eigrp_AfT;
        }

        // This object holds eigrp neighbor information
        container adj-items {
            list AdjEp-list {
                config "false";
                key "addr";

                // Added containment: Prefix=adj
                // Acquired From Package eigrp
                uses eigrp_AdjEp-group;
            }
        }

        // This object holds EIGRP interface statistics
        // operational information.
        container stats-items {

            // Added containment as a singleton: Prefix=stats
            // Acquired From Package eigrp
            uses eigrp_IfAfStats-group;
        }

        // This object holds summary address
        container summ-items {
            list Summ-list {
                key "addr";

                // Added containment: Prefix=summ
                // Acquired From Package eigrp
                uses eigrp_Summ-group;
            }
        }
    }

    grouping eigrp_AdjEp-group {
        leaf addr {
            config "false";
            type address_Ip;
        }

        // Neighbor ID
        // Type is an MO-Defined-Type
        leaf id {
            config "false";
            description "Neighbor ID";

            // Type is an MO-Defined-Type
            type eigrp_NbrId;
        }

        // Neighbor software major version
        // Type is an MO-Defined-Type
        leaf swMajVer {
            config "false";
            description "Neighbor Software Major Version";

            // Type is an MO-Defined-Type
            type eigrp_SwMajVer;
        }

        // Neighbor software minor version
        // Type is an MO-Defined-Type
        leaf swMinVer {
            config "false";
            description "Neighbor Software Minor Version";

            // Type is an MO-Defined-Type
            type eigrp_SwMinVer;
        }

        // Neighbor eigrp major version
        // Type is an MO-Defined-Type
        leaf eigrpMajVer {
            config "false";
            description "Neighbor Eigrp Major Version";

            // Type is an MO-Defined-Type
            type eigrp_EigrpMajVer;
        }

        // Neighbor eigrp minor version
        // Type is an MO-Defined-Type
        leaf eigrpMinVer {
            config "false";
            description "Neighbor Eigrp Minor Version";

            // Type is an MO-Defined-Type
            type eigrp_EigrpMinVer;
        }

        // Neighbor hold time
        // Type is an MO-Defined-Type
        leaf holdIntvl {
            config "false";
            description "Neighbor's Hold Interval";

            // Type is an MO-Defined-Type
            type eigrp_HoldIntvl;
        }

        // Neighbor state
        // Type is an MO-Defined-Type
        leaf operSt {
            config "false";
            description "Operational State";

            // Type is an MO-Defined-Type
            type eigrp_AdjOperSt;
        }

        // NSF state
        // Type is an MO-Defined-Type
        leaf nsfOperSt {
            config "false";
            description "NSF Operational State";

            // Type is an MO-Defined-Type
            type eigrp_NsfOperSt;
        }

        // Stub options
        // Type is an MO-Defined-Type
        leaf stubFlags {
            config "false";
            description "Stub options";

            // Type is an MO-Defined-Type
            type eigrp_AdjStubRtAdvFlags;
        }
        leaf lastUpTs {
            config "false";
            type uint64;
        }

        // Inherited From nw:Conn
        // Modified by Override: nw:Ep->name
        // Type is an MO-Defined-Type
        leaf name {
            description "Name";

            // Type is an MO-Defined-Type
            type naming_Name {
                length "1..64";
            }
        }

        // This object holds EIGRP neighbor statistics
        // operational information.
        container stats-items {

            // Added containment as a singleton: Prefix=stats
            // Acquired From Package eigrp
            uses eigrp_AdjStats-group;
        }
    }

    grouping eigrp_AdjStats-group {
        leaf srtt {
            config "false";
            type uint64;
        }
        leaf rto {
            config "false";
            type uint64;
        }

        // Count of number of packets in xmitQ
        // Type is an MO-Defined-Type
        leaf xmitQCnt {
            config "false";
            description "Count of packets in xmitQ";

            // Type is an MO-Defined-Type
            type nw_Counter32;
        }

        // Last Received Sequence number
        // Type is an MO-Defined-Type
        leaf lastSeqNo {
            config "false";
            description "Last received sequence number";

            // Type is an MO-Defined-Type
            type eigrp_SeqNo;
        }

        // Number of retransmissions
        // Type is an MO-Defined-Type
        leaf rexmitCnt {
            config "false";
            description "Number of retransmissions";

            // Type is an MO-Defined-Type
            type nw_Counter32;
        }

        // Number of retries for the current packet
        // Type is an MO-Defined-Type
        leaf retryCnt {
            config "false";
            description "Number of retries for the current packet";

            // Type is an MO-Defined-Type
            type nw_Counter32;
        }

        // Expected Sequence number when in Conditional Receive mode
        // Type is an MO-Defined-Type
        leaf condRcvSeqNo {
            config "false";
            description "Expected Sequence number in Conditional Receive mode";

            // Type is an MO-Defined-Type
            type eigrp_SeqNo;
        }

        // Unicast startup Target Serial Number
        // Type is an MO-Defined-Type
        leaf ucStupTgtSerNo {
            config "false";
            description "Unicast startup target serial number";

            // Type is an MO-Defined-Type
            type eigrp_SerNo;
        }

        // Number of prefixes learnt from the peer
        // Type is an MO-Defined-Type
        leaf pfxCount {
            config "false";
            description "Number of prefixes learnt from the peer";

            // Type is an MO-Defined-Type
            type nw_Counter32;
        }
    }

    grouping eigrp_IfAfStats-group {

        // xmitQ Reliable Count
        // Type is an MO-Defined-Type
        leaf xmitRelCnt {
            config "false";
            description "xmitQ Reliable Count";

            // Type is an MO-Defined-Type
            type nw_Counter32;
        }

        // xmitQ Unreliable Count
        // Type is an MO-Defined-Type
        leaf xmitUnrelCnt {
            config "false";
            description "xmitQ Unreliable Count";

            // Type is an MO-Defined-Type
            type nw_Counter32;
        }
        leaf relPktSendIntvl {
            config "false";
            type uint64;
        }
        leaf unRelPktSendIntvl {
            config "false";
            type uint64;
        }
        leaf mcFlowDelay {
            config "false";
            type uint32;
        }

        // Pending Routes
        // Type is an MO-Defined-Type
        leaf pendRt {
            config "false";
            description "Pending Routes";

            // Type is an MO-Defined-Type
            type nw_Counter32;
        }
        leaf xmitSerno {
            config "false";
            type uint64;
        }

        // Unreliable Multicast Packet Count
        // Type is an MO-Defined-Type
        leaf unrelMcCnt {
            config "false";
            description "Unreliable Multicast Packet Count";

            // Type is an MO-Defined-Type
            type nw_Counter32;
        }

        // Reliable Multicast Packet Count
        // Type is an MO-Defined-Type
        leaf relMcCnt {
            config "false";
            description "Reliable Multicast Packet Count";

            // Type is an MO-Defined-Type
            type nw_Counter32;
        }

        // Unreliable Unicast Packet Count
        // Type is an MO-Defined-Type
        leaf unrelUcCnt {
            config "false";
            description "Unreliable Unicast Packet Count";

            // Type is an MO-Defined-Type
            type nw_Counter32;
        }

        // Reliable Unicast Packet Count
        // Type is an MO-Defined-Type
        leaf relUcCnt {
            config "false";
            description "Reliable Unicast Packet Count";

            // Type is an MO-Defined-Type
            type nw_Counter32;
        }

        // Multicast Exception Packets Count
        // Type is an MO-Defined-Type
        leaf mcExcep {
            config "false";
            description "Multicast Exception Packets Count";

            // Type is an MO-Defined-Type
            type nw_Counter32;
        }

        // Count of packets sent with Condition Receive
        // Type is an MO-Defined-Type
        leaf crCnt {
            config "false";
            description "Count of packets sent with CR";

            // Type is an MO-Defined-Type
            type nw_Counter32;
        }

        // Count of Acks Suppressed
        // Type is an MO-Defined-Type
        leaf acksSupp {
            config "false";
            description "Count of Acks Suppressed";

            // Type is an MO-Defined-Type
            type nw_Counter32;
        }

        // Count of Retransmissions Sent
        // Type is an MO-Defined-Type
        leaf rexmitSent {
            config "false";
            description "Count of Retransmissions Sent";

            // Type is an MO-Defined-Type
            type nw_Counter32;
        }

        // Count of Out of Sequence Packets Received
        // Type is an MO-Defined-Type
        leaf outOfSeqRcvd {
            config "false";
            description "Count of Out of Seq Packets Received";

            // Type is an MO-Defined-Type
            type nw_Counter32;
        }
    }

    grouping eigrp_Summ-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf addr {
            type address_Ip;
        }
    }

    grouping hsrp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects holds HSRP instance information. There is     only one instance of HSRP supported currently
        container inst-items {

            // Added containment as a singleton: Prefix=inst
            // Acquired From Package hsrp
            uses hsrp_Inst-group;
        }
    }

    grouping hsrp_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds interface information
        container if-items {
            list If-list {
                key "id";

                // Added containment: Prefix=if
                // Acquired From Package hsrp
                uses hsrp_If-group;
            }
        }
    }

    grouping hsrp_If-group {

        // Hsrp version
        // Type is an MO-Defined-Type
        leaf version {
            description "Hsrp version";

            // Type is an MO-Defined-Type
            type hsrp_HsrpVersion;
        }

        // Interface controls
        // Type is an MO-Defined-Type
        leaf ctrl {
            description "Controls";

            // Type is an MO-Defined-Type
            type hsrp_IfControl;
        }

        // Use-Bia Scope
        // Type is an MO-Defined-Type
        leaf biaScope {
            description "Use-Bia Scope";

            // Type is an MO-Defined-Type
            type hsrp_BiaScopeType;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }
        container grp-items {
            list Group-list {
                key "id af";

                // Added containment: Prefix=grp
                // Acquired From Package hsrp
                uses hsrp_Group-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping hsrp_Group-group {

        // HSRP Group ID
        // Type is an MO-Defined-Type
        leaf id {
            description "Group Id";

            // Type is an MO-Defined-Type
            type hsrp_GroupId;
        }

        // HSRP Address Family
        // Type is an MO-Defined-Type
        leaf af {
            description "Group Address Family";

            // Type is an MO-Defined-Type
            type hsrp_GroupAf;
        }
        leaf ip {
            type address_Ip;
        }

        // HSRP primary IP Obtain Mode
        // Type is an MO-Defined-Type
        leaf ipObtainMode {
            description "IP Obtain Mode";

            // Type is an MO-Defined-Type
            type hsrp_GrpIpObtainMode;
        }

        // Control Bits
        // Type is an MO-Defined-Type
        leaf ctrl {
            description "Group control bits";

            // Type is an MO-Defined-Type
            type hsrp_GrpControl;
        }

        // Minimum Preemption delay before this group can preempt    a high priority Active
        // Type is an MO-Defined-Type
        leaf preemptDelayMin {
            description "Miminum delay before preempt";

            // Type is an MO-Defined-Type
            type hsrp_PreemptDelay;
        }

        // Preemption delay after a switch reboot before this group    can preempt a High priority Active
        // Type is an MO-Defined-Type
        leaf preemptDelayReload {
            description "Preempt delay after a switch reload";

            // Type is an MO-Defined-Type
            type hsrp_PreemptDelay;
        }

        // Maximum number of seconds to allow IP   redundancy clients to prevent preemption    @@@ Dont expose thi to user
        // Type is an MO-Defined-Type
        leaf preemptDelaySync {
            description "Wait for IP redundancy clients";

            // Type is an MO-Defined-Type
            type hsrp_PreemptDelay;
        }

        // HSRP Hello packet interval
        // Type is an MO-Defined-Type
        leaf helloIntvl {
            description "Hello Interval";

            // Type is an MO-Defined-Type
            type hsrp_HelloIntvl;
        }

        // HSRP Hold interval
        // Type is an MO-Defined-Type
        leaf holdIntvl {
            description "Hold Interval";

            // Type is an MO-Defined-Type
            type hsrp_HoldIntvl;
        }

        // Grouph Priority
        // Type is an MO-Defined-Type
        leaf prio {
            description "Group Priority";

            // Type is an MO-Defined-Type
            type hsrp_GrpPrio;
        }

        // forwarding lower threshold
        // Type is an MO-Defined-Type
        leaf fwdLwrThrld {
            description "Fowarding Lower Threshold";

            // Type is an MO-Defined-Type
            type hsrp_GrpPrio;
        }

        // forwarding upper threshold
        // Type is an MO-Defined-Type
        leaf fwdUprThrld {
            description "Forwarding Upper Threshold";

            // Type is an MO-Defined-Type
            type hsrp_GrpPrio;
        }
        leaf mac {
            type address_Mac;
        }

        // Class for HSRP secondary vips
        container addr-items {
            list Addr-list {
                key "ip";

                // Added containment: Prefix=addr
                // Acquired From Package hsrp
                uses hsrp_Addr-group;
            }
        }
    }

    grouping hsrp_Addr-group {
        leaf ip {
            type address_Ip;
        }
    }

    grouping icmpv4_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per icmpv4 instance information. There is
        // only one instance of icmpv4 running in the system today
        container inst-items {

            // Added containment as a singleton: Prefix=inst
            // Acquired From Package icmpv4
            uses icmpv4_Inst-group;
        }
    }

    grouping icmpv4_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This objects hold per icmpv4 layer3 domain (vrf)
        // information
        container dom-items {
            list Dom-list {
                key "name";

                // Added containment: Prefix=dom
                // Acquired From Package icmpv4
                uses icmpv4_Dom-group;
            }
        }
    }

    grouping icmpv4_Dom-group {

        // Inherited From nw:Conn
        // Modified by Override: nw:CpDom->name
        // Type is an MO-Defined-Type
        leaf name {
            description "Name";

            // Type is an MO-Defined-Type
            type naming_Name {
                length "1..64";
            }
        }

        // This object holds icmp information that is operated at a
        // interface level
        container if-items {
            list If-list {
                key "id";

                // Added containment: Prefix=if
                // Acquired From Package icmpv4
                uses icmpv4_If-group;
            }
        }
    }

    grouping icmpv4_If-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From icmp:If
        // Modified by Override: icmpv4:If->ctrl
        // Type is an MO-Defined-Type
        // Default value handled in local MO type
        leaf ctrl {
            description "Controls";

            // Type is a Local-MO-Defined-Type
            type icmp_IfControl_If_ctrl;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping icmpv6_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per icmpv6 instance information. There is
        // only one instance of icmpv6 running in the system today
        container inst-items {

            // Added containment as a singleton: Prefix=inst
            // Acquired From Package icmpv6
            uses icmpv6_Inst-group;
        }
    }

    grouping icmpv6_Inst-group {

        // Operational state
        // Type is an MO-Defined-Type
        leaf operSt {
            config "false";
            description "Operational State";

            // Type is an MO-Defined-Type
            type icmpv6_OperSt;
        }

        // Adjacency stale timer
        // Type is an MO-Defined-Type
        leaf adjStaleTimer {
            description "Adjacency stale timer";

            // Type is an MO-Defined-Type
            type icmpv6_AdjStaleTimer;
        }

        // Adjacency stale timer with icmp option
        // Type is an MO-Defined-Type
        leaf adjStaleTimerIcmp {
            description "Ipv6 adjacency stale timer with ICMP option";

            // Type is an MO-Defined-Type
            type nw_AdminSt;
        }

        // ICMPv6 Logging Level
        // Type is an MO-Defined-Type
        leaf loggingLevel {
            description "Logging Level";

            // Type is an MO-Defined-Type
            type icmpv6_LoggingLevel;
        }

        // Logging Level  for IPv6 or ICMPv6
        // Type is an MO-Defined-Type
        leaf defaultLoggingLevel {
            description "Logging option for IPv6 ICMP";

            // Type is an MO-Defined-Type
            type arp_LoggingLevel;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds icmpv6 information that is operated at a
        // interface level
        container if-items {
            list If-list {
                key "id";

                // Added containment: Prefix=if
                // Acquired From Package icmpv6
                uses icmpv6_If-group;
            }
        }
        container logs-items {
            list ICMPv6EventLogs-list {
                key "eventType";

                // Added containment: Prefix=logs
                // Acquired From Package icmpv6
                uses icmpv6_ICMPv6EventLogs-group;
            }
        }

        // Interface statistics    icmpv6 common packet counters (global and per-i/f)
        container ifstats-items {

            // Added containment as a singleton: Prefix=ifstats
            // Acquired From Package icmpv6
            uses icmpv6_IfStats-group;
        }
    }

    grouping icmpv6_If-group {

        // Interface controls
        // Type is an MO-Defined-Type
        leaf ctrl {
            description "Controls";

            // Type is an MO-Defined-Type
            type icmpv6_IfControl;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface statistics    icmpv6 common packet counters (global and per-i/f)
        container ifstats-items {

            // Added containment as a singleton: Prefix=ifstats
            // Acquired From Package icmpv6
            uses icmpv6_IfStats-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping icmpv6_IfStats-group {

        // Total Messages sent     @@@ ICMPV6_PKT_MSGS_SNT_CNT
        // From Interface icmpv6:globalTraffic
        // Type is an MO-Defined-Type
        leaf totSent {
            config "false";
            description "Total messages sent";

            // Type is an MO-Defined-Type
            type nw_Counter64;
        }

        // Total Messages received     @@@ ICMPV6_PKT_MSGS_RECV_CNT
        // From Interface icmpv6:globalTraffic
        // Type is an MO-Defined-Type
        leaf totRvcd {
            config "false";
            description "Total messages received";

            // Type is an MO-Defined-Type
            type nw_Counter64;
        }

        // Error Messages sent     @@@ ICMPV6_PKT_ERR_SNT_CNT
        // From Interface icmpv6:globalTraffic
        // Type is an MO-Defined-Type
        leaf errSent {
            config "false";
            description "Error messages sent";

            // Type is an MO-Defined-Type
            type nw_Counter64;
        }

        // Error Messages received     @@@ ICMPV6_PKT_ERR_RECV_CNT
        // From Interface icmpv6:globalTraffic
        // Type is an MO-Defined-Type
        leaf errRcvd {
            config "false";
            description "Error messages received";

            // Type is an MO-Defined-Type
            type nw_Counter64;
        }

        // Interface Down Drop Count sent     @@@ ICMPV6_PKT_SNT_DROP_IF_DOWN_CNT
        // From Interface icmpv6:globalTraffic
        // Type is an MO-Defined-Type
        leaf ifDownDropSent {
            config "false";
            description "Interface Down Drop Count sent";

            // Type is an MO-Defined-Type
            type nw_Counter64;
        }

        // Interface Down Drop Count received     @@@ ICMPV6_PKT_RECV_DROP_IF_DOWN_CNT
        // From Interface icmpv6:globalTraffic
        // Type is an MO-Defined-Type
        leaf ifDownDropRcvd {
            config "false";
            description "Interface Down Drop Count received";

            // Type is an MO-Defined-Type
            type nw_Counter64;
        }

        // Adjacency not recovered from AM after HA     @@@ ICMPV6_PKT_DROPPED_HA_NOT_READY
        // From Interface icmpv6:globalTraffic
        // Type is an MO-Defined-Type
        leaf dropHaNotRdy {
            config "false";
            description "Adjacency not recovered from AM after HA";

            // Type is an MO-Defined-Type
            type nw_Counter64;
        }

        // Pkts allowed due to inv ttl on vPC-MCT     @@@ ICMPV6_PKT_ALLOW_MCT_TTL_CNT
        // From Interface icmpv6:globalTraffic
        // Type is an MO-Defined-Type
        leaf dropInvldTtlMct {
            config "false";
            description "Pkts allowed due to inv ttl on vPC-MCT";

            // Type is an MO-Defined-Type
            type nw_Counter64;
        }

        // Pkts dropped as source mac addr is own     @@@ ICMPV6_PKT_RECV_DROP_OWN_SRC_MAC_COUNT
        // From Interface icmpv6:globalTraffic
        // Type is an MO-Defined-Type
        leaf dropSrcMacOwnRcvd {
            config "false";
            description "Pkts dropped as source mac addr is own";

            // Type is an MO-Defined-Type
            type nw_Counter64;
        }

        // Pkts dropped as tgt ip addr is not own     @@@ ICMPV6_PKT_RECV_DROP_TARGET_NOT_US_COUNT
        // From Interface icmpv6:globalTraffic
        // Type is an MO-Defined-Type
        leaf dropTgtIpNotOwnRcvd {
            config "false";
            description "Pkts dropped as tgt ip addr is not own";

            // Type is an MO-Defined-Type
            type nw_Counter64;
        }

        // Pkts dropped as src ip addr is not own     @@@ ICMPV6_PKT_RECV_DROP_SRC_NOT_US_COUNT
        // From Interface icmpv6:globalTraffic
        // Type is an MO-Defined-Type
        leaf dropSrcIpNotOwnRcvd {
            config "false";
            description "Pkts dropped as src ip addr is not own";

            // Type is an MO-Defined-Type
            type nw_Counter64;
        }

        // Destination Unreachables sent     @@@ ICMPV6_PKT_DEST_UNREACHS_SNT_CNT
        // From Interface icmpv6:globalTraffic
        // Type is an MO-Defined-Type
        leaf destUnreachSent {
            config "false";
            description "Destination Unreachables sent";

            // Type is an MO-Defined-Type
            type nw_Counter64;
        }

        // Destination Unreachables received    @@@ ICMPV6_PKT_DEST_UNREACHS_RECV_CNT
        // From Interface icmpv6:globalTraffic
        // Type is an MO-Defined-Type
        leaf destUnreachRcvd {
            config "false";
            description "Destination Unreachables received";

            // Type is an MO-Defined-Type
            type nw_Counter64;
        }

        // Administratively Prohibited sent    @@@ ICMPV6_PKT_ADMIN_PROHIBS_SNT_CNT
        // From Interface icmpv6:globalTraffic
        // Type is an MO-Defined-Type
        leaf adminProhibSent {
            config "false";
            description "Administratively Prohibited sent";

            // Type is an MO-Defined-Type
            type nw_Counter64;
        }

        // Administratively Prohibited received    @@@ ICMPV6_PKT_ADMIN_PROHIBS_RECV_CNT
        // From Interface icmpv6:globalTraffic
        // Type is an MO-Defined-Type
        leaf adminProhibRcvd {
            config "false";
            description "Administratively Prohibited received";

            // Type is an MO-Defined-Type
            type nw_Counter64;
        }

        // Time Exceeded sent    @@@ ICMPV6_PKT_TIME_EXCDS_SNT_CNT
        // From Interface icmpv6:globalTraffic
        // Type is an MO-Defined-Type
        leaf timeExcdSent {
            config "false";
            description "Time Exceeded sent ";

            // Type is an MO-Defined-Type
            type nw_Counter64;
        }

        // Time Exceeded received    @@@ ICMPV6_PKT_TIME_EXCDS_RECV_CNT
        // From Interface icmpv6:globalTraffic
        // Type is an MO-Defined-Type
        leaf timeExcdRcvd {
            config "false";
            description "Time Exceeded received";

            // Type is an MO-Defined-Type
            type nw_Counter64;
        }

        // Parameter Problems sent    @@@ ICMPV6_PKT_PARM_PROBS_SNT_CNT
        // From Interface icmpv6:globalTraffic
        // Type is an MO-Defined-Type
        leaf parmPrblmSent {
            config "false";
            description "Parameter Problems sent";

            // Type is an MO-Defined-Type
            type nw_Counter64;
        }

        // Parameter Problems received    @@@ ICMPV6_PKT_PARM_PROBS_RECV_CNT
        // From Interface icmpv6:globalTraffic
        // Type is an MO-Defined-Type
        leaf parmPrblmRcvd {
            config "false";
            description "Parameter Problems received";

            // Type is an MO-Defined-Type
            type nw_Counter64;
        }

        // Echo Request sent    @@@ ICMPV6_PKT_ECHOS_SNT_CNT
        // From Interface icmpv6:globalTraffic
        // Type is an MO-Defined-Type
        leaf echoReqSent {
            config "false";
            description "Echo Request sent";

            // Type is an MO-Defined-Type
            type nw_Counter64;
        }

        // Echo Request received    @@@ ICMPV6_PKT_ECHOS_RECV_CNT
        // From Interface icmpv6:globalTraffic
        // Type is an MO-Defined-Type
        leaf echoReqRcvd {
            config "false";
            description "Echo Request received";

            // Type is an MO-Defined-Type
            type nw_Counter64;
        }

        // Echo Replies sent    @@@ ICMPV6_PKT_ECHO_REPLIES_SNT_CNT
        // From Interface icmpv6:globalTraffic
        // Type is an MO-Defined-Type
        leaf echoRepSent {
            config "false";
            description "Echo Replies sent";

            // Type is an MO-Defined-Type
            type nw_Counter64;
        }

        // Echo Replies received    @@@ ICMPV6_PKT_ECHO_REPLIES_RECV_CNT
        // From Interface icmpv6:globalTraffic
        // Type is an MO-Defined-Type
        leaf echoRepRcvd {
            config "false";
            description "Echo Replies received";

            // Type is an MO-Defined-Type
            type nw_Counter64;
        }

        // Redirects sent    @@@ ICMPV6_PKT_REDIRECTS_SNT_CNT
        // From Interface icmpv6:globalTraffic
        // Type is an MO-Defined-Type
        leaf redirSent {
            config "false";
            description "Redirects sent";

            // Type is an MO-Defined-Type
            type nw_Counter64;
        }

        // Redirects received    @@@ ICMPV6_PKT_REDIRECTS_RECV_CNT
        // From Interface icmpv6:globalTraffic
        // Type is an MO-Defined-Type
        leaf redirRcvd {
            config "false";
            description "Redirects received";

            // Type is an MO-Defined-Type
            type nw_Counter64;
        }

        // Packet Too Big sent    @@@ ICMPV6_PKT_TOO_BIG_SNT_CNT
        // From Interface icmpv6:globalTraffic
        // Type is an MO-Defined-Type
        leaf tooBigSent {
            config "false";
            description "Packet Too Big sent";

            // Type is an MO-Defined-Type
            type nw_Counter64;
        }

        // Packet Too Big received    @@@ ICMPV6_PKT_TOO_BIG_RECV_CNT
        // From Interface icmpv6:globalTraffic
        // Type is an MO-Defined-Type
        leaf tooBigRcvd {
            config "false";
            description "Packet Too Big received";

            // Type is an MO-Defined-Type
            type nw_Counter64;
        }

        // Router Advertisements sent    @@@ ICMPV6_PKT_ROUTER_ADV_SNT_CNT
        // From Interface icmpv6:globalTraffic
        // Type is an MO-Defined-Type
        leaf raSent {
            config "false";
            description "Router Advertisements sent";

            // Type is an MO-Defined-Type
            type nw_Counter64;
        }

        // Router Advertisements received    @@@ ICMPV6_PKT_ROUTER_ADV_RECV_CNT
        // From Interface icmpv6:globalTraffic
        // Type is an MO-Defined-Type
        leaf raRcvd {
            config "false";
            description "Router Advertisements received";

            // Type is an MO-Defined-Type
            type nw_Counter64;
        }

        // Router Solicitations sent    @@@ ICMPV6_PKT_ROUTER_SOLICITS_SNT_CNT
        // From Interface icmpv6:globalTraffic
        // Type is an MO-Defined-Type
        leaf rsSent {
            config "false";
            description "Router Solicitations sent";

            // Type is an MO-Defined-Type
            type nw_Counter64;
        }

        // Router Solicitations received    @@@ ICMPV6_PKT_ROUTER_SOLICITS_RECV_CNT
        // From Interface icmpv6:globalTraffic
        // Type is an MO-Defined-Type
        leaf rsRcvd {
            config "false";
            description "Router Solicitations received";

            // Type is an MO-Defined-Type
            type nw_Counter64;
        }

        // Neighbor Advertisements sent    @@@ ICMPV6_PKT_NEIGHBOR_ADV_SNT_CNT
        // From Interface icmpv6:globalTraffic
        // Type is an MO-Defined-Type
        leaf naSent {
            config "false";
            description "Neighbor Advertisements sent";

            // Type is an MO-Defined-Type
            type nw_Counter64;
        }

        // Neighbor Advertisements received    @@@ ICMPV6_PKT_NEIGHBOR_ADV_RECV_CNT
        // From Interface icmpv6:globalTraffic
        // Type is an MO-Defined-Type
        leaf naRcvd {
            config "false";
            description "Neighbor Advertisements received";

            // Type is an MO-Defined-Type
            type nw_Counter64;
        }

        // Neighbor Solicitations sent    @@@ ICMPV6_PKT_NEIGHBOR_SOLICITS_SNT_CNT
        // From Interface icmpv6:globalTraffic
        // Type is an MO-Defined-Type
        leaf nsSent {
            config "false";
            description "Neighbor Solicitations sent";

            // Type is an MO-Defined-Type
            type nw_Counter64;
        }

        // Neighbor Solicitations received    @@@ ICMPV6_PKT_NEIGHBOR_SOLICITS_RECV_CNT
        // From Interface icmpv6:globalTraffic
        // Type is an MO-Defined-Type
        leaf nsRcvd {
            config "false";
            description "Neighbor Solicitations received";

            // Type is an MO-Defined-Type
            type nw_Counter64;
        }

        // Duplicate router RA received    @@@ ICMPV6_PKT_DUP_ROUTER
        // From Interface icmpv6:globalTraffic
        // Type is an MO-Defined-Type
        leaf dupRAReceived {
            config "false";
            description "Duplicate router RA received";

            // Type is an MO-Defined-Type
            type nw_Counter64;
        }

        // Fastpath Packets     @@@ ICMPV6_PKT_FASTPATH_RECV_CNT
        // From Interface icmpv6:globalTrafficFastPath
        // Type is an MO-Defined-Type
        leaf fastpthRcvd {
            config "false";
            description "Fastpath Packets";

            // Type is an MO-Defined-Type
            type nw_Counter64;
        }

        // Ignored Fastpath Packets - Fastpath disabled    @@@ ICMPV6_PKT_RECV_DROP_FASTPATH_DISABLED_CNT
        // From Interface icmpv6:globalTrafficFastPath
        // Type is an MO-Defined-Type
        leaf fastpathDsbleIgnRcvd {
            config "false";
            description "Ignored Fastpath Packets - Fastpath disabled";

            // Type is an MO-Defined-Type
            type nw_Counter64;
        }

        // Ignored Fastpath Packets - others    @@@ ICMPV6_PKT_RECV_DROP_REQUEST_IGNORE_CNT
        // From Interface icmpv6:globalTrafficFastPath
        // Type is an MO-Defined-Type
        leaf fastpathOtherIgnRcvd {
            config "false";
            description "Ignored fastpath packets - others";

            // Type is an MO-Defined-Type
            type nw_Counter64;
        }

        // @@@ ICMPV6_PKT_MLD_V1_QUERY_SNT_CNT
        // From Interface icmpv6:GlobalMLDStats
        // Type is an MO-Defined-Type
        leaf mldV1QueriesSent {
            config "false";
            description "V1 queries sent";

            // Type is an MO-Defined-Type
            type nw_Counter64;
        }

        // @@@ ICMPV6_PKT_MLD_V1_QUERY_RECV_CNT
        // From Interface icmpv6:GlobalMLDStats
        // Type is an MO-Defined-Type
        leaf mldV1QueriesRecv {
            config "false";
            description "V1 queries received";

            // Type is an MO-Defined-Type
            type nw_Counter64;
        }

        // @@@ ICMPV6_PKT_MLD_V2_QUERY_SNT_CNT
        // From Interface icmpv6:GlobalMLDStats
        // Type is an MO-Defined-Type
        leaf mldV2QueriesSent {
            config "false";
            description "V2 queries sent";

            // Type is an MO-Defined-Type
            type nw_Counter64;
        }

        // @@@ ICMPV6_PKT_MLD_V2_QUERY_RECV_CNT
        // From Interface icmpv6:GlobalMLDStats
        // Type is an MO-Defined-Type
        leaf mldV2QueriesRecv {
            config "false";
            description "V2 queries received";

            // Type is an MO-Defined-Type
            type nw_Counter64;
        }

        // @@@ ICMPV6_PKT_MLD_V1_REPORTS_SNT_CNT
        // From Interface icmpv6:GlobalMLDStats
        // Type is an MO-Defined-Type
        leaf mldV1ReportsSent {
            config "false";
            description "V1 reports sent";

            // Type is an MO-Defined-Type
            type nw_Counter64;
        }

        // @@@ ICMPV6_PKT_MLD_V1_REPORTS_RECV_CNT
        // From Interface icmpv6:GlobalMLDStats
        // Type is an MO-Defined-Type
        leaf mldV1ReportsRecv {
            config "false";
            description "V1 reports received";

            // Type is an MO-Defined-Type
            type nw_Counter64;
        }

        // @@@ ICMPV6_PKT_MLD_V2_REPORTS_SNT_CNT
        // From Interface icmpv6:GlobalMLDStats
        // Type is an MO-Defined-Type
        leaf mldV2ReportsSent {
            config "false";
            description "V2 reports sent";

            // Type is an MO-Defined-Type
            type nw_Counter64;
        }

        // @@@ ICMPV6_PKT_MLD_V2_REPORTS_RECV_CNT
        // From Interface icmpv6:GlobalMLDStats
        // Type is an MO-Defined-Type
        leaf mldV2ReportsRecv {
            config "false";
            description "V2 reports received";

            // Type is an MO-Defined-Type
            type nw_Counter64;
        }

        // @@@ ICMPV6_PKT_MLD_V1_LEAVES_SNT_CNT
        // From Interface icmpv6:GlobalMLDStats
        // Type is an MO-Defined-Type
        leaf mldV1LeavesSent {
            config "false";
            description "V1 leaves sent";

            // Type is an MO-Defined-Type
            type nw_Counter64;
        }

        // @@@ ICMPV6_PKT_MLD_V1_LEAVES_RECV_CNT
        // From Interface icmpv6:GlobalMLDStats
        // Type is an MO-Defined-Type
        leaf mldV1LeavesRecv {
            config "false";
            description "V1 leaves received";

            // Type is an MO-Defined-Type
            type nw_Counter64;
        }
    }

    grouping icmpv6_ICMPv6EventLogs-group {

        // Type of Event
        // Type is an MO-Defined-Type
        leaf eventType {
            description "Event Log Type";

            // Type is an MO-Defined-Type
            type icmpv6_EventType;
        }

        // Type of Event LogSize
        // Type is an MO-Defined-Type
        leaf logSize {
            description "Event Log Size";

            // Type is an MO-Defined-Type
            type icmpv6_EventLogSize;
        }
    }

    grouping igmpsnoop_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per igmp instance information. There is only
        // one instance of igmp running in the system today
        container inst-items {

            // Added containment as a singleton: Prefix=inst
            // Acquired From Package igmpsnoop
            uses igmpsnoop_Inst-group;
        }
    }

    grouping igmpsnoop_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // All router multicast group address (GIPo), outer multicast
        // encapsulation ip address
        // Inherited From ipmcsnoop:Inst
        // Type is an MO-Defined-Type
        leaf allRtrMcastEncap {
            config "false";
            description "All Router Multicast Encapsulation";

            // Type is an MO-Defined-Type
            type mcast_GrpIp;
        }

        // Flags
        // Inherited From ipmcsnoop:Inst
        // Type is an MO-Defined-Type
        leaf flags {
            config "false";
            description "Flags";

            // Type is an MO-Defined-Type
            type ipmcsnoop_InstFlags;
        }

        // This objects hold per igmp domain information
        container dom-items {
            list Dom-list {
                config "false";
                key "encap";

                // Added containment: Prefix=dom
                // Acquired From Package igmpsnoop
                uses igmpsnoop_Dom-group;
            }
        }

        // This objects hold per Instance statistics operational
        // information. This is a singleton within Instance
        container inststats-items {

            // Added containment as a singleton: Prefix=inststats
            // Acquired From Package igmpsnoop
            uses igmpsnoop_InstStats-group;
        }
    }

    grouping igmpsnoop_Dom-group {

        // Inherited From nw:Conn
        // Modified by Override: nw:CpDom->name
        // Modified by Override: ipmcsnoop:Dom->name
        // Type is an MO-Defined-Type
        leaf name {
            description "Name";

            // Type is an MO-Defined-Type
            type naming_Name {
                length "1..64";
            }
        }

        // Id for this domain    @@@ This comes from the domain id assigned by the
        // PE for the bridge domain
        // Inherited From ipmcsnoop:Dom
        // Type is an MO-Defined-Type
        leaf id {
            config "false";
            description "ID";

            // Type is an MO-Defined-Type
            type l2_DomId;
        }
        leaf encap {
            config "false";
            type string;
        }

        // Admin State
        // Inherited From ipmcsnoop:Dom
        // Type is an MO-Defined-Type
        leaf adminSt {
            config "false";
            description "Admin State";

            // Type is an MO-Defined-Type
            type nw_AdminSt;
        }

        // Controls
        // Inherited From ipmcsnoop:Dom
        // Type is an MO-Defined-Type
        leaf ctrl {
            config "false";
            description "Controls";

            // Type is an MO-Defined-Type
            type ipmcsnoop_DomControl;
        }

        // Flags
        // Inherited From ipmcsnoop:Dom
        // Modified by Override: igmpsnoop:Dom->flags
        // Type is an MO-Defined-Type
        leaf flags {
            config "false";
            description "Flags";

            // Type is an MO-Defined-Type
            type ipmcsnoop_DomFlags;
        }

        // Forwarding mode
        // Inherited From ipmcsnoop:Dom
        // Type is an MO-Defined-Type
        leaf fwdMode {
            config "false";
            description "Fowarding Mode";

            // Type is an MO-Defined-Type
            type ipmcsnoop_FwdMode;
        }

        // Number of router interfaces
        // Inherited From ipmcsnoop:Dom
        // Type is an MO-Defined-Type
        leaf numRtrIf {
            config "false";
            description "Router Interfaces";

            // Type is an MO-Defined-Type
            type nw_Counter32;
        }

        // Number of multicast groups
        // Inherited From ipmcsnoop:Dom
        // Type is an MO-Defined-Type
        leaf numMcGrp {
            config "false";
            description "Multicast Groups";

            // Type is an MO-Defined-Type
            type nw_Counter32;
        }

        // Number of Source groups
        // Inherited From ipmcsnoop:Dom
        // Type is an MO-Defined-Type
        leaf numSrcGrp {
            config "false";
            description "Multicast Groups";

            // Type is an MO-Defined-Type
            type nw_Counter32;
        }
        leaf grpFlushTs {
            config "false";
            type uint64;
        }
        leaf nextQueryTs {
            config "false";
            type uint64;
        }
        leaf nextQueryExpTs {
            config "false";
            type uint64;
        }

        // Mrtr Epg Id used when sending packets to mrtr port
        // Inherited From ipmcsnoop:Dom
        // Type is an MO-Defined-Type
        leaf mrtrEpgId {
            config "false";
            description "Mrouter Endpoint Group ID";

            // Type is an MO-Defined-Type
            type l2_DomId;
        }

        // IGMP database
        container db-items {
            list Db-list {
                config "false";
                key "type";

                // Added containment: Prefix=db
                // Acquired From Package igmpsnoop
                uses igmpsnoop_Db-group;
            }
        }

        // This objects hold per igmp domain statistics operational
        // information. This is a singleton within a Dom
        container domstats-items {

            // Added containment as a singleton: Prefix=domstats
            // Acquired From Package igmpsnoop
            uses igmpsnoop_DomStats-group;
        }

        // Multicast router if that is configured statically
        container strtrif-items {
            list StRtrIf-list {
                key "id";

                // Added containment: Prefix=strtrif
                // Acquired From Package igmpsnoop
                uses igmpsnoop_StRtrIf-group;
            }
        }

        // Multicast router if    @@@ Mulitcast router if in the BD. These can be either
        // configured by the admin or discovered through protocols
        // like PIM, IGMP.
        container rtrif-items {
            list RtrIf-list {
                config "false";
                key "id";

                // Added containment: Prefix=rtrif
                // Acquired From Package igmpsnoop
                uses igmpsnoop_RtrIf-group;
            }
        }

        // Circuit endpoint representing EPG
        container cktep-items {
            list CktEp-list {
                config "false";
                key "encap";

                // Added containment: Prefix=cktep
                // Acquired From Package igmpsnoop
                uses igmpsnoop_CktEp-group;
            }
        }

        // Querier policy
        container querierp-items {

            // Added containment as a singleton: Prefix=querierp
            // Acquired From Package igmpsnoop
            uses igmpsnoop_QuerierP-group;
        }

        // Querier state
        container querierst-items {

            // Added containment as a singleton: Prefix=querierst
            // Acquired From Package igmpsnoop
            uses igmpsnoop_QuerierSt-group;
        }
    }

    grouping igmpsnoop_Db-group {

        // Inherited From nw:Conn
        // Modified by Override: nw:Db->name
        // Type is an MO-Defined-Type
        leaf name {
            description "Name";

            // Type is an MO-Defined-Type
            type naming_Name {
                length "1..64";
            }
        }

        // Type of the repository
        // Inherited From ipmcsnoop:Db
        // Type is an MO-Defined-Type
        leaf type {
            config "false";
            description "Type";

            // Type is an MO-Defined-Type
            type ipmcsnoop_DbT;
        }

        // Multicast Group records
        container mcgrp-items {
            list McGrpRec-list {
                config "false";
                key "addr";

                // Added containment: Prefix=mcgrp
                // Acquired From Package igmpsnoop
                uses igmpsnoop_McGrpRec-group;
            }
        }
    }

    grouping igmpsnoop_McGrpRec-group {

        // Inherited From nw:Conn
        // Modified by Override: nw:DbRec->name
        // Type is an MO-Defined-Type
        leaf name {
            description "Name";

            // Type is an MO-Defined-Type
            type naming_Name {
                length "1..64";
            }
        }

        // Group address
        // Inherited From ipmcsnoop:McGrpRec
        // Type is an MO-Defined-Type
        leaf addr {
            config "false";
            description "Multicast Address";

            // Type is an MO-Defined-Type
            type mcast_GrpIp;
        }

        // Version
        // Inherited From ipmcsnoop:McGrpRec
        // Modified by Override: igmpsnoop:McGrpRec->ver
        // Type is an MO-Defined-Type
        leaf ver {
            config "false";
            description "Version";

            // Type is an MO-Defined-Type
            type mcast_Ver;
        }

        // Latest reporter
        // Inherited From ipmcsnoop:McGrpRec
        // Type is an MO-Defined-Type
        leaf latReporter {
            config "false";
            description "Latest Reporter";

            // Type is an MO-Defined-Type
            type ipmcsnoop_Reporter;
        }
        leaf oldHostTs {
            config "false";
            type uint64;
        }
        leaf reportTs {
            config "false";
            type uint64;
        }

        // Number of Sources
        // Inherited From ipmcsnoop:McGrpRec
        // Type is an MO-Defined-Type
        leaf numSrc {
            config "false";
            description "Num of Sources";

            // Type is an MO-Defined-Type
            type nw_Counter32;
        }

        // EPG entries in mcast group record
        container epg-items {
            list EpgRec-list {
                config "false";
                key "fabEncap";

                // Added containment: Prefix=epg
                // Acquired From Package igmpsnoop
                uses igmpsnoop_EpgRec-group;
            }
        }

        // IGMP report record snooped by igmp-snoop application
        container rep-items {
            list ReportRec-list {
                config "false";
                key "mcastSrc ver";

                // Added containment: Prefix=rep
                // Acquired From Package igmpsnoop
                uses igmpsnoop_ReportRec-group;
            }
        }
    }

    grouping igmpsnoop_EpgRec-group {

        // Inherited From nw:Conn
        // Modified by Override: nw:DbRec->name
        // Type is an MO-Defined-Type
        leaf name {
            description "Name";

            // Type is an MO-Defined-Type
            type naming_Name {
                length "1..64";
            }
        }
        leaf fabEncap {
            config "false";
            type string;
        }

        // Epg id, identified using the circuit endpoint
        // id in the system
        // Inherited From ipmcsnoop:EpgRec
        // Type is an MO-Defined-Type
        leaf id {
            config "false";
            description "Endpoint Group ID";

            // Type is an MO-Defined-Type
            type l2_DomId;
        }

        // Multicast group address (GIPO'), Outer multicast
        // encapsulation ip address for this layer2 domain
        // Inherited From ipmcsnoop:EpgRec
        // Type is an MO-Defined-Type
        leaf mcastEncap {
            config "false";
            description "Multicat Encapsulation";

            // Type is an MO-Defined-Type
            type mcast_GrpIp;
        }

        // IGMP report record snooped by igmp-snoop application
        container rep-items {
            list ReportRec-list {
                config "false";
                key "mcastSrc ver";

                // Added containment: Prefix=rep
                // Acquired From Package igmpsnoop
                uses igmpsnoop_ReportRec-group;
            }
        }
    }

    grouping igmpsnoop_ReportRec-group {

        // Inherited From nw:Conn
        // Modified by Override: nw:DbRec->name
        // Type is an MO-Defined-Type
        leaf name {
            description "Name";

            // Type is an MO-Defined-Type
            type naming_Name {
                length "1..64";
            }
        }

        // Multicast traffic source
        // Inherited From ipmcsnoop:ReportRec
        // Type is an MO-Defined-Type
        leaf mcastSrc {
            config "false";
            description "Multicast Source";

            // Type is an MO-Defined-Type
            type ipmcsnoop_McastSrc;
        }

        // Version
        // Inherited From ipmcsnoop:ReportRec
        // Modified by Override: igmpsnoop:ReportRec->ver
        // Type is an MO-Defined-Type
        leaf ver {
            config "false";
            description "Version";

            // Type is an MO-Defined-Type
            type mcast_Ver;
        }

        // Filter mode
        // Inherited From ipmcsnoop:ReportRec
        // Type is an MO-Defined-Type
        leaf filtMode {
            config "false";
            description "Filter Mode";

            // Type is an MO-Defined-Type
            type mcast_FiltMode;
        }

        // Filter mode
        // Inherited From ipmcsnoop:ReportRec
        // Type is an MO-Defined-Type
        leaf flags {
            config "false";
            description "Flags";

            // Type is an MO-Defined-Type
            type ipmcsnoop_RepFlags;
        }

        // OIF list (outgoing interface list)
        container oif-items {
            list OIFRec-list {
                config "false";
                key "id";

                // Added containment: Prefix=oif
                // Acquired From Package igmpsnoop
                uses igmpsnoop_OIFRec-group;
            }
        }
    }

    grouping igmpsnoop_OIFRec-group {

        // Inherited From nw:Conn
        // Modified by Override: nw:DbRec->name
        // Type is an MO-Defined-Type
        leaf name {
            description "Name";

            // Type is an MO-Defined-Type
            type naming_Name {
                length "1..64";
            }
        }

        // Multicast traffic source
        // Inherited From ipmcsnoop:OIFRec
        // Type is an MO-Defined-Type
        leaf id {
            config "false";
            description "ID";

            // Type is an MO-Defined-Type
            type nw_IfId;
        }
        leaf numGqMiss {
            config "false";
            type uint16;
        }
        leaf expireTs {
            config "false";
            type uint64;
        }

        // Host Record List (Used for Explicit Host Tracking)
        container host-items {
            list HostRec-list {
                config "false";
                key "addr";

                // Added containment: Prefix=host
                // Acquired From Package igmpsnoop
                uses igmpsnoop_HostRec-group;
            }
        }
    }

    grouping igmpsnoop_HostRec-group {

        // Inherited From nw:Conn
        // Modified by Override: nw:DbRec->name
        // Type is an MO-Defined-Type
        leaf name {
            description "Name";

            // Type is an MO-Defined-Type
            type naming_Name {
                length "1..64";
            }
        }
        leaf addr {
            config "false";
            type address_Ip;
        }
        leaf upTs {
            config "false";
            type uint64;
        }
        leaf lastJoinTs {
            config "false";
            type uint64;
        }
        leaf nextExpiryTs {
            config "false";
            type uint64;
        }
    }

    grouping igmpsnoop_DomStats-group {

        // V1 Reports received
        // Type is an MO-Defined-Type
        leaf v1RepRcvd {
            config "false";
            description "V1 Reports Received";

            // Type is an MO-Defined-Type
            type nw_Counter32;
        }

        // V2 Reports received
        // Type is an MO-Defined-Type
        leaf v2RepRcvd {
            config "false";
            description "V2 Reports Received";

            // Type is an MO-Defined-Type
            type nw_Counter32;
        }

        // V2 Leave received
        // Type is an MO-Defined-Type
        leaf v2LeaveRcvd {
            config "false";
            description "V2 Leave Received";

            // Type is an MO-Defined-Type
            type nw_Counter32;
        }

        // V1 Query received
        // Type is an MO-Defined-Type
        leaf v1QueryRcvd {
            config "false";
            description "V1 Query Received";

            // Type is an MO-Defined-Type
            type nw_Counter32;
        }

        // V2 Query received
        // Type is an MO-Defined-Type
        leaf v2QueryRcvd {
            config "false";
            description "V2 Query Received";

            // Type is an MO-Defined-Type
            type nw_Counter32;
        }

        // V1 Reports suppressed
        // Type is an MO-Defined-Type
        leaf v1RepSupr {
            config "false";
            description "V1 Reports Suppressed";

            // Type is an MO-Defined-Type
            type nw_Counter32;
        }

        // V2 Reports suppressed
        // Type is an MO-Defined-Type
        leaf v2RepSupr {
            config "false";
            description "V2 Reports Suppressed";

            // Type is an MO-Defined-Type
            type nw_Counter32;
        }

        // V2 leaves suppressed
        // Type is an MO-Defined-Type
        leaf v2LeaveSupr {
            config "false";
            description "V2 Leaves Suppressed";

            // Type is an MO-Defined-Type
            type nw_Counter32;
        }

        // v1 Proxy Report Originated
        // Type is an MO-Defined-Type
        leaf v1RepOrig {
            config "false";
            description "V1 Reports Originated";

            // Type is an MO-Defined-Type
            type nw_Counter32;
        }

        // v2 Proxy Report Originated
        // Type is an MO-Defined-Type
        leaf v2RepOrig {
            config "false";
            description "V2 Reports Originated";

            // Type is an MO-Defined-Type
            type nw_Counter32;
        }

        // v2 Proxy Leave Originated
        // Type is an MO-Defined-Type
        leaf v2LeaveOrig {
            config "false";
            description "V2 Leaves Originated";

            // Type is an MO-Defined-Type
            type nw_Counter32;
        }

        // V3 Reports received
        // Type is an MO-Defined-Type
        leaf v3RepRcvd {
            config "false";
            description "V3 Reports Received";

            // Type is an MO-Defined-Type
            type nw_Counter32;
        }

        // V3 Query received
        // Type is an MO-Defined-Type
        leaf v3QueryRcvd {
            config "false";
            description "V3 Query Received";

            // Type is an MO-Defined-Type
            type nw_Counter32;
        }

        // V3 Group Record suppressed
        // Type is an MO-Defined-Type
        leaf v3GrpRecSupr {
            config "false";
            description "V3 Group Records Suppressed";

            // Type is an MO-Defined-Type
            type nw_Counter32;
        }

        // v3 Proxy Report Originated
        // Type is an MO-Defined-Type
        leaf v3RepOrig {
            config "false";
            description "V3 Reports Originated";

            // Type is an MO-Defined-Type
            type nw_Counter32;
        }
        leaf lastClearTs {
            config "false";
            type uint64;
        }

        // packets received
        // Inherited From ipmcsnoop:DomStats
        // Type is an MO-Defined-Type
        leaf pktsRcvd {
            config "false";
            description "Packets Received";

            // Type is an MO-Defined-Type
            type nw_Counter32;
        }

        // Pim Hello Rcvd
        // Inherited From ipmcsnoop:DomStats
        // Type is an MO-Defined-Type
        leaf pimHelloRcvd {
            config "false";
            description "Pim Hello Received";

            // Type is an MO-Defined-Type
            type nw_Counter32;
        }

        // Invalid Query Rcvd
        // Inherited From ipmcsnoop:DomStats
        // Type is an MO-Defined-Type
        leaf invQueryRcvd {
            config "false";
            description "Invalid Query Received";

            // Type is an MO-Defined-Type
            type nw_Counter32;
        }

        // Invalid Report Rcvd
        // Inherited From ipmcsnoop:DomStats
        // Type is an MO-Defined-Type
        leaf invRepRcvd {
            config "false";
            description "Invalid Report Received";

            // Type is an MO-Defined-Type
            type nw_Counter32;
        }

        // Version Mismatch Rcvd
        // Inherited From ipmcsnoop:DomStats
        // Type is an MO-Defined-Type
        leaf verMisMatchRcvd {
            config "false";
            description "Version Mismatch Received";

            // Type is an MO-Defined-Type
            type nw_Counter32;
        }

        // Unknown Packets Rcvd
        // Inherited From ipmcsnoop:DomStats
        // Type is an MO-Defined-Type
        leaf unknPktRcvd {
            config "false";
            description "Unknown Packets Received";

            // Type is an MO-Defined-Type
            type nw_Counter32;
        }

        // Query Originated
        // Inherited From ipmcsnoop:DomStats
        // Type is an MO-Defined-Type
        leaf queryPktsOrig {
            config "false";
            description "Query Packets Originated";

            // Type is an MO-Defined-Type
            type nw_Counter32;
        }

        // Packets Sent to Router Ports
        // Inherited From ipmcsnoop:DomStats
        // Type is an MO-Defined-Type
        leaf pktsToRport {
            config "false";
            description "Packets to Router Ports";

            // Type is an MO-Defined-Type
            type nw_Counter32;
        }

        // VPC Sync Packets Sent to Peer
        // Inherited From ipmcsnoop:DomStats
        // Type is an MO-Defined-Type
        leaf vpcSyncSent {
            config "false";
            description "VPC Sync Packets Sent";

            // Type is an MO-Defined-Type
            type nw_Counter32;
        }

        // VPC Sync Packets Rcvd from Peer
        // Inherited From ipmcsnoop:DomStats
        // Type is an MO-Defined-Type
        leaf vpcSyncRcvd {
            config "false";
            description "VPC Sync Packets Received";

            // Type is an MO-Defined-Type
            type nw_Counter32;
        }

        // VPC Sync Packets Failed to send to Peer
        // Inherited From ipmcsnoop:DomStats
        // Type is an MO-Defined-Type
        leaf vpcSyncFail {
            config "false";
            description "VPC Sync Packets Failed";

            // Type is an MO-Defined-Type
            type nw_Counter32;
        }

        // MRD Sync Packets Sent to Peer
        // Inherited From ipmcsnoop:DomStats
        // Type is an MO-Defined-Type
        leaf mrdSyncSent {
            config "false";
            description "MRD Sync Packets Sent";

            // Type is an MO-Defined-Type
            type nw_Counter32;
        }

        // MRD Sync Packets Rcvd from Peer
        // Inherited From ipmcsnoop:DomStats
        // Type is an MO-Defined-Type
        leaf mrdSyncRcvd {
            config "false";
            description "MRD Sync Packets Received";

            // Type is an MO-Defined-Type
            type nw_Counter32;
        }

        // MRD Sync Packets Failed to send to Peer
        // Inherited From ipmcsnoop:DomStats
        // Type is an MO-Defined-Type
        leaf mrdSyncFail {
            config "false";
            description "MRD Sync Packets Failed";

            // Type is an MO-Defined-Type
            type nw_Counter32;
        }
    }

    grouping igmpsnoop_StRtrIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }
        leaf encap {
            config "false";
            type string;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping igmpsnoop_RtrIf-group {

        // Identifier for the if
        // Inherited From ipmcsnoop:RtrIf
        // Type is an MO-Defined-Type
        leaf id {
            config "false";
            description "ID";

            // Type is an MO-Defined-Type
            type nw_IfId;
        }

        // Life cycle control
        // Inherited From ipmcsnoop:RtrIf
        // Type is an MO-Defined-Type
        leaf lcC {
            config "false";
            description "Life Cycle Control";

            // Type is an MO-Defined-Type
            type ipmcsnoop_LcC;
        }
        leaf upTs {
            config "false";
            type uint64;
        }
        leaf nextExpiryTs {
            config "false";
            type uint64;
        }
    }

    grouping igmpsnoop_CktEp-group {
        leaf encap {
            config "false";
            type string;
        }

        // Multicast Snoop Configured statically
        container mcgrp-items {
            list StMcGrp-list {
                key "addr";

                // Added containment: Prefix=mcgrp
                // Acquired From Package igmpsnoop
                uses igmpsnoop_StMcGrp-group;
            }
        }

        // Route control policy for igmp multicast snoop.
        container actrl-items {
            list ACtrlP-list {
                key "name";

                // Added containment: Prefix=actrl
                // Acquired From Package igmpsnoop
                uses igmpsnoop_ACtrlP-group;
            }
        }
    }

    grouping igmpsnoop_StMcGrp-group {

        // Inherited From nw:Conn
        // Modified by Override: mcast:Grp->name
        // Type is an MO-Defined-Type
        leaf name {
            description "Name";

            // Type is an MO-Defined-Type
            type naming_Name {
                length "1..64";
            }
        }

        // Multicast group address
        // Inherited From mcast:Grp
        // Type is an MO-Defined-Type
        leaf addr {
            description "Address";

            // Type is an MO-Defined-Type
            type mcast_GrpIp;
        }

        // IPMC Source IP
        container src-items {
            list McSrc-list {
                config "false";
                key "id";

                // Added containment: Prefix=src
                // Acquired From Package igmpsnoop
                uses igmpsnoop_McSrc-group;
            }
        }
    }

    grouping igmpsnoop_McSrc-group {

        // Multicast traffic source
        // Inherited From ipmcsnoop:McSrc
        // Type is an MO-Defined-Type
        leaf id {
            config "false";
            description "Multicast Source IP";

            // Type is an MO-Defined-Type
            type ipmcsnoop_McastSrc;
        }

        // Target Interface (outgoing interface list)
        container if-items {
            list TgtIf-list {
                config "false";
                key "id";

                // Added containment: Prefix=if
                // Acquired From Package igmpsnoop
                uses igmpsnoop_TgtIf-group;
            }
        }
    }

    grouping igmpsnoop_TgtIf-group {

        // Target interface Id
        // Inherited From ipmcsnoop:TgtIf
        // Type is an MO-Defined-Type
        leaf id {
            config "false";
            description "Multicast Source IP";

            // Type is an MO-Defined-Type
            type nw_IfId;
        }
    }

    grouping igmpsnoop_ACtrlP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Direction [in/out]
        // Inherited From rtctrl:RtCtrlP
        // Type is an MO-Defined-Type
        leaf direction {
            description "Direction";

            // Type is an MO-Defined-Type
            type rtctrl_RtCtrlDir;
        }
        leaf rtMap {
            type string;
        }

        // Target Interface (outgoing interface list)
        container if-items {
            list TgtIf-list {
                config "false";
                key "id";

                // Added containment: Prefix=if
                // Acquired From Package igmpsnoop
                uses igmpsnoop_TgtIf-group;
            }
        }
    }

    grouping igmpsnoop_QuerierP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Querier version
        // Inherited From mcast:AQuerier
        // Modified by Override: igmpsnoop:QuerierP->ver
        // Type is an MO-Defined-Type
        leaf ver {
            description "Version";

            // Type is an MO-Defined-Type
            type mcast_Ver;
        }

        // Querier IP address
        // Inherited From mcast:AQuerier
        // Type is an MO-Defined-Type
        leaf addr {
            description "Address";

            // Type is an MO-Defined-Type
            type mcast_QuerierIp;
        }

        // Query interval
        // Inherited From mcast:AQuerier
        // Type is an MO-Defined-Type
        leaf queryIntvl {
            description "Query Interval";

            // Type is an MO-Defined-Type
            type mcast_QueryIntvl;
        }

        // Query response interval
        // Inherited From mcast:AQuerier
        // Type is an MO-Defined-Type
        leaf rspIntvl {
            description "Response Interval";

            // Type is an MO-Defined-Type
            type mcast_QueryRspIntvl;
        }

        // Robustness factor
        // Inherited From mcast:AQuerier
        // Type is an MO-Defined-Type
        leaf robustFac {
            description "Robustness Factor";

            // Type is an MO-Defined-Type
            type mcast_RobustFactor;
        }

        // Startup query interval
        // Inherited From mcast:AQuerier
        // Type is an MO-Defined-Type
        leaf startQueryIntvl {
            description "Startup Query Interval";

            // Type is an MO-Defined-Type
            type mcast_StartQueryIntvl;
        }

        // Startup query count
        // Inherited From mcast:AQuerier
        // Type is an MO-Defined-Type
        leaf startQueryCnt {
            description "Startup Query Count";

            // Type is an MO-Defined-Type
            type mcast_QueryCnt;
        }

        // Last member query interval
        // Inherited From ipmcsnoop:QuerierP
        // Type is an MO-Defined-Type
        leaf lastMbrIntvl {
            config "false";
            description "Last Member Query Interval";

            // Type is an MO-Defined-Type
            type mcast_LastMbrQueryIntvl;
        }
    }

    grouping igmpsnoop_QuerierSt-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Querier version
        // Inherited From mcast:AQuerier
        // Modified by Override: igmpsnoop:QuerierSt->ver
        // Type is an MO-Defined-Type
        leaf ver {
            description "Version";

            // Type is an MO-Defined-Type
            type mcast_Ver;
        }

        // Querier IP address
        // Inherited From mcast:AQuerier
        // Type is an MO-Defined-Type
        leaf addr {
            description "Address";

            // Type is an MO-Defined-Type
            type mcast_QuerierIp;
        }

        // Query interval
        // Inherited From mcast:AQuerier
        // Type is an MO-Defined-Type
        leaf queryIntvl {
            description "Query Interval";

            // Type is an MO-Defined-Type
            type mcast_QueryIntvl;
        }

        // Query response interval
        // Inherited From mcast:AQuerier
        // Type is an MO-Defined-Type
        leaf rspIntvl {
            description "Response Interval";

            // Type is an MO-Defined-Type
            type mcast_QueryRspIntvl;
        }

        // Robustness factor
        // Inherited From mcast:AQuerier
        // Type is an MO-Defined-Type
        leaf robustFac {
            description "Robustness Factor";

            // Type is an MO-Defined-Type
            type mcast_RobustFactor;
        }

        // Startup query interval
        // Inherited From mcast:AQuerier
        // Type is an MO-Defined-Type
        leaf startQueryIntvl {
            description "Startup Query Interval";

            // Type is an MO-Defined-Type
            type mcast_StartQueryIntvl;
        }

        // Startup query count
        // Inherited From mcast:AQuerier
        // Type is an MO-Defined-Type
        leaf startQueryCnt {
            description "Startup Query Count";

            // Type is an MO-Defined-Type
            type mcast_QueryCnt;
        }

        // Last member query interval
        // Inherited From ipmcsnoop:QuerierP
        // Type is an MO-Defined-Type
        leaf lastMbrIntvl {
            config "false";
            description "Last Member Query Interval";

            // Type is an MO-Defined-Type
            type mcast_LastMbrQueryIntvl;
        }

        // Interface on which the querier is present
        // Inherited From ipmcsnoop:QuerierSt
        // Type is an MO-Defined-Type
        leaf if {
            config "false";
            description "Interface";

            // Type is an MO-Defined-Type
            type nw_IfId;
        }

        // Querier timeout
        // Inherited From ipmcsnoop:QuerierSt
        // Type is an MO-Defined-Type
        leaf timeout {
            config "false";
            description "Timeout";

            // Type is an MO-Defined-Type
            type mcast_QuerierTimeout;
        }

        // Querier flags
        // Inherited From ipmcsnoop:QuerierSt
        // Type is an MO-Defined-Type
        leaf flags {
            config "false";
            description "Flags";

            // Type is an MO-Defined-Type
            type ipmcsnoop_QuerierFlags;
        }
    }

    grouping igmpsnoop_InstStats-group {

        // Total Number of multicast groups
        // Inherited From ipmcsnoop:InstStats
        // Type is an MO-Defined-Type
        leaf totNumMcGrp {
            config "false";
            description "Total Number of Multicast Groups";

            // Type is an MO-Defined-Type
            type nw_Counter32;
        }

        // packets received
        // Inherited From ipmcsnoop:InstStats
        // Type is an MO-Defined-Type
        leaf pktsRcvd {
            config "false";
            description "Packets Received";

            // Type is an MO-Defined-Type
            type nw_Counter32;
        }

        // Invalid packets received
        // Inherited From ipmcsnoop:InstStats
        // Type is an MO-Defined-Type
        leaf invPktsRcvd {
            config "false";
            description "Invalid Packets Received";

            // Type is an MO-Defined-Type
            type nw_Counter32;
        }

        // Loopback packets received
        // Inherited From ipmcsnoop:InstStats
        // Type is an MO-Defined-Type
        leaf lpbkPktsRcvd {
            config "false";
            description "Loopback Packets Received";

            // Type is an MO-Defined-Type
            type nw_Counter32;
        }

        // packets Flooded
        // Inherited From ipmcsnoop:InstStats
        // Type is an MO-Defined-Type
        leaf pktsFlooded {
            config "false";
            description "Packets Flooded";

            // Type is an MO-Defined-Type
            type nw_Counter32;
        }

        // MRD Loopback packets received
        // Inherited From ipmcsnoop:InstStats
        // Type is an MO-Defined-Type
        leaf mrdLpbkPktsRcvd {
            config "false";
            description "MRD Loopback Packets Received";

            // Type is an MO-Defined-Type
            type nw_Counter32;
        }

        // No Vlan DB packets received
        // Inherited From ipmcsnoop:InstStats
        // Type is an MO-Defined-Type
        leaf noVlanDbPktsRcvd {
            config "false";
            description "No Vlan Db Packets Received";

            // Type is an MO-Defined-Type
            type nw_Counter32;
        }

        // Vpc ZMQ packets sent
        // Inherited From ipmcsnoop:InstStats
        // Type is an MO-Defined-Type
        leaf vpcZmqPktsSent {
            config "false";
            description "VPC ZMQ Packets Sent";

            // Type is an MO-Defined-Type
            type nw_Counter32;
        }

        // Vpc ZMQ packets received
        // Inherited From ipmcsnoop:InstStats
        // Type is an MO-Defined-Type
        leaf vpcZmqPktsRcvd {
            config "false";
            description "VPC ZMQ Packets Received";

            // Type is an MO-Defined-Type
            type nw_Counter32;
        }

        // Vpc ZMQ packets send Fail
        // Inherited From ipmcsnoop:InstStats
        // Type is an MO-Defined-Type
        leaf vpcZmqPktsSentFail {
            config "false";
            description "VPC ZMQ Packets Send Fail";

            // Type is an MO-Defined-Type
            type nw_Counter32;
        }

        // Vpc ZMQ packets receive Fail
        // Inherited From ipmcsnoop:InstStats
        // Type is an MO-Defined-Type
        leaf vpcZmqPktsRcvdFail {
            config "false";
            description "VPC ZMQ Packets Receive Fail";

            // Type is an MO-Defined-Type
            type nw_Counter32;
        }

        // Vpc Peer packets sent
        // Inherited From ipmcsnoop:InstStats
        // Type is an MO-Defined-Type
        leaf vpcPeerPktsSent {
            config "false";
            description "VPC Peer Packets Sent";

            // Type is an MO-Defined-Type
            type nw_Counter32;
        }

        // Vpc Peer packets received
        // Inherited From ipmcsnoop:InstStats
        // Type is an MO-Defined-Type
        leaf vpcPeerPktsRcvd {
            config "false";
            description "VPC Peer Packets Received";

            // Type is an MO-Defined-Type
            type nw_Counter32;
        }

        // Vpc Peer packets send Fail
        // Inherited From ipmcsnoop:InstStats
        // Type is an MO-Defined-Type
        leaf vpcPeerPktsSentFail {
            config "false";
            description "VPC Peer Packets Send Fail";

            // Type is an MO-Defined-Type
            type nw_Counter32;
        }

        // Vpc Peer packets receive Fail
        // Inherited From ipmcsnoop:InstStats
        // Type is an MO-Defined-Type
        leaf vpcPeerPktsRcvdFail {
            config "false";
            description "VPC Peer Packets Receive Fail";

            // Type is an MO-Defined-Type
            type nw_Counter32;
        }
    }

    grouping macsec_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per macsec instance information. There is
        // only one instance of macsec running in the system today
        container inst-items {

            // Added containment as a singleton: Prefix=inst
            // Acquired From Package macsec
            uses macsec_Inst-group;
        }
    }

    grouping macsec_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds macsec information that is operated at a
        // interface level
        container if-items {
            list If-list {
                key "id";

                // Added containment: Prefix=if
                // Acquired From Package macsec
                uses macsec_If-group;
            }
        }
    }

    grouping macsec_If-group {

        // Operational state
        // Type is an MO-Defined-Type
        leaf operSt {
            config "false";
            description "Operational State";

            // Type is an MO-Defined-Type
            type macsec_OperSt;
        }

        // Operational state qualifier
        // Type is an MO-Defined-Type
        leaf operStQual {
            config "false";
            description "Operational State Qualifier";

            // Type is an MO-Defined-Type
            type macsec_OperStQual;
        }

        // pre-shared key
        // Type is an MO-Defined-Type
        leaf preSharedKey {
            config "false";
            description "Pre-shared Key";

            // Type is an MO-Defined-Type
            type macsec_PreSharedKey;
        }

        // key name
        // Type is an MO-Defined-Type
        leaf keyName {
            config "false";
            description "Key Name";

            // Type is an MO-Defined-Type
            type macsec_KeyName;
        }

        // cipher suite
        // Type is an MO-Defined-Type
        leaf cipherSuite {
            config "false";
            description "Cipher Suite";

            // Type is an MO-Defined-Type
            type macsec_CipherSuite;
        }

        // server priority
        // <property name="serverPriority"
        // type="ServerPriority"
        // owner="management"
        // mod="implicit"
        // label="Server Priority"
        // />
        // confidentiality offset
        // Type is an MO-Defined-Type
        leaf confOffset {
            config "false";
            description "Confidentiality Offset";

            // Type is an MO-Defined-Type
            type macsec_ConfOffset;
        }

        // secure mode
        // Type is an MO-Defined-Type
        leaf secureMode {
            config "false";
            description "Secure Mode";

            // Type is an MO-Defined-Type
            type macsec_SecureMode;
        }

        // window size
        // Type is an MO-Defined-Type
        leaf windowSize {
            config "false";
            description "Window Size";

            // Type is an MO-Defined-Type
            type macsec_WindowSize;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        // Inherited From platform:If
        // Inherited From macsec:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        // Inherited From udld:PhysIf
        // Inherited From l1:PhysIfExtended
        // Inherited From pc:AggrIfExtended
        // Inherited From pc:ShadowAggrIfExtended
        // Inherited From platform:If
        // Inherited From macsec:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping mldsnoop_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per mld instance information. There is only
        // one instance of mld running in the system today
        container inst-items {

            // Added containment as a singleton: Prefix=inst
            // Acquired From Package mldsnoop
            uses mldsnoop_Inst-group;
        }
    }

    grouping mldsnoop_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // All router multicast group address (GIPo), outer multicast
        // encapsulation ip address
        // Inherited From ipmcsnoop:Inst
        // Type is an MO-Defined-Type
        leaf allRtrMcastEncap {
            config "false";
            description "All Router Multicast Encapsulation";

            // Type is an MO-Defined-Type
            type mcast_GrpIp;
        }

        // Flags
        // Inherited From ipmcsnoop:Inst
        // Type is an MO-Defined-Type
        leaf flags {
            config "false";
            description "Flags";

            // Type is an MO-Defined-Type
            type ipmcsnoop_InstFlags;
        }

        // This objects hold per mld snooping domain information
        container dom-items {
            list Dom-list {
                config "false";
                key "encap";

                // Added containment: Prefix=dom
                // Acquired From Package mldsnoop
                uses mldsnoop_Dom-group;
            }
        }

        // This objects hold per Instance statistics operational
        // information. This is a singleton within Instance
        container inststats-items {

            // Added containment as a singleton: Prefix=inststats
            // Acquired From Package mldsnoop
            uses mldsnoop_InstStats-group;
        }
    }

    grouping mldsnoop_Dom-group {

        // Inherited From nw:Conn
        // Modified by Override: nw:CpDom->name
        // Modified by Override: ipmcsnoop:Dom->name
        // Type is an MO-Defined-Type
        leaf name {
            description "Name";

            // Type is an MO-Defined-Type
            type naming_Name {
                length "1..64";
            }
        }

        // Id for this domain    @@@ This comes from the domain id assigned by the
        // PE for the bridge domain
        // Inherited From ipmcsnoop:Dom
        // Type is an MO-Defined-Type
        leaf id {
            config "false";
            description "ID";

            // Type is an MO-Defined-Type
            type l2_DomId;
        }
        leaf encap {
            config "false";
            type string;
        }

        // Admin State
        // Inherited From ipmcsnoop:Dom
        // Type is an MO-Defined-Type
        leaf adminSt {
            config "false";
            description "Admin State";

            // Type is an MO-Defined-Type
            type nw_AdminSt;
        }

        // Controls
        // Inherited From ipmcsnoop:Dom
        // Type is an MO-Defined-Type
        leaf ctrl {
            config "false";
            description "Controls";

            // Type is an MO-Defined-Type
            type ipmcsnoop_DomControl;
        }

        // Flags
        // Inherited From ipmcsnoop:Dom
        // Modified by Override: mldsnoop:Dom->flags
        // Type is an MO-Defined-Type
        leaf flags {
            config "false";
            description "Flags";

            // Type is an MO-Defined-Type
            type ipmcsnoop_DomFlags;
        }

        // Forwarding mode
        // Inherited From ipmcsnoop:Dom
        // Type is an MO-Defined-Type
        leaf fwdMode {
            config "false";
            description "Fowarding Mode";

            // Type is an MO-Defined-Type
            type ipmcsnoop_FwdMode;
        }

        // Number of router interfaces
        // Inherited From ipmcsnoop:Dom
        // Type is an MO-Defined-Type
        leaf numRtrIf {
            config "false";
            description "Router Interfaces";

            // Type is an MO-Defined-Type
            type nw_Counter32;
        }

        // Number of multicast groups
        // Inherited From ipmcsnoop:Dom
        // Type is an MO-Defined-Type
        leaf numMcGrp {
            config "false";
            description "Multicast Groups";

            // Type is an MO-Defined-Type
            type nw_Counter32;
        }

        // Number of Source groups
        // Inherited From ipmcsnoop:Dom
        // Type is an MO-Defined-Type
        leaf numSrcGrp {
            config "false";
            description "Multicast Groups";

            // Type is an MO-Defined-Type
            type nw_Counter32;
        }
        leaf grpFlushTs {
            config "false";
            type uint64;
        }
        leaf nextQueryTs {
            config "false";
            type uint64;
        }
        leaf nextQueryExpTs {
            config "false";
            type uint64;
        }

        // Mrtr Epg Id used when sending packets to mrtr port
        // Inherited From ipmcsnoop:Dom
        // Type is an MO-Defined-Type
        leaf mrtrEpgId {
            config "false";
            description "Mrouter Endpoint Group ID";

            // Type is an MO-Defined-Type
            type l2_DomId;
        }

        // IGMP database
        container db-items {
            list Db-list {
                config "false";
                key "type";

                // Added containment: Prefix=db
                // Acquired From Package mldsnoop
                uses mldsnoop_Db-group;
            }
        }

        // This objects hold per mld domain statistics operational
        // information. This is a singleton within a Dom
        container domstats-items {

            // Added containment as a singleton: Prefix=domstats
            // Acquired From Package mldsnoop
            uses mldsnoop_DomStats-group;
        }

        // Multicast router if that is configured statically
        container strtrif-items {
            list StRtrIf-list {
                key "id";

                // Added containment: Prefix=strtrif
                // Acquired From Package mldsnoop
                uses mldsnoop_StRtrIf-group;
            }
        }

        // Multicast router if    @@@ Mulitcast router if in the BD. These can be either
        // configured by the admin or discovered through protocols
        // like PIM, IGMP, MLD
        container rtrif-items {
            list RtrIf-list {
                config "false";
                key "id";

                // Added containment: Prefix=rtrif
                // Acquired From Package mldsnoop
                uses mldsnoop_RtrIf-group;
            }
        }

        // Querier policy
        container querierp-items {

            // Added containment as a singleton: Prefix=querierp
            // Acquired From Package mldsnoop
            uses mldsnoop_QuerierP-group;
        }

        // Querier state
        container querierst-items {

            // Added containment as a singleton: Prefix=querierst
            // Acquired From Package mldsnoop
            uses mldsnoop_QuerierSt-group;
        }
    }

    grouping mldsnoop_Db-group {

        // Inherited From nw:Conn
        // Modified by Override: nw:Db->name
        // Type is an MO-Defined-Type
        leaf name {
            description "Name";

            // Type is an MO-Defined-Type
            type naming_Name {
                length "1..64";
            }
        }

        // Type of the repository
        // Inherited From ipmcsnoop:Db
        // Type is an MO-Defined-Type
        leaf type {
            config "false";
            description "Type";

            // Type is an MO-Defined-Type
            type ipmcsnoop_DbT;
        }

        // Multicast Group records
        container mcgrp-items {
            list McGrpRec-list {
                config "false";
                key "addr";

                // Added containment: Prefix=mcgrp
                // Acquired From Package mldsnoop
                uses mldsnoop_McGrpRec-group;
            }
        }
    }

    grouping mldsnoop_McGrpRec-group {

        // Inherited From nw:Conn
        // Modified by Override: nw:DbRec->name
        // Type is an MO-Defined-Type
        leaf name {
            description "Name";

            // Type is an MO-Defined-Type
            type naming_Name {
                length "1..64";
            }
        }

        // Group address
        // Inherited From ipmcsnoop:McGrpRec
        // Type is an MO-Defined-Type
        leaf addr {
            config "false";
            description "Multicast Address";

            // Type is an MO-Defined-Type
            type mcast_GrpIp;
        }

        // Version
        // Inherited From ipmcsnoop:McGrpRec
        // Modified by Override: mldsnoop:McGrpRec->ver
        // Type is an MO-Defined-Type
        leaf ver {
            config "false";
            description "Version";

            // Type is an MO-Defined-Type
            type mcast_Ver;
        }

        // Latest reporter
        // Inherited From ipmcsnoop:McGrpRec
        // Type is an MO-Defined-Type
        leaf latReporter {
            config "false";
            description "Latest Reporter";

            // Type is an MO-Defined-Type
            type ipmcsnoop_Reporter;
        }
        leaf oldHostTs {
            config "false";
            type uint64;
        }
        leaf reportTs {
            config "false";
            type uint64;
        }

        // Number of Sources
        // Inherited From ipmcsnoop:McGrpRec
        // Type is an MO-Defined-Type
        leaf numSrc {
            config "false";
            description "Num of Sources";

            // Type is an MO-Defined-Type
            type nw_Counter32;
        }

        // EPG entries in mcast group record
        container epg-items {
            list EpgRec-list {
                config "false";
                key "fabEncap";

                // Added containment: Prefix=epg
                // Acquired From Package mldsnoop
                uses mldsnoop_EpgRec-group;
            }
        }

        // MLD report record snooped by mld-snoop application
        container rep-items {
            list ReportRec-list {
                config "false";
                key "mcastSrc ver";

                // Added containment: Prefix=rep
                // Acquired From Package mldsnoop
                uses mldsnoop_ReportRec-group;
            }
        }
    }

    grouping mldsnoop_EpgRec-group {

        // Inherited From nw:Conn
        // Modified by Override: nw:DbRec->name
        // Type is an MO-Defined-Type
        leaf name {
            description "Name";

            // Type is an MO-Defined-Type
            type naming_Name {
                length "1..64";
            }
        }
        leaf fabEncap {
            config "false";
            type string;
        }

        // Epg id, identified using the circuit endpoint
        // id in the system
        // Inherited From ipmcsnoop:EpgRec
        // Type is an MO-Defined-Type
        leaf id {
            config "false";
            description "Endpoint Group ID";

            // Type is an MO-Defined-Type
            type l2_DomId;
        }

        // Multicast group address (GIPO'), Outer multicast
        // encapsulation ip address for this layer2 domain
        // Inherited From ipmcsnoop:EpgRec
        // Type is an MO-Defined-Type
        leaf mcastEncap {
            config "false";
            description "Multicat Encapsulation";

            // Type is an MO-Defined-Type
            type mcast_GrpIp;
        }

        // MLD report record snooped by mld-snoop application
        container rep-items {
            list ReportRec-list {
                config "false";
                key "mcastSrc ver";

                // Added containment: Prefix=rep
                // Acquired From Package mldsnoop
                uses mldsnoop_ReportRec-group;
            }
        }
    }

    grouping mldsnoop_ReportRec-group {

        // Inherited From nw:Conn
        // Modified by Override: nw:DbRec->name
        // Type is an MO-Defined-Type
        leaf name {
            description "Name";

            // Type is an MO-Defined-Type
            type naming_Name {
                length "1..64";
            }
        }

        // Multicast traffic source
        // Inherited From ipmcsnoop:ReportRec
        // Type is an MO-Defined-Type
        leaf mcastSrc {
            config "false";
            description "Multicast Source";

            // Type is an MO-Defined-Type
            type ipmcsnoop_McastSrc;
        }

        // Version
        // Inherited From ipmcsnoop:ReportRec
        // Modified by Override: mldsnoop:ReportRec->ver
        // Type is an MO-Defined-Type
        leaf ver {
            config "false";
            description "Version";

            // Type is an MO-Defined-Type
            type mcast_Ver;
        }

        // Filter mode
        // Inherited From ipmcsnoop:ReportRec
        // Type is an MO-Defined-Type
        leaf filtMode {
            config "false";
            description "Filter Mode";

            // Type is an MO-Defined-Type
            type mcast_FiltMode;
        }

        // Filter mode
        // Inherited From ipmcsnoop:ReportRec
        // Type is an MO-Defined-Type
        leaf flags {
            config "false";
            description "Flags";

            // Type is an MO-Defined-Type
            type ipmcsnoop_RepFlags;
        }

        // OIF list (outgoing interface list)
        container oif-items {
            list OIFRec-list {
                config "false";
                key "id";

                // Added containment: Prefix=oif
                // Acquired From Package mldsnoop
                uses mldsnoop_OIFRec-group;
            }
        }
    }

    grouping mldsnoop_OIFRec-group {

        // Inherited From nw:Conn
        // Modified by Override: nw:DbRec->name
        // Type is an MO-Defined-Type
        leaf name {
            description "Name";

            // Type is an MO-Defined-Type
            type naming_Name {
                length "1..64";
            }
        }

        // Multicast traffic source
        // Inherited From ipmcsnoop:OIFRec
        // Type is an MO-Defined-Type
        leaf id {
            config "false";
            description "ID";

            // Type is an MO-Defined-Type
            type nw_IfId;
        }
        leaf numGqMiss {
            config "false";
            type uint16;
        }
        leaf expireTs {
            config "false";
            type uint64;
        }

        // Host Record List (Used for Explicit Host Tracking)
        container host-items {
            list HostRec-list {
                config "false";
                key "addr";

                // Added containment: Prefix=host
                // Acquired From Package mldsnoop
                uses mldsnoop_HostRec-group;
            }
        }
    }

    grouping mldsnoop_HostRec-group {

        // Inherited From nw:Conn
        // Modified by Override: nw:DbRec->name
        // Type is an MO-Defined-Type
        leaf name {
            description "Name";

            // Type is an MO-Defined-Type
            type naming_Name {
                length "1..64";
            }
        }
        leaf addr {
            config "false";
            type address_Ip;
        }
        leaf upTs {
            config "false";
            type uint64;
        }
        leaf lastJoinTs {
            config "false";
            type uint64;
        }
        leaf nextExpiryTs {
            config "false";
            type uint64;
        }
    }

    grouping mldsnoop_DomStats-group {

        // V1 Reports received
        // Type is an MO-Defined-Type
        leaf v1RepRcvd {
            config "false";
            description "V1 Reports Received";

            // Type is an MO-Defined-Type
            type nw_Counter32;
        }

        // V1 Leave received
        // Type is an MO-Defined-Type
        leaf v1LeaveRcvd {
            config "false";
            description "V1 Leave Received";

            // Type is an MO-Defined-Type
            type nw_Counter32;
        }

        // V1 Query received
        // Type is an MO-Defined-Type
        leaf v1QueryRcvd {
            config "false";
            description "V1 Query Received";

            // Type is an MO-Defined-Type
            type nw_Counter32;
        }

        // V1 Reports suppressed
        // Type is an MO-Defined-Type
        leaf v1RepSupr {
            config "false";
            description "V1 Reports Suppressed";

            // Type is an MO-Defined-Type
            type nw_Counter32;
        }

        // V1 leaves suppressed
        // Type is an MO-Defined-Type
        leaf v1LeaveSupr {
            config "false";
            description "V1 Leaves Suppressed";

            // Type is an MO-Defined-Type
            type nw_Counter32;
        }

        // V1 Proxy Report Originated
        // Type is an MO-Defined-Type
        leaf v1RepOrig {
            config "false";
            description "V1 Reports Originated";

            // Type is an MO-Defined-Type
            type nw_Counter32;
        }

        // V1 Proxy Leave Originated
        // Type is an MO-Defined-Type
        leaf v1LeaveOrig {
            config "false";
            description "V1 Leaves Originated";

            // Type is an MO-Defined-Type
            type nw_Counter32;
        }

        // V2 Reports received
        // Type is an MO-Defined-Type
        leaf v2RepRcvd {
            config "false";
            description "V2 Reports Received";

            // Type is an MO-Defined-Type
            type nw_Counter32;
        }

        // V2 Query received
        // Type is an MO-Defined-Type
        leaf v2QueryRcvd {
            config "false";
            description "V2 Query Received";

            // Type is an MO-Defined-Type
            type nw_Counter32;
        }

        // V2 Group Record suppressed
        // Type is an MO-Defined-Type
        leaf v2GrpRecSupr {
            config "false";
            description "V2 Group Records Suppressed";

            // Type is an MO-Defined-Type
            type nw_Counter32;
        }

        // V2 Proxy Report Originated
        // Type is an MO-Defined-Type
        leaf v2RepOrig {
            config "false";
            description "V2 Reports Originated";

            // Type is an MO-Defined-Type
            type nw_Counter32;
        }
        leaf lastClearTs {
            config "false";
            type uint64;
        }

        // packets received
        // Inherited From ipmcsnoop:DomStats
        // Type is an MO-Defined-Type
        leaf pktsRcvd {
            config "false";
            description "Packets Received";

            // Type is an MO-Defined-Type
            type nw_Counter32;
        }

        // Pim Hello Rcvd
        // Inherited From ipmcsnoop:DomStats
        // Type is an MO-Defined-Type
        leaf pimHelloRcvd {
            config "false";
            description "Pim Hello Received";

            // Type is an MO-Defined-Type
            type nw_Counter32;
        }

        // Invalid Query Rcvd
        // Inherited From ipmcsnoop:DomStats
        // Type is an MO-Defined-Type
        leaf invQueryRcvd {
            config "false";
            description "Invalid Query Received";

            // Type is an MO-Defined-Type
            type nw_Counter32;
        }

        // Invalid Report Rcvd
        // Inherited From ipmcsnoop:DomStats
        // Type is an MO-Defined-Type
        leaf invRepRcvd {
            config "false";
            description "Invalid Report Received";

            // Type is an MO-Defined-Type
            type nw_Counter32;
        }

        // Version Mismatch Rcvd
        // Inherited From ipmcsnoop:DomStats
        // Type is an MO-Defined-Type
        leaf verMisMatchRcvd {
            config "false";
            description "Version Mismatch Received";

            // Type is an MO-Defined-Type
            type nw_Counter32;
        }

        // Unknown Packets Rcvd
        // Inherited From ipmcsnoop:DomStats
        // Type is an MO-Defined-Type
        leaf unknPktRcvd {
            config "false";
            description "Unknown Packets Received";

            // Type is an MO-Defined-Type
            type nw_Counter32;
        }

        // Query Originated
        // Inherited From ipmcsnoop:DomStats
        // Type is an MO-Defined-Type
        leaf queryPktsOrig {
            config "false";
            description "Query Packets Originated";

            // Type is an MO-Defined-Type
            type nw_Counter32;
        }

        // Packets Sent to Router Ports
        // Inherited From ipmcsnoop:DomStats
        // Type is an MO-Defined-Type
        leaf pktsToRport {
            config "false";
            description "Packets to Router Ports";

            // Type is an MO-Defined-Type
            type nw_Counter32;
        }

        // VPC Sync Packets Sent to Peer
        // Inherited From ipmcsnoop:DomStats
        // Type is an MO-Defined-Type
        leaf vpcSyncSent {
            config "false";
            description "VPC Sync Packets Sent";

            // Type is an MO-Defined-Type
            type nw_Counter32;
        }

        // VPC Sync Packets Rcvd from Peer
        // Inherited From ipmcsnoop:DomStats
        // Type is an MO-Defined-Type
        leaf vpcSyncRcvd {
            config "false";
            description "VPC Sync Packets Received";

            // Type is an MO-Defined-Type
            type nw_Counter32;
        }

        // VPC Sync Packets Failed to send to Peer
        // Inherited From ipmcsnoop:DomStats
        // Type is an MO-Defined-Type
        leaf vpcSyncFail {
            config "false";
            description "VPC Sync Packets Failed";

            // Type is an MO-Defined-Type
            type nw_Counter32;
        }

        // MRD Sync Packets Sent to Peer
        // Inherited From ipmcsnoop:DomStats
        // Type is an MO-Defined-Type
        leaf mrdSyncSent {
            config "false";
            description "MRD Sync Packets Sent";

            // Type is an MO-Defined-Type
            type nw_Counter32;
        }

        // MRD Sync Packets Rcvd from Peer
        // Inherited From ipmcsnoop:DomStats
        // Type is an MO-Defined-Type
        leaf mrdSyncRcvd {
            config "false";
            description "MRD Sync Packets Received";

            // Type is an MO-Defined-Type
            type nw_Counter32;
        }

        // MRD Sync Packets Failed to send to Peer
        // Inherited From ipmcsnoop:DomStats
        // Type is an MO-Defined-Type
        leaf mrdSyncFail {
            config "false";
            description "MRD Sync Packets Failed";

            // Type is an MO-Defined-Type
            type nw_Counter32;
        }
    }

    grouping mldsnoop_StRtrIf-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }
        leaf encap {
            config "false";
            type string;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping mldsnoop_RtrIf-group {

        // Identifier for the if
        // Inherited From ipmcsnoop:RtrIf
        // Type is an MO-Defined-Type
        leaf id {
            config "false";
            description "ID";

            // Type is an MO-Defined-Type
            type nw_IfId;
        }

        // Life cycle control
        // Inherited From ipmcsnoop:RtrIf
        // Type is an MO-Defined-Type
        leaf lcC {
            config "false";
            description "Life Cycle Control";

            // Type is an MO-Defined-Type
            type ipmcsnoop_LcC;
        }
        leaf upTs {
            config "false";
            type uint64;
        }
        leaf nextExpiryTs {
            config "false";
            type uint64;
        }
    }

    grouping mldsnoop_QuerierP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Querier version
        // Inherited From mcast:AQuerier
        // Modified by Override: mldsnoop:QuerierP->ver
        // Type is an MO-Defined-Type
        leaf ver {
            description "Version";

            // Type is an MO-Defined-Type
            type mcast_Ver;
        }

        // Querier IP address
        // Inherited From mcast:AQuerier
        // Type is an MO-Defined-Type
        leaf addr {
            description "Address";

            // Type is an MO-Defined-Type
            type mcast_QuerierIp;
        }

        // Query interval
        // Inherited From mcast:AQuerier
        // Type is an MO-Defined-Type
        leaf queryIntvl {
            description "Query Interval";

            // Type is an MO-Defined-Type
            type mcast_QueryIntvl;
        }

        // Query response interval
        // Inherited From mcast:AQuerier
        // Type is an MO-Defined-Type
        leaf rspIntvl {
            description "Response Interval";

            // Type is an MO-Defined-Type
            type mcast_QueryRspIntvl;
        }

        // Robustness factor
        // Inherited From mcast:AQuerier
        // Type is an MO-Defined-Type
        leaf robustFac {
            description "Robustness Factor";

            // Type is an MO-Defined-Type
            type mcast_RobustFactor;
        }

        // Startup query interval
        // Inherited From mcast:AQuerier
        // Type is an MO-Defined-Type
        leaf startQueryIntvl {
            description "Startup Query Interval";

            // Type is an MO-Defined-Type
            type mcast_StartQueryIntvl;
        }

        // Startup query count
        // Inherited From mcast:AQuerier
        // Type is an MO-Defined-Type
        leaf startQueryCnt {
            description "Startup Query Count";

            // Type is an MO-Defined-Type
            type mcast_QueryCnt;
        }

        // Last member query interval
        // Inherited From ipmcsnoop:QuerierP
        // Type is an MO-Defined-Type
        leaf lastMbrIntvl {
            config "false";
            description "Last Member Query Interval";

            // Type is an MO-Defined-Type
            type mcast_LastMbrQueryIntvl;
        }
    }

    grouping mldsnoop_QuerierSt-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Querier version
        // Inherited From mcast:AQuerier
        // Modified by Override: mldsnoop:QuerierSt->ver
        // Type is an MO-Defined-Type
        leaf ver {
            description "Version";

            // Type is an MO-Defined-Type
            type mcast_Ver;
        }

        // Querier IP address
        // Inherited From mcast:AQuerier
        // Type is an MO-Defined-Type
        leaf addr {
            description "Address";

            // Type is an MO-Defined-Type
            type mcast_QuerierIp;
        }

        // Query interval
        // Inherited From mcast:AQuerier
        // Type is an MO-Defined-Type
        leaf queryIntvl {
            description "Query Interval";

            // Type is an MO-Defined-Type
            type mcast_QueryIntvl;
        }

        // Query response interval
        // Inherited From mcast:AQuerier
        // Type is an MO-Defined-Type
        leaf rspIntvl {
            description "Response Interval";

            // Type is an MO-Defined-Type
            type mcast_QueryRspIntvl;
        }

        // Robustness factor
        // Inherited From mcast:AQuerier
        // Type is an MO-Defined-Type
        leaf robustFac {
            description "Robustness Factor";

            // Type is an MO-Defined-Type
            type mcast_RobustFactor;
        }

        // Startup query interval
        // Inherited From mcast:AQuerier
        // Type is an MO-Defined-Type
        leaf startQueryIntvl {
            description "Startup Query Interval";

            // Type is an MO-Defined-Type
            type mcast_StartQueryIntvl;
        }

        // Startup query count
        // Inherited From mcast:AQuerier
        // Type is an MO-Defined-Type
        leaf startQueryCnt {
            description "Startup Query Count";

            // Type is an MO-Defined-Type
            type mcast_QueryCnt;
        }

        // Last member query interval
        // Inherited From ipmcsnoop:QuerierP
        // Type is an MO-Defined-Type
        leaf lastMbrIntvl {
            config "false";
            description "Last Member Query Interval";

            // Type is an MO-Defined-Type
            type mcast_LastMbrQueryIntvl;
        }

        // Interface on which the querier is present
        // Inherited From ipmcsnoop:QuerierSt
        // Type is an MO-Defined-Type
        leaf if {
            config "false";
            description "Interface";

            // Type is an MO-Defined-Type
            type nw_IfId;
        }

        // Querier timeout
        // Inherited From ipmcsnoop:QuerierSt
        // Type is an MO-Defined-Type
        leaf timeout {
            config "false";
            description "Timeout";

            // Type is an MO-Defined-Type
            type mcast_QuerierTimeout;
        }

        // Querier flags
        // Inherited From ipmcsnoop:QuerierSt
        // Type is an MO-Defined-Type
        leaf flags {
            config "false";
            description "Flags";

            // Type is an MO-Defined-Type
            type ipmcsnoop_QuerierFlags;
        }
    }

    grouping mldsnoop_InstStats-group {

        // Total Number of multicast groups
        // Inherited From ipmcsnoop:InstStats
        // Type is an MO-Defined-Type
        leaf totNumMcGrp {
            config "false";
            description "Total Number of Multicast Groups";

            // Type is an MO-Defined-Type
            type nw_Counter32;
        }

        // packets received
        // Inherited From ipmcsnoop:InstStats
        // Type is an MO-Defined-Type
        leaf pktsRcvd {
            config "false";
            description "Packets Received";

            // Type is an MO-Defined-Type
            type nw_Counter32;
        }

        // Invalid packets received
        // Inherited From ipmcsnoop:InstStats
        // Type is an MO-Defined-Type
        leaf invPktsRcvd {
            config "false";
            description "Invalid Packets Received";

            // Type is an MO-Defined-Type
            type nw_Counter32;
        }

        // Loopback packets received
        // Inherited From ipmcsnoop:InstStats
        // Type is an MO-Defined-Type
        leaf lpbkPktsRcvd {
            config "false";
            description "Loopback Packets Received";

            // Type is an MO-Defined-Type
            type nw_Counter32;
        }

        // packets Flooded
        // Inherited From ipmcsnoop:InstStats
        // Type is an MO-Defined-Type
        leaf pktsFlooded {
            config "false";
            description "Packets Flooded";

            // Type is an MO-Defined-Type
            type nw_Counter32;
        }

        // MRD Loopback packets received
        // Inherited From ipmcsnoop:InstStats
        // Type is an MO-Defined-Type
        leaf mrdLpbkPktsRcvd {
            config "false";
            description "MRD Loopback Packets Received";

            // Type is an MO-Defined-Type
            type nw_Counter32;
        }

        // No Vlan DB packets received
        // Inherited From ipmcsnoop:InstStats
        // Type is an MO-Defined-Type
        leaf noVlanDbPktsRcvd {
            config "false";
            description "No Vlan Db Packets Received";

            // Type is an MO-Defined-Type
            type nw_Counter32;
        }

        // Vpc ZMQ packets sent
        // Inherited From ipmcsnoop:InstStats
        // Type is an MO-Defined-Type
        leaf vpcZmqPktsSent {
            config "false";
            description "VPC ZMQ Packets Sent";

            // Type is an MO-Defined-Type
            type nw_Counter32;
        }

        // Vpc ZMQ packets received
        // Inherited From ipmcsnoop:InstStats
        // Type is an MO-Defined-Type
        leaf vpcZmqPktsRcvd {
            config "false";
            description "VPC ZMQ Packets Received";

            // Type is an MO-Defined-Type
            type nw_Counter32;
        }

        // Vpc ZMQ packets send Fail
        // Inherited From ipmcsnoop:InstStats
        // Type is an MO-Defined-Type
        leaf vpcZmqPktsSentFail {
            config "false";
            description "VPC ZMQ Packets Send Fail";

            // Type is an MO-Defined-Type
            type nw_Counter32;
        }

        // Vpc ZMQ packets receive Fail
        // Inherited From ipmcsnoop:InstStats
        // Type is an MO-Defined-Type
        leaf vpcZmqPktsRcvdFail {
            config "false";
            description "VPC ZMQ Packets Receive Fail";

            // Type is an MO-Defined-Type
            type nw_Counter32;
        }

        // Vpc Peer packets sent
        // Inherited From ipmcsnoop:InstStats
        // Type is an MO-Defined-Type
        leaf vpcPeerPktsSent {
            config "false";
            description "VPC Peer Packets Sent";

            // Type is an MO-Defined-Type
            type nw_Counter32;
        }

        // Vpc Peer packets received
        // Inherited From ipmcsnoop:InstStats
        // Type is an MO-Defined-Type
        leaf vpcPeerPktsRcvd {
            config "false";
            description "VPC Peer Packets Received";

            // Type is an MO-Defined-Type
            type nw_Counter32;
        }

        // Vpc Peer packets send Fail
        // Inherited From ipmcsnoop:InstStats
        // Type is an MO-Defined-Type
        leaf vpcPeerPktsSentFail {
            config "false";
            description "VPC Peer Packets Send Fail";

            // Type is an MO-Defined-Type
            type nw_Counter32;
        }

        // Vpc Peer packets receive Fail
        // Inherited From ipmcsnoop:InstStats
        // Type is an MO-Defined-Type
        leaf vpcPeerPktsRcvdFail {
            config "false";
            description "VPC Peer Packets Receive Fail";

            // Type is an MO-Defined-Type
            type nw_Counter32;
        }
    }

    grouping mpls_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds mpls information that is operated at a
        // interface level
        container If-items {
            list If-list {
                key "id";

                // Added containment: Prefix=If
                // Acquired From Package mpls
                uses mpls_If-group;
            }
        }
    }

    grouping mpls_If-group {

        // Type is an MO-Defined-Type
        leaf operSt {
            config "false";
            description "Administrative state of interface";

            // Type is an MO-Defined-Type
            type mpls_OperSt;
        }
        leaf deleted {
            config "false";
            type boolean;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping mplsstatic_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // MPLS Static address family domain
        container af-items {
            list Af-list {
                key "type";

                // Added containment: Prefix=af
                // Acquired From Package mplsstatic
                uses mplsstatic_Af-group;
            }
        }
    }

    grouping mplsstatic_Af-group {

        // Type
        // Type is an MO-Defined-Type
        leaf type {
            description "Type";

            // Type is an MO-Defined-Type
            type mplsstatic_AfT;
        }

        // Inherited From nw:Conn
        // Modified by Override: nw:CpDom->name
        // Type is an MO-Defined-Type
        leaf name {
            description "Name";

            // Type is an MO-Defined-Type
            type naming_Name {
                length "1..64";
            }
        }

        // Prefix local label
        container pfxlabel-items {
            list PfxLclLbl-list {
                key "label";

                // Added containment: Prefix=pfxlabel
                // Acquired From Package mplsstatic
                uses mplsstatic_PfxLclLbl-group;
            }
        }

        // Named LSP
        container lsp-items {
            list NamedLSP-list {
                key "name";

                // Added containment: Prefix=lsp
                // Acquired From Package mplsstatic
                uses mplsstatic_NamedLSP-group;
            }
        }
    }

    grouping mplsstatic_PfxLclLbl-group {
        leaf pfx {
            type address_Ip;
        }

        // Inherited From mplsstatic:BaseLclLbl
        // Type is an MO-Defined-Type
        leaf label {
            description "Label";

            // Type is an MO-Defined-Type
            type mplsstatic_InLabelVal;
        }

        // This object holds primary nexthop information
        // for prefix local label
        container nh-items {

            // Added containment as a singleton: Prefix=nh
            // Acquired From Package mplsstatic
            uses mplsstatic_Nh-group;
        }

        // This object holds auto resolve nexthop information
        // for prefix local label
        container autoresolvenh-items {

            // Added containment as a singleton: Prefix=autoresolvenh
            // Acquired From Package mplsstatic
            uses mplsstatic_AutoResolveNh-group;
        }

        // This object holds backup nexthop information
        // for prefix local label
        container backupnh-items {

            // Added containment as a singleton: Prefix=backupnh
            // Acquired From Package mplsstatic
            uses mplsstatic_BackupNh-group;
        }
    }

    grouping mplsstatic_Nh-group {

        // Type is an MO-Defined-Type
        leaf outLbl {
            description "Outgoing label";

            // Type is an MO-Defined-Type
            type mplsstatic_OutLabelVal;
        }
        leaf nhAddr {
            type address_Ip;
        }
    }

    grouping mplsstatic_AutoResolveNh-group {

        // Type is an MO-Defined-Type
        leaf outLbl {
            description "Outgoing label";

            // Type is an MO-Defined-Type
            type mplsstatic_OutLabelVal;
        }
    }

    grouping mplsstatic_BackupNh-group {

        // Type is an MO-Defined-Type
        leaf outLbl {
            description "Outgoing label";

            // Type is an MO-Defined-Type
            type mplsstatic_OutLabelVal;
        }
        leaf nhAddr {
            type address_Ip;
        }

        // Type is an MO-Defined-Type
        leaf if {
            description "Next Hop Interface";

            // Type is an MO-Defined-Type
            type nw_IfId;
        }
    }

    grouping mplsstatic_NamedLSP-group {
        leaf name {
            type string;
        }

        // Cross-connect local label
        container xclabel-items {
            list XcLclLbl-list {
                key "label";

                // Added containment: Prefix=xclabel
                // Acquired From Package mplsstatic
                uses mplsstatic_XcLclLbl-group;
            }
        }

        // Policy local label
        container pollabel-items {
            list PolicyLclLbl-list {
                key "label";

                // Added containment: Prefix=pollabel
                // Acquired From Package mplsstatic
                uses mplsstatic_PolicyLclLbl-group;
            }
        }
    }

    grouping mplsstatic_XcLclLbl-group {
        leaf name {
            type string;
        }

        // Inherited From mplsstatic:BaseLclLbl
        // Type is an MO-Defined-Type
        leaf label {
            description "Label";

            // Type is an MO-Defined-Type
            type mplsstatic_InLabelVal;
        }

        // This object holds primary nexthop information
        // for cross-connect local label
        container nh-items {
            list XcNh-list {
                key "pathId";

                // Added containment: Prefix=nh
                // Acquired From Package mplsstatic
                uses mplsstatic_XcNh-group;
            }
        }
    }

    grouping mplsstatic_XcNh-group {
        leaf outLblStack {
            type string;
        }
        leaf pathId {
            type uint16;
        }
        leaf nhAddr {
            type address_Ip;
        }
    }

    grouping mplsstatic_PolicyLclLbl-group {
        leaf pfx {
            type address_Ip;
        }
        leaf name {
            type string;
        }

        // Inherited From mplsstatic:BaseLclLbl
        // Type is an MO-Defined-Type
        leaf label {
            description "Label";

            // Type is an MO-Defined-Type
            type mplsstatic_InLabelVal;
        }

        // This object holds primary nexthop information
        // for policy local label
        container nh-items {
            list PolNh-list {
                key "pathId";

                // Added containment: Prefix=nh
                // Acquired From Package mplsstatic
                uses mplsstatic_PolNh-group;
            }
        }
    }

    grouping mplsstatic_PolNh-group {
        leaf outLblStack {
            type string;
        }
        leaf pathId {
            type uint16;
        }
        leaf nhAddr {
            type address_Ip;
        }
    }

    grouping ulib_LabelTable-group {

        // Type is an MO-Defined-Type
        leaf operLabels {
            config "false";
            description "Total Number of Labels";

            // Type is an MO-Defined-Type
            type ulib_LabelCnt;
        }

        // Type is an MO-Defined-Type
        leaf operIPv4Prefixes {
            config "false";
            description "Total Number of IPv4 Prefixes";

            // Type is an MO-Defined-Type
            type ulib_LabelCnt;
        }

        // Type is an MO-Defined-Type
        leaf operIPv6Prefixes {
            config "false";
            description "Total Number of IPv6 Prefixes";

            // Type is an MO-Defined-Type
            type ulib_LabelCnt;
        }

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Label Table Clients
        container client-items {
            list Clients-list {
                config "false";
                key "name";

                // Added containment: Prefix=client
                // Acquired From Package ulib
                uses ulib_Clients-group;
            }
        }

        // Label Range
        container lblrange-items {

            // Added containment as a singleton: Prefix=lblrange
            // Acquired From Package ulib
            uses ulib_LblRange-group;
        }

        // Labels
        container lbl-items {
            list Labels-list {
                config "false";
                key "label";

                // Added containment: Prefix=lbl
                // Acquired From Package ulib
                uses ulib_Labels-group;
            }
        }
    }

    grouping ulib_Clients-group {
        leaf name {
            config "false";
            type string;
        }
        leaf index {
            config "false";
            type uint32;
        }
        leaf uuid {
            config "false";
            type uint32;
        }
        leaf mtsSap {
            config "false";
            type uint32;
        }
        leaf staleTime {
            config "false";
            type uint64;
        }

        // Type is an MO-Defined-Type
        leaf flag {
            config "false";
            description "Flag for the client";

            // Type is an MO-Defined-Type
            type ulib_ClientFlag;
        }
        leaf regMsg {
            config "false";
            type uint32;
        }
        leaf convMsg {
            config "false";
            type uint32;
        }
        leaf fecMsg {
            config "false";
            type uint32;
        }
        leaf fecAdd {
            config "false";
            type uint32;
        }
        leaf ileAdd {
            config "false";
            type uint32;
        }
        leaf fecDel {
            config "false";
            type uint32;
        }
        leaf ileDel {
            config "false";
            type uint32;
        }
        leaf lastXid {
            config "false";
            type uint32;
        }
        leaf fecAck {
            config "false";
            type uint32;
        }
    }

    grouping ulib_LblRange-group {

        // Config : Dynamic Label Range
        // Type is an MO-Defined-Type
        leaf dynLblMin {
            description "Minimum Dynamic label";

            // Type is an MO-Defined-Type
            type ulib_DynLblMin;
        }

        // Type is an MO-Defined-Type
        leaf dynLblMax {
            description "Maximum Dynamic label";

            // Type is an MO-Defined-Type
            type ulib_DynLblMax;
        }

        // Config : Static Label Range
        // Type is an MO-Defined-Type
        leaf staticLblMin {
            description "Minimum Static Label";

            // Type is an MO-Defined-Type
            type ulib_LabelVal;
        }

        // Type is an MO-Defined-Type
        leaf staticLblMax {
            description "Maximum Static Label";

            // Type is an MO-Defined-Type
            type ulib_LabelVal;
        }

        // Config : Segment Routing Label Range
        // Type is an MO-Defined-Type
        leaf srLblMin {
            description "Segment Routing Global Block Min label";

            // Type is an MO-Defined-Type
            type ulib_LabelVal;
        }

        // Type is an MO-Defined-Type
        leaf srLblMax {
            description "Segment Routing Global Block Max label";

            // Type is an MO-Defined-Type
            type ulib_LabelVal;
        }

        // Oper : Dynamic Label Range
        // Type is an MO-Defined-Type
        leaf operDynLblMin {
            config "false";
            description "Minimum Dynamic label";

            // Type is an MO-Defined-Type
            type ulib_LabelVal;
        }

        // Type is an MO-Defined-Type
        leaf operDynLblMax {
            config "false";
            description "Maximum Dynamic label";

            // Type is an MO-Defined-Type
            type ulib_LabelVal;
        }

        // Oper : Static Label Range
        // Type is an MO-Defined-Type
        leaf operStaticLblMin {
            config "false";
            description "Minimum Static Label";

            // Type is an MO-Defined-Type
            type ulib_LabelVal;
        }

        // Type is an MO-Defined-Type
        leaf operStaticLblMax {
            config "false";
            description "Maximum Static Label";

            // Type is an MO-Defined-Type
            type ulib_LabelVal;
        }

        // Oper : Segment Routing Label Range
        // Type is an MO-Defined-Type
        leaf operSRLblMin {
            config "false";
            description "Segment Routing Global Block Min label";

            // Type is an MO-Defined-Type
            type ulib_LabelVal;
        }

        // Type is an MO-Defined-Type
        leaf operSRLblMax {
            config "false";
            description "Segment Routing Global Block Max label";

            // Type is an MO-Defined-Type
            type ulib_LabelVal;
        }

        // Fault : Static Labels Out Of Range
        // Type is an MO-Defined-Type
        leaf operStaticLblsOutOfRange {
            config "false";
            description "Number of Static Labels Out Of Range";

            // Type is an MO-Defined-Type
            type ulib_LabelCnt;
        }
    }

    grouping ulib_Labels-group {
        leaf label {
            config "false";
            type uint32;
        }
        leaf fecType {
            config "false";
            type string;
        }
        leaf labelByteStats {
            config "false";
            type uint64;
        }
        leaf labelPacketStats {
            config "false";
            type uint64;
        }

        // IPv4 FEC
        container FecIPv4-items {

            // Added containment as a singleton: Prefix=FecIPv4
            // Acquired From Package ulib
            uses ulib_FecIPv4-group;
        }

        // IPv6 FEC
        container FecIPv6-items {

            // Added containment as a singleton: Prefix=FecIPv6
            // Acquired From Package ulib
            uses ulib_FecIPv6-group;
        }

        // Policy IPv4 FEC
        container FecPolicyIPv4-items {

            // Added containment as a singleton: Prefix=FecPolicyIPv4
            // Acquired From Package ulib
            uses ulib_FecPolicyIPv4-group;
        }

        // Policy IPv6 FEC
        container FecPolicyIPv6-items {

            // Added containment as a singleton: Prefix=FecPolicyIPv6
            // Acquired From Package ulib
            uses ulib_FecPolicyIPv6-group;
        }

        // None FEC
        container FecNone-items {

            // Added containment as a singleton: Prefix=FecNone
            // Acquired From Package ulib
            uses ulib_FecNone-group;
        }

        // Per-CE FEC
        container FecPerCE-items {

            // Added containment as a singleton: Prefix=FecPerCE
            // Acquired From Package ulib
            uses ulib_FecPerCE-group;
        }

        // Reserved FEC
        container FecReserved-items {

            // Added containment as a singleton: Prefix=FecReserved
            // Acquired From Package ulib
            uses ulib_FecReserved-group;
        }

        // Deagg FEC
        container FecDeagg-items {

            // Added containment as a singleton: Prefix=FecDeagg
            // Acquired From Package ulib
            uses ulib_FecDeagg-group;
        }

        // NHLFE
        container Nhlfe-items {
            list Nhlfe-list {
                config "false";
                key "idx";

                // Added containment: Prefix=Nhlfe
                // Acquired From Package ulib
                uses ulib_Nhlfe-group;
            }
        }
    }

    grouping ulib_FecIPv4-group {
        leaf fecType {
            config "false";
            type string;
        }
        leaf state {
            config "false";
            type string;
        }
        leaf tableId {
            config "false";
            type string;
        }
        leaf prefix {
            config "false";
            type string;
        }
        leaf maskLength {
            config "false";
            type uint8;
        }
    }

    grouping ulib_FecIPv6-group {
        leaf fecType {
            config "false";
            type string;
        }
        leaf state {
            config "false";
            type string;
        }
        leaf tableId {
            config "false";
            type string;
        }
        leaf prefix {
            config "false";
            type string;
        }
        leaf maskLength {
            config "false";
            type uint8;
        }
    }

    grouping ulib_FecPolicyIPv4-group {
        leaf fecType {
            config "false";
            type string;
        }
        leaf state {
            config "false";
            type string;
        }
        leaf tableId {
            config "false";
            type string;
        }
        leaf prefix {
            config "false";
            type string;
        }
        leaf maskLength {
            config "false";
            type uint8;
        }
    }

    grouping ulib_FecPolicyIPv6-group {
        leaf fecType {
            config "false";
            type string;
        }
        leaf state {
            config "false";
            type string;
        }
        leaf tableId {
            config "false";
            type string;
        }
        leaf prefix {
            config "false";
            type string;
        }
        leaf maskLength {
            config "false";
            type uint8;
        }
    }

    grouping ulib_FecNone-group {
        leaf label {
            config "false";
            type uint32;
        }
        leaf fecType {
            config "false";
            type string;
        }
        leaf state {
            config "false";
            type string;
        }
    }

    grouping ulib_FecPerCE-group {
        leaf nextHopSet {
            config "false";
            type uint32;
        }
        leaf addressFamily {
            config "false";
            type string;
        }
        leaf fecType {
            config "false";
            type string;
        }
        leaf state {
            config "false";
            type string;
        }
        leaf tableId {
            config "false";
            type string;
        }
    }

    grouping ulib_FecReserved-group {
        leaf fecType {
            config "false";
            type string;
        }
        leaf state {
            config "false";
            type string;
        }
        leaf tableId {
            config "false";
            type string;
        }
    }

    grouping ulib_FecDeagg-group {
        leaf fecType {
            config "false";
            type string;
        }
        leaf state {
            config "false";
            type string;
        }
        leaf tableId {
            config "false";
            type string;
        }
    }

    grouping ulib_Nhlfe-group {
        leaf idx {
            config "false";
            type uint32;
        }
        leaf ip {
            config "false";
            type string;
        }
        leaf outLabel {
            config "false";
            type string;
        }
        leaf interface {
            config "false";
            type string;
        }
        leaf outLabelByteStats {
            config "false";
            type uint64;
        }
        leaf outLabelPacketStats {
            config "false";
            type uint64;
        }
    }

    grouping mrib_Entity-group {

        // This objects hold per mrib instance information
        container inst-items {

            // Added containment as a singleton: Prefix=inst
            // Acquired From Package mrib
            uses mrib_Inst-group;
        }
    }

    grouping mrib_Inst-group {

        // This object holds mrib route db information
        container routeDb-items {

            // Added containment as a singleton: Prefix=routeDb
            // Acquired From Package mrib
            uses mrib_RouteDb-group;
        }
    }

    grouping mrib_RouteDb-group {

        // This objects hold per pim domain (vrf) information
        container vrf-items {
            list Vrf-list {
                key "name";

                // Added containment: Prefix=vrf
                // Acquired From Package mrib
                uses mrib_Vrf-group;
            }
        }
    }

    grouping mrib_Vrf-group {
        leaf name {
            type string;
        }
        leaf totalNumRoutes {
            config "false";
            type uint32;
        }
        leaf starGRoute {
            config "false";
            type uint32;
        }
        leaf sgRoute {
            config "false";
            type uint32;
        }
        leaf starGPrfx {
            config "false";
            type uint32;
        }

        // This object holds mrib route group information
        container group-items {
            list Group-list {
                key "grpAddr";

                // Added containment: Prefix=group
                // Acquired From Package mrib
                uses mrib_Group-group;
            }
        }
    }

    grouping mrib_Group-group {
        leaf grpAddr {
            type address_Ip;
        }
        leaf grpMasklen {
            config "false";
            type uint32;
        }
        leaf bidir {
            config "false";
            type boolean;
        }

        // This object holds mrib route source information
        container source-items {
            list Source-list {
                key "srcAddr";

                // Added containment: Prefix=source
                // Acquired From Package mrib
                uses mrib_Source-group;
            }
        }
    }

    grouping mrib_Source-group {
        leaf srcAddr {
            type address_Ip;
        }
        leaf pending {
            config "false";
            type boolean;
        }
        leaf uptime {
            config "false";
            type uint64;
        }
        leaf oifcount {
            config "false";
            type uint32;
        }
        leaf statsPkts {
            config "false";
            type uint32;
        }
        leaf statsBytes {
            config "false";
            type uint32;
        }
        leaf statsRateBuf {
            config "false";
            type string;
        }
        leaf lispSrcRloc {
            config "false";
            type string;
        }
        leaf routeIif {
            config "false";
            type string;
        }
        leaf rpfNbr {
            config "false";
            type string;
        }
        leaf internal {
            config "false";
            type boolean;
        }
        leaf rpfNbrUptime {
            config "false";
            type uint64;
        }
        leaf fabricOif {
            config "false";
            type boolean;
        }
        leaf fabricLoser {
            config "false";
            type boolean;
        }
        leaf numVpcSviOifs {
            config "false";
            type uint32;
        }
        leaf routeMdtIod {
            config "false";
            type boolean;
        }
        leaf mdtEncapIndex {
            config "false";
            type uint32;
        }

        // This object holds mrib mpib information
        container mpib-items {
            list Mpib-list {
                key "mpibName";

                // Added containment: Prefix=mpib
                // Acquired From Package mrib
                uses mrib_Mpib-group;
            }
        }

        // This object holds mrib OIF information
        container oif-items {
            list Oif-list {
                key "oifName";

                // Added containment: Prefix=oif
                // Acquired From Package mrib
                uses mrib_Oif-group;
            }
        }
    }

    grouping mrib_Mpib-group {
        leaf mpibName {
            type string;
        }
        leaf oifCount {
            config "false";
            type uint32;
        }
        leaf staleRoute {
            config "false";
            type boolean;
        }
    }

    grouping mrib_Oif-group {
        leaf oifName {
            type string;
        }
        leaf oifUptime {
            config "false";
            type uint64;
        }
        leaf oifRPF {
            config "false";
            type boolean;
        }
        leaf oifLispEncapEntries {
            config "false";
            type uint32;
        }

        // This object holds lisp encap information
        container lispEncap-items {
            list LispEncap-list {
                key "index";

                // Added containment: Prefix=lispEncap
                // Acquired From Package mrib
                uses mrib_LispEncap-group;
            }
        }

        // This object holds mrib OIF MPIB information
        container oifMpib-items {
            list OifMpib-list {
                key "oifMpibName";

                // Added containment: Prefix=oifMpib
                // Acquired From Package mrib
                uses mrib_OifMpib-group;
            }
        }
    }

    grouping mrib_LispEncap-group {
        leaf index {
            type uint32;
        }
        leaf srcRloc {
            config "false";
            type address_Ip;
        }
        leaf dstRloc {
            config "false";
            type address_Ip;
        }
    }

    grouping mrib_OifMpib-group {
        leaf oifMpibName {
            type string;
        }
        leaf staleOif {
            config "false";
            type boolean;
        }
        leaf VpcSvi {
            config "false";
            type boolean;
        }
    }

    grouping msdp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per MSDP instance information
        container inst-items {

            // Added containment as a singleton: Prefix=inst
            // Acquired From Package msdp
            uses msdp_Inst-group;
        }
    }

    grouping msdp_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This objects hold per domain (vrf)  MSDP information
        container dom-items {
            list Dom-list {
                key "name";

                // Added containment: Prefix=dom
                // Acquired From Package msdp
                uses msdp_Dom-group;
            }
        }
    }

    grouping msdp_Dom-group {

        // Type is an MO-Defined-Type
        leaf origIf {
            description "Originator Interface";

            // Type is an MO-Defined-Type
            type nw_IfId;
        }

        // Type is an MO-Defined-Type
        leaf srcActiveMsgIntvl {
            description "Source Active msg Interval";

            // Type is an MO-Defined-Type
            type msdp_SrcActiveMsgIntvl;
        }

        // Type is an MO-Defined-Type
        leaf reConnIntvl {
            description "Reconnect Interval";

            // Type is an MO-Defined-Type
            type msdp_ReConnIntvl;
        }

        // Type is an MO-Defined-Type
        leaf ctrl {
            description "Flush routes";

            // Type is an MO-Defined-Type
            type msdp_DomCtrl;
        }

        // Inherited From nw:Conn
        // Modified by Override: nw:CpDom->name
        // Type is an MO-Defined-Type
        leaf name {
            description "Name";

            // Type is an MO-Defined-Type
            type naming_Name {
                length "1..64";
            }
        }

        // msdp databases
        container db-items {
            list Db-list {
                config "false";
                key "type";

                // Added containment: Prefix=db
                // Acquired From Package msdp
                uses msdp_Db-group;
            }
        }

        // This object holds  group limt and source range info
        container maxgrp-items {
            list MaxGrpP-list {
                key "srcPfx";

                // Added containment: Prefix=maxgrp
                // Acquired From Package msdp
                uses msdp_MaxGrpP-group;
            }
        }

        // This object holds MSDP information pertaining to a peer
        container peer-items {
            list Peer-list {
                key "addr";

                // Added containment: Prefix=peer
                // Acquired From Package msdp
                uses msdp_Peer-group;
            }
        }

        container interleakp-items {

            // Added containment as a singleton: Prefix=interleakp
            // Acquired From Package msdp
            uses msdp_InterLeakP-group;
        }
    }

    grouping msdp_Db-group {

        // Type of the repository
        // Type is an MO-Defined-Type
        leaf type {
            config "false";
            description "Type";

            // Type is an MO-Defined-Type
            type msdp_DbT;
        }

        // Inherited From nw:Conn
        // Modified by Override: nw:Db->name
        // Type is an MO-Defined-Type
        leaf name {
            description "Name";

            // Type is an MO-Defined-Type
            type naming_Name {
                length "1..64";
            }
        }

        // This object holds the MSDP SA-Cache related information
        container src-items {
            list Route-list {
                config "false";
                key "src grp rp";

                // Added containment: Prefix=src
                // Acquired From Package msdp
                uses msdp_Route-group;
            }
        }

        // This class holds information of learnt sources
        container source-items {
            list Source-list {
                config "false";
                key "addr";

                // Added containment: Prefix=source
                // Acquired From Package msdp
                uses msdp_Source-group;
            }
        }
    }

    grouping msdp_Route-group {
        leaf src {
            config "false";
            type address_Ip;
        }
        leaf grp {
            config "false";
            type address_Ip;
        }
        leaf rp {
            config "false";
            type address_Ip;
        }
        leaf peer {
            config "false";
            type address_Ip;
        }
        leaf asn {
            config "false";
            type string;
        }
        leaf createTs {
            config "false";
            type uint64;
        }
        leaf expireTs {
            config "false";
            type uint64;
        }
        leaf saCnt {
            config "false";
            type uint32;
        }
        leaf dataPkt {
            config "false";
            type uint32;
        }
    }

    grouping msdp_Source-group {
        leaf addr {
            config "false";
            type address_Ip;
        }
        leaf grpCnt {
            config "false";
            type uint32;
        }
        leaf grpLimit {
            config "false";
            type uint32;
        }
        leaf srcPfx {
            config "false";
            type address_Ip;
        }
        leaf violations {
            config "false";
            type uint32;
        }
    }

    grouping msdp_MaxGrpP-group {
        leaf srcPfx {
            type address_Ip;
        }

        // Type is an MO-Defined-Type
        leaf maxGrp {
            description "Max Group count";

            // Type is an MO-Defined-Type
            type msdp_MaxGrpLimit;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping msdp_Peer-group {
        leaf addr {
            type address_Ip;
        }

        // Administrative state up/down
        // Type is an MO-Defined-Type
        leaf adminSt {
            description "Administrative State";

            // Type is an MO-Defined-Type
            type nw_AdminSt;
        }

        // source interface
        // Type is an MO-Defined-Type
        leaf srcIf {
            description "Source Interface";

            // Type is an MO-Defined-Type
            type nw_IfId;
        }
        leaf asn {
            type string;
        }

        // sa-limit
        // Type is an MO-Defined-Type
        leaf srcActiveMsgLimit {
            description "Source Active msg Limit";

            // Type is an MO-Defined-Type
            type msdp_SrcActiveMsgLimit;
        }

        // Keepalive interval, how often you send keepalives
        // Type is an MO-Defined-Type
        leaf kaIntvl {
            description "Keepalive Interval";

            // Type is an MO-Defined-Type
            type msdp_KaIntvl;
        }

        // Keepalive timeout
        // Type is an MO-Defined-Type
        leaf kaTimeout {
            description "Keepalive Timeout";

            // Type is an MO-Defined-Type
            type msdp_KaTimeout;
        }

        // Operationsl state
        // Type is an MO-Defined-Type
        leaf operSt {
            config "false";
            description "Operational Status";

            // Type is an MO-Defined-Type
            type msdp_OperSt;
        }

        // Remote port of TCP connection to this peer
        // Type is an MO-Defined-Type
        leaf remPort {
            config "false";
            description "Remote Port";

            // Type is an MO-Defined-Type
            type l4_Port;
        }

        // Local port of TCP connection to this peer
        // Type is an MO-Defined-Type
        leaf localPort {
            config "false";
            description "Local Port";

            // Type is an MO-Defined-Type
            type l4_Port;
        }
        leaf lastResetOperQual {
            config "false";
            type string;
        }
        leaf discontinuityTs {
            config "false";
            type uint64;
        }
        leaf upTs {
            config "false";
            type uint64;
        }
        leaf connTmrTs {
            config "false";
            type uint64;
        }

        // Count of established transitions
        // Type is an MO-Defined-Type
        leaf establishTransitions {
            config "false";
            description "Established Transitions";

            // Type is an MO-Defined-Type
            type nw_Counter32;
        }

        // From Interface naming:Described
        // Type is an MO-Defined-Type
        leaf descr {
            description "Description";

            // Type is an MO-Defined-Type
            type naming_Descr;
        }

        // Inherited From nw:Conn
        // Modified by Override: nw:Ep->name
        // Type is an MO-Defined-Type
        leaf name {
            description "Name";

            // Type is an MO-Defined-Type
            type naming_Name {
                length "1..64";
            }
        }

        // This object holds authentication policy information
        container auth-items {

            // Added containment as a singleton: Prefix=auth
            // Acquired From Package msdp
            uses msdp_AuthP-group;
        }

        // This object holds mesh group information
        container meshgrp-items {

            // Added containment as a singleton: Prefix=meshgrp
            // Acquired From Package msdp
            uses msdp_MeshGrp-group;
        }

        // SA policy MO
        container rtctrl-items {
            list RtCtrlP-list {
                key "direction";

                // Added containment: Prefix=rtctrl
                // Acquired From Package msdp
                uses msdp_RtCtrlP-group;
            }
        }

        // This object holds the MSDP peer related statistics
        container peerstats-items {

            // Added containment as a singleton: Prefix=peerstats
            // Acquired From Package msdp
            uses msdp_PeerStats-group;
        }
    }

    grouping msdp_AuthP-group {

        // Authentication type
        // Type is an MO-Defined-Type
        leaf type {
            description "Type";

            // Type is an MO-Defined-Type
            type msdp_AuthT;
        }

        // Authentication key
        // Type is an MO-Defined-Type
        leaf key {
            description "Key";

            // Type is an MO-Defined-Type
            type msdp_AuthKey;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping msdp_MeshGrp-group {
        leaf grpName {
            type string;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
    }

    grouping msdp_RtCtrlP-group {
        leaf pfxList {
            config "false";
            type string;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Direction [in/out]
        // Inherited From rtctrl:RtCtrlP
        // Type is an MO-Defined-Type
        leaf direction {
            description "Direction";

            // Type is an MO-Defined-Type
            type rtctrl_RtCtrlDir;
        }
        leaf rtMap {
            type string;
        }
    }

    grouping msdp_PeerStats-group {
        leaf lastMessageRcvd {
            config "false";
            type uint64;
        }

        // Count of SA requests received
        // Type is an MO-Defined-Type
        leaf saReqRcvd {
            config "false";
            description "SA Request Received";

            // Type is an MO-Defined-Type
            type nw_Counter32;
        }

        // Count of SA requests sent
        // Type is an MO-Defined-Type
        leaf saReqSent {
            config "false";
            description "SA Request Sent";

            // Type is an MO-Defined-Type
            type nw_Counter32;
        }

        // Count of SA responses received
        // Type is an MO-Defined-Type
        leaf saRspRcvd {
            config "false";
            description "SA Response Received";

            // Type is an MO-Defined-Type
            type nw_Counter32;
        }

        // Count of SA responses sent
        // Type is an MO-Defined-Type
        leaf saRspSent {
            config "false";
            description "SA Response Sent";

            // Type is an MO-Defined-Type
            type nw_Counter32;
        }

        // Count of control messages received
        // Type is an MO-Defined-Type
        leaf ctrlMessagesRcvd {
            config "false";
            description "Control Messages Received";

            // Type is an MO-Defined-Type
            type nw_Counter32;
        }

        // Count of control messages sent
        // Type is an MO-Defined-Type
        leaf ctrlMessagesSent {
            config "false";
            description "Control Messages Sent";

            // Type is an MO-Defined-Type
            type nw_Counter32;
        }

        // Count of data packets received
        // Type is an MO-Defined-Type
        leaf dataMessagesRcvd {
            config "false";
            description "Data Messages Received";

            // Type is an MO-Defined-Type
            type nw_Counter32;
        }

        // Count of data packets sent
        // Type is an MO-Defined-Type
        leaf dataMessagesSent {
            config "false";
            description "Data Messages Sent";

            // Type is an MO-Defined-Type
            type nw_Counter32;
        }

        // Count of notifications received
        // Type is an MO-Defined-Type
        leaf notifRcvd {
            config "false";
            description "SA Notifications Received";

            // Type is an MO-Defined-Type
            type nw_Counter32;
        }

        // Count of SA notifications sent
        // Type is an MO-Defined-Type
        leaf notifSent {
            config "false";
            description "SA Notifications Sent";

            // Type is an MO-Defined-Type
            type nw_Counter32;
        }

        // Count of keepalive messages received
        // Type is an MO-Defined-Type
        leaf kaRcvd {
            config "false";
            description "Keepalives Received";

            // Type is an MO-Defined-Type
            type nw_Counter32;
        }

        // Count of keepalive messages sent
        // Type is an MO-Defined-Type
        leaf kaSent {
            config "false";
            description "Keepalives Sent";

            // Type is an MO-Defined-Type
            type nw_Counter32;
        }

        // Count of RPF check failures
        // Type is an MO-Defined-Type
        leaf rpfChkFail {
            config "false";
            description "RPF Check Failures";

            // Type is an MO-Defined-Type
            type nw_Counter32;
        }

        // Count of connection attempts
        // Type is an MO-Defined-Type
        leaf connAttempts {
            config "false";
            description "Connection Attempts";

            // Type is an MO-Defined-Type
            type nw_Counter32;
        }

        // Count of SA-cache entries learnt from this peer
        // Type is an MO-Defined-Type
        leaf rtCnt {
            config "false";
            description "Learnt SG Cache Entries";

            // Type is an MO-Defined-Type
            type nw_Counter32;
        }
    }

    grouping msdp_InterLeakP-group {
        leaf pfxList {
            type string;
        }

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Scope of the policy (intra protocol, inter protcol,
        // default route)
        // Inherited From rtleak:LeakP
        // Type is an MO-Defined-Type
        leaf scope {
            description "Scope";

            // Type is an MO-Defined-Type
            type rtleak_Scope;
        }
        leaf rtMap {
            type string;
        }
    }

    grouping nd_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per nd instance information. There is
        // only one instance of nd running in the system today
        container inst-items {

            // Added containment as a singleton: Prefix=inst
            // Acquired From Package nd
            uses nd_Inst-group;
        }
    }

    grouping nd_Inst-group {

        // Solicitated neighbor advertisement
        // Type is an MO-Defined-Type
        leaf solicitNghbrAdvertisement {
            description "Solicit neighbor advertisement";

            // Type is an MO-Defined-Type
            type nw_AdminSt;
        }

        // Solicitated neighbor advertisement with complete entry
        // Type is an MO-Defined-Type
        leaf acceptSolicitNghbrEntry {
            description "Accept or no-accept entry in Solicit neighbor advertisement";

            // Type is an MO-Defined-Type
            type nd_SolicitAcceptValue;
        }

        // Solicitated neighbor advertisement Probe value    Probe Value as 0 means no-probe
        // Type is an MO-Defined-Type
        leaf probeIntervalForSolicitNghbr {
            description "Probe interval";

            // Type is an MO-Defined-Type
            type nd_SolicitProbeValue;
        }

        // Aging timer for nd cached entires
        // Type is an MO-Defined-Type
        leaf agingInterval {
            description "Aging Interval";

            // Type is an MO-Defined-Type
            type nd_AgingInterval;
        }

        // Off-list timer for neighbor discovery
        // Type is an MO-Defined-Type
        leaf offListTimeout {
            description "Off-list timeout";

            // Type is an MO-Defined-Type
            type nd_OffListTimeout;
        }

        // IPv6 Route Distance
        // Type is an MO-Defined-Type
        leaf ipv6AdjRouteDistance {
            description "Ipv6 Adjacency Route Distance";

            // Type is an MO-Defined-Type
            type nd_adjRouteDist;
        }

        // ND Cache Limit
        // Type is an MO-Defined-Type
        leaf cacheLimit {
            description "Cache Limit";

            // Type is an MO-Defined-Type
            type nd_NdCacheLimit;
        }

        // ND Cache SysLog Rate
        // Type is an MO-Defined-Type
        leaf cacheSyslogRate {
            description "Cache Syslog Rate";

            // Type is an MO-Defined-Type
            type nd_NdCacheSyslogRate;
        }

        // Config error in this MO
        // Type is an MO-Defined-Type
        leaf configErr {
            config "false";
            description "Config error Inst";

            // Type is an MO-Defined-Type
            type nd_ConfigErrInst;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This objects hold per ND domain (vrf) information
        container dom-items {
            list Dom-list {
                key "name";

                // Added containment: Prefix=dom
                // Acquired From Package nd
                uses nd_Dom-group;
            }
        }

        // Glean throttling helps to discard packets at line card when
        // adjacency of the next hop is getting resolved.
        // Ref:
        // Guide: Cisco Nexus 9000 Series NX-OS Unicast Routing Configuration Guide
        // Chapter: Configuring IPv4
        container ipv6gleanthrottle-items {

            // Added containment as a singleton: Prefix=ipv6gleanthrottle
            // Acquired From Package nd
            uses nd_IpV6Throttle-group;
        }

        // This object holds IPv6 ND Sync for VPC
        container vpc-items {

            // Added containment as a singleton: Prefix=vpc
            // Acquired From Package nd
            uses nd_Vpc-group;
        }
        container offliststat-items {
            list OffListVlan-list {
                config "false";
                key "vlanId addr";

                // Added containment: Prefix=offliststat
                // Acquired From Package nd
                uses nd_OffListVlan-group;
            }
        }

        // icmpv6 packet counters (global)
        container glblpktstats-items {

            // Added containment as a singleton: Prefix=glblpktstats
            // Acquired From Package nd
            uses nd_GlobalTrafficStats-group;
        }

        // Link Local Global VADDR statistics
        container vaddrllstat-items {
            list VaddrLinkLocalStat-list {
                key "vAddr";

                // Added containment: Prefix=vaddrllstat
                // Acquired From Package nd
                uses nd_VaddrLinkLocalStat-group;
            }
        }

        container vpcstat-items {

            // Added containment as a singleton: Prefix=vpcstat
            // Acquired From Package nd
            uses nd_VPCStat-group;
        }
    }

    grouping nd_Dom-group {

        // Inherited From nw:Conn
        // Modified by Override: nw:CpDom->name
        // Type is an MO-Defined-Type
        leaf name {
            description "Name";

            // Type is an MO-Defined-Type
            type naming_Name {
                length "1..64";
            }
        }

        // ND databases
        container db-items {
            list Db-list {
                config "false";
                key "type";

                // Added containment: Prefix=db
                // Acquired From Package nd
                uses nd_Db-group;
            }
        }

        // This object holds nd information that is operated at a
        // interface level
        container if-items {
            list If-list {
                key "id";

                // Added containment: Prefix=if
                // Acquired From Package nd
                uses nd_If-group;
            }
        }

        // Only Global level VADDR statistics
        container vaddrstatglobal-items {
            list VaddrGlobalStat-list {
                key "vAddr";

                // Added containment: Prefix=vaddrstatglobal
                // Acquired From Package nd
                uses nd_VaddrGlobalStat-group;
            }
        }
    }

    grouping nd_Db-group {

        // Type of the repository
        // Type is an MO-Defined-Type
        leaf type {
            config "false";
            description "Type";

            // Type is an MO-Defined-Type
            type nd_DbT;
        }

        // Inherited From nw:Conn
        // Modified by Override: nw:Db->name
        // Type is an MO-Defined-Type
        leaf name {
            description "Name";

            // Type is an MO-Defined-Type
            type naming_Name {
                length "1..64";
            }
        }

        // ND adjacency definitions
        container adj-items {
            list AdjEp-list {
                config "false";
                key "ifId addr";

                // Added containment: Prefix=adj
                // Acquired From Package nd
                uses nd_AdjEp-group;
            }
        }
    }

    grouping nd_AdjEp-group {

        // Logical interface that this ep is associated with
        // Type is an MO-Defined-Type
        leaf ifId {
            config "false";
            description "Logical Interface ID";

            // Type is an MO-Defined-Type
            type nw_IfId;
        }

        // Operational state
        // Type is an MO-Defined-Type
        leaf operSt {
            config "false";
            description "Operational State";

            // Type is an MO-Defined-Type
            type nd_AdjOperSt;
        }

        // Physical interface that this ep is associated with
        // Type is an MO-Defined-Type
        leaf physIfId {
            config "false";
            description "Physical Interface ID";

            // Type is an MO-Defined-Type
            type nw_IfId;
        }

        // Inherited From nw:Conn
        // Modified by Override: nw:Ep->name
        // Type is an MO-Defined-Type
        leaf name {
            description "Name";

            // Type is an MO-Defined-Type
            type naming_Name {
                length "1..64";
            }
        }
        leaf addr {
            config "false";
            type address_Ip;
        }

        // Mac address
        // Inherited From nd:AAdjEp
        // Type is an MO-Defined-Type
        leaf mac {
            config "false";
            description "MAC";

            // Type is an MO-Defined-Type
            type nd_AdjMac;
        }
        leaf upTS {
            config "false";
            type uint64;
        }
    }

    grouping nd_If-group {

        // Extract next hop MAC address embedded in IPV6 address
        // Type is an MO-Defined-Type
        leaf macExtract {
            description "Extract next hop MAC address";

            // Type is an MO-Defined-Type
            type nd_MacExtract;
        }

        // Disable sending RDNSS in
        // Router-Advertisement messages
        // Type is an MO-Defined-Type
        leaf dnsSuppress {
            description "Do not send RDNSS in router advertisement";

            // Type is an MO-Defined-Type
            type nw_AdminSt;
        }

        // Disable sending DNSSL (DNS search-list) in
        // Router-Advertisement messages
        // Type is an MO-Defined-Type
        leaf dnsSearchListSuppress {
            description "Do not send DNSSL in router advertisement";

            // Type is an MO-Defined-Type
            type nw_AdminSt;
        }

        // Disable sending Route Information Options in RA messages
        // Type is an MO-Defined-Type
        leaf routeSuppress {
            description "Do Not send Route Information in RA";

            // Type is an MO-Defined-Type
            type nw_AdminSt;
        }

        // Set Default Router Preference Value (RFC 4191)
        // Type is an MO-Defined-Type
        leaf routerPreference {
            description "Set Router Preference (RFC 4191)";

            // Type is an MO-Defined-Type
            type nd_RtPrefForCmd;
        }

        // Interface controls for:
        // redirects, managed-config-flag, other-config-flag,
        // supress-ra, supress-ra-mtu
        // Type is an MO-Defined-Type
        leaf ctrl {
            description "Controls";

            // Type is an MO-Defined-Type
            type nd_IfControl;
        }

        // Neighbor Solicitation: Sent by a node to determine the
        // link-layer address of a neighbor, or to verify that a
        // neighbor is still reachable via a cached link-layer
        // address. Neighbor Solicitations are also used for
        // Duplicate Address Detection.    Retransmission interval between IPv6 neighbor
        // solication messages
        // Type is an MO-Defined-Type
        leaf nsIntvl {
            description "Neighbor Solicit Interval";

            // Type is an MO-Defined-Type
            type nd_NsIntvl;
        }

        // Retransmission retry count sending neighbor
        // soliciation messages
        // <property name="nsRetries"
        // type="NsRetries"
        // owner="management"
        // mod="explicit"
        // label="Neighbor Solicit Retry count"
        // />
        // Routers send out Router Advertisement messages
        // periodically, or in response to Router Solicitations    Interval between sending ICMPv6 router advertisement
        // messages
        // Type is an MO-Defined-Type
        leaf raIntvl {
            description "Router Advertisement Interval";

            // Type is an MO-Defined-Type
            type nd_RaIntvl;
        }

        // Interval between RA transmissions minimum
        // Type is an MO-Defined-Type
        leaf raIntvlMin {
            description "Router Advertisement Interval Minimum";

            // Type is an MO-Defined-Type
            type nd_RaIntvlMin;
        }

        // Router Advertisement (RA) messages also contain Internet
        // parameters such as the hop limit that hosts should
        // use in outgoing packets and, optionally, link parameters
        // such as the link MTU. This facilitates centralized
        // administration of critical parameters that can be set on
        // routers and automatically propagated to all attached
        // hosts    Hop limit
        // Type is an MO-Defined-Type
        leaf hopLimit {
            description "Hop limit";

            // Type is an MO-Defined-Type
            type nd_HopLimit;
        }

        // Link MTU (sent in RA message)
        // Type is an MO-Defined-Type
        leaf mtu {
            description "MTU";

            // Type is an MO-Defined-Type
            type nd_Mtu;
        }

        // Router Lifetime. The lifetime associated with the
        // default router in units of seconds.
        // Type is an MO-Defined-Type
        leaf raLifetime {
            description "Router Advertisement lifetime";

            // Type is an MO-Defined-Type
            type nd_RaLifetime;
        }

        // Reachable time. The time, in milliseconds, that a
        // node assumes a neighbor is reachable after having
        // received a reachability confirmation. Used by the
        // Neighbor Unreachability Detection algorithm
        // Type is an MO-Defined-Type
        leaf reachableTime {
            description "Reachable time";

            // Type is an MO-Defined-Type
            type nd_ReachableTime;
        }

        // Retransmit timer. The time, in milliseconds, between
        // retransmitted Neighbor Solicitation messages. Used
        // by address resolution and the Neighbor Unreachability
        // Detection algorithm.  A value of zero means unspecified
        // (by this router)
        // Type is an MO-Defined-Type
        leaf retransTimer {
            description "Retransmit timer";

            // Type is an MO-Defined-Type
            type nd_RetransTimer;
        }

        // Duplicate address detection attempts limit
        // Type is an MO-Defined-Type
        leaf dadAttempts {
            description "Dad attempts";

            // Type is an MO-Defined-Type
            type nd_DadAttempts;
        }

        // Discover host from DADNS
        // Type is an MO-Defined-Type
        leaf dadnsInterval {
            description "Dadns interval";

            // Type is an MO-Defined-Type
            type nd_DadnsInverval;
        }

        // To Handle the config fault for this MO
        // Type is an MO-Defined-Type
        leaf configError {
            config "false";
            description "Config error";

            // Type is an MO-Defined-Type
            type nd_ConfigErr;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Static ND adjacency definitions
        container sadj-items {
            list StAdjEp-list {
                config "false";
                key "addr";

                // Added containment: Prefix=sadj
                // Acquired From Package nd
                uses nd_StAdjEp-group;
            }
        }

        // DNS Search-list statistics
        container dnsslif-items {

            // Added containment as a singleton: Prefix=dnsslif
            // Acquired From Package nd
            uses nd_DNSIfSearchListStats-group;
        }

        // DNS Server statistics
        container dnsstat-items {

            // Added containment as a singleton: Prefix=dnsstat
            // Acquired From Package nd
            uses nd_DNSIfStats-group;
        }

        // This object holds all IPv6 ND Routes as children
        container routes-items {

            // Added containment as a singleton: Prefix=routes
            // Acquired From Package nd
            uses nd_IfRoutes-group;
        }

        // A list of prefixes to be placed in Prefix Information
        // options in Router Advertisement messages sent from the
        // interface.
        container pfx-items {
            list Pfx-list {
                key "addr";

                // Added containment: Prefix=pfx
                // Acquired From Package nd
                uses nd_Pfx-group;
            }
        }

        container defpfx-items {

            // Added containment as a singleton: Prefix=defpfx
            // Acquired From Package nd
            uses nd_DefaultPrefix-group;
        }

        // ND DNS Server
        container dns-items {
            list RouteAdvDNSServer-list {
                key "dnsServerAddr dnsSequenceNum";

                // Added containment: Prefix=dns
                // Acquired From Package nd
                uses nd_RouteAdvDNSServer-group;
            }
        }

        // ND DNS Search List
        container dnssl-items {
            list RouteAdvDNSSearchList-list {
                key "dnsSearchListName dnsSequenceNum";

                // Added containment: Prefix=dnssl
                // Acquired From Package nd
                uses nd_RouteAdvDNSSearchList-group;
            }
        }
        container rtrstat-items {
            list RouterStat-list {
                key "routerAddr";

                // Added containment: Prefix=rtrstat
                // Acquired From Package nd
                uses nd_RouterStat-group;
            }
        }

        // Interface statistics    ND packet counters (per-i/f)
        container ifstats-items {

            // Added containment as a singleton: Prefix=ifstats
            // Acquired From Package nd
            uses nd_IfStats-group;
        }

        // VADDR Statistics per i/f for specific client
        container vaddrstat-items {
            list VaddrStat-list {
                key "vaddrProto";

                // Added containment: Prefix=vaddrstat
                // Acquired From Package nd
                uses nd_VaddrStat-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping nd_StAdjEp-group {

        // Operational state
        // Type is an MO-Defined-Type
        leaf operSt {
            config "false";
            description "Operational State";

            // Type is an MO-Defined-Type
            type nd_StAdjOperSt;
        }

        // Operational state qualifier
        // Type is an MO-Defined-Type
        leaf operStQual {
            config "false";
            description "Operational State Qualifier";

            // Type is an MO-Defined-Type
            type nd_StAdjOperStQual;
        }

        // Inherited From nw:Conn
        // Modified by Override: nw:Ep->name
        // Type is an MO-Defined-Type
        leaf name {
            description "Name";

            // Type is an MO-Defined-Type
            type naming_Name {
                length "1..64";
            }
        }
        leaf addr {
            config "false";
            type address_Ip;
        }

        // Mac address
        // Inherited From nd:AAdjEp
        // Type is an MO-Defined-Type
        leaf mac {
            config "false";
            description "MAC";

            // Type is an MO-Defined-Type
            type nd_AdjMac;
        }
        leaf upTS {
            config "false";
            type uint64;
        }

        // Rel-def target from EpDefRefToStAdjEpV6
        // Inherited From nd:StAdjEp
        container rtfvEpDefRefToStAdjEpV6-items {

            // Abstract containment of rtfvEpDefRefToStAdjEpV6 derived from nd:StAdjEp
            list RtFvEpDefRefToStAdjEpV6-list {
                config "false";
                key "tDn";

                // Added containment: Prefix=rtfvEpDefRefToStAdjEpV6
                // Acquired From Package fv
                uses fv_RtFvEpDefRefToStAdjEpV6_target-group;
            }
        }
    }

    grouping nd_DNSIfSearchListStats-group {
        leaf dnsSearchListSuppress {
            config "false";
            type boolean;
        }
        container server-items {
            list DNSSearchListStats-list {
                key "dnsSearchList";

                // Added containment: Prefix=server
                // Acquired From Package nd
                uses nd_DNSSearchListStats-group;
            }
        }
    }

    grouping nd_DNSSearchListStats-group {
        leaf dnsSearchList {
            type string;
        }
        leaf dnsSearchListLife {
            config "false";
            type uint32;
        }
        leaf dnsSearchListSeq {
            config "false";
            type uint32;
        }
    }

    grouping nd_DNSIfStats-group {
        leaf dnsServerSuppress {
            config "false";
            type boolean;
        }
        container server-items {
            list DNSServerStats-list {
                key "addr";

                // Added containment: Prefix=server
                // Acquired From Package nd
                uses nd_DNSServerStats-group;
            }
        }
    }

    grouping nd_DNSServerStats-group {
        leaf addr {
            type address_Ip;
        }
        leaf dnsServerLife {
            config "false";
            type uint32;
        }
        leaf dnsServerSeq {
            config "false";
            type uint32;
        }
    }

    grouping nd_IfRoutes-group {

        // This object holds IPv6 ND Route command related properties
        container rt-items {
            list Route-list {
                key "ndRouteAddr";

                // Added containment: Prefix=rt
                // Acquired From Package nd
                uses nd_Route-group;
            }
        }
    }

    grouping nd_Route-group {
        leaf ndRouteAddr {
            type address_Ip;
        }

        // Nd Route Life Time
        // Type is an MO-Defined-Type
        leaf ndRouteLifeTime {
            description "Nd Route life time";

            // Type is an MO-Defined-Type
            type nd_NdRtLifeTime;
        }

        // Nd Route Infinite Life Time
        // Type is an MO-Defined-Type
        leaf ndRouteLifeTimeInfinite {
            description "Nd Route life time infinite";

            // Type is an MO-Defined-Type
            type nw_AdminSt;
        }

        // Set Default Route Preference Value for ND Route (RFC 4191)
        // Type is an MO-Defined-Type
        leaf routePreference {
            description "Set Route Preference for ND Route (RFC 4191)";

            // Type is an MO-Defined-Type
            type nd_RtPrefForNdRt;
        }

        // Verify if route is present in Route table
        // Type is an MO-Defined-Type
        leaf verifyReachability {
            description "Verify if route is present in Route table";

            // Type is an MO-Defined-Type
            type nw_AdminSt;
        }
    }

    grouping nd_Pfx-group {
        leaf addr {
            type address_Ip;
        }

        // Valid lifetime of the prefix    @@@ (0xffffffff == infinite)
        // Type is an MO-Defined-Type
        leaf lifetime {
            description "Valid Lifetime";

            // Type is an MO-Defined-Type
            type nd_Lifetime;
        }

        // Preferred lifetime of the prefix    @@@ (0xffffffff == infinite)
        // Type is an MO-Defined-Type
        leaf prefLifetime {
            description "Preferred Lifetime";

            // Type is an MO-Defined-Type
            type nd_PrefLifetime;
        }

        // RA prefix Controls
        // Type is an MO-Defined-Type
        leaf ctrl {
            description "Prefix Controls";

            // Type is an MO-Defined-Type
            type nd_PfxControl;
        }
    }

    grouping nd_DefaultPrefix-group {

        // Default prefix
        // Type is an MO-Defined-Type
        leaf defPrefix {
            description "Default prefix";

            // Type is an MO-Defined-Type
            type nw_AdminSt;
        }

        // Valid lifetime of the prefix default
        // Type is an MO-Defined-Type
        leaf defLifetime {
            description "Valid lifetime for default prefix";

            // Type is an MO-Defined-Type
            type nd_Lifetime;
        }

        // Preferred lifetime of the prefix default
        // Type is an MO-Defined-Type
        leaf defPrefLifetime {
            description "Preferred lifetime for default prefix";

            // Type is an MO-Defined-Type
            type nd_PrefLifetime;
        }

        // Default RA prefix Controls
        // Type is an MO-Defined-Type
        leaf ctrl {
            description "Prefix Controls";

            // Type is an MO-Defined-Type
            type nd_PfxControl;
        }
    }

    grouping nd_RouteAdvDNSServer-group {
        leaf dnsServerAddr {
            type address_Ip;
        }

        // DNS Server Life Time
        // Type is an MO-Defined-Type
        // Default value handled in local MO type
        leaf dnsServerLifeTime {
            description "DNS server life time";

            // Type is a Local-MO-Defined-Type
            type nd_DNSServerLifeTime_RouteAdvDNSServer_dnsServerLifeTime;
        }

        // DNS Server Infinite Life Time
        // Type is an MO-Defined-Type
        leaf dnsServerLifeTimeInfinite {
            description "DNS server life time infinite";

            // Type is an MO-Defined-Type
            type nw_AdminSt;
        }

        // DNS Server Sequence Number
        // Type is an MO-Defined-Type
        leaf dnsSequenceNum {
            description "DNS server sequence number";

            // Type is an MO-Defined-Type
            type nd_DNSSeqNum;
        }

        // Flag to indicate if dns server is configured or not
        // Type is an MO-Defined-Type
        leaf dnsServer {
            description "IPv6 nd ra DNS server";

            // Type is an MO-Defined-Type
            type nw_AdminSt;
        }
    }

    grouping nd_RouteAdvDNSSearchList-group {
        leaf dnsSearchListName {
            type string;
        }

        // DNS Search List Life Time
        // Type is an MO-Defined-Type
        // Default value handled in local MO type
        leaf dnsSearchListLifeTime {
            description "DNS search list life time";

            // Type is a Local-MO-Defined-Type
            type nd_DNSServerLifeTime_RouteAdvDNSSearchList_dnsSearchListLifeTime;
        }

        // DNS Search List Infinite Life Time
        // Type is an MO-Defined-Type
        leaf dnsSearchListLifeTimeInfinite {
            description "DNS search list life time infinite";

            // Type is an MO-Defined-Type
            type nw_AdminSt;
        }

        // DNS Search List Sequence Number
        // Type is an MO-Defined-Type
        leaf dnsSequenceNum {
            description "DNS search list sequence number";

            // Type is an MO-Defined-Type
            type nd_DNSSeqNum;
        }

        // Flag to indicate if dns search list is configured or not
        // Type is an MO-Defined-Type
        leaf dnssl {
            description "IPv6 nd ra DNS search list";

            // Type is an MO-Defined-Type
            type nw_AdminSt;
        }
    }

    grouping nd_RouterStat-group {
        leaf routerAddr {
            type address_Ip;
        }
        leaf ifName {
            config "false";
            type string;
        }
        leaf lastUpdateTime {
            config "false";
            type decimal64 {
                fraction-digits 2;
            }
        }
        leaf hopLimit {
            config "false";
            type uint32;
        }
        leaf lifetime {
            config "false";
            type uint32;
        }
        leaf addrFlag {
            config "false";
            type uint16;
        }
        leaf otherFlag {
            config "false";
            type uint16;
        }
        leaf mtu {
            config "false";
            type uint16;
        }
        leaf homeagentFlag {
            config "false";
            type uint16;
        }

        // Type is an MO-Defined-Type
        leaf preference {
            config "false";
            description "Preference flag";

            // Type is an MO-Defined-Type
            type nd_RouterPreference;
        }
        leaf reachableTime {
            config "false";
            type uint64;
        }
        leaf retransmissionTime {
            config "false";
            type uint64;
        }
        container pfxstat-items {
            list RaPrefixStat-list {
                key "prefixAddr";

                // Added containment: Prefix=pfxstat
                // Acquired From Package nd
                uses nd_RaPrefixStat-group;
            }
        }
    }

    grouping nd_RaPrefixStat-group {
        leaf prefixAddr {
            type address_Ip;
        }
        leaf onlinkFlag {
            config "false";
            type boolean;
        }
        leaf autonomousFlag {
            config "false";
            type boolean;
        }
        leaf validLifetime {
            config "false";
            type uint64;
        }
        leaf prefLifetime {
            config "false";
            type uint32;
        }
    }

    grouping nd_IfStats-group {

        // Total Messages sent     @@@ ICMPV6_PKT_MSGS_SNT_CNT
        // From Interface icmpv6:globalTraffic
        // Type is an MO-Defined-Type
        leaf totSent {
            config "false";
            description "Total messages sent";

            // Type is an MO-Defined-Type
            type nw_Counter64;
        }

        // Total Messages received     @@@ ICMPV6_PKT_MSGS_RECV_CNT
        // From Interface icmpv6:globalTraffic
        // Type is an MO-Defined-Type
        leaf totRvcd {
            config "false";
            description "Total messages received";

            // Type is an MO-Defined-Type
            type nw_Counter64;
        }

        // Error Messages sent     @@@ ICMPV6_PKT_ERR_SNT_CNT
        // From Interface icmpv6:globalTraffic
        // Type is an MO-Defined-Type
        leaf errSent {
            config "false";
            description "Error messages sent";

            // Type is an MO-Defined-Type
            type nw_Counter64;
        }

        // Error Messages received     @@@ ICMPV6_PKT_ERR_RECV_CNT
        // From Interface icmpv6:globalTraffic
        // Type is an MO-Defined-Type
        leaf errRcvd {
            config "false";
            description "Error messages received";

            // Type is an MO-Defined-Type
            type nw_Counter64;
        }

        // Interface Down Drop Count sent     @@@ ICMPV6_PKT_SNT_DROP_IF_DOWN_CNT
        // From Interface icmpv6:globalTraffic
        // Type is an MO-Defined-Type
        leaf ifDownDropSent {
            config "false";
            description "Interface Down Drop Count sent";

            // Type is an MO-Defined-Type
            type nw_Counter64;
        }

        // Interface Down Drop Count received     @@@ ICMPV6_PKT_RECV_DROP_IF_DOWN_CNT
        // From Interface icmpv6:globalTraffic
        // Type is an MO-Defined-Type
        leaf ifDownDropRcvd {
            config "false";
            description "Interface Down Drop Count received";

            // Type is an MO-Defined-Type
            type nw_Counter64;
        }

        // Adjacency not recovered from AM after HA     @@@ ICMPV6_PKT_DROPPED_HA_NOT_READY
        // From Interface icmpv6:globalTraffic
        // Type is an MO-Defined-Type
        leaf dropHaNotRdy {
            config "false";
            description "Adjacency not recovered from AM after HA";

            // Type is an MO-Defined-Type
            type nw_Counter64;
        }

        // Pkts allowed due to inv ttl on vPC-MCT     @@@ ICMPV6_PKT_ALLOW_MCT_TTL_CNT
        // From Interface icmpv6:globalTraffic
        // Type is an MO-Defined-Type
        leaf dropInvldTtlMct {
            config "false";
            description "Pkts allowed due to inv ttl on vPC-MCT";

            // Type is an MO-Defined-Type
            type nw_Counter64;
        }

        // Pkts dropped as source mac addr is own     @@@ ICMPV6_PKT_RECV_DROP_OWN_SRC_MAC_COUNT
        // From Interface icmpv6:globalTraffic
        // Type is an MO-Defined-Type
        leaf dropSrcMacOwnRcvd {
            config "false";
            description "Pkts dropped as source mac addr is own";

            // Type is an MO-Defined-Type
            type nw_Counter64;
        }

        // Pkts dropped as tgt ip addr is not own     @@@ ICMPV6_PKT_RECV_DROP_TARGET_NOT_US_COUNT
        // From Interface icmpv6:globalTraffic
        // Type is an MO-Defined-Type
        leaf dropTgtIpNotOwnRcvd {
            config "false";
            description "Pkts dropped as tgt ip addr is not own";

            // Type is an MO-Defined-Type
            type nw_Counter64;
        }

        // Pkts dropped as src ip addr is not own     @@@ ICMPV6_PKT_RECV_DROP_SRC_NOT_US_COUNT
        // From Interface icmpv6:globalTraffic
        // Type is an MO-Defined-Type
        leaf dropSrcIpNotOwnRcvd {
            config "false";
            description "Pkts dropped as src ip addr is not own";

            // Type is an MO-Defined-Type
            type nw_Counter64;
        }

        // Destination Unreachables sent     @@@ ICMPV6_PKT_DEST_UNREACHS_SNT_CNT
        // From Interface icmpv6:globalTraffic
        // Type is an MO-Defined-Type
        leaf destUnreachSent {
            config "false";
            description "Destination Unreachables sent";

            // Type is an MO-Defined-Type
            type nw_Counter64;
        }

        // Destination Unreachables received    @@@ ICMPV6_PKT_DEST_UNREACHS_RECV_CNT
        // From Interface icmpv6:globalTraffic
        // Type is an MO-Defined-Type
        leaf destUnreachRcvd {
            config "false";
            description "Destination Unreachables received";

            // Type is an MO-Defined-Type
            type nw_Counter64;
        }

        // Administratively Prohibited sent    @@@ ICMPV6_PKT_ADMIN_PROHIBS_SNT_CNT
        // From Interface icmpv6:globalTraffic
        // Type is an MO-Defined-Type
        leaf adminProhibSent {
            config "false";
            description "Administratively Prohibited sent";

            // Type is an MO-Defined-Type
            type nw_Counter64;
        }

        // Administratively Prohibited received    @@@ ICMPV6_PKT_ADMIN_PROHIBS_RECV_CNT
        // From Interface icmpv6:globalTraffic
        // Type is an MO-Defined-Type
        leaf adminProhibRcvd {
            config "false";
            description "Administratively Prohibited received";

            // Type is an MO-Defined-Type
            type nw_Counter64;
        }

        // Time Exceeded sent    @@@ ICMPV6_PKT_TIME_EXCDS_SNT_CNT
        // From Interface icmpv6:globalTraffic
        // Type is an MO-Defined-Type
        leaf timeExcdSent {
            config "false";
            description "Time Exceeded sent ";

            // Type is an MO-Defined-Type
            type nw_Counter64;
        }

        // Time Exceeded received    @@@ ICMPV6_PKT_TIME_EXCDS_RECV_CNT
        // From Interface icmpv6:globalTraffic
        // Type is an MO-Defined-Type
        leaf timeExcdRcvd {
            config "false";
            description "Time Exceeded received";

            // Type is an MO-Defined-Type
            type nw_Counter64;
        }

        // Parameter Problems sent    @@@ ICMPV6_PKT_PARM_PROBS_SNT_CNT
        // From Interface icmpv6:globalTraffic
        // Type is an MO-Defined-Type
        leaf parmPrblmSent {
            config "false";
            description "Parameter Problems sent";

            // Type is an MO-Defined-Type
            type nw_Counter64;
        }

        // Parameter Problems received    @@@ ICMPV6_PKT_PARM_PROBS_RECV_CNT
        // From Interface icmpv6:globalTraffic
        // Type is an MO-Defined-Type
        leaf parmPrblmRcvd {
            config "false";
            description "Parameter Problems received";

            // Type is an MO-Defined-Type
            type nw_Counter64;
        }

        // Echo Request sent    @@@ ICMPV6_PKT_ECHOS_SNT_CNT
        // From Interface icmpv6:globalTraffic
        // Type is an MO-Defined-Type
        leaf echoReqSent {
            config "false";
            description "Echo Request sent";

            // Type is an MO-Defined-Type
            type nw_Counter64;
        }

        // Echo Request received    @@@ ICMPV6_PKT_ECHOS_RECV_CNT
        // From Interface icmpv6:globalTraffic
        // Type is an MO-Defined-Type
        leaf echoReqRcvd {
            config "false";
            description "Echo Request received";

            // Type is an MO-Defined-Type
            type nw_Counter64;
        }

        // Echo Replies sent    @@@ ICMPV6_PKT_ECHO_REPLIES_SNT_CNT
        // From Interface icmpv6:globalTraffic
        // Type is an MO-Defined-Type
        leaf echoRepSent {
            config "false";
            description "Echo Replies sent";

            // Type is an MO-Defined-Type
            type nw_Counter64;
        }

        // Echo Replies received    @@@ ICMPV6_PKT_ECHO_REPLIES_RECV_CNT
        // From Interface icmpv6:globalTraffic
        // Type is an MO-Defined-Type
        leaf echoRepRcvd {
            config "false";
            description "Echo Replies received";

            // Type is an MO-Defined-Type
            type nw_Counter64;
        }

        // Redirects sent    @@@ ICMPV6_PKT_REDIRECTS_SNT_CNT
        // From Interface icmpv6:globalTraffic
        // Type is an MO-Defined-Type
        leaf redirSent {
            config "false";
            description "Redirects sent";

            // Type is an MO-Defined-Type
            type nw_Counter64;
        }

        // Redirects received    @@@ ICMPV6_PKT_REDIRECTS_RECV_CNT
        // From Interface icmpv6:globalTraffic
        // Type is an MO-Defined-Type
        leaf redirRcvd {
            config "false";
            description "Redirects received";

            // Type is an MO-Defined-Type
            type nw_Counter64;
        }

        // Packet Too Big sent    @@@ ICMPV6_PKT_TOO_BIG_SNT_CNT
        // From Interface icmpv6:globalTraffic
        // Type is an MO-Defined-Type
        leaf tooBigSent {
            config "false";
            description "Packet Too Big sent";

            // Type is an MO-Defined-Type
            type nw_Counter64;
        }

        // Packet Too Big received    @@@ ICMPV6_PKT_TOO_BIG_RECV_CNT
        // From Interface icmpv6:globalTraffic
        // Type is an MO-Defined-Type
        leaf tooBigRcvd {
            config "false";
            description "Packet Too Big received";

            // Type is an MO-Defined-Type
            type nw_Counter64;
        }

        // Router Advertisements sent    @@@ ICMPV6_PKT_ROUTER_ADV_SNT_CNT
        // From Interface icmpv6:globalTraffic
        // Type is an MO-Defined-Type
        leaf raSent {
            config "false";
            description "Router Advertisements sent";

            // Type is an MO-Defined-Type
            type nw_Counter64;
        }

        // Router Advertisements received    @@@ ICMPV6_PKT_ROUTER_ADV_RECV_CNT
        // From Interface icmpv6:globalTraffic
        // Type is an MO-Defined-Type
        leaf raRcvd {
            config "false";
            description "Router Advertisements received";

            // Type is an MO-Defined-Type
            type nw_Counter64;
        }

        // Router Solicitations sent    @@@ ICMPV6_PKT_ROUTER_SOLICITS_SNT_CNT
        // From Interface icmpv6:globalTraffic
        // Type is an MO-Defined-Type
        leaf rsSent {
            config "false";
            description "Router Solicitations sent";

            // Type is an MO-Defined-Type
            type nw_Counter64;
        }

        // Router Solicitations received    @@@ ICMPV6_PKT_ROUTER_SOLICITS_RECV_CNT
        // From Interface icmpv6:globalTraffic
        // Type is an MO-Defined-Type
        leaf rsRcvd {
            config "false";
            description "Router Solicitations received";

            // Type is an MO-Defined-Type
            type nw_Counter64;
        }

        // Neighbor Advertisements sent    @@@ ICMPV6_PKT_NEIGHBOR_ADV_SNT_CNT
        // From Interface icmpv6:globalTraffic
        // Type is an MO-Defined-Type
        leaf naSent {
            config "false";
            description "Neighbor Advertisements sent";

            // Type is an MO-Defined-Type
            type nw_Counter64;
        }

        // Neighbor Advertisements received    @@@ ICMPV6_PKT_NEIGHBOR_ADV_RECV_CNT
        // From Interface icmpv6:globalTraffic
        // Type is an MO-Defined-Type
        leaf naRcvd {
            config "false";
            description "Neighbor Advertisements received";

            // Type is an MO-Defined-Type
            type nw_Counter64;
        }

        // Neighbor Solicitations sent    @@@ ICMPV6_PKT_NEIGHBOR_SOLICITS_SNT_CNT
        // From Interface icmpv6:globalTraffic
        // Type is an MO-Defined-Type
        leaf nsSent {
            config "false";
            description "Neighbor Solicitations sent";

            // Type is an MO-Defined-Type
            type nw_Counter64;
        }

        // Neighbor Solicitations received    @@@ ICMPV6_PKT_NEIGHBOR_SOLICITS_RECV_CNT
        // From Interface icmpv6:globalTraffic
        // Type is an MO-Defined-Type
        leaf nsRcvd {
            config "false";
            description "Neighbor Solicitations received";

            // Type is an MO-Defined-Type
            type nw_Counter64;
        }

        // Duplicate router RA received    @@@ ICMPV6_PKT_DUP_ROUTER
        // From Interface icmpv6:globalTraffic
        // Type is an MO-Defined-Type
        leaf dupRAReceived {
            config "false";
            description "Duplicate router RA received";

            // Type is an MO-Defined-Type
            type nw_Counter64;
        }

        // Fastpath Packets     @@@ ICMPV6_PKT_FASTPATH_RECV_CNT
        // From Interface icmpv6:globalTrafficFastPath
        // Type is an MO-Defined-Type
        leaf fastpthRcvd {
            config "false";
            description "Fastpath Packets";

            // Type is an MO-Defined-Type
            type nw_Counter64;
        }

        // Ignored Fastpath Packets - Fastpath disabled    @@@ ICMPV6_PKT_RECV_DROP_FASTPATH_DISABLED_CNT
        // From Interface icmpv6:globalTrafficFastPath
        // Type is an MO-Defined-Type
        leaf fastpathDsbleIgnRcvd {
            config "false";
            description "Ignored Fastpath Packets - Fastpath disabled";

            // Type is an MO-Defined-Type
            type nw_Counter64;
        }

        // Ignored Fastpath Packets - others    @@@ ICMPV6_PKT_RECV_DROP_REQUEST_IGNORE_CNT
        // From Interface icmpv6:globalTrafficFastPath
        // Type is an MO-Defined-Type
        leaf fastpathOtherIgnRcvd {
            config "false";
            description "Ignored fastpath packets - others";

            // Type is an MO-Defined-Type
            type nw_Counter64;
        }
        leaf lastNghbrSolicitSent {
            config "false";
            type string;
        }
        leaf lastNghbrAdvertisementSent {
            config "false";
            type string;
        }
        leaf lastRouterAdvertisementSent {
            config "false";
            type string;
        }
        leaf nextRouterAdvertisementSent {
            config "false";
            type string;
        }
        leaf nsRetransmitInterval {
            config "false";
            type uint64;
        }
        leaf ndNudRetryBase {
            config "false";
            type uint64;
        }
        leaf ndNudRetryInterval {
            config "false";
            type uint64;
        }
        leaf ndNudRetryAttemps {
            config "false";
            type uint64;
        }
        leaf sendRedirect {
            config "false";
            type boolean;
        }
        leaf redirectCause {
            config "false";
            type uint64;
        }
        leaf sendUnreachables {
            config "false";
            type boolean;
        }
        leaf maxDadAttempts {
            config "false";
            type uint16;
        }
        leaf currentDadAttempt {
            config "false";
            type uint16;
        }
        leaf ifState {
            config "false";
            type string;
        }
        leaf ifAddr {
            config "false";
            type string;
        }
        leaf linkLocalAddr {
            config "false";
            type string;
        }
        leaf linkLocalAddrState {
            config "false";
            type string;
        }
        leaf ndMacExtractState {
            config "false";
            type string;
        }
        leaf statsLastReset {
            config "false";
            type string;
        }

        // Vinci specific: Proxy NA count    @@@ ICMPV6_PKT_PROXY_NA_CNT
        // From Interface nd:VinciStats
        // Type is an MO-Defined-Type
        leaf proxyNaCount {
            config "false";
            description "Proxy NA count";

            // Type is an MO-Defined-Type
            type nw_Counter64;
        }

        // Vinci specific: Proxy NA to BD count    @@@ ICMPV6_PKT_FLOOD_BACK_TO_BD_NA
        // From Interface nd:VinciStats
        // Type is an MO-Defined-Type
        leaf proxyNaToBdCount {
            config "false";
            description "Proxy NA to BD count";

            // Type is an MO-Defined-Type
            type nw_Counter64;
        }

        // Vinci specific: Proxy NS to BD count    @@@ ICMPV6_PKT_FLOOD_BACK_TO_BD_NS
        // From Interface nd:VinciStats
        // Type is an MO-Defined-Type
        leaf proxyNsToBdCount {
            config "false";
            description "Proxy NS to BD count";

            // Type is an MO-Defined-Type
            type nw_Counter64;
        }

        // Vinci specific: RARP NS Count    @@@ ICMPV6_PKT_NS_SENT_FOR_RARP_CASE
        // From Interface nd:VinciStats
        // Type is an MO-Defined-Type
        leaf rarpNsCount {
            config "false";
            description "RARP NS count";

            // Type is an MO-Defined-Type
            type nw_Counter64;
        }

        container ra-items {

            // Added containment as a singleton: Prefix=ra
            // Acquired From Package nd
            uses nd_RouterAdv-group;
        }

        container vip-items {

            // Added containment as a singleton: Prefix=vip
            // Acquired From Package nd
            uses nd_IfVipClientStats-group;
        }
        container addr-items {
            list IfIPv6AddrStats-list {
                config "false";
                key "addr";

                // Added containment: Prefix=addr
                // Acquired From Package nd
                uses nd_IfIPv6AddrStats-group;
            }
        }
        container pfx-items {
            list PrefixStats-list {
                key "addr";

                // Added containment: Prefix=pfx
                // Acquired From Package nd
                uses nd_PrefixStats-group;
            }
        }
        container rt-items {
            list RouteStats-list {
                key "addr";

                // Added containment: Prefix=rt
                // Acquired From Package nd
                uses nd_RouteStats-group;
            }
        }
        container addrtree-items {
            list AddrTreeStats-list {
                key "addr";

                // Added containment: Prefix=addrtree
                // Acquired From Package nd
                uses nd_AddrTreeStats-group;
            }
        }
    }

    grouping nd_RouterAdv-group {
        leaf raInterval {
            config "false";
            type uint64;
        }
        leaf raIntervalMin {
            config "false";
            type uint64;
        }
        leaf mFlag {
            config "false";
            type boolean;
        }
        leaf oFlag {
            config "false";
            type boolean;
        }
        leaf hopLimit {
            config "false";
            type uint64;
        }
        leaf mtu {
            config "false";
            type uint64;
        }
        leaf routerLifetime {
            config "false";
            type uint64;
        }
        leaf reachableTime {
            config "false";
            type uint64;
        }
        leaf retransmitTime {
            config "false";
            type uint64;
        }
        leaf suppressRa {
            config "false";
            type boolean;
        }
        leaf suppressRaMtu {
            config "false";
            type boolean;
        }
    }

    grouping nd_IfVipClientStats-group {
        leaf groupId {
            config "false";
            type uint32;
        }
        leaf protocol {
            config "false";
            type string;
        }
        leaf uuid {
            config "false";
            type uint32;
        }
        leaf isActive {
            config "false";
            type string;
        }
        leaf inUse {
            config "false";
            type uint32;
        }
        container vipaddr-items {
            list IfVipAddrStats-list {
                config "false";
                key "addr";

                // Added containment: Prefix=vipaddr
                // Acquired From Package nd
                uses nd_IfVipAddrStats-group;
            }
        }
    }

    grouping nd_IfVipAddrStats-group {
        leaf addr {
            config "false";
            type address_Ip;
        }
        leaf vipMac {
            config "false";
            type string;
        }
        leaf contextName {
            config "false";
            type string;
        }
        leaf contextId {
            config "false";
            type uint32;
        }
        leaf lastNghbrSolicitSent {
            config "false";
            type string;
        }
        leaf lastNghbrAdvertisementSent {
            config "false";
            type string;
        }
        leaf lastRouterAdvertisementSent {
            config "false";
            type string;
        }
        leaf nextRouterAdvertisementSent {
            config "false";
            type string;
        }
    }

    grouping nd_IfIPv6AddrStats-group {
        leaf addr {
            config "false";
            type address_Ip;
        }
        leaf addrState {
            config "false";
            type string;
        }
    }

    grouping nd_PrefixStats-group {
        leaf addr {
            type address_Ip;
        }
        leaf maskLen {
            config "false";
            type uint16;
        }
        leaf enabled {
            config "false";
            type boolean;
        }

        // Valid lifetime of the prefix    @@@ (0xffffffff == infinite)
        // Type is an MO-Defined-Type
        leaf lifetime {
            config "false";
            description "Valid Lifetime";

            // Type is an MO-Defined-Type
            type nd_Lifetime;
        }

        // Preferred lifetime of the prefix    @@@ (0xffffffff == infinite)
        // Type is an MO-Defined-Type
        leaf prefLifetime {
            config "false";
            description "Preferred Lifetime";

            // Type is an MO-Defined-Type
            type nd_Lifetime;
        }
        leaf onLink {
            config "false";
            type boolean;
        }
        leaf offLink {
            config "false";
            type boolean;
        }
        leaf autonomous {
            config "false";
            type boolean;
        }
        leaf rtrAddr {
            config "false";
            type boolean;
        }
        leaf ifAssignedAddr {
            config "false";
            type boolean;
        }
        leaf refCount {
            config "false";
            type uint32;
        }
    }

    grouping nd_RouteStats-group {
        leaf addr {
            type address_Ip;
        }

        // Type is an MO-Defined-Type
        leaf routePreference {
            config "false";
            description "Route Preference";

            // Type is an MO-Defined-Type
            type nd_RouterPreference;
        }

        // Valid lifetime of the prefix    @@@ (0xffffffff == infinite)
        // Type is an MO-Defined-Type
        leaf routeLifetime {
            config "false";
            description "Route Lifetime";

            // Type is an MO-Defined-Type
            type nd_OperNdRtLifeTime;
        }
        leaf octetUnits {
            config "false";
            type uint32;
        }
        leaf verifyReachability {
            config "false";
            type boolean;
        }
        leaf advRouteInRoute {
            config "false";
            type boolean;
        }
        leaf advRouteWithZeroLifetime {
            config "false";
            type boolean;
        }
    }

    grouping nd_AddrTreeStats-group {
        leaf addr {
            type address_Ip;
        }
        leaf maskLen {
            config "false";
            type uint8;
        }

        // Type is an MO-Defined-Type
        leaf addrType {
            config "false";
            description "IPv6 address";

            // Type is an MO-Defined-Type
            type nd_AddrType;
        }
        leaf dadState {
            config "false";
            type string;
        }
        leaf dadAttempt {
            config "false";
            type uint16;
        }
    }

    grouping nd_VaddrStat-group {
        leaf vaddrProto {
            type string;
        }
        leaf groupId {
            config "false";
            type uint16;
        }
        leaf clientUUID {
            config "false";
            type uint32;
        }

        // From Interface nd:VADDRCommonField
        // Type is an MO-Defined-Type
        leaf clientState {
            config "false";
            description "Client state";

            // Type is an MO-Defined-Type
            type nd_VaddrClientState;
        }
        leaf clientInUse {
            config "false";
            type uint16;
        }
        leaf clientActiveState {
            config "false";
            type string;
        }
        leaf interface {
            config "false";
            type string;
        }
        leaf context {
            config "false";
            type string;
        }

        // VADDR Statistics per i/f for
        // specific client(protocol) -> VIP addr
        container vip-items {
            list VaddrStatVip-list {
                key "vAddr";

                // Added containment: Prefix=vip
                // Acquired From Package nd
                uses nd_VaddrStatVip-group;
            }
        }
    }

    grouping nd_VaddrStatVip-group {
        leaf vAddr {
            type address_Ip;
        }
        leaf virtualMac {
            config "false";
            type string;
        }

        // Total Messages sent     @@@ ICMPV6_PKT_MSGS_SNT_CNT
        // From Interface icmpv6:globalTraffic
        // Type is an MO-Defined-Type
        leaf totSent {
            config "false";
            description "Total messages sent";

            // Type is an MO-Defined-Type
            type nw_Counter64;
        }

        // Total Messages received     @@@ ICMPV6_PKT_MSGS_RECV_CNT
        // From Interface icmpv6:globalTraffic
        // Type is an MO-Defined-Type
        leaf totRvcd {
            config "false";
            description "Total messages received";

            // Type is an MO-Defined-Type
            type nw_Counter64;
        }

        // Error Messages sent     @@@ ICMPV6_PKT_ERR_SNT_CNT
        // From Interface icmpv6:globalTraffic
        // Type is an MO-Defined-Type
        leaf errSent {
            config "false";
            description "Error messages sent";

            // Type is an MO-Defined-Type
            type nw_Counter64;
        }

        // Error Messages received     @@@ ICMPV6_PKT_ERR_RECV_CNT
        // From Interface icmpv6:globalTraffic
        // Type is an MO-Defined-Type
        leaf errRcvd {
            config "false";
            description "Error messages received";

            // Type is an MO-Defined-Type
            type nw_Counter64;
        }

        // Interface Down Drop Count sent     @@@ ICMPV6_PKT_SNT_DROP_IF_DOWN_CNT
        // From Interface icmpv6:globalTraffic
        // Type is an MO-Defined-Type
        leaf ifDownDropSent {
            config "false";
            description "Interface Down Drop Count sent";

            // Type is an MO-Defined-Type
            type nw_Counter64;
        }

        // Interface Down Drop Count received     @@@ ICMPV6_PKT_RECV_DROP_IF_DOWN_CNT
        // From Interface icmpv6:globalTraffic
        // Type is an MO-Defined-Type
        leaf ifDownDropRcvd {
            config "false";
            description "Interface Down Drop Count received";

            // Type is an MO-Defined-Type
            type nw_Counter64;
        }

        // Adjacency not recovered from AM after HA     @@@ ICMPV6_PKT_DROPPED_HA_NOT_READY
        // From Interface icmpv6:globalTraffic
        // Type is an MO-Defined-Type
        leaf dropHaNotRdy {
            config "false";
            description "Adjacency not recovered from AM after HA";

            // Type is an MO-Defined-Type
            type nw_Counter64;
        }

        // Pkts allowed due to inv ttl on vPC-MCT     @@@ ICMPV6_PKT_ALLOW_MCT_TTL_CNT
        // From Interface icmpv6:globalTraffic
        // Type is an MO-Defined-Type
        leaf dropInvldTtlMct {
            config "false";
            description "Pkts allowed due to inv ttl on vPC-MCT";

            // Type is an MO-Defined-Type
            type nw_Counter64;
        }

        // Pkts dropped as source mac addr is own     @@@ ICMPV6_PKT_RECV_DROP_OWN_SRC_MAC_COUNT
        // From Interface icmpv6:globalTraffic
        // Type is an MO-Defined-Type
        leaf dropSrcMacOwnRcvd {
            config "false";
            description "Pkts dropped as source mac addr is own";

            // Type is an MO-Defined-Type
            type nw_Counter64;
        }

        // Pkts dropped as tgt ip addr is not own     @@@ ICMPV6_PKT_RECV_DROP_TARGET_NOT_US_COUNT
        // From Interface icmpv6:globalTraffic
        // Type is an MO-Defined-Type
        leaf dropTgtIpNotOwnRcvd {
            config "false";
            description "Pkts dropped as tgt ip addr is not own";

            // Type is an MO-Defined-Type
            type nw_Counter64;
        }

        // Pkts dropped as src ip addr is not own     @@@ ICMPV6_PKT_RECV_DROP_SRC_NOT_US_COUNT
        // From Interface icmpv6:globalTraffic
        // Type is an MO-Defined-Type
        leaf dropSrcIpNotOwnRcvd {
            config "false";
            description "Pkts dropped as src ip addr is not own";

            // Type is an MO-Defined-Type
            type nw_Counter64;
        }

        // Destination Unreachables sent     @@@ ICMPV6_PKT_DEST_UNREACHS_SNT_CNT
        // From Interface icmpv6:globalTraffic
        // Type is an MO-Defined-Type
        leaf destUnreachSent {
            config "false";
            description "Destination Unreachables sent";

            // Type is an MO-Defined-Type
            type nw_Counter64;
        }

        // Destination Unreachables received    @@@ ICMPV6_PKT_DEST_UNREACHS_RECV_CNT
        // From Interface icmpv6:globalTraffic
        // Type is an MO-Defined-Type
        leaf destUnreachRcvd {
            config "false";
            description "Destination Unreachables received";

            // Type is an MO-Defined-Type
            type nw_Counter64;
        }

        // Administratively Prohibited sent    @@@ ICMPV6_PKT_ADMIN_PROHIBS_SNT_CNT
        // From Interface icmpv6:globalTraffic
        // Type is an MO-Defined-Type
        leaf adminProhibSent {
            config "false";
            description "Administratively Prohibited sent";

            // Type is an MO-Defined-Type
            type nw_Counter64;
        }

        // Administratively Prohibited received    @@@ ICMPV6_PKT_ADMIN_PROHIBS_RECV_CNT
        // From Interface icmpv6:globalTraffic
        // Type is an MO-Defined-Type
        leaf adminProhibRcvd {
            config "false";
            description "Administratively Prohibited received";

            // Type is an MO-Defined-Type
            type nw_Counter64;
        }

        // Time Exceeded sent    @@@ ICMPV6_PKT_TIME_EXCDS_SNT_CNT
        // From Interface icmpv6:globalTraffic
        // Type is an MO-Defined-Type
        leaf timeExcdSent {
            config "false";
            description "Time Exceeded sent ";

            // Type is an MO-Defined-Type
            type nw_Counter64;
        }

        // Time Exceeded received    @@@ ICMPV6_PKT_TIME_EXCDS_RECV_CNT
        // From Interface icmpv6:globalTraffic
        // Type is an MO-Defined-Type
        leaf timeExcdRcvd {
            config "false";
            description "Time Exceeded received";

            // Type is an MO-Defined-Type
            type nw_Counter64;
        }

        // Parameter Problems sent    @@@ ICMPV6_PKT_PARM_PROBS_SNT_CNT
        // From Interface icmpv6:globalTraffic
        // Type is an MO-Defined-Type
        leaf parmPrblmSent {
            config "false";
            description "Parameter Problems sent";

            // Type is an MO-Defined-Type
            type nw_Counter64;
        }

        // Parameter Problems received    @@@ ICMPV6_PKT_PARM_PROBS_RECV_CNT
        // From Interface icmpv6:globalTraffic
        // Type is an MO-Defined-Type
        leaf parmPrblmRcvd {
            config "false";
            description "Parameter Problems received";

            // Type is an MO-Defined-Type
            type nw_Counter64;
        }

        // Echo Request sent    @@@ ICMPV6_PKT_ECHOS_SNT_CNT
        // From Interface icmpv6:globalTraffic
        // Type is an MO-Defined-Type
        leaf echoReqSent {
            config "false";
            description "Echo Request sent";

            // Type is an MO-Defined-Type
            type nw_Counter64;
        }

        // Echo Request received    @@@ ICMPV6_PKT_ECHOS_RECV_CNT
        // From Interface icmpv6:globalTraffic
        // Type is an MO-Defined-Type
        leaf echoReqRcvd {
            config "false";
            description "Echo Request received";

            // Type is an MO-Defined-Type
            type nw_Counter64;
        }

        // Echo Replies sent    @@@ ICMPV6_PKT_ECHO_REPLIES_SNT_CNT
        // From Interface icmpv6:globalTraffic
        // Type is an MO-Defined-Type
        leaf echoRepSent {
            config "false";
            description "Echo Replies sent";

            // Type is an MO-Defined-Type
            type nw_Counter64;
        }

        // Echo Replies received    @@@ ICMPV6_PKT_ECHO_REPLIES_RECV_CNT
        // From Interface icmpv6:globalTraffic
        // Type is an MO-Defined-Type
        leaf echoRepRcvd {
            config "false";
            description "Echo Replies received";

            // Type is an MO-Defined-Type
            type nw_Counter64;
        }

        // Redirects sent    @@@ ICMPV6_PKT_REDIRECTS_SNT_CNT
        // From Interface icmpv6:globalTraffic
        // Type is an MO-Defined-Type
        leaf redirSent {
            config "false";
            description "Redirects sent";

            // Type is an MO-Defined-Type
            type nw_Counter64;
        }

        // Redirects received    @@@ ICMPV6_PKT_REDIRECTS_RECV_CNT
        // From Interface icmpv6:globalTraffic
        // Type is an MO-Defined-Type
        leaf redirRcvd {
            config "false";
            description "Redirects received";

            // Type is an MO-Defined-Type
            type nw_Counter64;
        }

        // Packet Too Big sent    @@@ ICMPV6_PKT_TOO_BIG_SNT_CNT
        // From Interface icmpv6:globalTraffic
        // Type is an MO-Defined-Type
        leaf tooBigSent {
            config "false";
            description "Packet Too Big sent";

            // Type is an MO-Defined-Type
            type nw_Counter64;
        }

        // Packet Too Big received    @@@ ICMPV6_PKT_TOO_BIG_RECV_CNT
        // From Interface icmpv6:globalTraffic
        // Type is an MO-Defined-Type
        leaf tooBigRcvd {
            config "false";
            description "Packet Too Big received";

            // Type is an MO-Defined-Type
            type nw_Counter64;
        }

        // Router Advertisements sent    @@@ ICMPV6_PKT_ROUTER_ADV_SNT_CNT
        // From Interface icmpv6:globalTraffic
        // Type is an MO-Defined-Type
        leaf raSent {
            config "false";
            description "Router Advertisements sent";

            // Type is an MO-Defined-Type
            type nw_Counter64;
        }

        // Router Advertisements received    @@@ ICMPV6_PKT_ROUTER_ADV_RECV_CNT
        // From Interface icmpv6:globalTraffic
        // Type is an MO-Defined-Type
        leaf raRcvd {
            config "false";
            description "Router Advertisements received";

            // Type is an MO-Defined-Type
            type nw_Counter64;
        }

        // Router Solicitations sent    @@@ ICMPV6_PKT_ROUTER_SOLICITS_SNT_CNT
        // From Interface icmpv6:globalTraffic
        // Type is an MO-Defined-Type
        leaf rsSent {
            config "false";
            description "Router Solicitations sent";

            // Type is an MO-Defined-Type
            type nw_Counter64;
        }

        // Router Solicitations received    @@@ ICMPV6_PKT_ROUTER_SOLICITS_RECV_CNT
        // From Interface icmpv6:globalTraffic
        // Type is an MO-Defined-Type
        leaf rsRcvd {
            config "false";
            description "Router Solicitations received";

            // Type is an MO-Defined-Type
            type nw_Counter64;
        }

        // Neighbor Advertisements sent    @@@ ICMPV6_PKT_NEIGHBOR_ADV_SNT_CNT
        // From Interface icmpv6:globalTraffic
        // Type is an MO-Defined-Type
        leaf naSent {
            config "false";
            description "Neighbor Advertisements sent";

            // Type is an MO-Defined-Type
            type nw_Counter64;
        }

        // Neighbor Advertisements received    @@@ ICMPV6_PKT_NEIGHBOR_ADV_RECV_CNT
        // From Interface icmpv6:globalTraffic
        // Type is an MO-Defined-Type
        leaf naRcvd {
            config "false";
            description "Neighbor Advertisements received";

            // Type is an MO-Defined-Type
            type nw_Counter64;
        }

        // Neighbor Solicitations sent    @@@ ICMPV6_PKT_NEIGHBOR_SOLICITS_SNT_CNT
        // From Interface icmpv6:globalTraffic
        // Type is an MO-Defined-Type
        leaf nsSent {
            config "false";
            description "Neighbor Solicitations sent";

            // Type is an MO-Defined-Type
            type nw_Counter64;
        }

        // Neighbor Solicitations received    @@@ ICMPV6_PKT_NEIGHBOR_SOLICITS_RECV_CNT
        // From Interface icmpv6:globalTraffic
        // Type is an MO-Defined-Type
        leaf nsRcvd {
            config "false";
            description "Neighbor Solicitations received";

            // Type is an MO-Defined-Type
            type nw_Counter64;
        }

        // Duplicate router RA received    @@@ ICMPV6_PKT_DUP_ROUTER
        // From Interface icmpv6:globalTraffic
        // Type is an MO-Defined-Type
        leaf dupRAReceived {
            config "false";
            description "Duplicate router RA received";

            // Type is an MO-Defined-Type
            type nw_Counter64;
        }
        leaf lastNghbrSolicitSent {
            config "false";
            type string;
        }
        leaf lastNghbrAdvertisementSent {
            config "false";
            type string;
        }
        leaf lastRouterAdvertisementSent {
            config "false";
            type string;
        }
        leaf nextRouterAdvertisementSent {
            config "false";
            type string;
        }
    }

    grouping nd_VaddrGlobalStat-group {
        leaf vAddr {
            type address_Ip;
        }
        leaf protocol {
            config "false";
            type string;
        }
        leaf virtualMac {
            config "false";
            type string;
        }
        leaf groupId {
            config "false";
            type uint16;
        }
        leaf clientUUID {
            config "false";
            type uint32;
        }

        // From Interface nd:VADDRCommonField
        // Type is an MO-Defined-Type
        leaf clientState {
            config "false";
            description "Client state";

            // Type is an MO-Defined-Type
            type nd_VaddrClientState;
        }
        leaf clientInUse {
            config "false";
            type uint16;
        }
        leaf clientActiveState {
            config "false";
            type string;
        }
        leaf interface {
            config "false";
            type string;
        }
        leaf context {
            config "false";
            type string;
        }
    }

    grouping nd_IpV6Throttle-group {

        // Enable / Disable glean throttling
        // Type is an MO-Defined-Type
        leaf adminSt {
            description "Glean throttle state";

            // Type is an MO-Defined-Type
            type nw_AdminSt;
        }

        // Threshold for syslog for number of packets hitting the entry
        // Type is an MO-Defined-Type
        leaf syslog {
            description "Glean throttle syslog for number of packets";

            // Type is an MO-Defined-Type
            type nd_SyslogCnt;
        }

        // Max throttle packets count. Crossing this threshold,
        // packet will not be throttled for a particular adjacency
        // Type is an MO-Defined-Type
        leaf maxPacket {
            description "Glean throttle pack count";

            // Type is an MO-Defined-Type
            type nd_MaxPacket;
        }

        // Timeout for throttle setting for a particular adjacency
        // Type is an MO-Defined-Type
        leaf timeout {
            description "Ipv4 glean throttle timeout";

            // Type is an MO-Defined-Type
            type nd_ThrTimeout;
        }
    }

    grouping nd_Vpc-group {

        // This objects hold per vpc domain information. There is only
        // one vpc domain that is configurable in the system
        container dom-items {

            // Added containment as a singleton: Prefix=dom
            // Acquired From Package nd
            uses nd_VpcDom-group;
        }
    }

    grouping nd_VpcDom-group {

        // Enable/Disable IPV6 ND SYNC
        // Type is an MO-Defined-Type
        leaf ndSync {
            description "IPV6 ND Sync";

            // Type is an MO-Defined-Type
            type nw_AdminSt;
        }
    }

    grouping nd_OffListVlan-group {
        leaf vlanId {
            type uint16;
        }
        leaf totalOfflistEntries {
            config "false";
            type uint16;
        }
        leaf addr {
            config "false";
            type address_Ip;
        }
        leaf age {
            config "false";
            type string;
        }
        leaf macAddr {
            config "false";
            type string;
        }
        leaf flags {
            config "false";
            type uint16;
        }
    }

    grouping nd_GlobalTrafficStats-group {

        // Total Messages sent     @@@ ICMPV6_PKT_MSGS_SNT_CNT
        // From Interface icmpv6:globalTraffic
        // Type is an MO-Defined-Type
        leaf totSent {
            config "false";
            description "Total messages sent";

            // Type is an MO-Defined-Type
            type nw_Counter64;
        }

        // Total Messages received     @@@ ICMPV6_PKT_MSGS_RECV_CNT
        // From Interface icmpv6:globalTraffic
        // Type is an MO-Defined-Type
        leaf totRvcd {
            config "false";
            description "Total messages received";

            // Type is an MO-Defined-Type
            type nw_Counter64;
        }

        // Error Messages sent     @@@ ICMPV6_PKT_ERR_SNT_CNT
        // From Interface icmpv6:globalTraffic
        // Type is an MO-Defined-Type
        leaf errSent {
            config "false";
            description "Error messages sent";

            // Type is an MO-Defined-Type
            type nw_Counter64;
        }

        // Error Messages received     @@@ ICMPV6_PKT_ERR_RECV_CNT
        // From Interface icmpv6:globalTraffic
        // Type is an MO-Defined-Type
        leaf errRcvd {
            config "false";
            description "Error messages received";

            // Type is an MO-Defined-Type
            type nw_Counter64;
        }

        // Interface Down Drop Count sent     @@@ ICMPV6_PKT_SNT_DROP_IF_DOWN_CNT
        // From Interface icmpv6:globalTraffic
        // Type is an MO-Defined-Type
        leaf ifDownDropSent {
            config "false";
            description "Interface Down Drop Count sent";

            // Type is an MO-Defined-Type
            type nw_Counter64;
        }

        // Interface Down Drop Count received     @@@ ICMPV6_PKT_RECV_DROP_IF_DOWN_CNT
        // From Interface icmpv6:globalTraffic
        // Type is an MO-Defined-Type
        leaf ifDownDropRcvd {
            config "false";
            description "Interface Down Drop Count received";

            // Type is an MO-Defined-Type
            type nw_Counter64;
        }

        // Adjacency not recovered from AM after HA     @@@ ICMPV6_PKT_DROPPED_HA_NOT_READY
        // From Interface icmpv6:globalTraffic
        // Type is an MO-Defined-Type
        leaf dropHaNotRdy {
            config "false";
            description "Adjacency not recovered from AM after HA";

            // Type is an MO-Defined-Type
            type nw_Counter64;
        }

        // Pkts allowed due to inv ttl on vPC-MCT     @@@ ICMPV6_PKT_ALLOW_MCT_TTL_CNT
        // From Interface icmpv6:globalTraffic
        // Type is an MO-Defined-Type
        leaf dropInvldTtlMct {
            config "false";
            description "Pkts allowed due to inv ttl on vPC-MCT";

            // Type is an MO-Defined-Type
            type nw_Counter64;
        }

        // Pkts dropped as source mac addr is own     @@@ ICMPV6_PKT_RECV_DROP_OWN_SRC_MAC_COUNT
        // From Interface icmpv6:globalTraffic
        // Type is an MO-Defined-Type
        leaf dropSrcMacOwnRcvd {
            config "false";
            description "Pkts dropped as source mac addr is own";

            // Type is an MO-Defined-Type
            type nw_Counter64;
        }

        // Pkts dropped as tgt ip addr is not own     @@@ ICMPV6_PKT_RECV_DROP_TARGET_NOT_US_COUNT
        // From Interface icmpv6:globalTraffic
        // Type is an MO-Defined-Type
        leaf dropTgtIpNotOwnRcvd {
            config "false";
            description "Pkts dropped as tgt ip addr is not own";

            // Type is an MO-Defined-Type
            type nw_Counter64;
        }

        // Pkts dropped as src ip addr is not own     @@@ ICMPV6_PKT_RECV_DROP_SRC_NOT_US_COUNT
        // From Interface icmpv6:globalTraffic
        // Type is an MO-Defined-Type
        leaf dropSrcIpNotOwnRcvd {
            config "false";
            description "Pkts dropped as src ip addr is not own";

            // Type is an MO-Defined-Type
            type nw_Counter64;
        }

        // Destination Unreachables sent     @@@ ICMPV6_PKT_DEST_UNREACHS_SNT_CNT
        // From Interface icmpv6:globalTraffic
        // Type is an MO-Defined-Type
        leaf destUnreachSent {
            config "false";
            description "Destination Unreachables sent";

            // Type is an MO-Defined-Type
            type nw_Counter64;
        }

        // Destination Unreachables received    @@@ ICMPV6_PKT_DEST_UNREACHS_RECV_CNT
        // From Interface icmpv6:globalTraffic
        // Type is an MO-Defined-Type
        leaf destUnreachRcvd {
            config "false";
            description "Destination Unreachables received";

            // Type is an MO-Defined-Type
            type nw_Counter64;
        }

        // Administratively Prohibited sent    @@@ ICMPV6_PKT_ADMIN_PROHIBS_SNT_CNT
        // From Interface icmpv6:globalTraffic
        // Type is an MO-Defined-Type
        leaf adminProhibSent {
            config "false";
            description "Administratively Prohibited sent";

            // Type is an MO-Defined-Type
            type nw_Counter64;
        }

        // Administratively Prohibited received    @@@ ICMPV6_PKT_ADMIN_PROHIBS_RECV_CNT
        // From Interface icmpv6:globalTraffic
        // Type is an MO-Defined-Type
        leaf adminProhibRcvd {
            config "false";
            description "Administratively Prohibited received";

            // Type is an MO-Defined-Type
            type nw_Counter64;
        }

        // Time Exceeded sent    @@@ ICMPV6_PKT_TIME_EXCDS_SNT_CNT
        // From Interface icmpv6:globalTraffic
        // Type is an MO-Defined-Type
        leaf timeExcdSent {
            config "false";
            description "Time Exceeded sent ";

            // Type is an MO-Defined-Type
            type nw_Counter64;
        }

        // Time Exceeded received    @@@ ICMPV6_PKT_TIME_EXCDS_RECV_CNT
        // From Interface icmpv6:globalTraffic
        // Type is an MO-Defined-Type
        leaf timeExcdRcvd {
            config "false";
            description "Time Exceeded received";

            // Type is an MO-Defined-Type
            type nw_Counter64;
        }

        // Parameter Problems sent    @@@ ICMPV6_PKT_PARM_PROBS_SNT_CNT
        // From Interface icmpv6:globalTraffic
        // Type is an MO-Defined-Type
        leaf parmPrblmSent {
            config "false";
            description "Parameter Problems sent";

            // Type is an MO-Defined-Type
            type nw_Counter64;
        }

        // Parameter Problems received    @@@ ICMPV6_PKT_PARM_PROBS_RECV_CNT
        // From Interface icmpv6:globalTraffic
        // Type is an MO-Defined-Type
        leaf parmPrblmRcvd {
            config "false";
            description "Parameter Problems received";

            // Type is an MO-Defined-Type
            type nw_Counter64;
        }

        // Echo Request sent    @@@ ICMPV6_PKT_ECHOS_SNT_CNT
        // From Interface icmpv6:globalTraffic
        // Type is an MO-Defined-Type
        leaf echoReqSent {
            config "false";
            description "Echo Request sent";

            // Type is an MO-Defined-Type
            type nw_Counter64;
        }

        // Echo Request received    @@@ ICMPV6_PKT_ECHOS_RECV_CNT
        // From Interface icmpv6:globalTraffic
        // Type is an MO-Defined-Type
        leaf echoReqRcvd {
            config "false";
            description "Echo Request received";

            // Type is an MO-Defined-Type
            type nw_Counter64;
        }

        // Echo Replies sent    @@@ ICMPV6_PKT_ECHO_REPLIES_SNT_CNT
        // From Interface icmpv6:globalTraffic
        // Type is an MO-Defined-Type
        leaf echoRepSent {
            config "false";
            description "Echo Replies sent";

            // Type is an MO-Defined-Type
            type nw_Counter64;
        }

        // Echo Replies received    @@@ ICMPV6_PKT_ECHO_REPLIES_RECV_CNT
        // From Interface icmpv6:globalTraffic
        // Type is an MO-Defined-Type
        leaf echoRepRcvd {
            config "false";
            description "Echo Replies received";

            // Type is an MO-Defined-Type
            type nw_Counter64;
        }

        // Redirects sent    @@@ ICMPV6_PKT_REDIRECTS_SNT_CNT
        // From Interface icmpv6:globalTraffic
        // Type is an MO-Defined-Type
        leaf redirSent {
            config "false";
            description "Redirects sent";

            // Type is an MO-Defined-Type
            type nw_Counter64;
        }

        // Redirects received    @@@ ICMPV6_PKT_REDIRECTS_RECV_CNT
        // From Interface icmpv6:globalTraffic
        // Type is an MO-Defined-Type
        leaf redirRcvd {
            config "false";
            description "Redirects received";

            // Type is an MO-Defined-Type
            type nw_Counter64;
        }

        // Packet Too Big sent    @@@ ICMPV6_PKT_TOO_BIG_SNT_CNT
        // From Interface icmpv6:globalTraffic
        // Type is an MO-Defined-Type
        leaf tooBigSent {
            config "false";
            description "Packet Too Big sent";

            // Type is an MO-Defined-Type
            type nw_Counter64;
        }

        // Packet Too Big received    @@@ ICMPV6_PKT_TOO_BIG_RECV_CNT
        // From Interface icmpv6:globalTraffic
        // Type is an MO-Defined-Type
        leaf tooBigRcvd {
            config "false";
            description "Packet Too Big received";

            // Type is an MO-Defined-Type
            type nw_Counter64;
        }

        // Router Advertisements sent    @@@ ICMPV6_PKT_ROUTER_ADV_SNT_CNT
        // From Interface icmpv6:globalTraffic
        // Type is an MO-Defined-Type
        leaf raSent {
            config "false";
            description "Router Advertisements sent";

            // Type is an MO-Defined-Type
            type nw_Counter64;
        }

        // Router Advertisements received    @@@ ICMPV6_PKT_ROUTER_ADV_RECV_CNT
        // From Interface icmpv6:globalTraffic
        // Type is an MO-Defined-Type
        leaf raRcvd {
            config "false";
            description "Router Advertisements received";

            // Type is an MO-Defined-Type
            type nw_Counter64;
        }

        // Router Solicitations sent    @@@ ICMPV6_PKT_ROUTER_SOLICITS_SNT_CNT
        // From Interface icmpv6:globalTraffic
        // Type is an MO-Defined-Type
        leaf rsSent {
            config "false";
            description "Router Solicitations sent";

            // Type is an MO-Defined-Type
            type nw_Counter64;
        }

        // Router Solicitations received    @@@ ICMPV6_PKT_ROUTER_SOLICITS_RECV_CNT
        // From Interface icmpv6:globalTraffic
        // Type is an MO-Defined-Type
        leaf rsRcvd {
            config "false";
            description "Router Solicitations received";

            // Type is an MO-Defined-Type
            type nw_Counter64;
        }

        // Neighbor Advertisements sent    @@@ ICMPV6_PKT_NEIGHBOR_ADV_SNT_CNT
        // From Interface icmpv6:globalTraffic
        // Type is an MO-Defined-Type
        leaf naSent {
            config "false";
            description "Neighbor Advertisements sent";

            // Type is an MO-Defined-Type
            type nw_Counter64;
        }

        // Neighbor Advertisements received    @@@ ICMPV6_PKT_NEIGHBOR_ADV_RECV_CNT
        // From Interface icmpv6:globalTraffic
        // Type is an MO-Defined-Type
        leaf naRcvd {
            config "false";
            description "Neighbor Advertisements received";

            // Type is an MO-Defined-Type
            type nw_Counter64;
        }

        // Neighbor Solicitations sent    @@@ ICMPV6_PKT_NEIGHBOR_SOLICITS_SNT_CNT
        // From Interface icmpv6:globalTraffic
        // Type is an MO-Defined-Type
        leaf nsSent {
            config "false";
            description "Neighbor Solicitations sent";

            // Type is an MO-Defined-Type
            type nw_Counter64;
        }

        // Neighbor Solicitations received    @@@ ICMPV6_PKT_NEIGHBOR_SOLICITS_RECV_CNT
        // From Interface icmpv6:globalTraffic
        // Type is an MO-Defined-Type
        leaf nsRcvd {
            config "false";
            description "Neighbor Solicitations received";

            // Type is an MO-Defined-Type
            type nw_Counter64;
        }

        // Duplicate router RA received    @@@ ICMPV6_PKT_DUP_ROUTER
        // From Interface icmpv6:globalTraffic
        // Type is an MO-Defined-Type
        leaf dupRAReceived {
            config "false";
            description "Duplicate router RA received";

            // Type is an MO-Defined-Type
            type nw_Counter64;
        }

        // Fastpath Packets     @@@ ICMPV6_PKT_FASTPATH_RECV_CNT
        // From Interface icmpv6:globalTrafficFastPath
        // Type is an MO-Defined-Type
        leaf fastpthRcvd {
            config "false";
            description "Fastpath Packets";

            // Type is an MO-Defined-Type
            type nw_Counter64;
        }

        // Ignored Fastpath Packets - Fastpath disabled    @@@ ICMPV6_PKT_RECV_DROP_FASTPATH_DISABLED_CNT
        // From Interface icmpv6:globalTrafficFastPath
        // Type is an MO-Defined-Type
        leaf fastpathDsbleIgnRcvd {
            config "false";
            description "Ignored Fastpath Packets - Fastpath disabled";

            // Type is an MO-Defined-Type
            type nw_Counter64;
        }

        // Ignored Fastpath Packets - others    @@@ ICMPV6_PKT_RECV_DROP_REQUEST_IGNORE_CNT
        // From Interface icmpv6:globalTrafficFastPath
        // Type is an MO-Defined-Type
        leaf fastpathOtherIgnRcvd {
            config "false";
            description "Ignored fastpath packets - others";

            // Type is an MO-Defined-Type
            type nw_Counter64;
        }

        // @@@ ICMPV6_PKT_MLD_V1_QUERY_SNT_CNT
        // From Interface icmpv6:GlobalMLDStats
        // Type is an MO-Defined-Type
        leaf mldV1QueriesSent {
            config "false";
            description "V1 queries sent";

            // Type is an MO-Defined-Type
            type nw_Counter64;
        }

        // @@@ ICMPV6_PKT_MLD_V1_QUERY_RECV_CNT
        // From Interface icmpv6:GlobalMLDStats
        // Type is an MO-Defined-Type
        leaf mldV1QueriesRecv {
            config "false";
            description "V1 queries received";

            // Type is an MO-Defined-Type
            type nw_Counter64;
        }

        // @@@ ICMPV6_PKT_MLD_V2_QUERY_SNT_CNT
        // From Interface icmpv6:GlobalMLDStats
        // Type is an MO-Defined-Type
        leaf mldV2QueriesSent {
            config "false";
            description "V2 queries sent";

            // Type is an MO-Defined-Type
            type nw_Counter64;
        }

        // @@@ ICMPV6_PKT_MLD_V2_QUERY_RECV_CNT
        // From Interface icmpv6:GlobalMLDStats
        // Type is an MO-Defined-Type
        leaf mldV2QueriesRecv {
            config "false";
            description "V2 queries received";

            // Type is an MO-Defined-Type
            type nw_Counter64;
        }

        // @@@ ICMPV6_PKT_MLD_V1_REPORTS_SNT_CNT
        // From Interface icmpv6:GlobalMLDStats
        // Type is an MO-Defined-Type
        leaf mldV1ReportsSent {
            config "false";
            description "V1 reports sent";

            // Type is an MO-Defined-Type
            type nw_Counter64;
        }

        // @@@ ICMPV6_PKT_MLD_V1_REPORTS_RECV_CNT
        // From Interface icmpv6:GlobalMLDStats
        // Type is an MO-Defined-Type
        leaf mldV1ReportsRecv {
            config "false";
            description "V1 reports received";

            // Type is an MO-Defined-Type
            type nw_Counter64;
        }

        // @@@ ICMPV6_PKT_MLD_V2_REPORTS_SNT_CNT
        // From Interface icmpv6:GlobalMLDStats
        // Type is an MO-Defined-Type
        leaf mldV2ReportsSent {
            config "false";
            description "V2 reports sent";

            // Type is an MO-Defined-Type
            type nw_Counter64;
        }

        // @@@ ICMPV6_PKT_MLD_V2_REPORTS_RECV_CNT
        // From Interface icmpv6:GlobalMLDStats
        // Type is an MO-Defined-Type
        leaf mldV2ReportsRecv {
            config "false";
            description "V2 reports received";

            // Type is an MO-Defined-Type
            type nw_Counter64;
        }

        // @@@ ICMPV6_PKT_MLD_V1_LEAVES_SNT_CNT
        // From Interface icmpv6:GlobalMLDStats
        // Type is an MO-Defined-Type
        leaf mldV1LeavesSent {
            config "false";
            description "V1 leaves sent";

            // Type is an MO-Defined-Type
            type nw_Counter64;
        }

        // @@@ ICMPV6_PKT_MLD_V1_LEAVES_RECV_CNT
        // From Interface icmpv6:GlobalMLDStats
        // Type is an MO-Defined-Type
        leaf mldV1LeavesRecv {
            config "false";
            description "V1 leaves received";

            // Type is an MO-Defined-Type
            type nw_Counter64;
        }
    }

    grouping nd_VaddrLinkLocalStat-group {
        leaf vAddr {
            type address_Ip;
        }
        leaf virtualMac {
            config "false";
            type string;
        }
        leaf interface {
            config "false";
            type string;
        }
        leaf active {
            config "false";
            type string;
        }
    }

    grouping nd_VPCStat-group {
        leaf cfsStatus {
            config "false";
            type string;
        }
        leaf layer3Routing {
            config "false";
            type string;
        }
        leaf syncProcDropRecvPullReq {
            config "false";
            type uint16;
        }
        leaf syncProcDropRecvPushMsg {
            config "false";
            type uint16;
        }
        leaf syncIgnoreSendPullReq {
            config "false";
            type uint16;
        }
        leaf syncIgnoreSendPushMsg {
            config "false";
            type uint16;
        }
        leaf syncDropIMApiFailed {
            config "false";
            type uint16;
        }
        leaf syncDropMcemApiFailed {
            config "false";
            type uint16;
        }
        leaf syncDropInvalidPcIod {
            config "false";
            type uint16;
        }
        leaf syncProcDropPtLookupFailed {
            config "false";
            type uint16;
        }
        leaf syncProcDropRespFailedNomct {
            config "false";
            type uint16;
        }
        leaf syncProcDropRespFailed {
            config "false";
            type uint16;
        }
        leaf syncProcDropMCEMIfindexVpcConvFailed {
            config "false";
            type uint16;
        }
        leaf syncProcDropMCEMVpcIfindexConvFailed {
            config "false";
            type uint16;
        }
        leaf PeriodicSyncProcDropMCEMIfindexVpcConvFailed {
            config "false";
            type uint16;
        }
        leaf periodicSyncProcDropMCEMVpcIfindexConvFailed {
            config "false";
            type uint16;
        }
        leaf syncProcRespSent {
            config "false";
            type uint16;
        }
        leaf syncProcRespRcvd {
            config "false";
            type uint16;
        }
        leaf syncProcRespRcvdErr {
            config "false";
            type uint16;
        }
        leaf syncProcRcvdMsg {
            config "false";
            type uint16;
        }
        leaf syncProcSendFailed {
            config "false";
            type uint16;
        }
        leaf syncProcCfsRelDlvryFailed {
            config "false";
            type uint16;
        }
        leaf syncProcCfsRelDlvrySuccess {
            config "false";
            type uint16;
        }
        leaf offlistProcDropPtAddFailed {
            config "false";
            type uint16;
        }
        leaf offlistProcDropNoMem {
            config "false";
            type uint16;
        }
        leaf offlistProcDropTmrCreateFailed {
            config "false";
            type uint16;
        }
        leaf offlistProcDropAddAdjFailed {
            config "false";
            type uint16;
        }
        leaf offlistProcDropPtLookupFailed {
            config "false";
            type uint16;
        }
        leaf offlistProcNoDropVlanMismatch {
            config "false";
            type uint16;
        }
        leaf offlistProcDropSVIInvalid {
            config "false";
            type uint16;
        }
        leaf offlistProcNoDropSVIDown {
            config "false";
            type uint16;
        }
        leaf offlistProcDropMCTDown {
            config "false";
            type uint16;
        }
        leaf offlistProcDropCtxtInvalid {
            config "false";
            type uint16;
        }
        leaf offlistProcDropVRFInvalid {
            config "false";
            type uint16;
        }
        leaf offlistProcDropL3addrInvalid {
            config "false";
            type uint16;
        }
        leaf offlistProcDropL3addrSanityFailed {
            config "false";
            type uint16;
        }
        leaf offlistProcDropMacSanityFailed {
            config "false";
            type uint16;
        }
        leaf offlistProcDropOwnMac {
            config "false";
            type uint16;
        }
        leaf offlistProcDropOwnIpv6Addr {
            config "false";
            type uint16;
        }
        leaf offlistProcDropOwnVIPv6Addr {
            config "false";
            type uint16;
        }
        leaf offlistProcDropCreateAdjFailed {
            config "false";
            type uint16;
        }
        leaf offlistProcDropSubnetMismatch {
            config "false";
            type uint16;
        }
        leaf offlistProcDropAdjAlreadyExist {
            config "false";
            type uint16;
        }
        leaf offlistProcNoDropIpv6Disabled {
            config "false";
            type uint16;
        }
        leaf offlistProcDropCount {
            config "false";
            type uint16;
        }
        leaf offlistProcNoDropCount {
            config "false";
            type uint16;
        }
        leaf offlistProcAddAdj {
            config "false";
            type uint16;
        }
        leaf offlistProcDelAdj {
            config "false";
            type uint16;
        }
        leaf offlistProcAdjAlreadyExist {
            config "false";
            type uint16;
        }
    }

    grouping ospfv3_Entity-group {

        // Inherited From nw:Conn
        // Modified by Override: nw:CpEntity->name
        // Modified by Override: ospf:AEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per ospf instance information.
        container inst-items {
            list Inst-list {
                key "name";

                // Added containment: Prefix=inst
                // Acquired From Package ospfv3
                uses ospfv3_Inst-group;
            }
        }

        // This object holds ospfv3 information that is operated at a
        // interface level
        container if-items {
            list InternalIf-list {
                config "false";
                key "id instanceid";

                // Added containment: Prefix=if
                // Acquired From Package ospfv3
                uses ospfv3_InternalIf-group;
            }
        }
    }

    grouping ospfv3_Inst-group {

        // Inherited From nw:Conn
        // Modified by Override: nw:CpInst->name
        // Modified by Override: ospf:AInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Modified by Override: ospf:AInst->ctrl
        // Type is an MO-Defined-Type
        // Default value handled in local MO type
        leaf ctrl {
            description "Controls";

            // Type is a Local-MO-Defined-Type
            type nw_InstCtrl_Inst_ctrl;
        }

        // Operational errors qualifier
        // Inherited From nw:CpInst
        // Type is an MO-Defined-Type
        leaf operErr {
            config "false";
            description "Operational Errors Qualifier";

            // Type is an MO-Defined-Type
            type nw_OperErrQual;
        }

        // Memory alert level
        // Inherited From ospf:AInst
        // Type is an MO-Defined-Type
        leaf memAlert {
            config "false";
            description "Memory Alert Level";

            // Type is an MO-Defined-Type
            type nw_MemAlertLevel;
        }
        leaf deletedViaCLI {
            config "false";
            type boolean;
        }

        // This objects hold per ospf domain (vrf) information
        container dom-items {
            list Dom-list {
                key "name";

                // Added containment: Prefix=dom
                // Acquired From Package ospfv3
                uses ospfv3_Dom-group;
            }
        }

        // This object holds the size of the Logfiles for
        // various types of OSPFv3 events
        container evtLogs-items {
            list EventLogs-list {
                key "eventType";

                // Added containment: Prefix=evtLogs
                // Acquired From Package ospfv3
                uses ospfv3_EventLogs-group;
            }
        }
    }

    grouping ospfv3_Dom-group {

        // Inherited From nw:Conn
        // Modified by Override: nw:CpDom->name
        // Modified by Override: ospf:ADom->name
        // Type is an MO-Defined-Type
        leaf name {
            description "Name";

            // Type is an MO-Defined-Type
            type naming_Name {
                length "1..64";
            }
        }

        // Router id for this domain, if this is not specified
        // the router-id is automatically picked up based on the
        // first interface that comes up in that domain
        // Inherited From ospf:ADom
        // Type is an MO-Defined-Type
        leaf rtrId {
            description "Router ID";

            // Type is an MO-Defined-Type
            type ip_RtrId;
        }

        // Dom controls
        // Inherited From ospf:ADom
        // Type is an MO-Defined-Type
        leaf ctrl {
            description "Controls";

            // Type is an MO-Defined-Type
            type ospf_DomControl;
        }

        // Admin state
        // Inherited From ospf:ADom
        // Type is an MO-Defined-Type
        leaf adminSt {
            description "Administrative state";

            // Type is an MO-Defined-Type
            type nw_AdminSt;
        }

        // Administrative distance preference
        // Inherited From ospf:ADom
        // Type is an MO-Defined-Type
        leaf dist {
            description "Distance";

            // Type is an MO-Defined-Type
            type ospf_Dist;
        }

        // MAX ECMP
        // Inherited From ospf:ADom
        // Type is an MO-Defined-Type
        leaf maxEcmp {
            description "Max ECMP";

            // Type is an MO-Defined-Type
            type ospf_Ecmp;
        }

        // Bandwidth Reference value. If bwRefUnit is mbps, then the
        // range is 1 to 4000000 and if bwRefUnit is gbps, then the
        // range is 1 to 4000
        // Inherited From ospf:ADom
        // Type is an MO-Defined-Type
        leaf bwRef {
            description "Bandwidth Reference value";

            // Type is an MO-Defined-Type
            type ospf_BwRef;
        }

        // Bandwidth Reference Unit
        // Inherited From ospf:ADom
        // Type is an MO-Defined-Type
        leaf bwRefUnit {
            description "Bandwidth Reference Unit (Mbps or Gbps)";

            // Type is an MO-Defined-Type
            type ospf_BwRefUnit;
        }

        // Default Metric for redistributed routes
        // Inherited From ospf:ADom
        // Type is an MO-Defined-Type
        leaf defMetric {
            description "Default metric cost";

            // Type is an MO-Defined-Type
            type ospf_Metric;
        }
        leaf rfc1583Compat {
            type boolean;
        }
        leaf deletedViaCLI {
            config "false";
            type boolean;
        }

        // Adjacency change logging level
        // Inherited From ospf:ADom
        // Type is an MO-Defined-Type
        leaf adjChangeLogLevel {
            description "Adjacency change logging level";

            // Type is an MO-Defined-Type
            type ospf_AdjChangeLogLevel;
        }

        // L3VM Operational state
        // Inherited From ospf:ADom
        // Type is an MO-Defined-Type
        leaf operSt {
            config "false";
            description "L3vm Operational State";

            // Type is an MO-Defined-Type
            type ospf_OperSt;
        }

        // Operational Router id for this dom, if it is not specified
        // the router-id is automatically picked up based on the
        // first interface that comes up in that domain
        // Inherited From ospf:ADom
        // Type is an MO-Defined-Type
        leaf operRtrId {
            config "false";
            description "Operational Router ID";

            // Type is an MO-Defined-Type
            type ip_RtrId;
        }

        // Discard Route Bits
        // Inherited From ospf:ADom
        // Type is an MO-Defined-Type
        leaf discardRoute {
            description "Ctrl bits for discard-route external and internal";

            // Type is an MO-Defined-Type
            type ospf_DiscardRoute;
        }
        leaf downbitIgnore {
            type boolean;
        }

        // Capability vrf-lite
        // Inherited From ospf:ADom
        // Type is an MO-Defined-Type
        leaf capVrfLite {
            description "capability vrf-lite";

            // Type is an MO-Defined-Type
            type ospf_VrfLiteControl;
        }

        // This object holds ospf information that is operated at a
        // interface level
        container area-items {
            list Area-list {
                key "id";

                // Added containment: Prefix=area
                // Acquired From Package ospfv3
                uses ospfv3_Area-group;
            }
        }

        // OSPF databases
        container db-items {
            list Db-list {
                config "false";
                key "type";

                // Added containment: Prefix=db
                // Acquired From Package ospfv3
                uses ospfv3_Db-group;
            }
        }

        // This object holds per address family bgp vrf information
        container domaf-items {
            list DomAf-list {
                key "type";

                // Added containment: Prefix=domaf
                // Acquired From Package ospfv3
                uses ospfv3_DomAf-group;
            }
        }

        // This object holds spf computation frequency controls, none
        // of these need to be exposed to the user
        container spfcomp-items {

            // Added containment as a singleton: Prefix=spfcomp
            // Acquired From Package ospfv3
            uses ospfv3_SpfComp-group;
        }

        // This object holds lsa related frequency controls, none of
        // these need to be exposed to the user
        container lsactrl-items {

            // Added containment as a singleton: Prefix=lsactrl
            // Acquired From Package ospfv3
            uses ospfv3_LsaCtrl-group;
        }

        // This object holds the ospf dom related statistics
        container domstats-items {

            // Added containment as a singleton: Prefix=domstats
            // Acquired From Package ospfv3
            uses ospfv3_DomStats-group;
        }

        // This objects hold per domain graceful restart information
        container gr-items {

            // Added containment as a singleton: Prefix=gr
            // Acquired From Package ospfv3
            uses ospfv3_Gr-group;
        }

        // This object holds ospf information that is operated at a
        // interface level
        container if-items {
            list If-list {
                key "id";

                // Added containment: Prefix=if
                // Acquired From Package ospfv3
                uses ospfv3_If-group;
            }
        }

        // This object holds per domain max-lsa information
        container maxmetriclsap-items {

            // Added containment as a singleton: Prefix=maxmetriclsap
            // Acquired From Package ospfv3
            uses ospfv3_MaxMetricLsaP-group;
        }

        // This object holds the ospf traffic related information
        container trstats-items {

            // Added containment as a singleton: Prefix=trstats
            // Acquired From Package ospfv3
            uses ospfv3_TrafficStats-group;
        }
    }

    grouping ospfv3_Area-group {

        // Inherited From nw:Conn
        // Modified by Override: nw:CpDom->name
        // Modified by Override: ospf:AArea->name
        // Type is an MO-Defined-Type
        leaf name {
            description "Name";

            // Type is an MO-Defined-Type
            type naming_Name {
                length "1..64";
            }
        }

        // Area id
        // Inherited From ospf:AArea
        // Type is an MO-Defined-Type
        leaf id {
            description "ID";

            // Type is an MO-Defined-Type
            type ospf_AreaId;
        }

        // Area type (stub | nssa | backbone, etc)
        // Inherited From ospf:AArea
        // Type is an MO-Defined-Type
        leaf type {
            description "Type";

            // Type is an MO-Defined-Type
            type ospf_AreaT;
        }

        // Area controls
        // Inherited From ospf:AArea
        // Type is an MO-Defined-Type
        leaf ctrl {
            description "Controls";

            // Type is an MO-Defined-Type
            type ospf_AreaControl;
        }

        // Area cost, specifies cost for default summary LSAs.
        // Used with nssa/stub area types. Not applicable in
        // our fabric solution
        // Inherited From ospf:AArea
        // Type is an MO-Defined-Type
        leaf cost {
            description "Cost";

            // Type is an MO-Defined-Type
            type ospf_AreaCost;
        }

        // NSSA translator role
        // Inherited From ospf:AArea
        // Type is an MO-Defined-Type
        leaf nssaTransRole {
            description "NSSA Translator Role";

            // Type is an MO-Defined-Type
            type ospf_NssaTransRole;
        }

        // Border router count
        // Inherited From ospf:AArea
        // Type is an MO-Defined-Type
        leaf brCnt {
            config "false";
            description "Area Border Router Count";

            // Type is an MO-Defined-Type
            type ospf_BrCnt;
        }

        // AS Border router count
        // Inherited From ospf:AArea
        // Type is an MO-Defined-Type
        leaf asbrCnt {
            config "false";
            description "AS Border Router Count";

            // Type is an MO-Defined-Type
            type ospf_AsbrCnt;
        }

        // LSA checksum sum
        // Inherited From ospf:AArea
        // Type is an MO-Defined-Type
        leaf lsaCksumSum {
            config "false";
            description "LSA Checksum Sum";

            // Type is an MO-Defined-Type
            type ospf_LsaCksumSum;
        }

        // NSSA translator state
        // Inherited From ospf:AArea
        // Type is an MO-Defined-Type
        leaf nssaTransSt {
            config "false";
            description "NSSA Translator State";

            // Type is an MO-Defined-Type
            type ospf_NssaTransSt;
        }

        // NSSA translator stability interval
        // Inherited From ospf:AArea
        // Type is an MO-Defined-Type
        leaf nssaTransStabIntvl {
            config "false";
            description "NSSA Translator Stability Interval";

            // Type is an MO-Defined-Type
            type ospf_NssaTransStabIntvl;
        }

        // Authentication type
        // Inherited From ospf:AArea
        // Type is an MO-Defined-Type
        leaf authType {
            description "Type";

            // Type is an MO-Defined-Type
            type ospf_AuthT;
        }

        // This object holds per address family bgp vrf information
        container areaaf-items {
            list AreaAf-list {
                key "type";

                // Added containment: Prefix=areaaf
                // Acquired From Package ospfv3
                uses ospfv3_AreaAf-group;
            }
        }

        // This object holds the ospf area related statistics
        container areastats-items {

            // Added containment as a singleton: Prefix=areastats
            // Acquired From Package ospfv3
            uses ospfv3_AreaStats-group;
        }

        // OSPF databases
        container db-items {
            list Db-list {
                config "false";
                key "type";

                // Added containment: Prefix=db
                // Acquired From Package ospfv3
                uses ospfv3_Db-group;
            }
        }
    }

    grouping ospfv3_AreaAf-group {

        // Inherited From nw:Conn
        // Modified by Override: nw:CpDom->name
        // Type is an MO-Defined-Type
        leaf name {
            description "Name";

            // Type is an MO-Defined-Type
            type naming_Name {
                length "1..64";
            }
        }

        // Type
        // Inherited From ospf:Af
        // Type is an MO-Defined-Type
        leaf type {
            description "Type";

            // Type is an MO-Defined-Type
            type ospf_AfT;
        }

        // Inter-area route summarization. This is configured
        // on ABRs, summarizing routes between areas in the
        // autonomous system
        container iartsum-items {
            list InterAreaRtSum-list {
                key "addr";

                // Added containment: Prefix=iartsum
                // Acquired From Package ospfv3
                uses ospfv3_InterAreaRtSum-group;
            }
        }
    }

    grouping ospfv3_InterAreaRtSum-group {

        // From Interface naming:Named
        // Inherited From naming:NamedObject
        // Modified by Override: pol:Obj->name
        // Modified by Override: ospf:ARtSum->name
        // Type is an MO-Defined-Type
        leaf name {
            description "Name";

            // Type is an MO-Defined-Type
            type naming_Name {
                length "0..64";
            }
        }

        // From Interface naming:Described
        // Inherited From pol:Instr
        // Modified by Override: ospf:ARtSum->descr
        // Type is an MO-Defined-Type
        leaf descr {
            config "false";
            description "Description";

            // Type is an MO-Defined-Type
            type naming_Descr;
        }
        leaf addr {
            type address_Ip;
        }

        // Summary address no Advertise
        // Inherited From ospf:ARtSum
        // Type is an MO-Defined-Type
        leaf ctrl {
            description "Controls";

            // Type is an MO-Defined-Type
            type ospf_SumControl;
        }

        // Number of component routes
        // Inherited From ospf:ARtSum
        // Type is an MO-Defined-Type
        leaf compRtCnt {
            config "false";
            description "Number of component routes";

            // Type is an MO-Defined-Type
            type nw_Counter32;
        }

        // Route summary cost
        // Inherited From ospf:ARtSum
        // Type is an MO-Defined-Type
        leaf operCost {
            config "false";
            description "Route Summary Operational Cost";

            // Type is an MO-Defined-Type
            type ospf_SumCost;
        }

        // Area range cost
        // Inherited From ospf:AInterAreaRtSum
        // Type is an MO-Defined-Type
        leaf cost {
            description "Area range cost";

            // Type is an MO-Defined-Type
            type ospf_SumCost;
        }
    }

    grouping ospfv3_AreaStats-group {
        leaf areaCreatedTs {
            config "false";
            type uint64;
        }

        // Number of SPF runs
        // Inherited From ospf:AAreaStats
        // Type is an MO-Defined-Type
        leaf spfRuns {
            config "false";
            description "SPF Runs";

            // Type is an MO-Defined-Type
            type ospf_Counter32;
        }

        // LSA count
        // Inherited From ospf:AAreaStats
        // Type is an MO-Defined-Type
        leaf lsaCnt {
            config "false";
            description "LSA Count";

            // Type is an MO-Defined-Type
            type ospf_Counter32;
        }
        leaf lastSpfDuration {
            config "false";
            type uint32;
        }

        // Total number of interfaces
        // Inherited From ospf:AAreaStats
        // Type is an MO-Defined-Type
        leaf ifCnt {
            config "false";
            description "Interface Count";

            // Type is an MO-Defined-Type
            type ospf_Counter32;
        }

        // Number of active interfaces
        // Inherited From ospf:AAreaStats
        // Type is an MO-Defined-Type
        leaf activeIfCnt {
            config "false";
            description "Active Interface Count";

            // Type is an MO-Defined-Type
            type ospf_Counter32;
        }

        // Number of passive interfaces
        // Inherited From ospf:AAreaStats
        // Type is an MO-Defined-Type
        leaf passiveIfCnt {
            config "false";
            description "Passive Interface Count";

            // Type is an MO-Defined-Type
            type ospf_Counter32;
        }

        // Number of loopback interfaces
        // Inherited From ospf:AAreaStats
        // Type is an MO-Defined-Type
        leaf lpbkIfCnt {
            config "false";
            description "Loopback Interface Count";

            // Type is an MO-Defined-Type
            type ospf_Counter32;
        }

        // Number of adjacency
        // Inherited From ospf:AAreaStats
        // Type is an MO-Defined-Type
        leaf adjCnt {
            config "false";
            description "Adjacency Count";

            // Type is an MO-Defined-Type
            type ospf_Counter32;
        }

        // Number of peers in hitless helper mode
        // Inherited From ospf:AAreaStats
        // Type is an MO-Defined-Type
        leaf grHelperPeerCnt {
            config "false";
            description "GR Helper Peer Count";

            // Type is an MO-Defined-Type
            type ospf_Counter32;
        }
    }

    grouping ospfv3_Db-group {

        // Inherited From nw:Conn
        // Modified by Override: nw:Db->name
        // Type is an MO-Defined-Type
        leaf name {
            description "Name";

            // Type is an MO-Defined-Type
            type naming_Name {
                length "1..64";
            }
        }

        // Type of the repository
        // Inherited From ospf:ADb
        // Type is an MO-Defined-Type
        leaf type {
            config "false";
            description "Type";

            // Type is an MO-Defined-Type
            type ospf_DbT;
        }

        // LSA records
        container lsa-items {
            list LsaRec-list {
                config "false";
                key "type id advRtr";

                // Added containment: Prefix=lsa
                // Acquired From Package ospfv3
                uses ospfv3_LsaRec-group;
            }
        }

        // This object holds the ospf route information
        container rt-items {
            list Route-list {
                config "false";
                key "pfx";

                // Added containment: Prefix=rt
                // Acquired From Package ospfv3
                uses ospfv3_Route-group;
            }
        }
    }

    grouping ospfv3_LsaRec-group {

        // Inherited From nw:Conn
        // Modified by Override: nw:DbRec->name
        // Type is an MO-Defined-Type
        leaf name {
            description "Name";

            // Type is an MO-Defined-Type
            type naming_Name {
                length "1..64";
            }
        }

        // Lsa type
        // Inherited From ospf:ALsaRec
        // Type is an MO-Defined-Type
        leaf type {
            config "false";
            description "Type";

            // Type is an MO-Defined-Type
            type ospf_LsaT;
        }

        // Lsa id
        // Inherited From ospf:ALsaRec
        // Type is an MO-Defined-Type
        leaf id {
            config "false";
            description "ID";

            // Type is an MO-Defined-Type
            type ospf_LsaId;
        }

        // Router id
        // Inherited From ospf:ALsaRec
        // Type is an MO-Defined-Type
        leaf advRtr {
            config "false";
            description "Advertising Router";

            // Type is an MO-Defined-Type
            type ospf_LsaAdvRtr;
        }

        // Sequence number
        // Inherited From ospf:ALsaRec
        // Type is an MO-Defined-Type
        leaf seq {
            config "false";
            description "Sequence Number";

            // Type is an MO-Defined-Type
            type ospf_LsaSeq;
        }

        // Age
        // Inherited From ospf:ALsaRec
        // Type is an MO-Defined-Type
        leaf age {
            config "false";
            description "Age";

            // Type is an MO-Defined-Type
            type ospf_LsaAge;
        }
        leaf arrivalTs {
            config "false";
            type uint64;
        }

        // Checksum
        // Inherited From ospf:ALsaRec
        // Type is an MO-Defined-Type
        leaf cksum {
            config "false";
            description "Checksum";

            // Type is an MO-Defined-Type
            type ospf_LsaCksum;
        }

        // Advertisement
        // Inherited From ospf:ALsaRec
        // Type is an MO-Defined-Type
        leaf advert {
            config "false";
            description "LSA Advertisement";

            // Type is an MO-Defined-Type
            type ospf_LsaAdvert;
        }
    }

    grouping ospfv3_Route-group {

        // Inherited From nw:Conn
        // Modified by Override: nw:DbRec->name
        // Type is an MO-Defined-Type
        leaf name {
            description "Name";

            // Type is an MO-Defined-Type
            type naming_Name {
                length "1..64";
            }
        }
        leaf pfx {
            config "false";
            type address_Ip;
        }

        // Path type
        // Inherited From ospf:ARoute
        // Type is an MO-Defined-Type
        leaf pathT {
            config "false";
            description "Path Type";

            // Type is an MO-Defined-Type
            type ospf_PathT;
        }

        // Area id
        // Inherited From ospf:ARoute
        // Type is an MO-Defined-Type
        leaf area {
            config "false";
            description "Area ID";

            // Type is an MO-Defined-Type
            type ospf_AreaId;
        }

        // Flags
        // Inherited From ospf:ARoute
        // Type is an MO-Defined-Type
        leaf flags {
            config "false";
            description "Flags";

            // Type is an MO-Defined-Type
            type ospf_RtFlags;
        }

        // Unicast cost
        // Inherited From ospf:ARoute
        // Type is an MO-Defined-Type
        leaf ucastCost {
            config "false";
            description "Unicast Cost";

            // Type is an MO-Defined-Type
            type ospf_RtCost;
        }

        // Multicast cost
        // Inherited From ospf:ARoute
        // Type is an MO-Defined-Type
        leaf mcastCost {
            config "false";
            description "Multicast Cost";

            // Type is an MO-Defined-Type
            type ospf_RtCost;
        }

        // Route Tag
        // Inherited From ospf:ARoute
        // Type is an MO-Defined-Type
        leaf tag {
            config "false";
            description "Route Tag";

            // Type is an MO-Defined-Type
            type ospf_RtTag;
        }

        // Administrative distance preference
        // Inherited From ospf:ARoute
        // Type is an MO-Defined-Type
        leaf dist {
            config "false";
            description "Distance";

            // Type is an MO-Defined-Type
            type ospf_Dist;
        }

        // Unicast nexthop
        container ucnh-items {
            list UcNexthop-list {
                config "false";
                key "if addr";

                // Added containment: Prefix=ucnh
                // Acquired From Package ospfv3
                uses ospfv3_UcNexthop-group;
            }
        }

        // Multicast nexthop
        container mcnh-items {
            list McNexthop-list {
                config "false";
                key "if addr";

                // Added containment: Prefix=mcnh
                // Acquired From Package ospfv3
                uses ospfv3_McNexthop-group;
            }
        }
    }

    grouping ospfv3_UcNexthop-group {

        // Inherited From nw:Conn
        // Modified by Override: nw:DbRec->name
        // Type is an MO-Defined-Type
        leaf name {
            description "Name";

            // Type is an MO-Defined-Type
            type naming_Name {
                length "1..64";
            }
        }

        // Nexhop interface
        // Inherited From ospf:ANexthop
        // Type is an MO-Defined-Type
        leaf if {
            config "false";
            description "Interface";

            // Type is an MO-Defined-Type
            type nw_IfId;
        }
        leaf addr {
            config "false";
            type address_Ip;
        }

        // Flags
        // Inherited From ospf:ANexthop
        // Type is an MO-Defined-Type
        leaf flags {
            config "false";
            description "Flags";

            // Type is an MO-Defined-Type
            type ospf_NhFlags;
        }
    }

    grouping ospfv3_McNexthop-group {

        // Inherited From nw:Conn
        // Modified by Override: nw:DbRec->name
        // Type is an MO-Defined-Type
        leaf name {
            description "Name";

            // Type is an MO-Defined-Type
            type naming_Name {
                length "1..64";
            }
        }

        // Nexhop interface
        // Inherited From ospf:ANexthop
        // Type is an MO-Defined-Type
        leaf if {
            config "false";
            description "Interface";

            // Type is an MO-Defined-Type
            type nw_IfId;
        }
        leaf addr {
            config "false";
            type address_Ip;
        }

        // Flags
        // Inherited From ospf:ANexthop
        // Type is an MO-Defined-Type
        leaf flags {
            config "false";
            description "Flags";

            // Type is an MO-Defined-Type
            type ospf_NhFlags;
        }
    }

    grouping ospfv3_DomAf-group {

        // Inherited From nw:Conn
        // Modified by Override: nw:CpDom->name
        // Type is an MO-Defined-Type
        leaf name {
            description "Name";

            // Type is an MO-Defined-Type
            type naming_Name {
                length "1..64";
            }
        }

        // Type
        // Inherited From ospf:Af
        // Type is an MO-Defined-Type
        leaf type {
            description "Type";

            // Type is an MO-Defined-Type
            type ospf_AfT;
        }

        // This objects holds default route leak policy,
        // this is not needed for FCS in our solution
        container defrtleak-items {

            // Added containment as a singleton: Prefix=defrtleak
            // Acquired From Package ospfv3
            uses ospfv3_DefRtLeakP-group;
        }

        // Inter protocol route leak policy. This defines distribution
        // of routes from other protocols to ospf
        container interleak-items {
            list InterLeakP-list {
                key "proto inst asn";

                // Added containment: Prefix=interleak
                // Acquired From Package ospfv3
                uses ospfv3_InterLeakP-group;
            }
        }

        // Leak controls related to the number of routes leaked
        container leakctrl-items {

            // Added containment as a singleton: Prefix=leakctrl
            // Acquired From Package ospfv3
            uses ospfv3_LeakCtrlP-group;
        }

        // External route summarization is specific to external
        // routes that are injected into OSPF using route leak.
        // Configure external route summarization on ASBRs that
        // are leaking routes into OSPF
        container extrtsum-items {
            list ExtRtSum-list {
                key "addr";

                // Added containment: Prefix=extrtsum
                // Acquired From Package ospfv3
                uses ospfv3_ExtRtSum-group;
            }
        }
    }

    grouping ospfv3_DefRtLeakP-group {

        // From Interface naming:Named
        // Inherited From naming:NamedObject
        // Modified by Override: pol:Obj->name
        // Modified by Override: ospf:ADefRtLeakP->name
        // Type is an MO-Defined-Type
        leaf name {
            description "Name";

            // Type is an MO-Defined-Type
            type naming_Name {
                length "0..64";
            }
        }

        // From Interface naming:Described
        // Inherited From pol:Instr
        // Modified by Override: ospf:ADefRtLeakP->descr
        // Type is an MO-Defined-Type
        leaf descr {
            config "false";
            description "Description";

            // Type is an MO-Defined-Type
            type naming_Descr;
        }

        // Scope of the policy (intra protocol, inter protcol,
        // default route)
        // Inherited From rtleak:LeakP
        // Modified by Override: rtleak:DefRtLeakP->scope
        // Type is an MO-Defined-Type
        leaf scope {
            description "Scope";

            // Type is an MO-Defined-Type
            type rtleak_Scope;
        }
        leaf rtMap {
            type string {
            }
        }

        // DefRtLeak always advertise
        // Inherited From ospf:ADefRtLeakP
        // Type is an MO-Defined-Type
        leaf always {
            description "Always advertise default leak";

            // Type is an MO-Defined-Type
            type ospf_Always;
        }
    }

    grouping ospfv3_InterLeakP-group {

        // From Interface naming:Named
        // Inherited From naming:NamedObject
        // Modified by Override: pol:Obj->name
        // Modified by Override: ospf:AInterLeakP->name
        // Type is an MO-Defined-Type
        leaf name {
            description "Name";

            // Type is an MO-Defined-Type
            type naming_Name {
                length "0..64";
            }
        }

        // From Interface naming:Described
        // Inherited From pol:Instr
        // Modified by Override: ospf:AInterLeakP->descr
        // Type is an MO-Defined-Type
        leaf descr {
            config "false";
            description "Description";

            // Type is an MO-Defined-Type
            type naming_Descr;
        }

        // Scope of the policy (intra protocol, inter protcol,
        // default route)
        // Inherited From rtleak:LeakP
        // Modified by Override: rtleak:InterLeakP->scope
        // Type is an MO-Defined-Type
        leaf scope {
            description "Scope";

            // Type is an MO-Defined-Type
            type rtleak_Scope;
        }
        leaf rtMap {
            type string {
            }
        }

        // Protocol from where the routes are leaked
        // Inherited From rtleak:InterLeakP
        // Type is an MO-Defined-Type
        leaf proto {
            description "Protocol";

            // Type is an MO-Defined-Type
            type rtleak_Proto;
        }

        // Routing protocol instance, the routing instance of the
        // protocol from where the routes are being leaked
        // Inherited From rtleak:InterLeakP
        // Type is an MO-Defined-Type
        leaf inst {
            description "Instance";

            // Type is an MO-Defined-Type
            type rtleak_Inst;
        }

        // Leak BGP routes from this Autonomous System (AS)    <1-4294967295>|<1-65535>[.<0-65535>]  Autonomous system number
        // Inherited From rtleak:InterLeakP
        // Type is an MO-Defined-Type
        leaf asn {
            description "Autonomous System Number";

            // Type is an MO-Defined-Type
            type rtleak_Asn {
            }
        }

        // DefRtLeak always advertise
        // Inherited From ospf:AInterLeakP
        // Type is an MO-Defined-Type
        leaf always {
            description "Always advertise default leak";

            // Type is an MO-Defined-Type
            type ospf_Always;
        }
    }

    grouping ospfv3_LeakCtrlP-group {

        // From Interface naming:Named
        // Inherited From naming:NamedObject
        // Modified by Override: pol:Obj->name
        // Modified by Override: ospf:ALeakCtrlP->name
        // Type is an MO-Defined-Type
        leaf name {
            description "Name";

            // Type is an MO-Defined-Type
            type naming_Name {
                length "0..64";
            }
        }

        // From Interface naming:Described
        // Inherited From pol:Instr
        // Modified by Override: ospf:ALeakCtrlP->descr
        // Type is an MO-Defined-Type
        leaf descr {
            config "false";
            description "Description";

            // Type is an MO-Defined-Type
            type naming_Descr;
        }

        // Controls on what to do when the number of routes cross
        // the maximum route/prefix limit
        // Inherited From rtleak:LeakCtrlP
        // Type is an MO-Defined-Type
        leaf ctrl {
            description "Controls";

            // Type is an MO-Defined-Type
            type rtleak_Ctrl;
        }

        // Maximum limit on routes leaked
        // Inherited From rtleak:LeakCtrlP
        // Type is an MO-Defined-Type
        leaf max {
            description "Maximum Limit";

            // Type is an MO-Defined-Type
            type rtleak_MaxPfx;
        }

        // Threshold at which warning is issued when number of
        // routes crosses the threshold
        // Inherited From rtleak:LeakCtrlP
        // Type is an MO-Defined-Type
        leaf thresh {
            description "Threshold";

            // Type is an MO-Defined-Type
            type rtleak_Thresh;
        }

        // Maximum number of retries to retrieve the leaked routes,
        // this is applicable only when the routes are withdrawn
        // Inherited From rtleak:LeakCtrlP
        // Type is an MO-Defined-Type
        leaf retries {
            description "Retries";

            // Type is an MO-Defined-Type
            type rtleak_Retries;
        }

        // Duration between the retries
        // Inherited From rtleak:LeakCtrlP
        // Type is an MO-Defined-Type
        leaf duration {
            description "Duration";

            // Type is an MO-Defined-Type
            type rtleak_Duration;
        }
    }

    grouping ospfv3_ExtRtSum-group {

        // From Interface naming:Named
        // Inherited From naming:NamedObject
        // Modified by Override: pol:Obj->name
        // Modified by Override: ospf:ARtSum->name
        // Type is an MO-Defined-Type
        leaf name {
            description "Name";

            // Type is an MO-Defined-Type
            type naming_Name {
                length "0..64";
            }
        }

        // From Interface naming:Described
        // Inherited From pol:Instr
        // Modified by Override: ospf:ARtSum->descr
        // Type is an MO-Defined-Type
        leaf descr {
            config "false";
            description "Description";

            // Type is an MO-Defined-Type
            type naming_Descr;
        }
        leaf addr {
            type address_Ip;
        }

        // Summary address no Advertise
        // Inherited From ospf:ARtSum
        // Type is an MO-Defined-Type
        leaf ctrl {
            description "Controls";

            // Type is an MO-Defined-Type
            type ospf_SumControl;
        }

        // Number of component routes
        // Inherited From ospf:ARtSum
        // Type is an MO-Defined-Type
        leaf compRtCnt {
            config "false";
            description "Number of component routes";

            // Type is an MO-Defined-Type
            type nw_Counter32;
        }

        // Route summary cost
        // Inherited From ospf:ARtSum
        // Type is an MO-Defined-Type
        leaf operCost {
            config "false";
            description "Route Summary Operational Cost";

            // Type is an MO-Defined-Type
            type ospf_SumCost;
        }

        // Summary address tag
        // Inherited From ospf:AExtRtSum
        // Type is an MO-Defined-Type
        leaf tag {
            description "Route Tag";

            // Type is an MO-Defined-Type
            type ospf_RtTag;
        }
    }

    grouping ospfv3_SpfComp-group {

        // From Interface naming:Named
        // Inherited From naming:NamedObject
        // Modified by Override: pol:Obj->name
        // Modified by Override: ospf:ASpfComp->name
        // Type is an MO-Defined-Type
        leaf name {
            description "Name";

            // Type is an MO-Defined-Type
            type naming_Name {
                length "0..64";
            }
        }

        // From Interface naming:Described
        // Inherited From pol:Instr
        // Modified by Override: ospf:ASpfComp->descr
        // Type is an MO-Defined-Type
        leaf descr {
            config "false";
            description "Description";

            // Type is an MO-Defined-Type
            type naming_Descr;
        }

        // Initial spf schedule delay interval
        // Inherited From ospf:ASpfComp
        // Type is an MO-Defined-Type
        leaf initIntvl {
            description "Initial Interval";

            // Type is an MO-Defined-Type
            type ospf_SpfCompInitIntvl;
        }

        // Minimum hold time between spf calculations
        // Inherited From ospf:ASpfComp
        // Type is an MO-Defined-Type
        leaf holdIntvl {
            description "Hold Interval";

            // Type is an MO-Defined-Type
            type ospf_SpfCompHoldIntvl;
        }

        // Maximum wait time between spf calculations
        // Inherited From ospf:ASpfComp
        // Type is an MO-Defined-Type
        leaf maxIntvl {
            description "Maximum Interval";

            // Type is an MO-Defined-Type
            type ospf_SpfCompMaxIntvl;
        }
    }

    grouping ospfv3_LsaCtrl-group {

        // From Interface naming:Named
        // Inherited From naming:NamedObject
        // Modified by Override: pol:Obj->name
        // Modified by Override: ospf:ALsaCtrl->name
        // Type is an MO-Defined-Type
        leaf name {
            description "Name";

            // Type is an MO-Defined-Type
            type naming_Name {
                length "0..64";
            }
        }

        // From Interface naming:Described
        // Inherited From pol:Instr
        // Modified by Override: ospf:ALsaCtrl->descr
        // Type is an MO-Defined-Type
        leaf descr {
            config "false";
            description "Description";

            // Type is an MO-Defined-Type
            type naming_Descr;
        }

        // LSA group pacing interval
        // Inherited From ospf:ALsaCtrl
        // Type is an MO-Defined-Type
        leaf gpPacingIntvl {
            description "Group Pacing Interval";

            // Type is an MO-Defined-Type
            type ospf_LsaGpPacingIntvl;
        }

        // Minimum interval between arrival of a LSA
        // Inherited From ospf:ALsaCtrl
        // Type is an MO-Defined-Type
        leaf arrivalIntvl {
            description "Arrival Interval";

            // Type is an MO-Defined-Type
            type ospf_LsaArrivalIntvl;
        }

        // LSA generation throttle start wait interval
        // Inherited From ospf:ALsaCtrl
        // Type is an MO-Defined-Type
        leaf startIntvl {
            description "Start Interval";

            // Type is an MO-Defined-Type
            type ospf_LsaThStartIntvl;
        }

        // LSA generation throttle hold interval
        // Inherited From ospf:ALsaCtrl
        // Type is an MO-Defined-Type
        leaf holdIntvl {
            description "Hold Interval";

            // Type is an MO-Defined-Type
            type ospf_LsaThHoldIntvl;
        }

        // LSA generation throttle maximum interval
        // Inherited From ospf:ALsaCtrl
        // Type is an MO-Defined-Type
        leaf maxIntvl {
            description "Maximum Interval";

            // Type is an MO-Defined-Type
            type ospf_LsaThMaxIntvl;
        }
    }

    grouping ospfv3_DomStats-group {

        // Interface count
        // Inherited From ospf:ADomStats
        // Type is an MO-Defined-Type
        leaf ifCnt {
            config "false";
            description "Interface Count";

            // Type is an MO-Defined-Type
            type ospf_Counter32;
        }

        // Area count
        // Inherited From ospf:ADomStats
        // Type is an MO-Defined-Type
        leaf areaCnt {
            config "false";
            description "Area Count";

            // Type is an MO-Defined-Type
            type ospf_Counter32;
        }

        // Stub area count
        // Inherited From ospf:ADomStats
        // Type is an MO-Defined-Type
        leaf stubAreaCnt {
            config "false";
            description "Stub Area Count";

            // Type is an MO-Defined-Type
            type ospf_Counter32;
        }

        // NSSA area count
        // Inherited From ospf:ADomStats
        // Type is an MO-Defined-Type
        leaf nssaAreaCnt {
            config "false";
            description "NSSA Area Count";

            // Type is an MO-Defined-Type
            type ospf_Counter32;
        }

        // External area count
        // Inherited From ospf:ADomStats
        // Type is an MO-Defined-Type
        leaf extAreaCnt {
            config "false";
            description "External Area Count";

            // Type is an MO-Defined-Type
            type ospf_Counter32;
        }

        // Active stub area count
        // Inherited From ospf:ADomStats
        // Type is an MO-Defined-Type
        leaf activeStubAreaCnt {
            config "false";
            description "Active Stub Area Count";

            // Type is an MO-Defined-Type
            type ospf_Counter32;
        }

        // Active NSSA area count
        // Inherited From ospf:ADomStats
        // Type is an MO-Defined-Type
        leaf activeNssaAreaCnt {
            config "false";
            description "Active NSSA Area Count";

            // Type is an MO-Defined-Type
            type ospf_Counter32;
        }

        // Active external area count
        // Inherited From ospf:ADomStats
        // Type is an MO-Defined-Type
        leaf activeExtAreaCnt {
            config "false";
            description "Active External Area Count";

            // Type is an MO-Defined-Type
            type ospf_Counter32;
        }

        // Active Area count
        // Inherited From ospf:ADomStats
        // Type is an MO-Defined-Type
        leaf activeAreaCnt {
            config "false";
            description "Active Area Count";

            // Type is an MO-Defined-Type
            type ospf_Counter32;
        }
        leaf lastStatsClearTs {
            config "false";
            type uint64;
        }

        // Neighbor count
        // Inherited From ospf:ADomStats
        // Type is an MO-Defined-Type
        leaf peerCnt {
            config "false";
            description "Peer Count";

            // Type is an MO-Defined-Type
            type ospf_Counter32;
        }

        // External LSA count
        // Inherited From ospf:ADomStats
        // Type is an MO-Defined-Type
        leaf extLsaCnt {
            config "false";
            description "External LSA Count";

            // Type is an MO-Defined-Type
            type ospf_Counter32;
        }

        // Opaque AS LSA count
        // Inherited From ospf:ADomStats
        // Type is an MO-Defined-Type
        leaf opaqueAsLsaCnt {
            config "false";
            description "Opaque AS LSA Count";

            // Type is an MO-Defined-Type
            type ospf_Counter32;
        }

        // Total AS LSA count
        // Inherited From ospf:ADomStats
        // Type is an MO-Defined-Type
        leaf totalAsLsaCnt {
            config "false";
            description "Total AS LSA Count";

            // Type is an MO-Defined-Type
            type ospf_Counter32;
        }

        // New LSA Rx count
        // Inherited From ospf:ADomStats
        // Type is an MO-Defined-Type
        leaf newLsaRxCnt {
            config "false";
            description "New LSA Rx Count";

            // Type is an MO-Defined-Type
            type ospf_Counter32;
        }

        // New LSA Tx count
        // Inherited From ospf:ADomStats
        // Type is an MO-Defined-Type
        leaf newLsaTxCnt {
            config "false";
            description "New LSA Tx Count";

            // Type is an MO-Defined-Type
            type ospf_Counter32;
        }

        // Area Border Router Status
        // Inherited From ospf:ADomStats
        // Type is an MO-Defined-Type
        leaf areaBdrRtr {
            config "false";
            description "Area Border Router";

            // Type is an MO-Defined-Type
            type ospf_AreaBdrRtr;
        }

        // ASBR Router Status
        // Inherited From ospf:ADomStats
        // Type is an MO-Defined-Type
        leaf asBdrRtr {
            config "false";
            description "Autonomous System Boundary Router";

            // Type is an MO-Defined-Type
            type ospf_ASBdrRtr;
        }
    }

    grouping ospfv3_Gr-group {

        // From Interface naming:Named
        // Inherited From naming:NamedObject
        // Modified by Override: pol:Obj->name
        // Modified by Override: ospf:AGr->name
        // Type is an MO-Defined-Type
        leaf name {
            description "Name";

            // Type is an MO-Defined-Type
            type naming_Name {
                length "0..64";
            }
        }

        // From Interface naming:Described
        // Inherited From pol:Instr
        // Modified by Override: ospf:AGr->descr
        // Type is an MO-Defined-Type
        leaf descr {
            config "false";
            description "Description";

            // Type is an MO-Defined-Type
            type naming_Descr;
        }

        // Graceful restart controls
        // Inherited From ospf:AGr
        // Type is an MO-Defined-Type
        leaf ctrl {
            description "Control";

            // Type is an MO-Defined-Type
            type ospf_GrCtrl;
        }
        leaf helper {
            type boolean;
            default "true";
        }

        // Graceful restart period
        // Inherited From ospf:AGr
        // Type is an MO-Defined-Type
        leaf gracePeriod {
            description "Control";

            // Type is an MO-Defined-Type
            type ospf_GrPeriod;
        }

        // Graceful restart status
        // Inherited From ospf:AGr
        // Type is an MO-Defined-Type
        leaf restartStatus {
            config "false";
            description "Restart Status";

            // Type is an MO-Defined-Type
            type ospf_RestartStatus;
        }
        leaf restartAge {
            config "false";
            type uint32;
        }

        // Graceful restart exit reason
        // Inherited From ospf:AGr
        // Type is an MO-Defined-Type
        leaf restartExitReason {
            config "false";
            description "Restart Exit Reason";

            // Type is an MO-Defined-Type
            type ospf_RestartExitReason;
        }
    }

    grouping ospfv3_If-group {

        // Inherited From nw:Conn
        // Modified by Override: nw:Ep->name
        // Modified by Override: ospf:AIf->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: ospf:AIf->descr
        // Type is an MO-Defined-Type
        leaf descr {
            config "false";
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ospf:AIf
        // Type is an MO-Defined-Type
        leaf ctrl {
            description "Controls";

            // Type is an MO-Defined-Type
            type ospf_IfControl;
        }

        // Passive interface control
        // Inherited From ospf:AIf
        // Type is an MO-Defined-Type
        leaf passiveCtrl {
            description "Passive Interface Control";

            // Type is an MO-Defined-Type
            type ospf_PassiveControl;
        }

        // BFD control
        // Inherited From ospf:AIf
        // Type is an MO-Defined-Type
        leaf bfdCtrl {
            description "BFD Control";

            // Type is an MO-Defined-Type
            type ospf_BfdControl;
        }

        // Network type
        // Inherited From ospf:AIf
        // Type is an MO-Defined-Type
        leaf nwT {
            description "Network Type";

            // Type is an MO-Defined-Type
            type ospf_NwT;
        }

        // Priority, used in determining the designated router on
        // this network
        // Inherited From ospf:AIf
        // Type is an MO-Defined-Type
        leaf prio {
            description "Priority";

            // Type is an MO-Defined-Type
            type ospf_DesigPrio;
        }

        // Area to which this interface belongs to
        // Inherited From ospf:AIf
        // Type is an MO-Defined-Type
        leaf area {
            description "Area ID";

            // Type is an MO-Defined-Type
            type ospf_AreaId;
        }
        leaf advertiseSecondaries {
            type boolean;
            default "true";
        }

        // Operational state
        // Inherited From ospf:AIf
        // Type is an MO-Defined-Type
        leaf operSt {
            config "false";
            description "Operational State";

            // Type is an MO-Defined-Type
            type ospf_IfOperSt;
        }

        // Operational failed state qualifier
        // Inherited From ospf:AIf
        // Type is an MO-Defined-Type
        leaf failStQual {
            config "false";
            description "Failed State Qualifier";

            // Type is an MO-Defined-Type
            type ospf_FailStQual;
        }

        // Interface type
        // Inherited From ospf:AIf
        // Type is an MO-Defined-Type
        leaf type {
            config "false";
            description "Type";

            // Type is an MO-Defined-Type
            type ospf_IfType;
        }

        // Flags
        // Inherited From ospf:AIf
        // Type is an MO-Defined-Type
        leaf flags {
            config "false";
            description "Flags";

            // Type is an MO-Defined-Type
            type ospf_IfFlags;
        }
        leaf addr {
            config "false";
            type address_Ip;
        }
        leaf dr {
            config "false";
            type address_Ip;
        }
        leaf bdr {
            config "false";
            type address_Ip;
        }

        // Designated router id
        // Inherited From ospf:AIf
        // Type is an MO-Defined-Type
        leaf drId {
            config "false";
            description "DR Id";

            // Type is an MO-Defined-Type
            type ip_RtrId;
        }

        // Backup designated router id
        // Inherited From ospf:AIf
        // Type is an MO-Defined-Type
        leaf bdrId {
            config "false";
            description "BDR Id";

            // Type is an MO-Defined-Type
            type ip_RtrId;
        }

        // LSA checksum sum
        // Inherited From ospf:AIf
        // Type is an MO-Defined-Type
        leaf lsaCksumSum {
            config "false";
            description "LSA Checksum Sum";

            // Type is an MO-Defined-Type
            type ospf_LsaCksumSum;
        }

        // Operational Cost
        // Inherited From ospf:AIf
        // Type is an MO-Defined-Type
        leaf operCost {
            config "false";
            description "Operational Cost";

            // Type is an MO-Defined-Type
            type ospf_IfCost;
        }

        // Operational Dead interval
        // Inherited From ospf:AIf
        // Type is an MO-Defined-Type
        leaf operDeadIntvl {
            config "false";
            description "Operational Dead Interval";

            // Type is an MO-Defined-Type
            type ospf_DeadIntvl;
        }

        // Hello interval, interval between hello packets that
        // OSPF sends on the interface
        // From Interface ospf:IIntfIntvl
        // Inherited From ospf:AIf
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:AIf
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:AIf
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:AIf
        // Type is an MO-Defined-Type
        leaf xmitDelay {
            description "Transmit Delay";

            // Type is an MO-Defined-Type
            type ospf_XmitDelay;
        }

        // Cost of the interface
        // From Interface ospf:IIntfCost
        // Inherited From ospf:AIf
        // Type is an MO-Defined-Type
        leaf cost {
            description "Cost";

            // Type is an MO-Defined-Type
            type ospf_IfCost;
        }

        // This object holds ospf neighbor information
        container adj-items {
            list AdjEp-list {
                config "false";
                key "id";

                // Added containment: Prefix=adj
                // Acquired From Package ospfv3
                uses ospfv3_AdjEp-group;
            }
        }

        // OSPF databases
        container db-items {
            list Db-list {
                config "false";
                key "type";

                // Added containment: Prefix=db
                // Acquired From Package ospfv3
                uses ospfv3_Db-group;
            }
        }

        // This object holds the ospf interface related statistics
        container ifstats-items {

            // Added containment as a singleton: Prefix=ifstats
            // Acquired From Package ospfv3
            uses ospfv3_IfStats-group;
        }

        // This object holds the ospf traffic related information
        container trstats-items {

            // Added containment as a singleton: Prefix=trstats
            // Acquired From Package ospfv3
            uses ospfv3_TrafficStats-group;
        }

        // Rel-def target from IfDefToOspfv3If
        // Inherited From ospfv3:If
        container rtospfIfDefToOspfv3If-items {

            // Abstract containment of rtospfIfDefToOspfv3If derived from ospfv3:If
            list RtOspfIfDefToOspfv3If-list {
                config "false";
                key "tDn";

                // Added containment: Prefix=rtospfIfDefToOspfv3If
                // Acquired From Package ospf
                uses ospf_RtOspfIfDefToOspfv3If_target-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping ospfv3_AdjEp-group {

        // Inherited From nw:Conn
        // Modified by Override: nw:Ep->name
        // Type is an MO-Defined-Type
        leaf name {
            description "Name";

            // Type is an MO-Defined-Type
            type naming_Name {
                length "1..64";
            }
        }

        // Neighbor's router id
        // Inherited From ospf:AAdjEp
        // Type is an MO-Defined-Type
        leaf id {
            config "false";
            description "ID";

            // Type is an MO-Defined-Type
            type ospf_AdjId;
        }

        // Neighbor's interface id
        // Inherited From ospf:AAdjEp
        // Type is an MO-Defined-Type
        leaf ifId {
            config "false";
            description "Interface ID";

            // Type is an MO-Defined-Type
            type ospf_AdjIfId;
        }

        // Adjacency state
        // Inherited From ospf:AAdjEp
        // Type is an MO-Defined-Type
        leaf operSt {
            config "false";
            description "Operational State";

            // Type is an MO-Defined-Type
            type ospf_AdjOperSt;
        }

        // BFD state
        // Inherited From ospf:AAdjEp
        // Type is an MO-Defined-Type
        leaf bfdSt {
            config "false";
            description "BFD State";

            // Type is an MO-Defined-Type
            type ospf_BfdOperSt;
        }

        // Area id
        // Inherited From ospf:AAdjEp
        // Type is an MO-Defined-Type
        leaf area {
            config "false";
            description "Area ID";

            // Type is an MO-Defined-Type
            type ospf_AreaId;
        }

        // Neighbor priority
        // Inherited From ospf:AAdjEp
        // Type is an MO-Defined-Type
        leaf prio {
            config "false";
            description "Priority";

            // Type is an MO-Defined-Type
            type ospf_DesigPrio;
        }

        // Designated router address
        // Inherited From ospf:AAdjEp
        // Type is an MO-Defined-Type
        leaf dr {
            config "false";
            description "Designated Router";

            // Type is an MO-Defined-Type
            type ospf_DesigAddr;
        }

        // Backup designated router address
        // Inherited From ospf:AAdjEp
        // Type is an MO-Defined-Type
        leaf bdr {
            config "false";
            description "Backup Designated Router";

            // Type is an MO-Defined-Type
            type ospf_DesigAddr;
        }
        leaf peerIp {
            config "false";
            type address_Ip;
        }

        // Peer options from hello packet
        // Inherited From ospf:AAdjEp
        // Type is an MO-Defined-Type
        leaf helloOptions {
            config "false";
            description "Hello Options";

            // Type is an MO-Defined-Type
            type ospf_Options;
        }

        // Peer options from DBD packet
        // Inherited From ospf:AAdjEp
        // Type is an MO-Defined-Type
        leaf dbdOptions {
            config "false";
            description "DBD Options";

            // Type is an MO-Defined-Type
            type ospf_Options;
        }

        // Flags
        // Inherited From ospf:AAdjEp
        // Type is an MO-Defined-Type
        leaf flags {
            config "false";
            description "Flags";

            // Type is an MO-Defined-Type
            type ospf_AdjFlags;
        }
        leaf peerName {
            config "false";
            type string;
        }

        // This object holds the ospf neighbor related statistics
        container adjstats-items {

            // Added containment as a singleton: Prefix=adjstats
            // Acquired From Package ospfv3
            uses ospfv3_AdjStats-group;
        }

        // This object holds ospf graceful restart operational
        // information
        container gr-items {

            // Added containment as a singleton: Prefix=gr
            // Acquired From Package ospfv3
            uses ospfv3_GrSt-group;
        }
    }

    grouping ospfv3_AdjStats-group {

        // State change count
        // Inherited From ospf:AAdjStats
        // Type is an MO-Defined-Type
        leaf stChgCnt {
            config "false";
            description "State Change Count";

            // Type is an MO-Defined-Type
            type ospf_Counter32;
        }
        leaf lastStChgTs {
            config "false";
            type uint64;
        }
        leaf lastNonHelloPktTs {
            config "false";
            type uint64;
        }

        // DBD Sequence number
        // Inherited From ospf:AAdjStats
        // Type is an MO-Defined-Type
        leaf dbdSeqNum {
            config "false";
            description "DBD Sequence Number";

            // Type is an MO-Defined-Type
            type ospf_Counter32;
        }

        // Number of LSAs on request list
        // Inherited From ospf:AAdjStats
        // Type is an MO-Defined-Type
        leaf reqLsaCnt {
            config "false";
            description "Request LSA Count";

            // Type is an MO-Defined-Type
            type ospf_Counter32;
        }

        // Outstanding LSAs from last request
        // Inherited From ospf:AAdjStats
        // Type is an MO-Defined-Type
        leaf outstandingLsaCnt {
            config "false";
            description "Outstanding LSA Count";

            // Type is an MO-Defined-Type
            type ospf_Counter32;
        }

        // Number of retransmissions of LSA request
        // Inherited From ospf:AAdjStats
        // Type is an MO-Defined-Type
        leaf lsaReqRexmitCnt {
            config "false";
            description "LSA Request Retransmission Count";

            // Type is an MO-Defined-Type
            type ospf_Counter32;
        }
        leaf deadTimerExpTs {
            config "false";
            type uint64;
        }
    }

    grouping ospfv3_GrSt-group {

        // Peer restart helper Status
        // Inherited From ospf:AGrSt
        // Type is an MO-Defined-Type
        leaf helperSt {
            config "false";
            description "Peer Restart Helper Status";

            // Type is an MO-Defined-Type
            type ospf_HelperSt;
        }

        // Peer restart helper age
        // Inherited From ospf:AGrSt
        // Type is an MO-Defined-Type
        leaf helperAge {
            config "false";
            description "Peer Restart Helper Age";

            // Type is an MO-Defined-Type
            type ospf_HelperAge;
        }

        // Peer restart helper exit qualifier
        // Inherited From ospf:AGrSt
        // Type is an MO-Defined-Type
        leaf helperExitQual {
            config "false";
            description "Peer Restart Helper Exit Qualifier";

            // Type is an MO-Defined-Type
            type ospf_HelperExitQual;
        }
    }

    grouping ospfv3_IfStats-group {

        // If events count
        // Inherited From ospf:AIfStats
        // Type is an MO-Defined-Type
        leaf evCnt {
            config "false";
            description "If Events Count";

            // Type is an MO-Defined-Type
            type ospf_Counter32;
        }

        // LSA count
        // Inherited From ospf:AIfStats
        // Type is an MO-Defined-Type
        leaf lsaCnt {
            config "false";
            description "LSA Count";

            // Type is an MO-Defined-Type
            type ospf_Counter32;
        }

        // Neighbor count
        // Inherited From ospf:AIfStats
        // Type is an MO-Defined-Type
        leaf peerCnt {
            config "false";
            description "Peer Count";

            // Type is an MO-Defined-Type
            type ospf_Counter32;
        }

        // Flood to neighbor count
        // Inherited From ospf:AIfStats
        // Type is an MO-Defined-Type
        leaf floodToPeerCnt {
            config "false";
            description "Flood To Peer Count";

            // Type is an MO-Defined-Type
            type ospf_Counter32;
        }

        // Number of adjacency
        // Inherited From ospf:AIfStats
        // Type is an MO-Defined-Type
        leaf adjCnt {
            config "false";
            description "Adjacency Count";

            // Type is an MO-Defined-Type
            type ospf_Counter32;
        }

        // Number of peers in hitless helper mode
        // Inherited From ospf:AIfStats
        // Type is an MO-Defined-Type
        leaf grHelperPeerCnt {
            config "false";
            description "GR Helper Peer Count";

            // Type is an MO-Defined-Type
            type ospf_Counter32;
        }
    }

    grouping ospfv3_TrafficStats-group {

        // Total packets received
        // Inherited From ospf:ATrafficStats
        // Type is an MO-Defined-Type
        leaf totalPktsRcvd {
            config "false";
            description "Total Packets Received";

            // Type is an MO-Defined-Type
            type ospf_Counter32;
        }

        // Hello packets received
        // Inherited From ospf:ATrafficStats
        // Type is an MO-Defined-Type
        leaf helloPktsRcvd {
            config "false";
            description "Hello Packets Received";

            // Type is an MO-Defined-Type
            type ospf_Counter32;
        }

        // Database description packets received
        // Inherited From ospf:ATrafficStats
        // Type is an MO-Defined-Type
        leaf dbdPktsRcvd {
            config "false";
            description "DBD Packets Received";

            // Type is an MO-Defined-Type
            type ospf_Counter32;
        }

        // Link-state request packets received
        // Inherited From ospf:ATrafficStats
        // Type is an MO-Defined-Type
        leaf lsReqPktsRcvd {
            config "false";
            description "LSREQ Packets Received";

            // Type is an MO-Defined-Type
            type ospf_Counter32;
        }

        // Link-state update packets received
        // Inherited From ospf:ATrafficStats
        // Type is an MO-Defined-Type
        leaf lsUpdPktsRcvd {
            config "false";
            description "LSU Packets Received";

            // Type is an MO-Defined-Type
            type ospf_Counter32;
        }

        // Link-state ack packets received
        // Inherited From ospf:ATrafficStats
        // Type is an MO-Defined-Type
        leaf lsAckPktsRcvd {
            config "false";
            description "LSACK Packets Received";

            // Type is an MO-Defined-Type
            type ospf_Counter32;
        }

        // Received packets dropped
        // Inherited From ospf:ATrafficStats
        // Type is an MO-Defined-Type
        leaf rcvdPktsDropped {
            config "false";
            description "Received Packets Dropped";

            // Type is an MO-Defined-Type
            type ospf_Counter32;
        }

        // Error packets rcvd
        // Inherited From ospf:ATrafficStats
        // Type is an MO-Defined-Type
        leaf errPktsRcvd {
            config "false";
            description "Error Packets Received";

            // Type is an MO-Defined-Type
            type ospf_Counter32;
        }

        // Error hello packets received
        // Inherited From ospf:ATrafficStats
        // Type is an MO-Defined-Type
        leaf errHelloPktsRcvd {
            config "false";
            description "Error Hello Packets Received";

            // Type is an MO-Defined-Type
            type ospf_Counter32;
        }

        // Error database description packets received
        // Inherited From ospf:ATrafficStats
        // Type is an MO-Defined-Type
        leaf errDbdPktsRcvd {
            config "false";
            description "Error DBD Packets Received";

            // Type is an MO-Defined-Type
            type ospf_Counter32;
        }

        // Error link-state request packets received
        // Inherited From ospf:ATrafficStats
        // Type is an MO-Defined-Type
        leaf errLsReqPktsRcvd {
            config "false";
            description "Error LSREQ Packets Received";

            // Type is an MO-Defined-Type
            type ospf_Counter32;
        }

        // Error link-state update packets received
        // Inherited From ospf:ATrafficStats
        // Type is an MO-Defined-Type
        leaf errLsUpdPktsRcvd {
            config "false";
            description "Error LSU Packets Received";

            // Type is an MO-Defined-Type
            type ospf_Counter32;
        }

        // Error link-state ack packets received
        // Inherited From ospf:ATrafficStats
        // Type is an MO-Defined-Type
        leaf errLsAckPktsRcvd {
            config "false";
            description "Error LSACK Packets Received";

            // Type is an MO-Defined-Type
            type ospf_Counter32;
        }

        // Unknown packets received
        // Inherited From ospf:ATrafficStats
        // Type is an MO-Defined-Type
        leaf unknownPktsRcvd {
            config "false";
            description "Unknown Packets Received";

            // Type is an MO-Defined-Type
            type ospf_Counter32;
        }

        // Duplicate routerid packets received
        // Inherited From ospf:ATrafficStats
        // Type is an MO-Defined-Type
        leaf dupRtrIdPktsRcvd {
            config "false";
            description "Duplicate RouterId Packets Received";

            // Type is an MO-Defined-Type
            type ospf_Counter32;
        }

        // Duplicate source addr packets received
        // Inherited From ospf:ATrafficStats
        // Type is an MO-Defined-Type
        leaf dupSrcAddrPktsRcvd {
            config "false";
            description "Duplicate Source Addr Packets Received";

            // Type is an MO-Defined-Type
            type ospf_Counter32;
        }

        // Wrong area packets received
        // Inherited From ospf:ATrafficStats
        // Type is an MO-Defined-Type
        leaf wrongAreaPktsRcvd {
            config "false";
            description "Wrong Area Packets Received";

            // Type is an MO-Defined-Type
            type ospf_Counter32;
        }

        // Invalid source addr packets received
        // Inherited From ospf:ATrafficStats
        // Type is an MO-Defined-Type
        leaf invalidSrcAddrPktsRcvd {
            config "false";
            description "Invalid Source Addr Packets Received";

            // Type is an MO-Defined-Type
            type ospf_Counter32;
        }

        // Invalid destination addr packets received
        // Inherited From ospf:ATrafficStats
        // Type is an MO-Defined-Type
        leaf invalidDestAddrPktsRcvd {
            config "false";
            description "Invalid Destination Addr Packets Received";

            // Type is an MO-Defined-Type
            type ospf_Counter32;
        }

        // Bad CRC packets received
        // Inherited From ospf:ATrafficStats
        // Type is an MO-Defined-Type
        leaf badCRCPktsRcvd {
            config "false";
            description "Bad CRC Packets Received";

            // Type is an MO-Defined-Type
            type ospf_Counter32;
        }

        // Bad version packets received
        // Inherited From ospf:ATrafficStats
        // Type is an MO-Defined-Type
        leaf badVersionPktsRcvd {
            config "false";
            description "Bad Version Packets Received";

            // Type is an MO-Defined-Type
            type ospf_Counter32;
        }

        // Bad reserved fields packets received
        // Inherited From ospf:ATrafficStats
        // Type is an MO-Defined-Type
        leaf badResvFieldPktsRcvd {
            config "false";
            description "Bad Reserved Field Packets Received";

            // Type is an MO-Defined-Type
            type ospf_Counter32;
        }

        // Changed neighbor routerId or ip address packets received
        // Inherited From ospf:ATrafficStats
        // Type is an MO-Defined-Type
        leaf peerRtrIdChgdPktsRcvd {
            config "false";
            description "Peer RouterId Changed Packets Received";

            // Type is an MO-Defined-Type
            type ospf_Counter32;
        }

        // Non hello received packets for which neighbor is not found
        // Inherited From ospf:ATrafficStats
        // Type is an MO-Defined-Type
        leaf peerNotFoundPktsRcvd {
            config "false";
            description "Peer Not Found Packets Received";

            // Type is an MO-Defined-Type
            type ospf_Counter32;
        }

        // Authentication failed packets received
        // Inherited From ospf:ATrafficStats
        // Type is an MO-Defined-Type
        leaf badAuthPktsRcvd {
            config "false";
            description "Bad Authentication Packets Received";

            // Type is an MO-Defined-Type
            type ospf_Counter32;
        }

        // Bad length packets received
        // Inherited From ospf:ATrafficStats
        // Type is an MO-Defined-Type
        leaf badLenPktsRcvd {
            config "false";
            description "Bad Length Packets Received";

            // Type is an MO-Defined-Type
            type ospf_Counter32;
        }

        // Packets received on passive interface
        // Inherited From ospf:ATrafficStats
        // Type is an MO-Defined-Type
        leaf passiveIntfPktsRcvd {
            config "false";
            description "Passive Interface Packets Received";

            // Type is an MO-Defined-Type
            type ospf_Counter32;
        }

        // Packets received on OSPF not enabled interface
        // Inherited From ospf:ATrafficStats
        // Type is an MO-Defined-Type
        leaf noOspfIntfPktsRcvd {
            config "false";
            description "No OSPF Interface Packets Received";

            // Type is an MO-Defined-Type
            type ospf_Counter32;
        }

        // Received LSA packets ignored
        // Inherited From ospf:ATrafficStats
        // Type is an MO-Defined-Type
        leaf rcvdLsaPktsIgnored {
            config "false";
            description "Received LSA Packets Ignored";

            // Type is an MO-Defined-Type
            type ospf_Counter32;
        }

        // Number of LSA packets dropped during SPF run
        // Inherited From ospf:ATrafficStats
        // Type is an MO-Defined-Type
        leaf droppedLsaPktsWhileSPF {
            config "false";
            description "LSA Packets Dropped During SPF";

            // Type is an MO-Defined-Type
            type ospf_Counter32;
        }

        // Number of LSA packets dropped during graceful restart
        // Inherited From ospf:ATrafficStats
        // Type is an MO-Defined-Type
        leaf droppedLsaPktsWhileGR {
            config "false";
            description "LSA Packets Dropped During GR";

            // Type is an MO-Defined-Type
            type ospf_Counter32;
        }

        // Total packets sent
        // Inherited From ospf:ATrafficStats
        // Type is an MO-Defined-Type
        leaf totalPktsSent {
            config "false";
            description "Total Packets Sent";

            // Type is an MO-Defined-Type
            type ospf_Counter32;
        }

        // Hello packets sent
        // Inherited From ospf:ATrafficStats
        // Type is an MO-Defined-Type
        leaf helloPktsSent {
            config "false";
            description "Hello Packets Sent";

            // Type is an MO-Defined-Type
            type ospf_Counter32;
        }

        // Database description packets sent
        // Inherited From ospf:ATrafficStats
        // Type is an MO-Defined-Type
        leaf dbdPktsSent {
            config "false";
            description "DBD Packets Sent";

            // Type is an MO-Defined-Type
            type ospf_Counter32;
        }

        // Link-state request packets sent
        // Inherited From ospf:ATrafficStats
        // Type is an MO-Defined-Type
        leaf lsReqPktsSent {
            config "false";
            description "LSREQ Packets Sent";

            // Type is an MO-Defined-Type
            type ospf_Counter32;
        }

        // Link-state update packets sent
        // Inherited From ospf:ATrafficStats
        // Type is an MO-Defined-Type
        leaf lsUpdPktsSent {
            config "false";
            description "LSU Packets Sent";

            // Type is an MO-Defined-Type
            type ospf_Counter32;
        }

        // Link-state ack packets sent
        // Inherited From ospf:ATrafficStats
        // Type is an MO-Defined-Type
        leaf lsAckPktsSent {
            config "false";
            description "LSACK Packets Sent";

            // Type is an MO-Defined-Type
            type ospf_Counter32;
        }

        // Dropped send packets
        // Inherited From ospf:ATrafficStats
        // Type is an MO-Defined-Type
        leaf droppedSendPkts {
            config "false";
            description "Dropped Send Packets";

            // Type is an MO-Defined-Type
            type ospf_Counter32;
        }

        // Error send packets
        // Inherited From ospf:ATrafficStats
        // Type is an MO-Defined-Type
        leaf errSendPkts {
            config "false";
            description "Error Send Packets";

            // Type is an MO-Defined-Type
            type ospf_Counter32;
        }

        // Unknown send packets
        // Inherited From ospf:ATrafficStats
        // Type is an MO-Defined-Type
        leaf unknownSendPkts {
            config "false";
            description "Unknown Send Packets";

            // Type is an MO-Defined-Type
            type ospf_Counter32;
        }

        // Number of first transmission of LSU packets
        // Inherited From ospf:ATrafficStats
        // Type is an MO-Defined-Type
        leaf lsuFirstTxPkts {
            config "false";
            description "LSU First Tx Packets";

            // Type is an MO-Defined-Type
            type ospf_Counter32;
        }

        // Number of retransmissions of LSU packets
        // Inherited From ospf:ATrafficStats
        // Type is an MO-Defined-Type
        leaf lsuRexmitPkts {
            config "false";
            description "LSU Retransmission Packets";

            // Type is an MO-Defined-Type
            type ospf_Counter32;
        }

        // Number of LSU packets sent in response to LSREQ packets
        // Inherited From ospf:ATrafficStats
        // Type is an MO-Defined-Type
        leaf lsuForLsreqPkts {
            config "false";
            description "LSU Packets For LSREQ Packets";

            // Type is an MO-Defined-Type
            type ospf_Counter32;
        }

        // Number of LSU packets sent to a neighbor specifically
        // Inherited From ospf:ATrafficStats
        // Type is an MO-Defined-Type
        leaf lsuPeerTxPkts {
            config "false";
            description "LSU Packets To Peer";

            // Type is an MO-Defined-Type
            type ospf_Counter32;
        }

        // Number of times flooding packets dropped due to IP queue throttling
        // Inherited From ospf:ATrafficStats
        // Type is an MO-Defined-Type
        leaf floodPktSendIpThrottle {
            config "false";
            description "Flood Packet Send IP Throttle";

            // Type is an MO-Defined-Type
            type ospf_Counter32;
        }

        // Number of times flooding packets dropped due to token throttling
        // Inherited From ospf:ATrafficStats
        // Type is an MO-Defined-Type
        leaf floodPktSendTokenThrottle {
            config "false";
            description "Flood Packet Send Token Throttle";

            // Type is an MO-Defined-Type
            type ospf_Counter32;
        }
        leaf lastStatsClearTs {
            config "false";
            type uint64;
        }
    }

    grouping ospfv3_MaxMetricLsaP-group {

        // Max metric controls - specifies when to send max
        // metric LSAs and for which routes/links
        // Inherited From ospf:AMaxMetricLsaP
        // Type is an MO-Defined-Type
        leaf ctrl {
            description "Maximum Metric Controls";

            // Type is an MO-Defined-Type
            type ospf_MaxMetricControl;
        }

        // Max metric value to be used for external LSAs
        // Inherited From ospf:AMaxMetricLsaP
        // Type is an MO-Defined-Type
        leaf maxMetricExtLsa {
            description "Maximum metric value for external LSAs";

            // Type is an MO-Defined-Type
            type ospf_MaxMetric;
        }

        // Max metric value to be used for summary LSAs
        // Inherited From ospf:AMaxMetricLsaP
        // Type is an MO-Defined-Type
        leaf maxMetricSummLsa {
            description "Maximum metric value for summary LSAs";

            // Type is an MO-Defined-Type
            type ospf_MaxMetric;
        }

        // Time (in secs) for which max metric should be advertised
        // at startup
        // Inherited From ospf:AMaxMetricLsaP
        // Type is an MO-Defined-Type
        leaf startupIntvl {
            description "Startup interval";

            // Type is an MO-Defined-Type
            type ospf_StartupIntvl;
        }

        // At startup, advertise max metric until convergence of BGP ASN
        // Inherited From ospf:AMaxMetricLsaP
        // Type is an MO-Defined-Type
        leaf awaitConvBgpAsn {
            description "BGP ASN to wait for";

            // Type is an MO-Defined-Type
            type rtleak_Asn;
        }
    }

    grouping ospfv3_EventLogs-group {

        // Event LogType
        // Inherited From ospf:AEventLogs
        // Type is an MO-Defined-Type
        leaf eventType {
            description "Event Log Type";

            // Type is an MO-Defined-Type
            type ospf_EventType;
        }

        // Event LogSize
        // Inherited From ospf:AEventLogs
        // Type is an MO-Defined-Type
        leaf logSize {
            description "Event Log Size";

            // Type is an MO-Defined-Type
            type ospf_EventLogSize;
        }

        // Event Log size in bytes
        // Inherited From ospf:AEventLogs
        // Type is an MO-Defined-Type
        leaf logSizeKBytes {
            description "Event Log Size in KBytes";

            // Type is an MO-Defined-Type
            type ospf_EventLogSizeKBytes;
        }
    }

    grouping ospfv3_InternalIf-group {

        // Inherited From nw:Conn
        // Modified by Override: nw:Ep->name
        // Modified by Override: ospf:AIf->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: ospf:AIf->descr
        // Type is an MO-Defined-Type
        leaf descr {
            config "false";
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface controls
        // Inherited From ospf:AIf
        // Type is an MO-Defined-Type
        leaf ctrl {
            description "Controls";

            // Type is an MO-Defined-Type
            type ospf_IfControl;
        }

        // Passive interface control
        // Inherited From ospf:AIf
        // Type is an MO-Defined-Type
        leaf passiveCtrl {
            description "Passive Interface Control";

            // Type is an MO-Defined-Type
            type ospf_PassiveControl;
        }

        // BFD control
        // Inherited From ospf:AIf
        // Type is an MO-Defined-Type
        leaf bfdCtrl {
            description "BFD Control";

            // Type is an MO-Defined-Type
            type ospf_BfdControl;
        }

        // Network type
        // Inherited From ospf:AIf
        // Type is an MO-Defined-Type
        leaf nwT {
            description "Network Type";

            // Type is an MO-Defined-Type
            type ospf_NwT;
        }

        // Priority, used in determining the designated router on
        // this network
        // Inherited From ospf:AIf
        // Type is an MO-Defined-Type
        leaf prio {
            description "Priority";

            // Type is an MO-Defined-Type
            type ospf_DesigPrio;
        }

        // Area to which this interface belongs to
        // Inherited From ospf:AIf
        // Type is an MO-Defined-Type
        leaf area {
            description "Area ID";

            // Type is an MO-Defined-Type
            type ospf_AreaId;
        }
        leaf advertiseSecondaries {
            type boolean;
            default "true";
        }

        // Operational state
        // Inherited From ospf:AIf
        // Type is an MO-Defined-Type
        leaf operSt {
            config "false";
            description "Operational State";

            // Type is an MO-Defined-Type
            type ospf_IfOperSt;
        }

        // Operational failed state qualifier
        // Inherited From ospf:AIf
        // Type is an MO-Defined-Type
        leaf failStQual {
            config "false";
            description "Failed State Qualifier";

            // Type is an MO-Defined-Type
            type ospf_FailStQual;
        }

        // Interface type
        // Inherited From ospf:AIf
        // Type is an MO-Defined-Type
        leaf type {
            config "false";
            description "Type";

            // Type is an MO-Defined-Type
            type ospf_IfType;
        }

        // Flags
        // Inherited From ospf:AIf
        // Type is an MO-Defined-Type
        leaf flags {
            config "false";
            description "Flags";

            // Type is an MO-Defined-Type
            type ospf_IfFlags;
        }
        leaf addr {
            config "false";
            type address_Ip;
        }
        leaf dr {
            config "false";
            type address_Ip;
        }
        leaf bdr {
            config "false";
            type address_Ip;
        }

        // Designated router id
        // Inherited From ospf:AIf
        // Type is an MO-Defined-Type
        leaf drId {
            config "false";
            description "DR Id";

            // Type is an MO-Defined-Type
            type ip_RtrId;
        }

        // Backup designated router id
        // Inherited From ospf:AIf
        // Type is an MO-Defined-Type
        leaf bdrId {
            config "false";
            description "BDR Id";

            // Type is an MO-Defined-Type
            type ip_RtrId;
        }

        // LSA checksum sum
        // Inherited From ospf:AIf
        // Type is an MO-Defined-Type
        leaf lsaCksumSum {
            config "false";
            description "LSA Checksum Sum";

            // Type is an MO-Defined-Type
            type ospf_LsaCksumSum;
        }

        // Operational Cost
        // Inherited From ospf:AIf
        // Type is an MO-Defined-Type
        leaf operCost {
            config "false";
            description "Operational Cost";

            // Type is an MO-Defined-Type
            type ospf_IfCost;
        }

        // Operational Dead interval
        // Inherited From ospf:AIf
        // Type is an MO-Defined-Type
        leaf operDeadIntvl {
            config "false";
            description "Operational Dead Interval";

            // Type is an MO-Defined-Type
            type ospf_DeadIntvl;
        }

        // Hello interval, interval between hello packets that
        // OSPF sends on the interface
        // From Interface ospf:IIntfIntvl
        // Inherited From ospf:AIf
        // Type is an MO-Defined-Type
        leaf helloIntvl {
            description "Hello Interval";

            // Type is an MO-Defined-Type
            type ospf_HelloIntvl;
        }

        // Dead interval, interval during which at least one
        // hello packet must be received from a neighbor before
        // the router declares that neighbor as down
        // From Interface ospf:IIntfIntvl
        // Inherited From ospf:AIf
        // Type is an MO-Defined-Type
        leaf deadIntvl {
            description "Dead Interval";

            // Type is an MO-Defined-Type
            type ospf_DeadIntvl;
        }

        // Retransmit interval, time between LSA retransmissions.
        // When a router sends an LSA to its neighbor, it keeps
        // the LSA until it receives an acknowledgement from the
        // neighbor. If the router receives no acknowldegement
        // within the retransmit interval, the local router
        // resends the LSA
        // From Interface ospf:IIntfIntvl
        // Inherited From ospf:AIf
        // Type is an MO-Defined-Type
        leaf rexmitIntvl {
            description "Retransmit Interval";

            // Type is an MO-Defined-Type
            type ospf_RexmitIntvl;
        }

        // Transmit delay, estimated time needed to send an LSA
        // update packet
        // From Interface ospf:IIntfIntvl
        // Inherited From ospf:AIf
        // Type is an MO-Defined-Type
        leaf xmitDelay {
            description "Transmit Delay";

            // Type is an MO-Defined-Type
            type ospf_XmitDelay;
        }

        // Cost of the interface
        // From Interface ospf:IIntfCost
        // Inherited From ospf:AIf
        // Type is an MO-Defined-Type
        leaf cost {
            description "Cost";

            // Type is an MO-Defined-Type
            type ospf_IfCost;
        }

        // Instance name
        // Inherited From ospf:AInternalIf
        // Type is an MO-Defined-Type
        leaf instance {
            config "false";
            description "Owning Instance";

            // Type is an MO-Defined-Type
            type ospf_InstanceName;
        }

        // Instance id
        // Inherited From ospf:AInternalIf
        // Type is an MO-Defined-Type
        leaf instanceid {
            config "false";
            description "Instance ID to be used in OSPF packets";

            // Type is an MO-Defined-Type
            type ospf_InstanceID;
        }

        // Dom name
        // Inherited From ospf:AInternalIf
        // Type is an MO-Defined-Type
        leaf dom {
            config "false";
            description "Dom to which the interface belongs to";

            // Type is an MO-Defined-Type
            type ospf_DomName;
        }

        // Instance name deleted by CLI
        // Inherited From ospf:AInternalIf
        // Type is an MO-Defined-Type
        leaf instanceDeletedViaCLI {
            config "false";
            description "Instance Name deleted via CLI";

            // Type is an MO-Defined-Type
            type ospf_InstanceName;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping pim_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per pim instance information
        container inst-items {

            // Added containment as a singleton: Prefix=inst
            // Acquired From Package pim
            uses pim_Inst-group;
        }
    }

    grouping pim_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // Inter Packet Delay
        // Inherited From rtdmc:AInst
        // Type is an MO-Defined-Type
        leaf jpDelay {
            description "Inter Packet Delay";

            // Type is an MO-Defined-Type
            type rtdmc_JPDelay;
        }

        // Null Register Inter Batch Delay
        // Inherited From rtdmc:AInst
        // Type is an MO-Defined-Type
        leaf nrDelay {
            description "Null Register Inter Batch Delay";

            // Type is an MO-Defined-Type
            type rtdmc_NRDelay;
        }

        // Number of routes in a null register
        // Inherited From rtdmc:AInst
        // Type is an MO-Defined-Type
        leaf nrNumRt {
            description "Null Register Number of Routes";

            // Type is an MO-Defined-Type
            type rtdmc_NRNumRt;
        }
        leaf regStop {
            type boolean;
        }

        // This objects hold per pim domain (vrf) information
        container dom-items {
            list Dom-list {
                key "name";

                // Added containment: Prefix=dom
                // Acquired From Package pim
                uses pim_Dom-group;
            }
        }
    }

    grouping pim_Dom-group {

        // Inherited From nw:Conn
        // Modified by Override: nw:CpDom->name
        // Type is an MO-Defined-Type
        leaf name {
            description "Name";

            // Type is an MO-Defined-Type
            type naming_Name {
                length "1..64";
            }
        }

        // Admin State
        // Inherited From rtdmc:ADom
        // Type is an MO-Defined-Type
        leaf adminSt {
            description "Admin State";

            // Type is an MO-Defined-Type
            type nw_AdminSt;
        }

        // Per-Dom Controls
        // Inherited From rtdmc:ADom
        // Type is an MO-Defined-Type
        leaf ctrl {
            description "Domain Controls";

            // Type is an MO-Defined-Type
            type rtdmc_DomCtrl;
        }

        // Protocol packet MTU
        // Inherited From rtdmc:ADom
        // Type is an MO-Defined-Type
        leaf mtu {
            description "Maximum Transmission Unit";

            // Type is an MO-Defined-Type
            type rtdmc_Mtu;
        }

        // Auto Enable
        // Inherited From rtdmc:ADom
        // Type is an MO-Defined-Type
        leaf autoEnable {
            description "Auto Enable";

            // Type is an MO-Defined-Type
            type rtdmc_AutoEnable;
        }
        leaf logNbhChng {
            type boolean;
        }
        leaf flushRoutes {
            type boolean;
        }
        leaf bfd {
            type boolean;
        }

        // This object holds policy for Anycast RP Function
        // Specifies the anycast and local interface for the anycast RP
        // and all the peer's local info    Anycast RP is not supported for BSR and Auto-RP
        container acastrpfunc-items {

            // Added containment as a singleton: Prefix=acastrpfunc
            // Acquired From Package pim
            uses pim_AcastRPFuncP-group;
        }

        // This object holds policy for
        // Auto-RP method of RP discovery
        container autorp-items {

            // Added containment as a singleton: Prefix=autorp
            // Acquired From Package pim
            uses pim_AutoRPP-group;
        }

        // This object holds policy for
        // Bootstrap Router method of RP discovery
        container bsr-items {

            // Added containment as a singleton: Prefix=bsr
            // Acquired From Package pim
            uses pim_BSRP-group;
        }

        // PIM databases
        container db-items {
            list Db-list {
                key "type";

                // Added containment: Prefix=db
                // Acquired From Package pim
                uses pim_Db-group;
            }
        }

        // This object holds the pim dom related statistics
        container domstats-items {

            // Added containment as a singleton: Prefix=domstats
            // Acquired From Package pim
            uses pim_DomStats-group;
        }

        // This object holds pim information that is operated at a
        // interface level
        container if-items {
            list If-list {
                key "id";

                // Added containment: Prefix=if
                // Acquired From Package pim
                uses pim_If-group;
            }
        }

        // This object holds resource (router state) limit policy
        // to limit amount of multicast routing state on the router
        container limit-items {

            // Added containment as a singleton: Prefix=limit
            // Acquired From Package pim
            uses pim_ResP-group;
        }

        // This object holds policy for
        // Any Source Multicast (ASM) pattern
        container asm-items {

            // Added containment as a singleton: Prefix=asm
            // Acquired From Package pim
            uses pim_ASMPatP-group;
        }

        // This object holds policy for
        // Source Specific Multicast (SSM) pattern
        container ssm-items {

            // Added containment as a singleton: Prefix=ssm
            // Acquired From Package pim
            uses pim_SSMPatP-group;
        }

        // This object holds policy for
        // Bidirectional Multicast (BiDir) pattern
        container bidir-items {

            // Added containment as a singleton: Prefix=bidir
            // Acquired From Package pim
            uses pim_BidirPatP-group;
        }

        // This object holds policy for Static RP
        container staticrp-items {

            // Added containment as a singleton: Prefix=staticrp
            // Acquired From Package pim
            uses pim_StaticRPP-group;
        }

        // This object holds the pim control traffic stats
        container trstats-items {

            // Added containment as a singleton: Prefix=trstats
            // Acquired From Package pim
            uses pim_TrafficStats-group;
        }
    }

    grouping pim_AcastRPFuncP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Source Interface
        // Inherited From rtdmc:AFuncP
        // Type is an MO-Defined-Type
        leaf srcIf {
            description "Source Interface";

            // Type is an MO-Defined-Type
            type nw_IfId;
        }

        // Anycast RP Unique Local Interface
        // Inherited From rtdmc:AAcastRPFuncP
        // Type is an MO-Defined-Type
        leaf localIf {
            description "Local Interface";

            // Type is an MO-Defined-Type
            type nw_IfId;
        }

        // This object holds Anycast RP Peer Info
        container peer-items {
            list AcastRPPeer-list {
                key "addr rpSetAddr";

                // Added containment: Prefix=peer
                // Acquired From Package pim
                uses pim_AcastRPPeer-group;
            }
        }
    }

    grouping pim_AcastRPPeer-group {
        leaf rpSetAddr {
            type address_Ip;
        }
        leaf addr {
            type address_Ip;
        }
    }

    grouping pim_AutoRPP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Auto-RP Control
        // Inherited From rtdmc:AAutoRPP
        // Type is an MO-Defined-Type
        leaf ctrl {
            description "Control";

            // Type is an MO-Defined-Type
            type rtdmc_AutoRPCtrl;
        }

        // End Child MOs    This object holds policy for
        // choosing RPs from among RP candidates
        container rpfilter-items {

            // Added containment as a singleton: Prefix=rpfilter
            // Acquired From Package pim
            uses pim_RPFilterP-group;
        }

        // This object holds policy for
        // choosing Mapping Agent from among the candidates
        container mafilter-items {

            // Added containment as a singleton: Prefix=mafilter
            // Acquired From Package pim
            uses pim_MAFilterP-group;
        }

        // This object holds policy for RP Function
        container rpfunc-items {

            // Added containment as a singleton: Prefix=rpfunc
            // Acquired From Package pim
            uses pim_RPFuncP-group;
        }

        // This object holds policy for
        // Auto-RP Mapping Agent Function
        container mafunc-items {

            // Added containment as a singleton: Prefix=mafunc
            // Acquired From Package pim
            uses pim_MAFuncP-group;
        }
    }

    grouping pim_RPFilterP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf rtMap {
            type string {
            }
        }
    }

    grouping pim_MAFilterP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf rtMap {
            type string {
            }
        }
    }

    grouping pim_RPFuncP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Source Interface
        // Inherited From rtdmc:AFuncP
        // Type is an MO-Defined-Type
        leaf srcIf {
            description "Source Interface";

            // Type is an MO-Defined-Type
            type nw_IfId;
        }

        // Priority
        // Inherited From rtdmc:ARPFuncP
        // Type is an MO-Defined-Type
        leaf prio {
            description "Priority";

            // Type is an MO-Defined-Type
            type rtdmc_BSRPrio;
        }

        // Interval
        // Inherited From rtdmc:ARPFuncP
        // Type is an MO-Defined-Type
        leaf interval {
            description "Interval";

            // Type is an MO-Defined-Type
            type rtdmc_BSRInterval;
        }

        // Scope
        // Inherited From rtdmc:ARPFuncP
        // Type is an MO-Defined-Type
        leaf scope {
            description "Scope";

            // Type is an MO-Defined-Type
            type rtdmc_AutoRPScope;
        }
        leaf addr {
            type address_Ip;
        }
        leaf useSendRPAnnCommand {
            type boolean;
        }

        // This object holds multicast group ranges for RP
        container range-items {
            list RPGrpRange-list {
                key "bidir";

                // Added containment: Prefix=range
                // Acquired From Package pim
                uses pim_RPGrpRange-group;
            }
        }
    }

    grouping pim_RPGrpRange-group {
        leaf override {
            type boolean;
        }
        leaf rtMap {
            type string {
            }
        }
        leaf pfxList {
            type string {
            }
        }
        leaf grpList {
            type address_Ip;
        }
        leaf grpList1 {
            type address_Ip;
        }
        leaf grpList2 {
            type address_Ip;
        }
        leaf grpList3 {
            type address_Ip;
        }
        leaf ssmNone {
            type boolean;
        }
        leaf bidir {
            type boolean;
        }
    }

    grouping pim_MAFuncP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Source Interface
        // Inherited From rtdmc:AFuncP
        // Type is an MO-Defined-Type
        leaf srcIf {
            description "Source Interface";

            // Type is an MO-Defined-Type
            type nw_IfId;
        }

        // Scope
        // Inherited From rtdmc:AMAFuncP
        // Type is an MO-Defined-Type
        leaf scope {
            description "Scope";

            // Type is an MO-Defined-Type
            type rtdmc_AutoRPScope;
        }
        leaf useSendRPDisCommand {
            type boolean;
        }
    }

    grouping pim_BSRP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // BSR Control
        // Inherited From rtdmc:ABSRP
        // Type is an MO-Defined-Type
        leaf ctrl {
            description "Control";

            // Type is an MO-Defined-Type
            type rtdmc_BSRCtrl;
        }

        // End Child MOs    This object holds policy for
        // choosing RPs from among RP candidates
        container rpfilter-items {

            // Added containment as a singleton: Prefix=rpfilter
            // Acquired From Package pim
            uses pim_RPFilterP-group;
        }

        // This object holds policy for
        // choosing BSRs from among BSR candidates
        container bsrfilter-items {

            // Added containment as a singleton: Prefix=bsrfilter
            // Acquired From Package pim
            uses pim_BSRFilterP-group;
        }

        // This object holds policy for RP Function
        container rpfunc-items {

            // Added containment as a singleton: Prefix=rpfunc
            // Acquired From Package pim
            uses pim_RPFuncP-group;
        }

        // This object holds policy for
        // Bootstrap Router Function
        container bsrfunc-items {

            // Added containment as a singleton: Prefix=bsrfunc
            // Acquired From Package pim
            uses pim_BSRFuncP-group;
        }
    }

    grouping pim_BSRFilterP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf rtMap {
            type string {
            }
        }
    }

    grouping pim_BSRFuncP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Source Interface
        // Inherited From rtdmc:AFuncP
        // Type is an MO-Defined-Type
        leaf srcIf {
            description "Source Interface";

            // Type is an MO-Defined-Type
            type nw_IfId;
        }

        // Hash Mask Len
        // Inherited From rtdmc:ABSRFuncP
        // Modified by Override: pim:BSRFuncP->hashLen
        // Type is an MO-Defined-Type
        leaf hashLen {
            description "Hash Mask Len";

            // Type is an MO-Defined-Type
            type rtdmc_BSRHashLen {
                range "1..32";
            }
        }

        // Priority
        // Inherited From rtdmc:ABSRFuncP
        // Type is an MO-Defined-Type
        leaf prio {
            description "Priority";

            // Type is an MO-Defined-Type
            type rtdmc_BSRPrio;
        }

        // Priority
        // Inherited From rtdmc:ABSRFuncP
        // Type is an MO-Defined-Type
        leaf interval {
            description "Interval";

            // Type is an MO-Defined-Type
            type rtdmc_BSRInterval;
        }
    }

    grouping pim_Db-group {

        // Inherited From nw:Conn
        // Modified by Override: nw:Db->name
        // Type is an MO-Defined-Type
        leaf name {
            description "Name";

            // Type is an MO-Defined-Type
            type naming_Name {
                length "1..64";
            }
        }

        // Type of the repository
        // Inherited From rtdmc:ADb
        // Type is an MO-Defined-Type
        leaf type {
            description "Type";

            // Type is an MO-Defined-Type
            type rtdmc_DbT;
        }
        container autorp-items {
            list AutoRPPInfo-list {
                key "addr";

                // Added containment: Prefix=autorp
                // Acquired From Package pim
                uses pim_AutoRPPInfo-group;
            }
        }
        container bsr-items {
            list BSRInfo-list {
                key "addr";

                // Added containment: Prefix=bsr
                // Acquired From Package pim
                uses pim_BSRInfo-group;
            }
        }
        container grange-items {
            list RPGrange-list {
                key "addr";

                // Added containment: Prefix=grange
                // Acquired From Package pim
                uses pim_RPGrange-group;
            }
        }

        // PIM Group/Src MOs
        container src-items {
            list Route-list {
                key "src grp";

                // Added containment: Prefix=src
                // Acquired From Package pim
                uses pim_Route-group;
            }
        }
        container rp-items {
            list RPInfo-list {
                key "addr";

                // Added containment: Prefix=rp
                // Acquired From Package pim
                uses pim_RPInfo-group;
            }
        }
    }

    grouping pim_AutoRPPInfo-group {

        // Inherited From nw:Conn
        // Modified by Override: nw:Db->name
        // Type is an MO-Defined-Type
        leaf name {
            description "Name";

            // Type is an MO-Defined-Type
            type naming_Name {
                length "1..64";
            }
        }
        leaf addr {
            type address_Ip;
        }
        leaf expiry {
            type uint64;
        }
        leaf uptime {
            type uint64;
        }
        leaf priority {
            type uint32;
        }
        leaf hashMaskLen {
            type uint32;
        }
    }

    grouping pim_BSRInfo-group {

        // Inherited From nw:Conn
        // Modified by Override: nw:Db->name
        // Type is an MO-Defined-Type
        leaf name {
            description "Name";

            // Type is an MO-Defined-Type
            type naming_Name {
                length "1..64";
            }
        }
        leaf addr {
            type address_Ip;
        }
        leaf expiry {
            type uint64;
        }
        leaf uptime {
            type uint64;
        }
        leaf priority {
            type uint32;
        }
        leaf hashMaskLen {
            type uint32;
        }
    }

    grouping pim_RPGrange-group {
        leaf addr {
            type address_Ip;
        }

        // Inherited From rtdmc:RPGrange
        // Type is an MO-Defined-Type
        leaf flags {
            description "Group Range Address";

            // Type is an MO-Defined-Type
            type rtdmc_GRangeFlags;
        }
        leaf rpAddr {
            type address_Ip;
        }
    }

    grouping pim_Route-group {

        // Inherited From nw:Conn
        // Modified by Override: nw:DbRec->name
        // Type is an MO-Defined-Type
        leaf name {
            description "Name";

            // Type is an MO-Defined-Type
            type naming_Name {
                length "1..64";
            }
        }
        leaf ver {
            config "false";
            type uint32;
        }
        leaf src {
            type address_Ip;
        }
        leaf grp {
            type address_Ip;
        }
        leaf rpAddrRoute {
            type address_Ip;
        }

        // Inherited From rtdmc:SGRoute
        // Type is an MO-Defined-Type
        leaf iif {
            config "false";
            description "Incoming interface";

            // Type is an MO-Defined-Type
            type nw_IfId;
        }
        leaf expiryTs {
            config "false";
            type uint64;
        }
        leaf rpfNbr {
            config "false";
            type address_Ip;
        }
        leaf rpfSrc {
            config "false";
            type address_Ip;
        }
        leaf createTs {
            config "false";
            type uint64;
        }
        leaf assertTime {
            config "false";
            type uint64;
        }

        // Inherited From rtdmc:SGRoute
        // Type is an MO-Defined-Type
        leaf rtType {
            config "false";
            description "Route Uptime";

            // Type is an MO-Defined-Type
            type rtdmc_RtFlags;
        }

        // Inherited From rtdmc:SGRoute
        // Type is an MO-Defined-Type
        leaf swPktCnt {
            config "false";
            description "Software Packet Count";

            // Type is an MO-Defined-Type
            type rtdmc_PktCntType;
        }

        // Inherited From rtdmc:SGRoute
        // Type is an MO-Defined-Type
        leaf swByteCnt {
            config "false";
            description "Software Byte Count";

            // Type is an MO-Defined-Type
            type rtdmc_PktCntType;
        }

        // Inherited From rtdmc:SGRoute
        // Type is an MO-Defined-Type
        leaf hwPktCnt {
            config "false";
            description "Hardware Packet Count";

            // Type is an MO-Defined-Type
            type rtdmc_ByteCntType;
        }

        // Inherited From rtdmc:SGRoute
        // Type is an MO-Defined-Type
        leaf hwByteCnt {
            config "false";
            description "Hardware Byte Count";

            // Type is an MO-Defined-Type
            type rtdmc_ByteCntType;
        }
        leaf assertMetric {
            type uint32;
        }
        leaf assertMetricPref {
            type uint32;
        }

        // Inherited From rtdmc:SGRoute
        // Type is an MO-Defined-Type
        leaf routeBits {
            config "false";
            description "RP WC Bit";

            // Type is an MO-Defined-Type
            type rtdmc_RouteBits;
        }
        leaf rtTimeOutInvtl {
            config "false";
            type uint32;
        }
        leaf jpHoldTime {
            config "false";
            type uint32;
        }

        // PIM OIF list MOs
        container oif-items {
            list Oif-list {
                key "oIf";

                // Added containment: Prefix=oif
                // Acquired From Package pim
                uses pim_Oif-group;
            }
        }
    }

    grouping pim_Oif-group {

        // Inherited From rtdmc:Oif
        // Type is an MO-Defined-Type
        leaf oIf {
            description "Outgoing interface";

            // Type is an MO-Defined-Type
            type nw_IfId;
        }

        // Inherited From rtdmc:Oif
        // Type is an MO-Defined-Type
        leaf flags {
            description "pim route oif lists";

            // Type is an MO-Defined-Type
            type rtdmc_OifFlags;
        }
    }

    grouping pim_RPInfo-group {

        // Inherited From nw:Conn
        // Modified by Override: nw:Db->name
        // Type is an MO-Defined-Type
        leaf name {
            description "Name";

            // Type is an MO-Defined-Type
            type naming_Name {
                length "1..64";
            }
        }
        leaf addr {
            type address_Ip;
        }
        leaf local {
            type boolean;
        }
        leaf uptime {
            type uint64;
        }
        leaf arpExp {
            type uint64;
        }
        leaf bsrExp {
            type uint64;
        }
        leaf bsrAddr {
            type address_Ip;
        }
        leaf priority {
            type uint32;
        }

        // Inherited From rtdmc:RPInfo
        // Type is an MO-Defined-Type
        leaf discType {
            description "RP source type";

            // Type is an MO-Defined-Type
            type rtdmc_RPSourceType;
        }
        leaf dfOrdinal {
            type uint32;
        }

        // Rel-def from RP2Grange
        container rsrP2Grange-items {

            // Abstract containment of rsrP2Grange derived from pim:RPInfo
            list RsRP2Grange-list {
                config "false";
                key "tDn";

                // Added containment: Prefix=rsrP2Grange
                // Acquired From Package pim
                uses pim_RsRP2Grange_source-group;
            }
        }
    }

    grouping pim_DomStats-group {

        // Inherited From rtdmc:DomStats
        // Type is an MO-Defined-Type
        leaf regSent {
            config "false";
            description "Registers Sent";

            // Type is an MO-Defined-Type
            type rtdmc_Counter32;
        }

        // Inherited From rtdmc:DomStats
        // Type is an MO-Defined-Type
        leaf regRcvd {
            config "false";
            description "Registers Received ";

            // Type is an MO-Defined-Type
            type rtdmc_Counter32;
        }

        // Inherited From rtdmc:DomStats
        // Type is an MO-Defined-Type
        leaf nullRegSent {
            config "false";
            description "Null Registers Sent";

            // Type is an MO-Defined-Type
            type rtdmc_Counter32;
        }

        // Inherited From rtdmc:DomStats
        // Type is an MO-Defined-Type
        leaf nullRegRcvd {
            config "false";
            description "Null Registers Received";

            // Type is an MO-Defined-Type
            type rtdmc_Counter32;
        }

        // Inherited From rtdmc:DomStats
        // Type is an MO-Defined-Type
        leaf regStopSent {
            config "false";
            description "Register Stop Sent";

            // Type is an MO-Defined-Type
            type rtdmc_Counter32;
        }

        // Inherited From rtdmc:DomStats
        // Type is an MO-Defined-Type
        leaf regStopRcvd {
            config "false";
            description "Register Stop Received ";

            // Type is an MO-Defined-Type
            type rtdmc_Counter32;
        }

        // Inherited From rtdmc:DomStats
        // Type is an MO-Defined-Type
        leaf regRcvdSSM {
            config "false";
            description "Registers Received for SSM";

            // Type is an MO-Defined-Type
            type rtdmc_Counter32;
        }

        // Inherited From rtdmc:DomStats
        // Type is an MO-Defined-Type
        leaf regRcvdBiDir {
            config "false";
            description "Registers Received for BiDir";

            // Type is an MO-Defined-Type
            type rtdmc_Counter32;
        }

        // Inherited From rtdmc:DomStats
        // Type is an MO-Defined-Type
        leaf regRcvdAndNotRP {
            config "false";
            description "Registers Received but not RP";

            // Type is an MO-Defined-Type
            type rtdmc_Counter32;
        }

        // Inherited From rtdmc:DomStats
        // Type is an MO-Defined-Type
        leaf bsrBsSent {
            config "false";
            description "Bootstrap message sent";

            // Type is an MO-Defined-Type
            type rtdmc_Counter32;
        }

        // Inherited From rtdmc:DomStats
        // Type is an MO-Defined-Type
        leaf bsrBsRcvd {
            config "false";
            description "Bootstrap message received";

            // Type is an MO-Defined-Type
            type rtdmc_Counter32;
        }

        // Inherited From rtdmc:DomStats
        // Type is an MO-Defined-Type
        leaf bsrCRPSent {
            config "false";
            description "Candidate RP message sent";

            // Type is an MO-Defined-Type
            type rtdmc_Counter32;
        }

        // Inherited From rtdmc:DomStats
        // Type is an MO-Defined-Type
        leaf bsrCRPRcvd {
            config "false";
            description "Candidate RP message received";

            // Type is an MO-Defined-Type
            type rtdmc_Counter32;
        }

        // Inherited From rtdmc:DomStats
        // Type is an MO-Defined-Type
        leaf bsrBsFromNonNbr {
            config "false";
            description "Bootstrap message from non-neighbor";

            // Type is an MO-Defined-Type
            type rtdmc_Counter32;
        }

        // Inherited From rtdmc:DomStats
        // Type is an MO-Defined-Type
        leaf bsrBsFromBorderIF {
            config "false";
            description "Bootstrap message from border interface";

            // Type is an MO-Defined-Type
            type rtdmc_Counter32;
        }

        // Inherited From rtdmc:DomStats
        // Type is an MO-Defined-Type
        leaf bsrBsLenErr {
            config "false";
            description "Bootstrap length error";

            // Type is an MO-Defined-Type
            type rtdmc_Counter32;
        }

        // Inherited From rtdmc:DomStats
        // Type is an MO-Defined-Type
        leaf bsrBsRPFFail {
            config "false";
            description "Bootstrap messages for which RPF Failed";

            // Type is an MO-Defined-Type
            type rtdmc_Counter32;
        }

        // Inherited From rtdmc:DomStats
        // Type is an MO-Defined-Type
        leaf bsrBsRcvdLisNotConf {
            config "false";
            description "Bootstrap received listen not configured";

            // Type is an MO-Defined-Type
            type rtdmc_Counter32;
        }

        // Inherited From rtdmc:DomStats
        // Type is an MO-Defined-Type
        leaf bsrCRPFromBorderIF {
            config "false";
            description "Bootstrap Candidate RP From border interface";

            // Type is an MO-Defined-Type
            type rtdmc_Counter32;
        }

        // Inherited From rtdmc:DomStats
        // Type is an MO-Defined-Type
        leaf bsrCRPRcvdLisNotConf {
            config "false";
            description "Bootstrap candidate RP received but listen not configured";

            // Type is an MO-Defined-Type
            type rtdmc_Counter32;
        }

        // Inherited From rtdmc:DomStats
        // Type is an MO-Defined-Type
        leaf autoRPAnnouncesSent {
            config "false";
            description "RP announcements sent";

            // Type is an MO-Defined-Type
            type rtdmc_Counter32;
        }

        // Inherited From rtdmc:DomStats
        // Type is an MO-Defined-Type
        leaf autoRPAnnouncesRcvd {
            config "false";
            description "RP announcements received";

            // Type is an MO-Defined-Type
            type rtdmc_Counter32;
        }

        // Inherited From rtdmc:DomStats
        // Type is an MO-Defined-Type
        leaf autoRPDiscoveriesSent {
            config "false";
            description "RP discoveries sent";

            // Type is an MO-Defined-Type
            type rtdmc_Counter32;
        }

        // Inherited From rtdmc:DomStats
        // Type is an MO-Defined-Type
        leaf autoRPDiscoveriesRcvd {
            config "false";
            description "RP discoveries received";

            // Type is an MO-Defined-Type
            type rtdmc_Counter32;
        }

        // Inherited From rtdmc:DomStats
        // Type is an MO-Defined-Type
        leaf autoRPRPFFailed {
            config "false";
            description "Auto RP RPF Failed";

            // Type is an MO-Defined-Type
            type rtdmc_Counter32;
        }

        // Inherited From rtdmc:DomStats
        // Type is an MO-Defined-Type
        leaf autoRPFromBorderIF {
            config "false";
            description "Auto RP from border interface";

            // Type is an MO-Defined-Type
            type rtdmc_Counter32;
        }

        // Inherited From rtdmc:DomStats
        // Type is an MO-Defined-Type
        leaf autoRPInvalidType {
            config "false";
            description "Auto RP invalid type";

            // Type is an MO-Defined-Type
            type rtdmc_Counter32;
        }

        // Inherited From rtdmc:DomStats
        // Type is an MO-Defined-Type
        leaf autoRPTTLExp {
            config "false";
            description "Auto RP TTL expired";

            // Type is an MO-Defined-Type
            type rtdmc_Counter32;
        }

        // Inherited From rtdmc:DomStats
        // Type is an MO-Defined-Type
        leaf autoRPRcvdLisNotConf {
            config "false";
            description "Auto RP received but listen not configured";

            // Type is an MO-Defined-Type
            type rtdmc_Counter32;
        }

        // Inherited From rtdmc:DomStats
        // Type is an MO-Defined-Type
        leaf cpRPFFailNoRoute {
            config "false";
            description "Control plane RPF fail due to no route";

            // Type is an MO-Defined-Type
            type rtdmc_Counter32;
        }

        // Inherited From rtdmc:DomStats
        // Type is an MO-Defined-Type
        leaf dpRPFFailNoRoute {
            config "false";
            description "Data Plane RPF fail due to no route";

            // Type is an MO-Defined-Type
            type rtdmc_Counter32;
        }

        // Inherited From rtdmc:DomStats
        // Type is an MO-Defined-Type
        leaf dpNoMcastState {
            config "false";
            description "Data Plane no multicast state found";

            // Type is an MO-Defined-Type
            type rtdmc_Counter32;
        }

        // Inherited From rtdmc:DomStats
        // Type is an MO-Defined-Type
        leaf dpCrtRouteStateCnt {
            config "false";
            description "Data Plane create route state count";

            // Type is an MO-Defined-Type
            type rtdmc_Counter32;
        }
    }

    grouping pim_If-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // Interface Control
        // Inherited From rtdmc:AIf
        // Type is an MO-Defined-Type
        leaf ctrl {
            description "Controls";

            // Type is an MO-Defined-Type
            type rtdmc_IfCtrl;
        }

        // Designated Router Priority
        // Inherited From rtdmc:AIf
        // Type is an MO-Defined-Type
        leaf drPrio {
            description "Designated Router Priority";

            // Type is an MO-Defined-Type
            type rtdmc_DRPrio;
        }

        // Designated Router Delay
        // Inherited From rtdmc:AIf
        // Type is an MO-Defined-Type
        leaf drDelay {
            description "Designated Router Delay";

            // Type is an MO-Defined-Type
            type rtdmc_DRDelay;
        }
        leaf jpRtMap {
            type string {
            }
        }
        leaf neighRtMap {
            type string {
            }
        }
        leaf neighpfxList {
            type string {
            }
        }
        leaf border {
            type boolean;
        }
        leaf dr {
            config "false";
            type address_Ip;
        }
        leaf rtEpPDn {
            type string;
        }
        leaf nbrHoldTime {
            config "false";
            type uint32;
        }

        // Generation id
        // Inherited From rtdmc:AIf
        // Type is an MO-Defined-Type
        leaf genID {
            config "false";
            description "Generation ID";

            // Type is an MO-Defined-Type
            type rtdmc_GenId;
        }
        leaf nextHello {
            config "false";
            type uint64;
        }
        leaf ipAddr {
            config "false";
            type address_Ip;
        }

        // Inherited From rtdmc:AIf
        // Type is an MO-Defined-Type
        leaf bfdInst {
            description "BFD Instance";

            // Type is an MO-Defined-Type
            type rtdmc_BfdInstSt;
        }
        leaf pimSparseMode {
            type boolean;
        }

        // This object holds pim neighbor information
        container adj-items {
            list AdjEp-list {
                key "addr";

                // Added containment: Prefix=adj
                // Acquired From Package pim
                uses pim_AdjEp-group;
            }
        }

        // PIM databases
        container db-items {
            list Db-list {
                key "type";

                // Added containment: Prefix=db
                // Acquired From Package pim
                uses pim_Db-group;
            }
        }

        // This object holds the pim interface related statistics
        container ifstats-items {

            // Added containment as a singleton: Prefix=ifstats
            // Acquired From Package pim
            uses pim_IfStats-group;
        }

        // This object holds the join-prune traffic policy
        container jp-items {
            list JPTrP-list {
                key "policyDir";

                // Added containment: Prefix=jp
                // Acquired From Package pim
                uses pim_JPTrP-group;
            }
        }

        // This object holds the hello traffic policy
        container hello-items {

            // Added containment as a singleton: Prefix=hello
            // Acquired From Package pim
            uses pim_HelloTrP-group;
        }

        // This object holds the pim control traffic stats
        container trstats-items {

            // Added containment as a singleton: Prefix=trstats
            // Acquired From Package pim
            uses pim_TrafficStats-group;
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping pim_AdjEp-group {

        // Inherited From nw:Conn
        // Modified by Override: nw:Ep->name
        // Type is an MO-Defined-Type
        leaf name {
            description "Name";

            // Type is an MO-Defined-Type
            type naming_Name {
                length "1..64";
            }
        }
        leaf addr {
            type address_Ip;
        }

        // DR Priority
        // Inherited From rtdmc:AAdjEp
        // Type is an MO-Defined-Type
        leaf drPrio {
            config "false";
            description "DR Priority";

            // Type is an MO-Defined-Type
            type rtdmc_DRPrio;
        }
        leaf learnTime {
            config "false";
            type uint64;
        }
        leaf expiryTime {
            config "false";
            type uint64;
        }

        // Generation id
        // Inherited From rtdmc:AAdjEp
        // Type is an MO-Defined-Type
        leaf genId {
            config "false";
            description "Generation ID";

            // Type is an MO-Defined-Type
            type rtdmc_GenId;
        }

        // BFD state
        // Inherited From rtdmc:AAdjEp
        // Type is an MO-Defined-Type
        leaf bfdSt {
            config "false";
            description "BFD State";

            // Type is an MO-Defined-Type
            type rtdmc_BfdOperSt;
        }

        // Adjacency state
        // Inherited From rtdmc:AAdjEp
        // Type is an MO-Defined-Type
        leaf operSt {
            config "false";
            description "Operational State";

            // Type is an MO-Defined-Type
            type rtdmc_AdjOperSt;
        }

        // Flags
        // Inherited From rtdmc:AAdjEp
        // Type is an MO-Defined-Type
        leaf flags {
            config "false";
            description "Flags";

            // Type is an MO-Defined-Type
            type rtdmc_AdjFlags;
        }

        // This object holds the pim neighbor related statistics
        container adjstats-items {

            // Added containment as a singleton: Prefix=adjstats
            // Acquired From Package pim
            uses pim_AdjStats-group;
        }
    }

    grouping pim_AdjStats-group {
        leaf lastHelloRcvd {
            config "false";
            type uint64;
        }

        // Longest Hello Interval
        // Inherited From rtdmc:AAdjStats
        // Type is an MO-Defined-Type
        leaf longHelloItvl {
            config "false";
            description "Longest Hello Interval";

            // Type is an MO-Defined-Type
            type rtdmc_HelloItvl;
        }

        // Last Hold Time advertised by Peer
        // Inherited From rtdmc:AAdjStats
        // Type is an MO-Defined-Type
        leaf lastHoldTime {
            config "false";
            description "Last Hold Time";

            // Type is an MO-Defined-Type
            type rtdmc_HoldTime;
        }

        // non-hello expiry timer resets
        // Inherited From rtdmc:AAdjStats
        // Type is an MO-Defined-Type
        leaf nonHelloExpResets {
            config "false";
            description "Non-Hello Expiry Timer Resets";

            // Type is an MO-Defined-Type
            type rtdmc_Counter32;
        }
    }

    grouping pim_IfStats-group {

        // Inherited From rtdmc:IfStats
        // Type is an MO-Defined-Type
        leaf helloSent {
            config "false";
            description "number of hello sent";

            // Type is an MO-Defined-Type
            type rtdmc_Counter32;
        }

        // Inherited From rtdmc:IfStats
        // Type is an MO-Defined-Type
        leaf helloRcvd {
            config "false";
            description "number of hello rcvd";

            // Type is an MO-Defined-Type
            type rtdmc_Counter32;
        }

        // Inherited From rtdmc:IfStats
        // Type is an MO-Defined-Type
        leaf jpSent {
            config "false";
            description "number of JP sent";

            // Type is an MO-Defined-Type
            type rtdmc_Counter32;
        }

        // Inherited From rtdmc:IfStats
        // Type is an MO-Defined-Type
        leaf jpRcvd {
            config "false";
            description "number of JP rcvd";

            // Type is an MO-Defined-Type
            type rtdmc_Counter32;
        }

        // Inherited From rtdmc:IfStats
        // Type is an MO-Defined-Type
        leaf assertSent {
            config "false";
            description "number of assert sent";

            // Type is an MO-Defined-Type
            type rtdmc_Counter32;
        }

        // Inherited From rtdmc:IfStats
        // Type is an MO-Defined-Type
        leaf assertRcvd {
            config "false";
            description "number of assert rcvd";

            // Type is an MO-Defined-Type
            type rtdmc_Counter32;
        }

        // Inherited From rtdmc:IfStats
        // Type is an MO-Defined-Type
        leaf graftsSent {
            config "false";
            description "number of grafts sent";

            // Type is an MO-Defined-Type
            type rtdmc_Counter32;
        }

        // Inherited From rtdmc:IfStats
        // Type is an MO-Defined-Type
        leaf graftsRcvd {
            config "false";
            description "number of grafts rcvd";

            // Type is an MO-Defined-Type
            type rtdmc_Counter32;
        }

        // Inherited From rtdmc:IfStats
        // Type is an MO-Defined-Type
        leaf grftAckSent {
            config "false";
            description "number of graft ack sent";

            // Type is an MO-Defined-Type
            type rtdmc_Counter32;
        }

        // Inherited From rtdmc:IfStats
        // Type is an MO-Defined-Type
        leaf grftAckRcvd {
            config "false";
            description "number of graft ack rcvd";

            // Type is an MO-Defined-Type
            type rtdmc_Counter32;
        }

        // Inherited From rtdmc:IfStats
        // Type is an MO-Defined-Type
        leaf dfOfferSent {
            config "false";
            description "number of DF-offer sent";

            // Type is an MO-Defined-Type
            type rtdmc_Counter32;
        }

        // Inherited From rtdmc:IfStats
        // Type is an MO-Defined-Type
        leaf dfOfferRcvd {
            config "false";
            description "number of DF-offer rcvd";

            // Type is an MO-Defined-Type
            type rtdmc_Counter32;
        }

        // Inherited From rtdmc:IfStats
        // Type is an MO-Defined-Type
        leaf dfWinnerSent {
            config "false";
            description "number of DF winner sent";

            // Type is an MO-Defined-Type
            type rtdmc_Counter32;
        }

        // Inherited From rtdmc:IfStats
        // Type is an MO-Defined-Type
        leaf dfWinnerRcvd {
            config "false";
            description "number of DF winner rcvd";

            // Type is an MO-Defined-Type
            type rtdmc_Counter32;
        }

        // Inherited From rtdmc:IfStats
        // Type is an MO-Defined-Type
        leaf dfBackoffSent {
            config "false";
            description "number of DF backoff sent";

            // Type is an MO-Defined-Type
            type rtdmc_Counter32;
        }

        // Inherited From rtdmc:IfStats
        // Type is an MO-Defined-Type
        leaf dfBackoffRcvd {
            config "false";
            description "number of DF backoff rcvd";

            // Type is an MO-Defined-Type
            type rtdmc_Counter32;
        }

        // Inherited From rtdmc:IfStats
        // Type is an MO-Defined-Type
        leaf dfPassesSent {
            config "false";
            description "number of DF Passes sent";

            // Type is an MO-Defined-Type
            type rtdmc_Counter32;
        }

        // Inherited From rtdmc:IfStats
        // Type is an MO-Defined-Type
        leaf dfPassesRcvd {
            config "false";
            description "number of DF Passes rcvd";

            // Type is an MO-Defined-Type
            type rtdmc_Counter32;
        }

        // Inherited From rtdmc:IfStats
        // Type is an MO-Defined-Type
        leaf chksumErr {
            config "false";
            description "Checksum errors";

            // Type is an MO-Defined-Type
            type rtdmc_Counter32;
        }

        // Inherited From rtdmc:IfStats
        // Type is an MO-Defined-Type
        leaf invalidPktSent {
            config "false";
            description "number of invalid pkt sent";

            // Type is an MO-Defined-Type
            type rtdmc_Counter32;
        }

        // Inherited From rtdmc:IfStats
        // Type is an MO-Defined-Type
        leaf invalidPktRcvd {
            config "false";
            description "number of invalid pkt rcvd";

            // Type is an MO-Defined-Type
            type rtdmc_Counter32;
        }

        // Inherited From rtdmc:IfStats
        // Type is an MO-Defined-Type
        leaf authFail {
            config "false";
            description "number of authentication failures";

            // Type is an MO-Defined-Type
            type rtdmc_Counter32;
        }

        // Inherited From rtdmc:IfStats
        // Type is an MO-Defined-Type
        leaf pktLenErr {
            config "false";
            description "number of packet length errors";

            // Type is an MO-Defined-Type
            type rtdmc_Counter32;
        }

        // Inherited From rtdmc:IfStats
        // Type is an MO-Defined-Type
        leaf badVerPkt {
            config "false";
            description "number of bad version pkts";

            // Type is an MO-Defined-Type
            type rtdmc_Counter32;
        }

        // Inherited From rtdmc:IfStats
        // Type is an MO-Defined-Type
        leaf pktFrmSelf {
            config "false";
            description "number of pkts from Self";

            // Type is an MO-Defined-Type
            type rtdmc_Counter32;
        }

        // Inherited From rtdmc:IfStats
        // Type is an MO-Defined-Type
        leaf pktFrmNonNbr {
            config "false";
            description "packets from Non-Neighbor";

            // Type is an MO-Defined-Type
            type rtdmc_Counter32;
        }

        // Inherited From rtdmc:IfStats
        // Type is an MO-Defined-Type
        leaf pktOnPassiveIf {
            config "false";
            description "number of packets on passive interface";

            // Type is an MO-Defined-Type
            type rtdmc_Counter32;
        }

        // Inherited From rtdmc:IfStats
        // Type is an MO-Defined-Type
        leaf jpRcvdOnRPF {
            config "false";
            description "number of packets rcvd on RPF interface";

            // Type is an MO-Defined-Type
            type rtdmc_Counter32;
        }

        // Inherited From rtdmc:IfStats
        // Type is an MO-Defined-Type
        leaf joinNoRP {
            config "false";
            description "*,G Join rcvd with no RP";

            // Type is an MO-Defined-Type
            type rtdmc_Counter32;
        }

        // Inherited From rtdmc:IfStats
        // Type is an MO-Defined-Type
        leaf joinWrongRp {
            config "false";
            description "number of packets rcvd on Wrong RP";

            // Type is an MO-Defined-Type
            type rtdmc_Counter32;
        }

        // Inherited From rtdmc:IfStats
        // Type is an MO-Defined-Type
        leaf jpSSMRcvd {
            config "false";
            description "number of packets rcvd for SSM groups";

            // Type is an MO-Defined-Type
            type rtdmc_Counter32;
        }

        // Inherited From rtdmc:IfStats
        // Type is an MO-Defined-Type
        leaf jpBidirRcvd {
            config "false";
            description "number of packets rcvd for Bidir groups";

            // Type is an MO-Defined-Type
            type rtdmc_Counter32;
        }

        // Inherited From rtdmc:IfStats
        // Type is an MO-Defined-Type
        leaf jpFilterIn {
            config "false";
            description "number of JP filtered by inbound policy ";

            // Type is an MO-Defined-Type
            type rtdmc_Counter32;
        }

        // Inherited From rtdmc:IfStats
        // Type is an MO-Defined-Type
        leaf jpFilterOut {
            config "false";
            description "number of JP filtered by outbound policy ";

            // Type is an MO-Defined-Type
            type rtdmc_Counter32;
        }
    }

    grouping pim_JPTrP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf RtMap {
            type string {
            }
        }
        leaf pfxList {
            type string {
            }
        }

        // in route-map for out-bound policy application
        // <property name="outpfxList"
        // type="string:Basic"
        // owner="management"
        // mod="implicit"
        // label="Out Prefix List"
        // />    Interval used between peers
        // Inherited From rtdmc:AJPTrP
        // Type is an MO-Defined-Type
        leaf itvl {
            description "Periodic Interval";

            // Type is an MO-Defined-Type
            type rtdmc_JPItvl;
        }

        // Inherited From rtdmc:AJPTrP
        // Type is an MO-Defined-Type
        leaf policyDir {
            description "Policy Direction ";

            // Type is an MO-Defined-Type
            type rtdmc_PolicyDirType;
        }
    }

    grouping pim_HelloTrP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Hello Interval
        // Inherited From rtdmc:AHelloTrP
        // Type is an MO-Defined-Type
        leaf helloItvl {
            description "Hello Interval";

            // Type is an MO-Defined-Type
            type rtdmc_HelloItvl;
        }

        // Authentication Type
        // Inherited From rtdmc:AHelloTrP
        // Type is an MO-Defined-Type
        leaf authT {
            description "Authentication Type";

            // Type is an MO-Defined-Type
            type rtdmc_AuthT;
        }

        // Authentication Key
        // Inherited From rtdmc:AHelloTrP
        // Type is an MO-Defined-Type
        leaf authKey {
            description "Authentication Key";

            // Type is an MO-Defined-Type
            type rtdmc_AuthKey;
        }
    }

    grouping pim_TrafficStats-group;

    grouping pim_ResP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Maximum Multicast Entries
        // Inherited From mcast:AResP
        // Type is an MO-Defined-Type
        leaf max {
            description "Maximum Multicast Entries";

            // Type is an MO-Defined-Type
            type mcast_NumEntries;
        }

        // Reserved Multicast Entries
        // Inherited From mcast:AResP
        // Type is an MO-Defined-Type
        leaf rsvd {
            description "Reserved Multicast Entries";

            // Type is an MO-Defined-Type
            type mcast_NumEntries;
        }
        leaf rtMap {
            type string;
        }
    }

    grouping pim_ASMPatP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Controls
        // Inherited From rtdmc:AASMPatP
        // Type is an MO-Defined-Type
        leaf ctrl {
            description "Controls";

            // Type is an MO-Defined-Type
            type rtdmc_ASMCtrl;
        }
        leaf preBuildSpt {
            type boolean;
        }
        leaf force {
            type boolean;
        }

        // This object holds (S,G) expiry timer
        // policy for specified range
        container sgexp-items {

            // Added containment as a singleton: Prefix=sgexp
            // Acquired From Package pim
            uses pim_SGRangeExpP-group;
        }

        // This object holds group range
        // to use only shared tree
        container shared-items {

            // Added containment as a singleton: Prefix=shared
            // Acquired From Package pim
            uses pim_SharedRangeP-group;
        }

        // This object holds the register traffic policy
        container reg-items {

            // Added containment as a singleton: Prefix=reg
            // Acquired From Package pim
            uses pim_RegTrP-group;
        }
    }

    grouping pim_SGRangeExpP-group {
        leaf rtMap {
            type string {
            }
        }
        leaf pfxList {
            type string {
            }
        }
        leaf grpList {
            type address_Ip;
        }
        leaf grpList1 {
            type address_Ip;
        }
        leaf grpList2 {
            type address_Ip;
        }
        leaf grpList3 {
            type address_Ip;
        }
        leaf ssmNone {
            type boolean;
        }

        // (S,G) entry inactivity expiry timer
        // Inherited From rtdmc:ASGRangeExpP
        // Type is an MO-Defined-Type
        leaf sgExpItvl {
            description "(S,G) Entry Expiry Timer";

            // Type is an MO-Defined-Type
            type rtdmc_SGExpItvl;
        }
    }

    grouping pim_SharedRangeP-group {
        leaf rtMap {
            type string {
            }
        }
        leaf pfxList {
            type string {
            }
        }
        leaf grpList {
            type address_Ip;
        }
        leaf grpList1 {
            type address_Ip;
        }
        leaf grpList2 {
            type address_Ip;
        }
        leaf grpList3 {
            type address_Ip;
        }
        leaf ssmNone {
            type boolean;
        }
        leaf useSPTCommand {
            type boolean;
        }
    }

    grouping pim_RegTrP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf addr {
            type address_Ip;
        }

        // Source Interface
        // Inherited From rtdmc:ARegTrP
        // Type is an MO-Defined-Type
        leaf srcIf {
            description "Source Interface";

            // Type is an MO-Defined-Type
            type nw_IfId;
        }

        // Max Rate
        // Inherited From rtdmc:ARegTrP
        // Type is an MO-Defined-Type
        leaf maxRate {
            description "Maximum Rate";

            // Type is an MO-Defined-Type
            type rtdmc_RegRate;
        }
        leaf rtMap {
            type string {
            }
        }
        leaf pfxList {
            type string {
            }
        }
    }

    grouping pim_SSMPatP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // This object holds SSM group range
        container range-items {

            // Added containment as a singleton: Prefix=range
            // Acquired From Package pim
            uses pim_SSMRangeP-group;
        }
    }

    grouping pim_SSMRangeP-group {
        leaf rtMap {
            type string {
            }
        }
        leaf pfxList {
            type string {
            }
        }
        leaf grpList {
            type address_Ip;
        }
        leaf grpList1 {
            type address_Ip;
        }
        leaf grpList2 {
            type address_Ip;
        }
        leaf grpList3 {
            type address_Ip;
        }
        leaf ssmNone {
            type boolean;
        }
    }

    grouping pim_BidirPatP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Maximum number of RPs
        // Inherited From rtdmc:ABidirPatP
        // Type is an MO-Defined-Type
        leaf maxRP {
            description "Maximum RPs";

            // Type is an MO-Defined-Type
            type rtdmc_BidirRPLimit;
        }

        // Designated Forwarder Offer Burst Interval
        // Inherited From rtdmc:ABidirPatP
        // Type is an MO-Defined-Type
        leaf dfobItvl {
            description "Designated Forwarder Offer Burst Interval";

            // Type is an MO-Defined-Type
            type rtdmc_DFOBItvl;
        }
    }

    grouping pim_StaticRPP-group {

        // From Interface naming:Named
        // Inherited From naming:NamedObject
        // Modified by Override: pol:Obj->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // This object holds Static RP Info
        // If rp addr is configured locally,
        // router assumes RP functionality
        container rp-items {
            list StaticRP-list {
                key "addr";

                // Added containment: Prefix=rp
                // Acquired From Package pim
                uses pim_StaticRP-group;
            }
        }
    }

    grouping pim_StaticRP-group {
        leaf addr {
            type address_Ip;
        }

        // This object holds multicast group ranges for RP
        container range-items {
            list RPGrpRange-list {
                key "bidir";

                // Added containment: Prefix=range
                // Acquired From Package pim
                uses pim_RPGrpRange-group;
            }
        }
        container rpgrplist-items {
            list RPGrpList-list {
                key "grpListName";

                // Added containment: Prefix=rpgrplist
                // Acquired From Package pim
                uses pim_RPGrpList-group;
            }
        }
    }

    grouping pim_RPGrpList-group {
        leaf grpListName {
            type address_Ip;
        }
        leaf bidir {
            type boolean;
        }
        leaf override {
            config "false";
            type boolean;
        }
    }

    grouping vrrp_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds per vrrp instance information. There is only
        // one instance supported in vrrp currently
        container inst-items {

            // Added containment as a singleton: Prefix=inst
            // Acquired From Package vrrp
            uses vrrp_Inst-group;
        }
    }

    grouping vrrp_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds the interfaces that will have VRRP interface.
        // Interface must already be created and should have an IP address
        container if-items {
            list Interface-list {
                key "id";

                // Added containment: Prefix=if
                // Acquired From Package vrrp
                uses vrrp_Interface-group;
            }
        }
    }

    grouping vrrp_Interface-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds vrrp id information
        container id-items {
            list Id-list {
                key "id";

                // Added containment: Prefix=id
                // Acquired From Package vrrp
                uses vrrp_Id-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping vrrp_Id-group {

        // vrrp id
        // Type is an MO-Defined-Type
        leaf id {
            description "VRRP Id";

            // Type is an MO-Defined-Type
            type vrrp_Id;
        }
        leaf primary {
            type address_Ip;
        }

        // advertise interval
        // Type is an MO-Defined-Type
        leaf advIntvl {
            description "Advertisement Interval";

            // Type is an MO-Defined-Type
            type vrrp_AdvIntvl;
        }

        // authentication text
        // Type is an MO-Defined-Type
        leaf authText {
            description "Authentication Text";

            // Type is an MO-Defined-Type
            type vrrp_AuthTextType;
        }

        // authentication type
        // Type is an MO-Defined-Type
        leaf authType {
            description "Authentication Type";

            // Type is an MO-Defined-Type
            type vrrp_AuthType;
        }

        // Preempt
        // Type is an MO-Defined-Type
        leaf preempt {
            description "Preempt";

            // Type is an MO-Defined-Type
            type vrrp_Preempt;
        }

        // priority configuration
        // Type is an MO-Defined-Type
        leaf priCfg {
            description "Configured Priority";

            // Type is an MO-Defined-Type
            type vrrp_PriVal;
        }
        leaf bfdPeerAddr {
            type address_Ip;
        }

        // forwarding lower threshold
        // Type is an MO-Defined-Type
        leaf fwdLwrThrld {
            description "Fowarding Lower Threshold";

            // Type is an MO-Defined-Type
            type vrrp_PriVal;
        }

        // forwarding upper threshold
        // Type is an MO-Defined-Type
        leaf fwdUprThrld {
            description "Forwarding Upper Threshold";

            // Type is an MO-Defined-Type
            type vrrp_UprThrshld;
        }

        // admin state
        // Type is an MO-Defined-Type
        leaf adminSt {
            description "Admin state";

            // Type is an MO-Defined-Type
            type vrrp_AdminSt;
        }

        // group state
        // Type is an MO-Defined-Type
        leaf groupSt {
            config "false";
            description "vrrp group state";

            // Type is an MO-Defined-Type
            type vrrp_GroupSt;
        }

        // group state qualifier
        // Type is an MO-Defined-Type
        leaf groupStQual {
            config "false";
            description "vrrp group state qualifier";

            // Type is an MO-Defined-Type
            type vrrp_GroupStQual;
        }
        leaf mac {
            config "false";
            type address_Mac;
        }
        leaf masterAddr {
            config "false";
            type address_Ip;
        }

        // bfd session status
        // Type is an MO-Defined-Type
        leaf bfdSessionSt {
            config "false";
            description "vrrp bfd session status";

            // Type is an MO-Defined-Type
            type vrrp_bfdSessionSt;
        }
        container secondary-items {
            list Secondary-list {
                key "secondary";

                // Added containment: Prefix=secondary
                // Acquired From Package vrrp
                uses vrrp_Secondary-group;
            }
        }

        // Object to hold vrrp tarck information
        container track-items {

            // Added containment as a singleton: Prefix=track
            // Acquired From Package vrrp
            uses vrrp_Track-group;
        }
    }

    grouping vrrp_Secondary-group {
        leaf secondary {
            type address_Ip;
        }
    }

    grouping vrrp_Track-group {

        // Object to hold native track information
        container nativeTrack-items {

            // Added containment as a singleton: Prefix=nativeTrack
            // Acquired From Package vrrp
            uses vrrp_NativeTrack-group;
        }

        // Contains track information of otm track object
        container track-items {
            list ObjectTrack-list {
                key "id";

                // Added containment: Prefix=track
                // Acquired From Package vrrp
                uses vrrp_ObjectTrack-group;
            }
        }
    }

    grouping vrrp_NativeTrack-group {

        // Interface name to be tracked, format to be specified
        // eth1/1, eth1/1.1, po1
        // Type is an MO-Defined-Type
        leaf id {
            description "Interface to be tracked by this VRRP instance";

            // Type is an MO-Defined-Type
            type nw_IfId;
        }
        leaf priority {
            type uint16 {
                range "1..254";
            }
        }
    }

    grouping vrrp_ObjectTrack-group {

        // Track id to be tracked
        // Type is an MO-Defined-Type
        leaf id {
            description "Track Id to be tracked";

            // Type is an MO-Defined-Type
            type track_TrackId;
        }
        leaf decrementPriority {
            type uint16 {
                range "1..254";
            }
            default "10";
        }
    }

    grouping vrrpv3_Entity-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This object holds per vrrpv3 instance information. There is only
        // one instance supported in vrrpv3 currently
        container inst-items {

            // Added containment as a singleton: Prefix=inst
            // Acquired From Package vrrpv3
            uses vrrpv3_Inst-group;
        }
    }

    grouping vrrpv3_Inst-group {

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }

        // This object holds the interfaces that will have VRRPv3 interface.
        container if-items {
            list Interface-list {
                key "id";

                // Added containment: Prefix=if
                // Acquired From Package vrrpv3
                uses vrrpv3_Interface-group;
            }
        }
    }

    grouping vrrpv3_Interface-group {

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Type is an MO-Defined-Type
        leaf descr {
            description "Description";

            // Type is an MO-Defined-Type
            type naming_Descr;
        }

        // Administrative state
        // Inherited From nw:ProtIf
        // Type is an MO-Defined-Type
        leaf adminSt {
            description "Admin State";

            // Type is an MO-Defined-Type
            type nw_IfAdminSt;
        }

        // This object holds Virtual Router ID information
        container id-items {
            list Vr-list {
                key "id af";

                // Added containment: Prefix=id
                // Acquired From Package vrrpv3
                uses vrrpv3_Vr-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        container rtvrfMbr-items {

            // Added containment as a singleton: Prefix=rtvrfMbr
            // Acquired From Package l3
            uses l3_RtVrfMbr_target-group;
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }
    }

    grouping vrrpv3_Vr-group {

        // Virtual Router ID
        // Type is an MO-Defined-Type
        leaf id {
            description "VRRPv3 Virtual Router Id";

            // Type is an MO-Defined-Type
            type vrrpv3_Id;
        }
        leaf ip {
            type address_Ip;
        }

        // Advertisement Interval
        // Type is an MO-Defined-Type
        leaf advIntvl {
            description "Advertisement Interval";

            // Type is an MO-Defined-Type
            type vrrpv3_AdvIntvl;
        }

        // Priority Configuration
        // Type is an MO-Defined-Type
        leaf priCfg {
            description "Configured Priority";

            // Type is an MO-Defined-Type
            type vrrpv3_PriVal;
        }

        // Preempt
        // Type is an MO-Defined-Type
        leaf preempt {
            description "Preempt";

            // Type is an MO-Defined-Type
            type vrrpv3_Preempt;
        }

        // Virtual Router Description string
        // Type is an MO-Defined-Type
        leaf name {
            description "Virtual Router Description";

            // Type is an MO-Defined-Type
            type vrrpv3_Desc;
        }

        // Minimum Preemption delay before this group can preempt    a high priority Masster
        // Type is an MO-Defined-Type
        leaf preemptDelayMin {
            description "Miminum delay before preempt";

            // Type is an MO-Defined-Type
            type vrrpv3_PreemptDelay;
        }

        // Admin State
        // Type is an MO-Defined-Type
        leaf adminSt {
            description "Admin state";

            // Type is an MO-Defined-Type
            type vrrpv3_AdminSt;
        }

        // Virtual Router Address family
        // Type is an MO-Defined-Type
        leaf af {
            description "Virtual Router Address Family";

            // Type is an MO-Defined-Type
            type vrrpv3_VrAf;
        }
        container addr-items {
            list Addr-list {
                key "addr";

                // Added containment: Prefix=addr
                // Acquired From Package vrrpv3
                uses vrrpv3_Addr-group;
            }
        }
    }

    grouping vrrpv3_Addr-group {
        leaf addr {
            type address_Ip;
        }
    }

    grouping scrtchpd_Root-group {

        // Holds rpm control plane entity information
        container rpmcli-items {

            // Added containment as a singleton: Prefix=rpmcli
            // Acquired From Package rpmcli
            uses rpmcli_EntityCli-group;
        }

        // Holds Vlan-mgr control plane entity information
        container vlanmgrcli-items {

            // Added containment as a singleton: Prefix=vlanmgrcli
            // Acquired From Package vlanmgrcli
            uses vlanmgrcli_EntityCli-group;
        }
    }

    grouping rpmcli_EntityCli-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // Route control rule for access lists
        container accesslistcli-items {
            list RuleCli-list {
                key "name";

                // Added containment: Prefix=accesslistcli
                // Acquired From Package rtlistcli
                uses rtlistcli_RuleCli-group;
            }
        }

        // Route control rule for V4 prefix lists
        container pfxlistv4cli-items {
            list RuleV4Cli-list {
                key "name";

                // Added containment: Prefix=pfxlistv4cli
                // Acquired From Package rtpfxcli
                uses rtpfxcli_RuleV4Cli-group;
            }
        }

        // Route control rule for V6 prefix lists
        container pfxlistv6cli-items {
            list RuleV6Cli-list {
                key "name";

                // Added containment: Prefix=pfxlistv6cli
                // Acquired From Package rtpfxcli
                uses rtpfxcli_RuleV6Cli-group;
            }
        }

        // Route control rule for regular community lists
        container rtregcomcli-items {
            list RuleCli-list {
                key "name";

                // Added containment: Prefix=rtregcomcli
                // Acquired From Package rtregcomcli
                uses rtregcomcli_RuleCli-group;
            }
        }
    }

    grouping rtlistcli_RuleCli-group {

        // From Interface naming:Named
        // Inherited From naming:NamedObject
        // Modified by Override: rtlistcli:RuleCli->name
        // Modified by Override: pol:Obj->name
        // Modified by Override: nw:FltRule->name
        // Type is an MO-Defined-Type
        leaf name {
            description "Name";

            // Type is an MO-Defined-Type
            type naming_Name {
                length "1..63";
            }
        }

        // From Interface naming:Described
        // Inherited From pol:Instr
        // Type is an MO-Defined-Type
        leaf descr {
            description "Description";

            // Type is an MO-Defined-Type
            type naming_Descr;
        }

        // Prefix list entry definition
        container entcli-items {

            // Added containment as a singleton: Prefix=entcli
            // Acquired From Package rtlistcli
            uses rtlistcli_EntryCli-group;
        }
    }

    grouping rtlistcli_EntryCli-group {

        // CLI Action
        // Type is an MO-Defined-Type
        leaf cliAction {
            description "Action";

            // Type is an MO-Defined-Type
            type scrtchpd_Action;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }
    }

    grouping rtpfxcli_RuleV4Cli-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Prefix list entry definition
        container entcli-items {

            // Added containment as a singleton: Prefix=entcli
            // Acquired From Package rtpfxcli
            uses rtpfxcli_EntryCli-group;
        }
    }

    grouping rtpfxcli_EntryCli-group {

        // CLI Action
        // Type is an MO-Defined-Type
        leaf cliAction {
            description "Action";

            // Type is an MO-Defined-Type
            type scrtchpd_Action;
        }
        leaf pfx {
            config "false";
            type address_Ip;
        }
        leaf mask {
            type address_Ip;
        }

        // criteria, exact match or inexact match
        // Type is an MO-Defined-Type
        leaf criteria {
            config "false";
            description "Criteria";

            // Type is an MO-Defined-Type
            type rtpfx_Criteria;
        }

        // If the criteria is not an exact match, use a range to
        // describe the prefix list range
        // Type is an MO-Defined-Type
        leaf fromPfxLen {
            config "false";
            description "Start of Prefix Length";

            // Type is an MO-Defined-Type
            type l3_IpPfxLen;
        }

        // Type is an MO-Defined-Type
        leaf toPfxLen {
            config "false";
            description "End of Prefix Length";

            // Type is an MO-Defined-Type
            type l3_IpPfxLen;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
    }

    grouping rtpfxcli_RuleV6Cli-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Prefix list entry definition
        container entcli-items {

            // Added containment as a singleton: Prefix=entcli
            // Acquired From Package rtpfxcli
            uses rtpfxcli_EntryCli-group;
        }
    }

    grouping rtregcomcli_RuleCli-group {

        // From Interface naming:Named
        // Inherited From naming:NamedObject
        // Modified by Override: pol:Obj->name
        // Modified by Override: nw:FltRule->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Type of the community list [regular | extended]
        // Inherited From rtcom:Rule
        // Modified by Override: rtregcomcli:RuleCli->type
        // Type is an MO-Defined-Type
        leaf type {
            description "Type";

            // Type is an MO-Defined-Type
            type rtcom_ComT;
        }

        // Mode
        // Inherited From rtcom:Rule
        // Type is an MO-Defined-Type
        leaf mode {
            description "Mode";

            // Type is an MO-Defined-Type
            type rtcom_Mode;
        }

        // Regular community list entry
        container entregcli-items {

            // Added containment as a singleton: Prefix=entregcli
            // Acquired From Package rtregcomcli
            uses rtregcomcli_EntryRegexCli-group;
        }

        // Regular community list entry
        container entcli-items {

            // Added containment as a singleton: Prefix=entcli
            // Acquired From Package rtregcomcli
            uses rtregcomcli_EntryCli-group;
        }
    }

    grouping rtregcomcli_EntryRegexCli-group {
        leaf numOfChildren {
            type uint32;
        }

        // CLI Action
        // Type is an MO-Defined-Type
        leaf cliAction {
            description "Action";

            // Type is an MO-Defined-Type
            type scrtchpd_Action;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }
    }

    grouping rtregcomcli_EntryCli-group {
        leaf numOfChildren {
            type uint32;
        }

        // CLI Action
        // Type is an MO-Defined-Type
        leaf cliAction {
            description "Action";

            // Type is an MO-Defined-Type
            type scrtchpd_Action;
        }

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }

        // Order
        // Inherited From rtflt:Entry
        // Type is an MO-Defined-Type
        leaf order {
            description "Order";

            // Type is an MO-Defined-Type
            type rtflt_Order {
                range "1..4294967294";
            }
        }

        // Action
        // Inherited From rtflt:Entry
        // Type is an MO-Defined-Type
        leaf action {
            description "Action";

            // Type is an MO-Defined-Type
            type rtflt_Action;
        }
        leaf regex {
            type string {
            }
        }

        // Item in the community list
        container itemcli-items {
            list ItemCli-list {
                key "community";

                // Added containment: Prefix=itemcli
                // Acquired From Package rtregcomcli
                uses rtregcomcli_ItemCli-group;
            }
        }
    }

    grouping rtregcomcli_ItemCli-group {

        // From Interface naming:Named
        // Inherited From naming:NamedObject
        // Modified by Override: pol:Obj->name
        // Modified by Override: nw:FltEntry->name
        // Type is an MO-Defined-Type
        leaf name {
            description "Name";

            // Type is an MO-Defined-Type
            type naming_Name {
                length "0..64";
            }
        }

        // From Interface naming:Described
        // Inherited From pol:Instr
        // Type is an MO-Defined-Type
        leaf descr {
            description "Description";

            // Type is an MO-Defined-Type
            type naming_Descr;
        }
        leaf community {
            type mtx_array_community;
        }
    }

    grouping vlanmgrcli_EntityCli-group {

        // Inherited From nw:Conn
        // Modified by Override: nw:CpEntity->name
        // Type is an MO-Defined-Type
        leaf name {
            description "Name";

            // Type is an MO-Defined-Type
            type naming_Name {
                length "1..64";
            }
        }

        // - Admin state
        // Inherited From nw:CpEntity
        // Type is an MO-Defined-Type
        leaf adminSt {
            description "Admin State";

            // Type is an MO-Defined-Type
            type nw_AdminSt;
        }

        // Operational state
        // Inherited From nw:CpEntity
        // Type is an MO-Defined-Type
        leaf operSt {
            config "false";
            description "Operational State";

            // Type is an MO-Defined-Type
            type nw_EntOperSt;
        }

        // Operational errors qualifier
        // Inherited From nw:CpEntity
        // Type is an MO-Defined-Type
        leaf operErr {
            config "false";
            description "Operational Errors Qualifier";

            // Type is an MO-Defined-Type
            type nw_OperErrQual;
        }

        // This objects hold per vlan-mgr instance information. There is only
        // one instance of vlan-mgr running in the system today
        container inst-items {

            // Added containment as a singleton: Prefix=inst
            // Acquired From Package vlanmgrcli
            uses vlanmgrcli_InstCli-group;
        }
    }

    grouping vlanmgrcli_InstCli-group {
        leaf vxlanNativeVlans {
            type boolean;
        }

        // Inherited From nw:Conn
        // Modified by Override: nw:CpInst->name
        // Type is an MO-Defined-Type
        leaf name {
            description "Name";

            // Type is an MO-Defined-Type
            type naming_Name {
                length "1..64";
            }
        }

        // Administrative state
        // Inherited From nw:CpInst
        // Type is an MO-Defined-Type
        leaf adminSt {
            description "Admin State";

            // Type is an MO-Defined-Type
            type nw_AdminSt;
        }

        // Instance controls
        // Inherited From nw:CpInst
        // Type is an MO-Defined-Type
        leaf ctrl {
            description "Controls";

            // Type is an MO-Defined-Type
            type nw_InstCtrl;
        }

        // Operational errors qualifier
        // Inherited From nw:CpInst
        // Type is an MO-Defined-Type
        leaf operErr {
            config "false";
            description "Operational Errors Qualifier";

            // Type is an MO-Defined-Type
            type nw_OperErrQual;
        }
    }

    // Has Polymorphic containment of abstract object synthetic:CTestObj
    grouping synthetic_SwTLTestObj-group {

        // From Interface naming:Named
        // Inherited From naming:NamedObject
        // Type is an MO-Defined-Type
        leaf name {
            description "Name";

            // Type is an MO-Defined-Type
            type naming_Name;
        }

        // From Interface naming:Identified
        // Inherited From naming:NamedIdentifiedObject
        // Type is an MO-Defined-Type
        leaf id {
            description "Id";

            // Type is an MO-Defined-Type
            type naming_Id;
        }

        // Inherited From synthetic:ATestObj
        // Type is an MO-Defined-Type
        leaf descr {
            description "TBD";

            // Type is an MO-Defined-Type
            type naming_Descr;
        }
        leaf propUint64 {
            type uint64;
        }
        leaf propUint32 {
            type uint32;
        }
        leaf propUByte {
            type uint8;
        }
        leaf propDate {
            type uint64;
        }
        leaf propString {
            type string;
        }

        // Inherited From synthetic:ATestObj
        // Type is an MO-Defined-Type
        leaf propBmp64 {
            description "TBD";

            // Type is an MO-Defined-Type
            type synthetic_TestBitmask64;
        }

        // Inherited From synthetic:ATestObj
        // Type is an MO-Defined-Type
        leaf propBmp8 {
            description "TBD";

            // Type is an MO-Defined-Type
            type synthetic_TestBitmask8;
        }

        // Inherited From synthetic:ATestObj
        // Type is an MO-Defined-Type
        leaf propEnum16 {
            description "TBD";

            // Type is an MO-Defined-Type
            type synthetic_TestEnum16;
        }
        leaf objDn {
            type string;
        }
        leaf priKey {
            type string;
        }
        container secc-items {
            list SwCTestObj-list {
                key "name";

                // Added containment: Prefix=secc
                // Acquired From Package synthetic
                uses synthetic_SwCTestObj-group;
            }
        }

        // Polymorphic containment of derivative object synthetic:IfcCTestObj (from synthetic:CTestObj)
        container iecc-items {

            // Abstract containment of synthetic:IfcCTestObj derived from synthetic:CTestObj
            list IfcCTestObj-list {
                key "name";

                // Added containment: Prefix=iecc
                // Acquired From Package synthetic
                uses synthetic_IfcCTestObj-group;
            }
        }

        // Rel-def target from toObj
        // Inherited From synthetic:IfcTLTestObj
        // Inherited From synthetic:SwTLTestObj
        container rttoObj-items {

            // Added containment as a singleton: Prefix=rttoObj
            // Acquired From Package synthetic
            uses synthetic_RtToObj_target-group;
        }
    }

    grouping sysdebug_Ep-group {

        // Log Control endpoint. Contains
        // specific Log Control Domain Endpoints.
        container logcontrol-items {

            // Added containment as a singleton: Prefix=logcontrol
            // Acquired From Package sysdebug
            uses sysdebug_LogControlEp-group;
        }
    }

    grouping sysdebug_LogControlEp-group {

        // Type is an MO-Defined-Type
        leaf level {
            description "TBD";

            // Type is an MO-Defined-Type
            type sysdebug_LogControlLevel;
        }
        leaf levelFlag {
            type boolean;
        }
        leaf reset {
            type boolean;
        }
        leaf persist {
            type boolean;
        }

        // Log Control Domain. An enumeration
        // describes the possible domains.
        container domain-items {
            list LogControlDomain-list {
                key "name";

                // Added containment: Prefix=domain
                // Acquired From Package sysdebug
                uses sysdebug_LogControlDomain-group;
            }
        }
    }

    grouping sysdebug_LogControlDomain-group {

        // Type is an MO-Defined-Type
        leaf name {
            description "TBD";

            // Type is an MO-Defined-Type
            type sysdebug_LogControlDomainEnum;
        }

        // Type is an MO-Defined-Type
        leaf level {
            description "TBD";

            // Type is an MO-Defined-Type
            type sysdebug_LogControlLevel;
        }
        leaf levelFlag {
            type boolean;
        }
        leaf reset {
            type boolean;
        }
        leaf persist {
            type boolean;
        }

        // Log Control file destination identifies
        // the log rotation parameters.
        container file-items {

            // Added containment as a singleton: Prefix=file
            // Acquired From Package sysdebug
            uses sysdebug_LogControlDestinationFile-group;
        }

        // Log Control syslog destination.
        container syslog-items {

            // Added containment as a singleton: Prefix=syslog
            // Acquired From Package sysdebug
            uses sysdebug_LogControlDestinationSyslog-group;
        }

        // Log Control module.
        container module-items {
            list LogControlModule-list {
                key "name";

                // Added containment: Prefix=module
                // Acquired From Package sysdebug
                uses sysdebug_LogControlModule-group;
            }
        }
    }

    grouping sysdebug_LogControlDestinationFile-group {

        // Type is an MO-Defined-Type
        leaf backupCount {
            description "TBD";

            // Type is an MO-Defined-Type
            type sysdebug_LogControlDestinationFileBackupCount;
        }

        // Type is an MO-Defined-Type
        leaf size {
            description "TBD";

            // Type is an MO-Defined-Type
            type sysdebug_LogControlDestinationFileSize;
        }

        // Type is an MO-Defined-Type
        leaf defaultSize {
            description "TBD";

            // Type is an MO-Defined-Type
            type sysdebug_LogControlDestinationFileSize;
        }

        // Type is an MO-Defined-Type
        leaf level {
            description "TBD";

            // Type is an MO-Defined-Type
            type sysdebug_LogControlLevel;
        }

        // Type is an MO-Defined-Type
        leaf defaultLevel {
            description "TBD";

            // Type is an MO-Defined-Type
            type sysdebug_LogControlLevel;
        }
    }

    grouping sysdebug_LogControlDestinationSyslog-group {

        // Type is an MO-Defined-Type
        leaf level {
            description "TBD";

            // Type is an MO-Defined-Type
            type sysdebug_LogControlLevel;
        }

        // Type is an MO-Defined-Type
        leaf defaultLevel {
            description "TBD";

            // Type is an MO-Defined-Type
            type sysdebug_LogControlLevel;
        }
    }

    grouping sysdebug_LogControlModule-group {
        leaf name {
            type string;
        }

        // Type is an MO-Defined-Type
        leaf level {
            description "TBD";

            // Type is an MO-Defined-Type
            type sysdebug_LogControlLevel;
        }

        // Type is an MO-Defined-Type
        leaf defaultLevel {
            description "TBD";

            // Type is an MO-Defined-Type
            type sysdebug_LogControlLevel;
        }
        leaf reset {
            type boolean;
        }
    }

    grouping sysdebug_CoreFileRepository-group {

        // A core dump file.
        container file-items {
            list Core-list {
                config "false";
                key "name switchId";

                // Added containment: Prefix=file
                // Acquired From Package sysdebug
                uses sysdebug_Core-group;
            }
        }

        container mutation-items {

            // Added containment as a singleton: Prefix=mutation
            // Acquired From Package sysfile
            uses sysfile_Mutation-group;
        }
    }

    grouping sysdebug_Core-group {

        // Core files' administration state. It is
        // used to trigger download operation
        // Type is an MO-Defined-Type
        leaf adminState {
            description "TBD";

            // Type is an MO-Defined-Type
            type sysdebug_CoreFileAdminState;
        }

        // Core files progress through a state sequence.
        // operState is used more in scenarios, when core
        // files are placed on subordinate switch.
        // Since GUI can't pull the files from the switch other
        // than primary, we need a mechanism to convey the message
        // to DME for copying the contents of a core file
        // before this file can be downloaded by the users.
        // operState is used exactly for this need. This property
        // highlights the state of a core file in terms of
        // readiness for download.
        // Type is an MO-Defined-Type
        leaf operState {
            config "false";
            description "TBD";

            // Type is an MO-Defined-Type
            type sysdebug_CoreFileOperState;
        }

        // From Interface naming:Named
        // Inherited From naming:NamedObject
        // Modified by Override: sysfile:Instance->name
        // Type is an MO-Defined-Type
        leaf name {
            description "Name";

            // Type is an MO-Defined-Type
            type naming_Name {
                length "1..128";
            }
        }
        leaf ts {
            config "false";
            type uint64;
        }
        leaf size {
            config "false";
            type uint32;
        }

        // Inherited From sysfile:Instance
        // Type is an MO-Defined-Type
        leaf uri {
            config "false";
            description "TBD";

            // Type is an MO-Defined-Type
            type reference_URI;
        }

        // Inherited From sysfile:Instance
        // Type is an MO-Defined-Type
        leaf switchId {
            config "false";
            description "TBD";

            // Type is an MO-Defined-Type
            type network_SwitchId;
        }

        // From Interface naming:Described
        // Inherited From sysfile:Instance
        // Type is an MO-Defined-Type
        leaf descr {
            description "Description";

            // Type is an MO-Defined-Type
            type naming_Descr;
        }

        container mutation-items {

            // Added containment as a singleton: Prefix=mutation
            // Acquired From Package sysfile
            uses sysfile_Mutation-group;
        }
    }

    grouping sysfile_Mutation-group {
        leaf action {
            type enumeration {
                enum none {
                    value 0;
                }
                enum remove {
                    value 1;
                }
            }
            default "remove";
        }

        // From Interface naming:Described
        // Type is an MO-Defined-Type
        leaf descr {
            description "Description";

            // Type is an MO-Defined-Type
            type naming_Descr;
        }
    }

    grouping sysdebug_TechSupFileRepository-group {

        // A tech-support file.
        container techsupport-items {
            list TechSupport-list {
                config "false";
                key "creationTS";

                // Added containment: Prefix=techsupport
                // Acquired From Package sysdebug
                uses sysdebug_TechSupport-group;
            }
        }
    }

    grouping sysdebug_TechSupport-group {
        leaf creationTS {
            config "false";
            type uint64;
        }

        // Tech-support files' administration state. It is
        // used to trigger different operations on this
        // file like create, delete etc.
        // Type is an MO-Defined-Type
        leaf adminState {
            description "TBD";

            // Type is an MO-Defined-Type
            type sysdebug_TechSupportAdminState;
        }

        // Tech-support files progress through a state sequence.
        // operState is used more in scenarios, when tech-support
        // files are placed on subordinate switch.
        // Since GUI can't pull the files from the switch other
        // than primary, we need a mechanism to convey the message
        // to DME for copying the contents of a tech-support file
        // before this file can be downloaded by the users.
        // operState is used exactly for this need. This property
        // highlights the state of a tech-support filein terms of
        // readiness for download.
        // Type is an MO-Defined-Type
        leaf operState {
            config "false";
            description "TBD";

            // Type is an MO-Defined-Type
            type sysdebug_TechSupportOperState;
        }

        // From Interface naming:Named
        // Inherited From naming:NamedObject
        // Modified by Override: sysfile:Instance->name
        // Type is an MO-Defined-Type
        leaf name {
            description "Name";

            // Type is an MO-Defined-Type
            type naming_Name {
                length "1..128";
            }
        }
        leaf ts {
            config "false";
            type uint64;
        }
        leaf size {
            config "false";
            type uint32;
        }

        // Inherited From sysfile:Instance
        // Type is an MO-Defined-Type
        leaf uri {
            config "false";
            description "TBD";

            // Type is an MO-Defined-Type
            type reference_URI;
        }

        // Inherited From sysfile:Instance
        // Type is an MO-Defined-Type
        leaf switchId {
            config "false";
            description "TBD";

            // Type is an MO-Defined-Type
            type network_SwitchId;
        }

        // From Interface naming:Described
        // Inherited From sysfile:Instance
        // Type is an MO-Defined-Type
        leaf descr {
            description "Description";

            // Type is an MO-Defined-Type
            type naming_Descr;
        }

        // Mo holding the command options for
        // a tech support file creation.
        container techsupportcmdopt-items {

            // Added containment as a singleton: Prefix=techsupportcmdopt
            // Acquired From Package sysdebug
            uses sysdebug_TechSupportCmdOpt-group;
        }
    }

    grouping sysdebug_TechSupportCmdOpt-group {

        // Type is an MO-Defined-Type
        leaf majorOptType {
            description "TBD";

            // Type is an MO-Defined-Type
            type sysdebug_TSCmdOptMajorType;
        }

        // Type is an MO-Defined-Type
        leaf chassisId {
            description "TBD";

            // Type is an MO-Defined-Type
            type sysdebug_TSCmdOptChassisId;
        }

        // Type is an MO-Defined-Type
        leaf fabExtId {
            description "TBD";

            // Type is an MO-Defined-Type
            type sysdebug_TSCmdOptFexId;
        }

        // Type is an MO-Defined-Type
        leaf rackServerId {
            description "TBD";

            // Type is an MO-Defined-Type
            type sysdebug_TSCmdOptServerId;
        }

        // Type is an MO-Defined-Type
        leaf chassisCimcId {
            description "TBD";

            // Type is an MO-Defined-Type
            type sysdebug_TSCmdOptChassisCIMCId;
        }

        // Type is an MO-Defined-Type
        leaf cimcAdapterId {
            description "TBD";

            // Type is an MO-Defined-Type
            type sysdebug_TSCmdOptChassisCIMCAdapterId;
        }

        // Type is an MO-Defined-Type
        leaf chassisIomId {
            description "TBD";

            // Type is an MO-Defined-Type
            type sysdebug_TSCmdOptChassisIOMId;
        }

        // Type is an MO-Defined-Type
        leaf rackServerAdapterId {
            description "TBD";

            // Type is an MO-Defined-Type
            type sysdebug_TSCmdOptServerAdapterId;
        }
    }

    grouping cnw_AggrIf-group {

        // Operational port state
        // Type is an MO-Defined-Type
        leaf operSt {
            config "false";
            description "Operational Status";

            // Type is an MO-Defined-Type
            type l1_OperSt;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Type is an MO-Defined-Type
        leaf adminSt {
            description "Administrative State";

            // Type is an MO-Defined-Type
            type l1_AdminSt;
        }

        // Administrative port speed    @@@ This comes from the host interface
        // @@@ configuration policy
        // Inherited From l1:If
        // Type is an MO-Defined-Type
        leaf speed {
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Administrative port mode    @@@ Internally set by PE
        // Inherited From l1:EthIf
        // Type is an MO-Defined-Type
        leaf mode {
            description "Mode";

            // Type is an MO-Defined-Type
            type l1_Mode;
        }

        // Administrative port layer    @@@ Internally set by PE
        // Inherited From l1:EthIf
        // Type is an MO-Defined-Type
        leaf layer {
            description "Layer";

            // Type is an MO-Defined-Type
            type l1_Layer;
        }

        // Administrative mdix mode    @@@ Theres no benefit in exposing this property
        // @@@ in IFC. Ask Marketing.
        // Inherited From l1:EthIf
        // Type is an MO-Defined-Type
        leaf mdix {
            description "MDIX";

            // Type is an MO-Defined-Type
            type l1_Mdix;
        }

        // Administrative port delay    @@@ is this exposed in IFC?
        // Inherited From l1:EthIf
        // Type is an MO-Defined-Type
        leaf delay {
            description "Delay";

            // Type is an MO-Defined-Type
            type l1_Delay;
        }

        // Administrative port link debounce interval    @@@ This comes from the interface configuration policy
        // Inherited From l1:EthIf
        // Type is an MO-Defined-Type
        leaf linkDebounce {
            description "Link Debounce Interval";

            // Type is an MO-Defined-Type
            type l1_LinkDebounce;
        }

        // Administrative port dot1q ether-type    @@@ This property is not supported in switch ??
        // Inherited From l1:EthIf
        // Type is an MO-Defined-Type
        leaf dot1qEtherType {
            description "Dot1q Ether Type";

            // Type is an MO-Defined-Type
            type l1_Dot1qEtherType;
        }

        // Administrative port bandwidth    @@@ Comes from QOS Policy
        // Inherited From l1:EthIf
        // Type is an MO-Defined-Type
        leaf bw {
            description "Bandwidth";

            // Type is an MO-Defined-Type
            type l1_Bw;
        }

        // Administrative port medium type    @@@ The fabric & Host connections are P2p.    @@@ No need to expose this property in IFC
        // Inherited From l1:EthIf
        // Type is an MO-Defined-Type
        leaf medium {
            description "Medium";

            // Type is an MO-Defined-Type
            type l1_Medium;
        }

        // Administrative port inherit bandwidth    @@@ It is used for specifying the bandwidth inherited
        // @@@ by the subinterfaces from the parent interface    @@@ It is not exposed in IFC. All the subinterfaces
        // @@@ inherit full parent interface's bandwidth
        // Inherited From l1:EthIf
        // Type is an MO-Defined-Type
        leaf inhBw {
            description "Inherit Bandwidth";

            // Type is an MO-Defined-Type
            type l1_InheritBw;
        }

        // Administrative port span mode    @@@ This comes from the span policy in IFC
        // Inherited From l1:EthIf
        // Type is an MO-Defined-Type
        leaf spanMode {
            description "Span Mode";

            // Type is an MO-Defined-Type
            type l1_SpanMode;
        }

        // Administrative link logging enable    @@@ This come from interface configuration policy
        // Inherited From l1:EthIf
        // Type is an MO-Defined-Type
        leaf linkLog {
            description "Link Logging";

            // Type is an MO-Defined-Type
            type l1_LinkLog;
        }

        // Administrative trunk logging enable    @@@ This come from interface configuration policy
        // Inherited From l1:EthIf
        // Type is an MO-Defined-Type
        leaf trunkLog {
            description "Trunk Logging";

            // Type is an MO-Defined-Type
            type l1_TrunkLog;
        }
        leaf routerMac {
            type address_Mac;
            default "0";
        }

        // Type of the port: Fabric vs Leaf    @@@ This property is not exposed in IFC
        // Inherited From l1:EthIf
        // Type is an MO-Defined-Type
        leaf portT {
            description "Port Type";

            // Type is an MO-Defined-Type
            type eqpt_PortT;
        }

        // Usage of the port: Fabric, Infra, Epg, Controller, Discovery   @@@ This property is not exposed in IFC
        // Inherited From l1:EthIf
        // Type is an MO-Defined-Type
        leaf usage {
            description "Port Usage";

            // Type is an MO-Defined-Type
            type l1_PortUsage;
        }

        // config trunk vlans
        // Inherited From l1:EthIf
        // Type is an MO-Defined-Type
        leaf trunkVlans {
            description "Configed Trunk Vlans";

            // Type is an MO-Defined-Type
            type l1_l1IfTrunkVlans;
        }

        // config access vlan
        // Inherited From l1:EthIf
        // Type is an MO-Defined-Type
        leaf accessVlan {
            description "Configured Access Vlan";

            // Type is an MO-Defined-Type
            type l1_l1IfAccessVlan;
        }

        // Controller Id
        // Inherited From l1:EthIf
        // Type is an MO-Defined-Type
        leaf controllerId {
            description "Controller ID";

            // Type is an MO-Defined-Type
            type aggregate_ControllerIdBitmap;
        }

        // config access vlan
        // Inherited From l1:EthIf
        // Type is an MO-Defined-Type
        leaf nativeVlan {
            description "Configured Native Vlan";

            // Type is an MO-Defined-Type
            type l1_l1IfNativeVlan;
        }

        // port user config flags
        // Inherited From l1:EthIf
        // Type is an MO-Defined-Type
        leaf userCfgdFlags {
            description "Port User Config Flags";

            // Type is an MO-Defined-Type
            type l1_userCfgdFlags;
        }

        // Dom info
        container dom-items {
            list DomDef-list {
                config "false";
                key "domPKey";

                // Added containment: Prefix=dom
                // Acquired From Package fv
                uses fv_DomDef-group;
            }
        }

        // Rel-def target from extConf
        // Inherited From l1:PhysIf
        // Inherited From pc:AggrIf
        // Inherited From pc:ShadowAggrIf
        // Inherited From cnw:AggrIf
        container rtextConf-items {

            // Added containment as a singleton: Prefix=rtextConf
            // Acquired From Package l2
            uses l2_RtExtConf_target-group;
        }

        // Rel-def target from brConf
        // Inherited From l1:PhysIf
        // Inherited From pc:AggrIf
        // Inherited From pc:ShadowAggrIf
        // Inherited From cnw:AggrIf
        container rtbrConf-items {

            // Added containment as a singleton: Prefix=rtbrConf
            // Acquired From Package l2
            uses l2_RtBrConf_target-group;
        }

        // Rel-def target from NodePortAtt
        // Inherited From l1:PhysIf
        // Inherited From pc:AggrIf
        // Inherited From pc:ShadowAggrIf
        // Inherited From cnw:AggrIf
        container rtfvNodePortAtt-items {

            // Abstract containment of rtfvNodePortAtt derived from l1:EthIf
            list RtFvNodePortAtt-list {
                config "false";
                key "tDn";

                // Added containment: Prefix=rtfvNodePortAtt
                // Acquired From Package fv
                uses fv_RtFvNodePortAtt_target-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        container rtvrfMbr-items {

            // Added containment as a singleton: Prefix=rtvrfMbr
            // Acquired From Package l3
            uses l3_RtVrfMbr_target-group;
        }

        // Rel-def target from physRtdConf
        // Inherited From l1:PhysIf
        // Inherited From pc:AggrIf
        // Inherited From pc:ShadowAggrIf
        // Inherited From cnw:AggrIf
        container rtphysRtdConf-items {

            // Added containment as a singleton: Prefix=rtphysRtdConf
            // Acquired From Package l3
            uses l3_RtPhysRtdConf_target-group;
        }

        // Rel-def target from encPhysRtdConf
        // Inherited From l1:PhysIf
        // Inherited From pc:AggrIf
        // Inherited From pc:ShadowAggrIf
        // Inherited From cnw:AggrIf
        container rtl3EncPhysRtdConf-items {

            // Abstract containment of rtl3EncPhysRtdConf derived from l1:EthIf
            list RtL3EncPhysRtdConf-list {
                key "tDn";

                // Added containment: Prefix=rtl3EncPhysRtdConf
                // Acquired From Package l3
                uses l3_RtL3EncPhysRtdConf_target-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def target from LsNodeToIf
        // Inherited From l1:PhysIf
        // Inherited From pc:AggrIf
        // Inherited From pc:ShadowAggrIf
        // Inherited From cnw:AggrIf
        container rtLsNodeToIf-items {

            // Added containment as a singleton: Prefix=rtLsNodeToIf
            // Acquired From Package leqpt
            uses leqpt_RtLsNodeToIf_target-group;
        }

        // Rel-def from mbrIfs
        container rsmbrIfs-items {

            // Abstract containment of rsmbrIfs derived from cnw:AggrIf
            list RsMbrIfs-list {
                config "false";
                key "tDn";

                // Added containment: Prefix=rsmbrIfs
                // Acquired From Package cnw
                uses cnw_RsMbrIfs_source-group;
            }
        }

        // Rel-def from activeIf
        container rsactiveIf-items {

            // Added containment as a singleton: Prefix=rsactiveIf
            // Acquired From Package cnw
            uses cnw_RsActiveIf_source-group;
        }
    }

    grouping cnw_PhysIf-group {

        // Operational port state
        // Type is an MO-Defined-Type
        leaf operSt {
            config "false";
            description "Operational Status";

            // Type is an MO-Defined-Type
            type l1_OperSt;
        }

        // Wiring Issues
        // Type is an MO-Defined-Type
        leaf wiringIssues {
            config "false";
            description "Wiring Issues";

            // Type is an MO-Defined-Type
            type lldp_WiringIssues;
        }

        // Inherited From nw:Conn
        // Modified by Override: nw:Ep->name
        // Type is an MO-Defined-Type
        leaf name {
            description "Name";

            // Type is an MO-Defined-Type
            type naming_Name {
                length "1..64";
            }
        }

        // Interface ID of this endpoint
        // Inherited From nw:If
        // Type is an MO-Defined-Type
        leaf id {
            description "Interface ID";

            // Type is an MO-Defined-Type
            type nw_IfId;
        }

        // From Interface naming:Described
        // Inherited From nw:If
        // Modified by Override: l1:If->descr
        // Type is an MO-Defined-Type
        leaf descr {
            description "descr";

            // Type is an MO-Defined-Type
            type naming_Descr {
                length "0..254";
            }
        }

        // Switching state
        // Inherited From l1:If
        // Type is an MO-Defined-Type
        leaf switchingSt {
            description "Switching State";

            // Type is an MO-Defined-Type
            type l1_SwitchingSt;
        }

        // Administrative port state    @@@ Comes from port out-of-service policy
        // Inherited From l1:If
        // Modified by Override: cnw:PhysIf->adminSt
        // Type is an MO-Defined-Type
        leaf adminSt {
            description "Administrative State";

            // Type is an MO-Defined-Type
            type l1_AdminSt;
        }

        // Administrative port speed    @@@ This comes from the host interface
        // @@@ configuration policy
        // Inherited From l1:If
        // Type is an MO-Defined-Type
        leaf speed {
            description "Speed";

            // Type is an MO-Defined-Type
            type l1_Speed;
        }

        // Administrative port duplex    @@@ This comes from the host interface
        // @@@ configuration policy
        // Inherited From l1:If
        // Type is an MO-Defined-Type
        leaf duplex {
            description "Duplex";

            // Type is an MO-Defined-Type
            type l1_Duplex;
        }

        // Administrative port auto-negotiation    @@@ It comes from the host interface configuration
        // @@@ policy. It is used for automatically negotiating
        // @@@ the speed
        // Inherited From l1:If
        // Type is an MO-Defined-Type
        leaf autoNeg {
            description "Auto Negotiation";

            // Type is an MO-Defined-Type
            type l1_AutoNeg;
        }

        // Administrative port mtu    @@@ This comes from QOS Policy
        // Inherited From l1:If
        // Type is an MO-Defined-Type
        leaf mtu {
            description "TBD";

            // Type is an MO-Defined-Type
            type l1_Mtu;
        }

        // Administrative port snmp trap state    @@@ This is a port level config. but it could go in
        // @@@ SNMP policy in IFC
        // Inherited From l1:If
        // Type is an MO-Defined-Type
        leaf snmpTrapSt {
            description "Snmp Trap State";

            // Type is an MO-Defined-Type
            type l1_SnmpTrapSt;
        }

        // Administrative port mode    @@@ Internally set by PE
        // Inherited From l1:EthIf
        // Type is an MO-Defined-Type
        leaf mode {
            description "Mode";

            // Type is an MO-Defined-Type
            type l1_Mode;
        }

        // Administrative port layer    @@@ Internally set by PE
        // Inherited From l1:EthIf
        // Type is an MO-Defined-Type
        leaf layer {
            description "Layer";

            // Type is an MO-Defined-Type
            type l1_Layer;
        }

        // Administrative mdix mode    @@@ Theres no benefit in exposing this property
        // @@@ in IFC. Ask Marketing.
        // Inherited From l1:EthIf
        // Type is an MO-Defined-Type
        leaf mdix {
            description "MDIX";

            // Type is an MO-Defined-Type
            type l1_Mdix;
        }

        // Administrative port delay    @@@ is this exposed in IFC?
        // Inherited From l1:EthIf
        // Type is an MO-Defined-Type
        leaf delay {
            description "Delay";

            // Type is an MO-Defined-Type
            type l1_Delay;
        }

        // Administrative port link debounce interval    @@@ This comes from the interface configuration policy
        // Inherited From l1:EthIf
        // Type is an MO-Defined-Type
        leaf linkDebounce {
            description "Link Debounce Interval";

            // Type is an MO-Defined-Type
            type l1_LinkDebounce;
        }

        // Administrative port dot1q ether-type    @@@ This property is not supported in switch ??
        // Inherited From l1:EthIf
        // Type is an MO-Defined-Type
        leaf dot1qEtherType {
            description "Dot1q Ether Type";

            // Type is an MO-Defined-Type
            type l1_Dot1qEtherType;
        }

        // Administrative port bandwidth    @@@ Comes from QOS Policy
        // Inherited From l1:EthIf
        // Type is an MO-Defined-Type
        leaf bw {
            description "Bandwidth";

            // Type is an MO-Defined-Type
            type l1_Bw;
        }

        // Administrative port medium type    @@@ The fabric & Host connections are P2p.    @@@ No need to expose this property in IFC
        // Inherited From l1:EthIf
        // Type is an MO-Defined-Type
        leaf medium {
            description "Medium";

            // Type is an MO-Defined-Type
            type l1_Medium;
        }

        // Administrative port inherit bandwidth    @@@ It is used for specifying the bandwidth inherited
        // @@@ by the subinterfaces from the parent interface    @@@ It is not exposed in IFC. All the subinterfaces
        // @@@ inherit full parent interface's bandwidth
        // Inherited From l1:EthIf
        // Type is an MO-Defined-Type
        leaf inhBw {
            description "Inherit Bandwidth";

            // Type is an MO-Defined-Type
            type l1_InheritBw;
        }

        // Administrative port span mode    @@@ This comes from the span policy in IFC
        // Inherited From l1:EthIf
        // Type is an MO-Defined-Type
        leaf spanMode {
            description "Span Mode";

            // Type is an MO-Defined-Type
            type l1_SpanMode;
        }

        // Administrative link logging enable    @@@ This come from interface configuration policy
        // Inherited From l1:EthIf
        // Type is an MO-Defined-Type
        leaf linkLog {
            description "Link Logging";

            // Type is an MO-Defined-Type
            type l1_LinkLog;
        }

        // Administrative trunk logging enable    @@@ This come from interface configuration policy
        // Inherited From l1:EthIf
        // Type is an MO-Defined-Type
        leaf trunkLog {
            description "Trunk Logging";

            // Type is an MO-Defined-Type
            type l1_TrunkLog;
        }
        leaf routerMac {
            type address_Mac;
            default "0";
        }

        // Type of the port: Fabric vs Leaf    @@@ This property is not exposed in IFC
        // Inherited From l1:EthIf
        // Type is an MO-Defined-Type
        leaf portT {
            description "Port Type";

            // Type is an MO-Defined-Type
            type eqpt_PortT;
        }

        // Usage of the port: Fabric, Infra, Epg, Controller, Discovery   @@@ This property is not exposed in IFC
        // Inherited From l1:EthIf
        // Type is an MO-Defined-Type
        leaf usage {
            description "Port Usage";

            // Type is an MO-Defined-Type
            type l1_PortUsage;
        }

        // config trunk vlans
        // Inherited From l1:EthIf
        // Type is an MO-Defined-Type
        leaf trunkVlans {
            description "Configed Trunk Vlans";

            // Type is an MO-Defined-Type
            type l1_l1IfTrunkVlans;
        }

        // config access vlan
        // Inherited From l1:EthIf
        // Type is an MO-Defined-Type
        leaf accessVlan {
            description "Configured Access Vlan";

            // Type is an MO-Defined-Type
            type l1_l1IfAccessVlan;
        }

        // Controller Id
        // Inherited From l1:EthIf
        // Type is an MO-Defined-Type
        leaf controllerId {
            description "Controller ID";

            // Type is an MO-Defined-Type
            type aggregate_ControllerIdBitmap;
        }

        // config access vlan
        // Inherited From l1:EthIf
        // Type is an MO-Defined-Type
        leaf nativeVlan {
            description "Configured Native Vlan";

            // Type is an MO-Defined-Type
            type l1_l1IfNativeVlan;
        }

        // port user config flags
        // Inherited From l1:EthIf
        // Type is an MO-Defined-Type
        leaf userCfgdFlags {
            description "Port User Config Flags";

            // Type is an MO-Defined-Type
            type l1_userCfgdFlags;
        }

        // Dom info
        container dom-items {
            list DomDef-list {
                config "false";
                key "domPKey";

                // Added containment: Prefix=dom
                // Acquired From Package fv
                uses fv_DomDef-group;
            }
        }

        // Rel-def target from extConf
        // Inherited From l1:PhysIf
        // Inherited From pc:AggrIf
        // Inherited From pc:ShadowAggrIf
        // Inherited From cnw:AggrIf
        // Inherited From cnw:PhysIf
        container rtextConf-items {

            // Added containment as a singleton: Prefix=rtextConf
            // Acquired From Package l2
            uses l2_RtExtConf_target-group;
        }

        // Rel-def target from brConf
        // Inherited From l1:PhysIf
        // Inherited From pc:AggrIf
        // Inherited From pc:ShadowAggrIf
        // Inherited From cnw:AggrIf
        // Inherited From cnw:PhysIf
        container rtbrConf-items {

            // Added containment as a singleton: Prefix=rtbrConf
            // Acquired From Package l2
            uses l2_RtBrConf_target-group;
        }

        // Rel-def target from NodePortAtt
        // Inherited From l1:PhysIf
        // Inherited From pc:AggrIf
        // Inherited From pc:ShadowAggrIf
        // Inherited From cnw:AggrIf
        // Inherited From cnw:PhysIf
        container rtfvNodePortAtt-items {

            // Abstract containment of rtfvNodePortAtt derived from l1:EthIf
            list RtFvNodePortAtt-list {
                config "false";
                key "tDn";

                // Added containment: Prefix=rtfvNodePortAtt
                // Acquired From Package fv
                uses fv_RtFvNodePortAtt_target-group;
            }
        }

        // Rel-def target from vrfMbr
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        container rtvrfMbr-items {

            // Added containment as a singleton: Prefix=rtvrfMbr
            // Acquired From Package l3
            uses l3_RtVrfMbr_target-group;
        }

        // Rel-def target from physRtdConf
        // Inherited From l1:PhysIf
        // Inherited From pc:AggrIf
        // Inherited From pc:ShadowAggrIf
        // Inherited From cnw:AggrIf
        // Inherited From cnw:PhysIf
        container rtphysRtdConf-items {

            // Added containment as a singleton: Prefix=rtphysRtdConf
            // Acquired From Package l3
            uses l3_RtPhysRtdConf_target-group;
        }

        // Rel-def target from encPhysRtdConf
        // Inherited From l1:PhysIf
        // Inherited From pc:AggrIf
        // Inherited From pc:ShadowAggrIf
        // Inherited From cnw:AggrIf
        // Inherited From cnw:PhysIf
        container rtl3EncPhysRtdConf-items {

            // Abstract containment of rtl3EncPhysRtdConf derived from l1:EthIf
            list RtL3EncPhysRtdConf-list {
                key "tDn";

                // Added containment: Prefix=rtl3EncPhysRtdConf
                // Acquired From Package l3
                uses l3_RtL3EncPhysRtdConf_target-group;
            }
        }

        // Rel-def target from pathToIf
        // Inherited From dhcp:DAIIf
        // Inherited From dhcp:ClientIf
        // Inherited From dhcp:RelayIf
        // Inherited From dhcp:PseudoIf
        // Inherited From dhcp:ServerIf
        // Inherited From dhcp:IpsgIf
        // Inherited From dhcp:SnoopIf
        // Inherited From igmp:ExtIf
        // Inherited From igmp:If
        // Inherited From ipv4:If
        // Inherited From ipv6:If
        // Inherited From isis:If
        // Inherited From ospf:If
        // Inherited From ospf:InternalIf
        // Inherited From ospfv3:InternalIf
        // Inherited From ospfv3:If
        // Inherited From hmm:FwdIf
        // Inherited From arp:If
        // Inherited From bfd:If
        // Inherited From eigrp:If
        // Inherited From hsrp:If
        // Inherited From icmpv4:If
        // Inherited From icmpv6:If
        // Inherited From mpls:If
        // Inherited From nd:If
        // Inherited From pim:If
        // Inherited From vrrp:Interface
        // Inherited From vrrpv3:Interface
        // Inherited From cdp:If
        // Inherited From lldp:If
        // Inherited From mcp:If
        // Inherited From vpc:OrphanPort
        // Inherited From vpc:PeerLink
        // Inherited From lacp:If
        // Inherited From stp:If
        // Inherited From igmpsnoop:StRtrIf
        // Inherited From mldsnoop:StRtrIf
        // Inherited From l2:InbandIf
        // Inherited From l2:ExtIf
        // Inherited From l2:BrIf
        // Inherited From mgmt:RtdMgmtIf
        // Inherited From l3:RtdIf
        // Inherited From l3:LbRtdIf
        // Inherited From l3:EncRtdIf
        // Inherited From svi:If
        // Inherited From tunnelif:If
        // Inherited From regress:If
        // Inherited From tunnel:If
        // Inherited From mgmt:MgmtIf
        // Inherited From l1:PhysIf
        // Inherited From pc:AggrIf
        // Inherited From pc:ShadowAggrIf
        // Inherited From cnw:AggrIf
        // Inherited From cnw:PhysIf
        container rtnwPathToIf-items {

            // Abstract containment of rtnwPathToIf derived from nw:If
            list RtNwPathToIf-list {
                key "tDn";

                // Added containment: Prefix=rtnwPathToIf
                // Acquired From Package nw
                uses nw_RtNwPathToIf_target-group;
            }
        }

        // Rel-def target from LsNodeToIf
        // Inherited From l1:PhysIf
        // Inherited From pc:AggrIf
        // Inherited From pc:ShadowAggrIf
        // Inherited From cnw:AggrIf
        // Inherited From cnw:PhysIf
        container rtLsNodeToIf-items {

            // Added containment as a singleton: Prefix=rtLsNodeToIf
            // Acquired From Package leqpt
            uses leqpt_RtLsNodeToIf_target-group;
        }

        // Rel-def target from mbrIfs
        // Inherited From cnw:PhysIf
        container rtmbrIfs-items {

            // Added containment as a singleton: Prefix=rtmbrIfs
            // Acquired From Package cnw
            uses cnw_RtMbrIfs_target-group;
        }

        // Rel-def target from activeIf
        // Inherited From cnw:PhysIf
        container rtactiveIf-items {

            // Added containment as a singleton: Prefix=rtactiveIf
            // Acquired From Package cnw
            uses cnw_RtActiveIf_target-group;
        }
    }

    grouping action_LCont-group {
        container tracertnve-items {
            list TraceRtNve-list {
                key "session";

                // Added containment: Prefix=tracertnve
                // Acquired From Package ngoam
                uses ngoam_TraceRtNve-group;
            }
        }
        container pathtracenve-items {
            list PathTraceNve-list {
                key "session";

                // Added containment: Prefix=pathtracenve
                // Acquired From Package ngoam
                uses ngoam_PathTraceNve-group;
            }
        }

        // Diag rule for on demand tests
        container eqptdiagrule-items {
            list OnDRule-list {
                config "false";
                key "type";

                // Added containment: Prefix=eqptdiagrule
                // Acquired From Package eqptdiag
                uses eqptdiag_OnDRule-group;
            }
        }
        container lsubj-items {
            list LSubj-list {
                config "false";
                key "oDn";

                // Added containment: Prefix=lsubj
                // Acquired From Package action
                uses action_LSubj-group;
            }
        }
    }

    grouping ngoam_TraceRtNve-group {

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: ngoam:ATraceRtNve->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }
        leaf session {
            type string;
        }

        // Prof. id
        // Inherited From ngoam:ATraceRtNve
        // Type is an MO-Defined-Type
        leaf profileId {
            description "Ngoam profile ID";

            // Type is an MO-Defined-Type
            type ngoam_ProfId;
        }
        leaf dstIp {
            type address_Ipv4;
        }
        leaf dstIpv6 {
            type address_Ipv6;
        }
        leaf dstMAC {
            type address_Mac;
        }
        leaf srcIp {
            type address_Ipv4;
        }
        leaf srcIpv6 {
            type address_Ipv6;
        }

        // dot1q
        // Inherited From ngoam:ATraceRtNve
        // Type is an MO-Defined-Type
        leaf dot1q {
            description "dot1q";

            // Type is an MO-Defined-Type
            type ngoam_Dot1q;
        }

        // source port
        // Inherited From ngoam:ATraceRtNve
        // Type is an MO-Defined-Type
        leaf srcPort {
            description "Source Port";

            // Type is an MO-Defined-Type
            type ngoam_SrcPort;
        }

        // source port
        // Inherited From ngoam:ATraceRtNve
        // Type is an MO-Defined-Type
        leaf dstPort {
            description "Destination Port";

            // Type is an MO-Defined-Type
            type ngoam_DestPort;
        }

        // Hop Count or TTL
        // Inherited From ngoam:ATraceRtNve
        // Type is an MO-Defined-Type
        leaf maxTtl {
            description "Time to live value";

            // Type is an MO-Defined-Type
            type ngoam_TTL;
        }

        // The vrf in which it is running
        // Inherited From ngoam:ATraceRtNve
        // Type is an MO-Defined-Type
        leaf vrf {
            description "VRF";

            // Type is an MO-Defined-Type
            type ngoam_Vrf;
        }

        // The VxLAN vni
        // Inherited From ngoam:ATraceRtNve
        // Type is an MO-Defined-Type
        leaf vni {
            description "VNI";

            // Type is an MO-Defined-Type
            type ngoam_Vnid;
        }

        // timeout
        // Inherited From ngoam:ATraceRtNve
        // Type is an MO-Defined-Type
        leaf timeout {
            description "Timeout";

            // Type is an MO-Defined-Type
            type ngoam_Timeout;
        }

        // Egress Interface id
        // Inherited From ngoam:ATraceRtNve
        // Type is an MO-Defined-Type
        leaf egressIf {
            description "Interface ID";

            // Type is an MO-Defined-Type
            type nw_IfId;
        }

        // MAC Interface
        // Inherited From ngoam:ATraceRtNve
        // Type is an MO-Defined-Type
        leaf macsrcif {
            description "payload source interface";

            // Type is an MO-Defined-Type
            type nw_IfId;
        }
        leaf sessionId {
            type uint32;
        }

        // Runtime status of the task
        // Inherited From ngoam:ATraceRtNve
        // Type is an MO-Defined-Type
        leaf operSt {
            config "false";
            description "Completion";

            // Type is an MO-Defined-Type
            type action_OperSt;
        }

        // dot1q
        // From Interface ngoam:Payload
        // Inherited From ngoam:ATraceRtNve
        // Type is an MO-Defined-Type
        leaf payload_dot1q {
            description "dot1q";

            // Type is an MO-Defined-Type
            type ngoam_Dot1q;
        }
        leaf payload_srcip {
            type address_Ipv4;
        }
        leaf payload_srcipv6 {
            type address_Ipv6;
        }
        leaf payload_srcmac {
            type address_Mac;
        }
        leaf payload_dstip {
            type address_Ipv4;
        }
        leaf payload_dstipv6 {
            type address_Ipv6;
        }
        leaf payload_dstmac {
            type address_Mac;
        }
        leaf payload_srcport {
            type uint16;
        }
        leaf payload_dstport {
            type uint16;
        }

        // protocol
        // From Interface ngoam:Payload
        // Inherited From ngoam:ATraceRtNve
        // Type is an MO-Defined-Type
        leaf payload_protocol {
            description "payload protocol";

            // Type is an MO-Defined-Type
            type ngoam_Protocol;
        }

        // Source Interface
        // From Interface ngoam:Payload
        // Inherited From ngoam:ATraceRtNve
        // Type is an MO-Defined-Type
        leaf payload_srcif {
            description "payload source interface";

            // Type is an MO-Defined-Type
            type nw_IfId;
        }

        // Result for fabric traceroute
        container trnverslt-items {
            list TraceRtNveRslt-list {
                config "false";
                key "sessionId";

                // Added containment: Prefix=trnverslt
                // Acquired From Package ngoam
                uses ngoam_TraceRtNveRslt-group;
            }
        }
    }

    grouping ngoam_TraceRtNveRslt-group {
        leaf dstIp {
            config "false";
            type address_Ipv4;
        }
        leaf dstIpv6 {
            config "false";
            type address_Ipv6;
        }

        // Maximum number of hops that the traceroute took to
        // reach the destination
        // Type is an MO-Defined-Type
        leaf maxHops {
            config "false";
            description "Max Hops";

            // Type is an MO-Defined-Type
            type ngoam_Hops;
        }

        // Prof. Name
        // Type is an MO-Defined-Type
        leaf sessionId {
            config "false";
            description "Name";

            // Type is an MO-Defined-Type
            type ngoam_SessionId;
        }
        leaf errorCode {
            config "false";
            type string;
        }
        leaf failReason {
            config "false";
            type string;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Each path represents a sequence of nodes towards the
        // destination
        container pathtr-items {
            list PathTr-list {
                config "false";
                key "id";

                // Added containment: Prefix=pathtr
                // Acquired From Package ngoam
                uses ngoam_PathTr-group;
            }
        }
    }

    grouping ngoam_PathTr-group {

        // Identifier of the path
        // Type is an MO-Defined-Type
        leaf id {
            config "false";
            description "ID";

            // Type is an MO-Defined-Type
            type ngoam_PathId;
        }

        // Node represents a given node in the traceroute path. Each
        // node is identified by the ip address and the order represents
        // its placement in the path
        container nodetr-items {
            list NodeTr-list {
                config "false";
                key "order";

                // Added containment: Prefix=nodetr
                // Acquired From Package ngoam
                uses ngoam_NodeTr-group;
            }
        }
    }

    grouping ngoam_NodeTr-group {

        // Node id
        // Type is an MO-Defined-Type
        leaf order {
            config "false";
            description "Order";

            // Type is an MO-Defined-Type
            type ngoam_Order;
        }
        leaf addr {
            config "false";
            type address_Ipv4;
        }
        leaf v6addr {
            config "false";
            type address_Ipv6;
        }
        leaf elapsedTime {
            config "false";
            type uint64;
        }
    }

    grouping ngoam_PathTraceNve-group {
        leaf reqStats {
            type boolean;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: ngoam:ATraceRtNve->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }
        leaf session {
            type string;
        }

        // Prof. id
        // Inherited From ngoam:ATraceRtNve
        // Type is an MO-Defined-Type
        leaf profileId {
            description "Ngoam profile ID";

            // Type is an MO-Defined-Type
            type ngoam_ProfId;
        }
        leaf dstIp {
            type address_Ipv4;
        }
        leaf dstIpv6 {
            type address_Ipv6;
        }
        leaf dstMAC {
            type address_Mac;
        }
        leaf srcIp {
            type address_Ipv4;
        }
        leaf srcIpv6 {
            type address_Ipv6;
        }

        // dot1q
        // Inherited From ngoam:ATraceRtNve
        // Type is an MO-Defined-Type
        leaf dot1q {
            description "dot1q";

            // Type is an MO-Defined-Type
            type ngoam_Dot1q;
        }

        // source port
        // Inherited From ngoam:ATraceRtNve
        // Type is an MO-Defined-Type
        leaf srcPort {
            description "Source Port";

            // Type is an MO-Defined-Type
            type ngoam_SrcPort;
        }

        // source port
        // Inherited From ngoam:ATraceRtNve
        // Type is an MO-Defined-Type
        leaf dstPort {
            description "Destination Port";

            // Type is an MO-Defined-Type
            type ngoam_DestPort;
        }

        // Hop Count or TTL
        // Inherited From ngoam:ATraceRtNve
        // Type is an MO-Defined-Type
        leaf maxTtl {
            description "Time to live value";

            // Type is an MO-Defined-Type
            type ngoam_TTL;
        }

        // The vrf in which it is running
        // Inherited From ngoam:ATraceRtNve
        // Type is an MO-Defined-Type
        leaf vrf {
            description "VRF";

            // Type is an MO-Defined-Type
            type ngoam_Vrf;
        }

        // The VxLAN vni
        // Inherited From ngoam:ATraceRtNve
        // Type is an MO-Defined-Type
        leaf vni {
            description "VNI";

            // Type is an MO-Defined-Type
            type ngoam_Vnid;
        }

        // timeout
        // Inherited From ngoam:ATraceRtNve
        // Type is an MO-Defined-Type
        leaf timeout {
            description "Timeout";

            // Type is an MO-Defined-Type
            type ngoam_Timeout;
        }

        // Egress Interface id
        // Inherited From ngoam:ATraceRtNve
        // Type is an MO-Defined-Type
        leaf egressIf {
            description "Interface ID";

            // Type is an MO-Defined-Type
            type nw_IfId;
        }

        // MAC Interface
        // Inherited From ngoam:ATraceRtNve
        // Type is an MO-Defined-Type
        leaf macsrcif {
            description "payload source interface";

            // Type is an MO-Defined-Type
            type nw_IfId;
        }
        leaf sessionId {
            type uint32;
        }

        // Runtime status of the task
        // Inherited From ngoam:ATraceRtNve
        // Type is an MO-Defined-Type
        leaf operSt {
            config "false";
            description "Completion";

            // Type is an MO-Defined-Type
            type action_OperSt;
        }

        // dot1q
        // From Interface ngoam:Payload
        // Inherited From ngoam:ATraceRtNve
        // Type is an MO-Defined-Type
        leaf payload_dot1q {
            description "dot1q";

            // Type is an MO-Defined-Type
            type ngoam_Dot1q;
        }
        leaf payload_srcip {
            type address_Ipv4;
        }
        leaf payload_srcipv6 {
            type address_Ipv6;
        }
        leaf payload_srcmac {
            type address_Mac;
        }
        leaf payload_dstip {
            type address_Ipv4;
        }
        leaf payload_dstipv6 {
            type address_Ipv6;
        }
        leaf payload_dstmac {
            type address_Mac;
        }
        leaf payload_srcport {
            type uint16;
        }
        leaf payload_dstport {
            type uint16;
        }

        // protocol
        // From Interface ngoam:Payload
        // Inherited From ngoam:ATraceRtNve
        // Type is an MO-Defined-Type
        leaf payload_protocol {
            description "payload protocol";

            // Type is an MO-Defined-Type
            type ngoam_Protocol;
        }

        // Source Interface
        // From Interface ngoam:Payload
        // Inherited From ngoam:ATraceRtNve
        // Type is an MO-Defined-Type
        leaf payload_srcif {
            description "payload source interface";

            // Type is an MO-Defined-Type
            type nw_IfId;
        }

        // Result for Pathtrace
        container ptrnverslt-items {
            list PathTraceNveRslt-list {
                config "false";
                key "sessionId";

                // Added containment: Prefix=ptrnverslt
                // Acquired From Package ngoam
                uses ngoam_PathTraceNveRslt-group;
            }
        }
    }

    grouping ngoam_PathTraceNveRslt-group {
        leaf dstIp {
            config "false";
            type address_Ipv4;
        }
        leaf dstIpv6 {
            config "false";
            type address_Ipv6;
        }

        // Maximum number of hops that the traceroute took to
        // reach the destination
        // Type is an MO-Defined-Type
        leaf maxHops {
            config "false";
            description "Max Hops";

            // Type is an MO-Defined-Type
            type ngoam_Hops;
        }

        // Prof. Name
        // Type is an MO-Defined-Type
        leaf sessionId {
            config "false";
            description "Name";

            // Type is an MO-Defined-Type
            type ngoam_SessionId;
        }
        leaf errorCode {
            config "false";
            type string;
        }
        leaf failReason {
            config "false";
            type string;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Each path represents a sequence of nodes towards the
        // destination
        container pathptr-items {
            list PathPtr-list {
                config "false";
                key "id";

                // Added containment: Prefix=pathptr
                // Acquired From Package ngoam
                uses ngoam_PathPtr-group;
            }
        }
    }

    grouping ngoam_PathPtr-group {

        // Identifier of the path
        // Type is an MO-Defined-Type
        leaf id {
            config "false";
            description "ID";

            // Type is an MO-Defined-Type
            type ngoam_PathId;
        }

        // Node represents a given node in the traceroute path. Each
        // node is identified by the ip address and the order represents
        // its placement in the path
        container nodeptr-items {
            list NodePtr-list {
                config "false";
                key "order";

                // Added containment: Prefix=nodeptr
                // Acquired From Package ngoam
                uses ngoam_NodePtr-group;
            }
        }
    }

    grouping ngoam_NodePtr-group {

        // Node id
        // Type is an MO-Defined-Type
        leaf order {
            config "false";
            description "Order";

            // Type is an MO-Defined-Type
            type ngoam_Order;
        }
        leaf addr {
            config "false";
            type address_Ipv4;
        }
        leaf v6addr {
            config "false";
            type address_Ipv6;
        }
        leaf elapsedTime {
            config "false";
            type uint64;
        }
        leaf ingressIf {
            config "false";
            type string;
        }
        leaf ingressIfState {
            config "false";
            type string;
        }
        leaf rxLen {
            config "false";
            type uint64;
        }
        leaf rxBytes {
            config "false";
            type uint64;
        }
        leaf rxPktRate {
            config "false";
            type uint64;
        }
        leaf rxByteRate {
            config "false";
            type uint64;
        }
        leaf rxLoad {
            config "false";
            type uint64;
        }
        leaf rxUcast {
            config "false";
            type uint64;
        }
        leaf rxMcast {
            config "false";
            type uint64;
        }
        leaf rxBcast {
            config "false";
            type uint64;
        }
        leaf rxDiscards {
            config "false";
            type uint64;
        }
        leaf rxErrors {
            config "false";
            type uint64;
        }
        leaf rxUnknown {
            config "false";
            type uint64;
        }
        leaf rxBandwidth {
            config "false";
            type uint32;
        }
        leaf egressIf {
            config "false";
            type string;
        }
        leaf egressIfState {
            config "false";
            type string;
        }
        leaf txLen {
            config "false";
            type uint64;
        }
        leaf txBytes {
            config "false";
            type uint64;
        }
        leaf txPktRate {
            config "false";
            type uint64;
        }
        leaf txByteRate {
            config "false";
            type uint64;
        }
        leaf txLoad {
            config "false";
            type uint64;
        }
        leaf txUcast {
            config "false";
            type uint64;
        }
        leaf txMcast {
            config "false";
            type uint64;
        }
        leaf txBcast {
            config "false";
            type uint64;
        }
        leaf txDiscards {
            config "false";
            type uint64;
        }
        leaf txErrors {
            config "false";
            type uint64;
        }
        leaf txBandwidth {
            config "false";
            type uint32;
        }
    }

    grouping eqptdiag_OnDRule-group {

        // From Interface naming:Named
        // Inherited From naming:NamedObject
        // Modified by Override: pol:Obj->name
        // Type is an MO-Defined-Type
        leaf name {
            description "Name";

            // Type is an MO-Defined-Type
            type naming_Name {
                length "0..64";
            }
        }

        // Clients can add their own data for entity correlation
        // Inherited From pol:Def
        // Type is an MO-Defined-Type
        leaf ownerKey {
            description "TBD";

            // Type is an MO-Defined-Type
            type naming_Descr;
        }

        // Clients can add their own data, for example, to indicate who created this object
        // Inherited From pol:Def
        // Type is an MO-Defined-Type
        leaf ownerTag {
            description "TBD";

            // Type is an MO-Defined-Type
            type naming_Descr {
                length "0..64";
            }
        }

        // From Interface naming:Described
        // Inherited From pol:Def
        // Type is an MO-Defined-Type
        leaf descr {
            description "Description";

            // Type is an MO-Defined-Type
            type naming_Descr;
        }

        // Trigger of this test
        // Inherited From test:Rule
        // Type is an MO-Defined-Type
        leaf trig {
            config "false";
            description "Trigger";

            // Type is an MO-Defined-Type
            type test_Trig;
        }

        // Test frequency
        // Inherited From test:Rule
        // Type is an MO-Defined-Type
        leaf freq {
            config "false";
            description "Frequency";

            // Type is an MO-Defined-Type
            type test_Freq;
        }

        // Test type
        // Inherited From eqptdiag:ARule
        // Type is an MO-Defined-Type
        leaf type {
            config "false";
            description "TBD";

            // Type is an MO-Defined-Type
            type eqptdiag_Type;
        }

        // On demand diag subject
        container subj-items {
            list OnDSubj-list {
                config "false";
                key "oDn";

                // Added containment: Prefix=subj
                // Acquired From Package eqptdiag
                uses eqptdiag_OnDSubj-group;
            }
        }
    }

    grouping eqptdiag_OnDSubj-group {

        // Admin state, used only with on demand tests
        // Type is an MO-Defined-Type
        leaf adminSt {
            description "Admin State";

            // Type is an MO-Defined-Type
            type action_AdminSt;
        }

        // Object primary key
        // Inherited From test:Subj
        // Type is an MO-Defined-Type
        leaf oPk {
            config "false";
            description "Object Primary Key";

            // Type is an MO-Defined-Type
            type test_PInstId;
        }

        // Object secondary key
        // Inherited From test:Subj
        // Type is an MO-Defined-Type
        leaf oSk {
            config "false";
            description "Object Secondary Key";

            // Type is an MO-Defined-Type
            type test_PInstId;
        }
        leaf oDn {
            config "false";
            type string;
        }

        // Consolidated operational state of the test
        // on this subject
        // Inherited From test:Subj
        // Modified by Override: eqptdiag:OnDSubj->operSt
        // Type is an MO-Defined-Type
        leaf operSt {
            config "false";
            description "Operational State";

            // Type is an MO-Defined-Type
            type test_OperSt;
        }

        // Operational state qualifier
        // Inherited From test:Subj
        // Type is an MO-Defined-Type
        leaf operStQual {
            config "false";
            description "Operational State Qualifier";

            // Type is an MO-Defined-Type
            type test_OperStQual;
        }

        // Last execution failed operational state qualifier
        // Inherited From test:Subj
        // Type is an MO-Defined-Type
        leaf lastExecFailQual {
            config "false";
            description "Last Execution Failure Qualifier";

            // Type is an MO-Defined-Type
            type test_OperStQual;
        }
        leaf lastExecTs {
            config "false";
            type uint64;
        }
        leaf nextExecTs {
            config "false";
            type uint64;
        }
        leaf lastExecPassTs {
            config "false";
            type uint64;
        }
        leaf firstExecFailTs {
            config "false";
            type uint64;
        }
        leaf lastExecFailTs {
            config "false";
            type uint64;
        }
        leaf numExec {
            config "false";
            type uint32;
        }
        leaf numExecFail {
            config "false";
            type uint32;
        }
        leaf numExecConsFail {
            config "false";
            type uint32;
        }

        // Prof. Name
        // Inherited From test:Subj
        // Type is an MO-Defined-Type
        leaf name {
            config "false";
            description "Name";

            // Type is an MO-Defined-Type
            type naming_Name;
        }

        // Diag result
        container rslt-items {
            list Rslt-list {
                config "false";
                key "ts";

                // Added containment: Prefix=rslt
                // Acquired From Package eqptdiag
                uses eqptdiag_Rslt-group;
            }
        }
    }

    // Has Polymorphic containment of abstract object action:LInst
    grouping action_LSubj-group {
        leaf oDn {
            config "false";
            type string;
        }
        leaf oCl {
            config "false";
            type string;
        }

        // Implicit DomainRef objects cannot be user created - they are implicitly created
        // and added to domainable objects created by the backend
        container idomain-items {
            list IDomainRef-list {
                key "name";

                // Added containment: Prefix=idomain
                // Acquired From Package aaa
                uses aaa_IDomainRef-group;
            }
        }

        // Nve ping
        container pingnve-items {
            list PingNve-list {
                key "session";

                // Added containment: Prefix=pingnve
                // Acquired From Package ngoam
                uses ngoam_PingNve-group;
            }
        }

        // Exec for fabric ping
        container pingexecfab-items {
            list ExecFab-list {
                key "name srcNodeId dstNodeId";

                // Added containment: Prefix=pingexecfab
                // Acquired From Package ping
                uses ping_ExecFab-group;
            }
        }

        // Exec for EP to EP (Tenant) ping
        container pingexectn-items {
            list ExecTn-list {
                key "tenant name srcIp dstIp";

                // Added containment: Prefix=pingexectn
                // Acquired From Package ping
                uses ping_ExecTn-group;
            }
        }

        // Result for fabric ping
        container pingrsltfab-items {
            list RsltFab-list {
                config "false";
                key "name srcNodeId dstNodeId startTs";

                // Added containment: Prefix=pingrsltfab
                // Acquired From Package ping
                uses ping_RsltFab-group;
            }
        }

        // Result for EP to EP (Tenant) ping
        container pingrslttn-items {
            list RsltTn-list {
                config "false";
                key "tenant name srcIp dstIp startTs";

                // Added containment: Prefix=pingrslttn
                // Acquired From Package ping
                uses ping_RsltTn-group;
            }
        }

        // Exec for fabric traceroute
        container trexecfab-items {
            list ExecFab-list {
                key "name srcNodeId dstNodeId";

                // Added containment: Prefix=trexecfab
                // Acquired From Package traceroute
                uses traceroute_ExecFab-group;
            }
        }

        // Exec for EP to EP (Tenant) traceroute
        container trexectn-items {
            list ExecTn-list {
                key "tenant name srcIp dstIp";

                // Added containment: Prefix=trexectn
                // Acquired From Package traceroute
                uses traceroute_ExecTn-group;
            }
        }

        // Result for fabric traceroute
        container trrsltfab-items {
            list RsltFab-list {
                config "false";
                key "name srcNodeId dstNodeId startTs";

                // Added containment: Prefix=trrsltfab
                // Acquired From Package traceroute
                uses traceroute_RsltFab-group;
            }
        }

        // Result for EP to EP (Tenant) traceroute
        container trrslttn-items {
            list RsltTn-list {
                config "false";
                key "tenant name srcIp dstIp startTs";

                // Added containment: Prefix=trrslttn
                // Acquired From Package traceroute
                uses traceroute_RsltTn-group;
            }
        }

        // Exec results
        container imginsttaskrslt-items {
            list Rslt-list {
                config "false";
                key "type startTs";

                // Added containment: Prefix=imginsttaskrslt
                // Acquired From Package imginstall
                uses imginstall_Rslt-group;
            }
        }

        // Polymorphic containment of derivative object eptrk:IpEpExec (from action:LInst)
        container trkip-items {

            // Abstract containment of eptrk:IpEpExec derived from action:LInst
            list IpEpExec-list {
                key "addr vrf";

                // Added containment: Prefix=trkip
                // Acquired From Package eptrk
                uses eptrk_IpEpExec-group;
            }
        }

        // Polymorphic containment of derivative object eptrk:MacEpExec (from action:LInst)
        container trkmac-items {

            // Abstract containment of eptrk:MacEpExec derived from action:LInst
            list MacEpExec-list {
                key "addr encap";

                // Added containment: Prefix=trkmac
                // Acquired From Package eptrk
                uses eptrk_MacEpExec-group;
            }
        }

        // IP EP Tracking Results
        // Polymorphic containment of derivative object eptrk:IpEpRslt (from action:LInst)
        container iprslt-items {

            // Abstract containment of eptrk:IpEpRslt derived from action:LInst
            list IpEpRslt-list {
                config "false";
                key "addr vrf";

                // Added containment: Prefix=iprslt
                // Acquired From Package eptrk
                uses eptrk_IpEpRslt-group;
            }
        }

        // Exec results
        // Polymorphic containment of derivative object eptrk:MacEpRslt (from action:LInst)
        container macrslt-items {

            // Abstract containment of eptrk:MacEpRslt derived from action:LInst
            list MacEpRslt-list {
                key "addr encap";

                // Added containment: Prefix=macrslt
                // Acquired From Package eptrk
                uses eptrk_MacEpRslt-group;
            }
        }

        // Result for fabric ping
        // Polymorphic containment of derivative object ngoam:PingNveRslt (from action:LInst)
        container pingnverslt-items {

            // Abstract containment of ngoam:PingNveRslt derived from action:LInst
            list PingNveRslt-list {
                config "false";
                key "sessionId";

                // Added containment: Prefix=pingnverslt
                // Acquired From Package ngoam
                uses ngoam_PingNveRslt-group;
            }
        }

        // Polymorphic containment of derivative object ngoam:TraceRtNve (from action:LInst)
        container tracertnve-items {

            // Abstract containment of ngoam:TraceRtNve derived from action:LInst
            list TraceRtNve-list {
                key "session";

                // Added containment: Prefix=tracertnve
                // Acquired From Package ngoam
                uses ngoam_TraceRtNve-group;
            }
        }

        // Polymorphic containment of derivative object ngoam:PathTraceNve (from action:LInst)
        container pathtracenve-items {

            // Abstract containment of ngoam:PathTraceNve derived from action:LInst
            list PathTraceNve-list {
                key "session";

                // Added containment: Prefix=pathtracenve
                // Acquired From Package ngoam
                uses ngoam_PathTraceNve-group;
            }
        }

        // Result for fabric traceroute
        // Polymorphic containment of derivative object ngoam:TraceRtNveRslt (from action:LInst)
        container trnverslt-items {

            // Abstract containment of ngoam:TraceRtNveRslt derived from action:LInst
            list TraceRtNveRslt-list {
                config "false";
                key "sessionId";

                // Added containment: Prefix=trnverslt
                // Acquired From Package ngoam
                uses ngoam_TraceRtNveRslt-group;
            }
        }

        // Result for Pathtrace
        // Polymorphic containment of derivative object ngoam:PathTraceNveRslt (from action:LInst)
        container ptrnverslt-items {

            // Abstract containment of ngoam:PathTraceNveRslt derived from action:LInst
            list PathTraceNveRslt-list {
                config "false";
                key "sessionId";

                // Added containment: Prefix=ptrnverslt
                // Acquired From Package ngoam
                uses ngoam_PathTraceNveRslt-group;
            }
        }

        // Rel-def from LSubjToDomainRef
        container rslSubjToDomainRef-items {

            // Added containment as a singleton: Prefix=rslSubjToDomainRef
            // Acquired From Package action
            uses action_RsLSubjToDomainRef_source-group;
        }
    }

    grouping ngoam_PingNve-group {
        leaf session {
            type string;
        }

        // Prof. id
        // Type is an MO-Defined-Type
        leaf profileId {
            description "Ngoam profile ID";

            // Type is an MO-Defined-Type
            type ngoam_ProfId;
        }
        leaf dstIp {
            type address_Ipv4;
        }
        leaf dstIpv6 {
            type address_Ipv6;
        }
        leaf dstMAC {
            type address_Mac;
        }
        leaf srcIp {
            type address_Ipv4;
        }
        leaf srcIpv6 {
            type address_Ipv6;
        }

        // dot1q
        // Type is an MO-Defined-Type
        leaf dot1q {
            description "dot1q";

            // Type is an MO-Defined-Type
            type ngoam_Dot1q;
        }

        // source port
        // Type is an MO-Defined-Type
        leaf srcPort {
            description "Source Port";

            // Type is an MO-Defined-Type
            type ngoam_Sport;
        }

        // count
        // Type is an MO-Defined-Type
        leaf count {
            description "Number of packets";

            // Type is an MO-Defined-Type
            type ngoam_NumPkt;
        }

        // timeout
        // Type is an MO-Defined-Type
        leaf timeout {
            description "Timeout";

            // Type is an MO-Defined-Type
            type ngoam_Timeout;
        }

        // interval
        // Type is an MO-Defined-Type
        leaf interval {
            description "Interval";

            // Type is an MO-Defined-Type
            type ngoam_SendIntvl;
        }

        // Type is an MO-Defined-Type
        leaf dataPattern {
            description "data pattern";

            // Type is an MO-Defined-Type
            type ngoam_PayloadPad;
        }

        // sweep min
        // Type is an MO-Defined-Type
        leaf sweepmin {
            description "Sweep Start of Range";

            // Type is an MO-Defined-Type
            type ngoam_SweepSz;
        }

        // sweep max
        // Type is an MO-Defined-Type
        leaf sweepmax {
            description "Sweep End of Range";

            // Type is an MO-Defined-Type
            type ngoam_SweepSz;
        }

        // packet size
        // Type is an MO-Defined-Type
        leaf packetSz {
            description "Payload Size";

            // Type is an MO-Defined-Type
            type ngoam_PktSz;
        }

        // The vrf in which it is running
        // Type is an MO-Defined-Type
        leaf vrf {
            description "VRF";

            // Type is an MO-Defined-Type
            type ngoam_Vrf;
        }

        // The VxLAN vni
        // Type is an MO-Defined-Type
        leaf vni {
            description "VNI";

            // Type is an MO-Defined-Type
            type ngoam_Vnid;
        }

        // Egress Interface id
        // Type is an MO-Defined-Type
        leaf egressIf {
            description "Interface ID";

            // Type is an MO-Defined-Type
            type nw_IfId;
        }

        // MAC Interface
        // Type is an MO-Defined-Type
        leaf macsrcif {
            description "payload source interface";

            // Type is an MO-Defined-Type
            type nw_IfId;
        }

        // Runtime status of the task
        // Type is an MO-Defined-Type
        leaf operSt {
            config "false";
            description "Completion";

            // Type is an MO-Defined-Type
            type action_OperSt;
        }
        leaf sessionId {
            type uint32;
        }

        // dot1q
        // From Interface ngoam:Payload
        // Type is an MO-Defined-Type
        leaf payload_dot1q {
            description "dot1q";

            // Type is an MO-Defined-Type
            type ngoam_Dot1q;
        }
        leaf payload_srcip {
            type address_Ipv4;
        }
        leaf payload_srcipv6 {
            type address_Ipv6;
        }
        leaf payload_srcmac {
            type address_Mac;
        }
        leaf payload_dstip {
            type address_Ipv4;
        }
        leaf payload_dstipv6 {
            type address_Ipv6;
        }
        leaf payload_dstmac {
            type address_Mac;
        }
        leaf payload_srcport {
            type uint16;
        }
        leaf payload_dstport {
            type uint16;
        }

        // protocol
        // From Interface ngoam:Payload
        // Type is an MO-Defined-Type
        leaf payload_protocol {
            description "payload protocol";

            // Type is an MO-Defined-Type
            type ngoam_Protocol;
        }

        // Source Interface
        // From Interface ngoam:Payload
        // Type is an MO-Defined-Type
        leaf payload_srcif {
            description "payload source interface";

            // Type is an MO-Defined-Type
            type nw_IfId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: ngoam:PingNve->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Result for fabric ping
        container pingnverslt-items {
            list PingNveRslt-list {
                config "false";
                key "sessionId";

                // Added containment: Prefix=pingnverslt
                // Acquired From Package ngoam
                uses ngoam_PingNveRslt-group;
            }
        }
    }

    grouping ngoam_PingNveRslt-group {

        // Prof. Name
        // Type is an MO-Defined-Type
        leaf sessionId {
            config "false";
            description "Name";

            // Type is an MO-Defined-Type
            type ngoam_SessionId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }
        leaf replyIp {
            config "false";
            type address_Ipv4;
        }
        leaf replyIpv6 {
            config "false";
            type address_Ipv6;
        }
        leaf errorCode {
            config "false";
            type string;
        }
        leaf failReason {
            config "false";
            type string;
        }

        // Source port
        // Inherited From ngoam:PingRslt
        // Type is an MO-Defined-Type
        leaf sPort {
            config "false";
            description "Source Port";

            // Type is an MO-Defined-Type
            type ngoam_SrcPort;
        }

        // packet size
        // Inherited From ngoam:PingRslt
        // Type is an MO-Defined-Type
        leaf packetSz {
            config "false";
            description "Packet Size";

            // Type is an MO-Defined-Type
            type ngoam_PktSz;
        }

        // Number of packets sent
        // Inherited From ngoam:PingRslt
        // Type is an MO-Defined-Type
        leaf sentPkts {
            config "false";
            description "Sent Packets";

            // Type is an MO-Defined-Type
            type ngoam_Counter;
        }

        // Number of packets not sent
        // Inherited From ngoam:PingRslt
        // Type is an MO-Defined-Type
        leaf notSentPkts {
            config "false";
            description "Not Sent Packets";

            // Type is an MO-Defined-Type
            type ngoam_Counter;
        }

        // Number of packets received
        // Inherited From ngoam:PingRslt
        // Type is an MO-Defined-Type
        leaf rcvdPkts {
            config "false";
            description "Received Packets";

            // Type is an MO-Defined-Type
            type ngoam_Counter;
        }

        // Minimum round trip time of all the packets that
        // have been sent in one exec
        // Inherited From ngoam:PingRslt
        // Type is an MO-Defined-Type
        leaf minRtt {
            config "false";
            description "Minimum Round Trip Time";

            // Type is an MO-Defined-Type
            type ngoam_Rtt;
        }

        // Average round trip time of all the packets that
        // have been sent in one exec
        // Inherited From ngoam:PingRslt
        // Type is an MO-Defined-Type
        leaf avgRtt {
            config "false";
            description "Average Round Trip Time";

            // Type is an MO-Defined-Type
            type ngoam_Rtt;
        }

        // Maximum round trip time of all the packets that
        // have been sent in one exec
        // Inherited From ngoam:PingRslt
        // Type is an MO-Defined-Type
        leaf maxRtt {
            config "false";
            description "Maximum Round Trip Time";

            // Type is an MO-Defined-Type
            type ngoam_Rtt;
        }

        // Total Rtt of all the packets sent
        // Inherited From ngoam:PingRslt
        // Type is an MO-Defined-Type
        leaf totalRtt {
            config "false";
            description "Total Round Trip Time";

            // Type is an MO-Defined-Type
            type ngoam_Rtt;
        }
    }

    grouping ping_ExecFab-group {

        // Destination Node ID
        // Type is an MO-Defined-Type
        leaf dstNodeId {
            description "Destination Node ID";

            // Type is an MO-Defined-Type
            type fabric_NodeId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: oam:Exec->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Prof. Name
        // Inherited From oam:Exec
        // Type is an MO-Defined-Type
        leaf name {
            description "Name";

            // Type is an MO-Defined-Type
            type oam_ProfName;
        }

        // Endpoint type, this oam test is run for this
        // type of the endpoint
        // Inherited From oam:Exec
        // Type is an MO-Defined-Type
        leaf epT {
            config "false";
            description "Endpoint Type";

            // Type is an MO-Defined-Type
            type oam_EpT;
        }

        // Source Node ID
        // Inherited From oam:Exec
        // Type is an MO-Defined-Type
        leaf srcNodeId {
            description "Source Node ID";

            // Type is an MO-Defined-Type
            type fabric_NodeId;
        }

        // The vrf in which it is running
        // Inherited From oam:Exec
        // Type is an MO-Defined-Type
        leaf vrf {
            description "VRF";

            // Type is an MO-Defined-Type
            type oam_Vrf;
        }

        // Source IP
        // Inherited From oam:Exec
        // Type is an MO-Defined-Type
        leaf srcIp {
            description "Source IP";

            // Type is an MO-Defined-Type
            type oam_IpId;
        }

        // Destination IP
        // Inherited From oam:Exec
        // Type is an MO-Defined-Type
        leaf dstIp {
            description "Destination IP";

            // Type is an MO-Defined-Type
            type oam_IpId;
        }

        // Payload size
        // Inherited From oam:Exec
        // Type is an MO-Defined-Type
        leaf payloadSz {
            description "Payload Size";

            // Type is an MO-Defined-Type
            type oam_PayloadSz;
        }

        // The following are used when the ping/traceroute
        // are done on behalf of the tenant endpoints
        // Inherited From oam:Exec
        // Type is an MO-Defined-Type
        leaf tenant {
            description "Tenant Name";

            // Type is an MO-Defined-Type
            type oam_TenantName;
        }

        // Source MAC
        // Inherited From oam:Exec
        // Type is an MO-Defined-Type
        leaf srcMac {
            description "Source MAC";

            // Type is an MO-Defined-Type
            type oam_MacId;
        }

        // Destination MAC
        // Inherited From oam:Exec
        // Type is an MO-Defined-Type
        leaf dstMac {
            description "Destination MAC";

            // Type is an MO-Defined-Type
            type oam_MacId;
        }
        leaf vtep {
            type address_Ip;
        }
        leaf vtepEncap {
            type string;
        }

        // Runtime status of the task
        // Inherited From oam:Exec
        // Type is an MO-Defined-Type
        leaf operSt {
            config "false";
            description "Completion";

            // Type is an MO-Defined-Type
            type action_OperSt;
        }
    }

    grouping ping_ExecTn-group {

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: oam:Exec->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Prof. Name
        // Inherited From oam:Exec
        // Type is an MO-Defined-Type
        leaf name {
            description "Name";

            // Type is an MO-Defined-Type
            type oam_ProfName;
        }

        // Endpoint type, this oam test is run for this
        // type of the endpoint
        // Inherited From oam:Exec
        // Type is an MO-Defined-Type
        leaf epT {
            config "false";
            description "Endpoint Type";

            // Type is an MO-Defined-Type
            type oam_EpT;
        }

        // Source Node ID
        // Inherited From oam:Exec
        // Type is an MO-Defined-Type
        leaf srcNodeId {
            description "Source Node ID";

            // Type is an MO-Defined-Type
            type fabric_NodeId;
        }

        // The vrf in which it is running
        // Inherited From oam:Exec
        // Type is an MO-Defined-Type
        leaf vrf {
            description "VRF";

            // Type is an MO-Defined-Type
            type oam_Vrf;
        }

        // Source IP
        // Inherited From oam:Exec
        // Type is an MO-Defined-Type
        leaf srcIp {
            description "Source IP";

            // Type is an MO-Defined-Type
            type oam_IpId;
        }

        // Destination IP
        // Inherited From oam:Exec
        // Type is an MO-Defined-Type
        leaf dstIp {
            description "Destination IP";

            // Type is an MO-Defined-Type
            type oam_IpId;
        }

        // Payload size
        // Inherited From oam:Exec
        // Type is an MO-Defined-Type
        leaf payloadSz {
            description "Payload Size";

            // Type is an MO-Defined-Type
            type oam_PayloadSz;
        }

        // The following are used when the ping/traceroute
        // are done on behalf of the tenant endpoints
        // Inherited From oam:Exec
        // Type is an MO-Defined-Type
        leaf tenant {
            description "Tenant Name";

            // Type is an MO-Defined-Type
            type oam_TenantName;
        }

        // Source MAC
        // Inherited From oam:Exec
        // Type is an MO-Defined-Type
        leaf srcMac {
            description "Source MAC";

            // Type is an MO-Defined-Type
            type oam_MacId;
        }

        // Destination MAC
        // Inherited From oam:Exec
        // Type is an MO-Defined-Type
        leaf dstMac {
            description "Destination MAC";

            // Type is an MO-Defined-Type
            type oam_MacId;
        }
        leaf vtep {
            type address_Ip;
        }
        leaf vtepEncap {
            type string;
        }

        // Runtime status of the task
        // Inherited From oam:Exec
        // Type is an MO-Defined-Type
        leaf operSt {
            config "false";
            description "Completion";

            // Type is an MO-Defined-Type
            type action_OperSt;
        }
    }

    grouping ping_RsltFab-group {

        // Destination Node ID
        // Type is an MO-Defined-Type
        leaf dstNodeId {
            config "false";
            description "Destination Node ID";

            // Type is an MO-Defined-Type
            type fabric_NodeId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Prof. Name
        // Inherited From oam:Rslt
        // Type is an MO-Defined-Type
        leaf name {
            config "false";
            description "Name";

            // Type is an MO-Defined-Type
            type oam_ProfName;
        }

        // Source Node ID
        // Inherited From oam:Rslt
        // Type is an MO-Defined-Type
        leaf srcNodeId {
            config "false";
            description "Source Node ID";

            // Type is an MO-Defined-Type
            type fabric_NodeId;
        }

        // The vrf in which it is running
        // Inherited From oam:Rslt
        // Type is an MO-Defined-Type
        leaf vrf {
            config "false";
            description "VRF";

            // Type is an MO-Defined-Type
            type oam_Vrf;
        }

        // Source IP
        // Inherited From oam:Rslt
        // Type is an MO-Defined-Type
        leaf srcIp {
            config "false";
            description "Source IP";

            // Type is an MO-Defined-Type
            type oam_IpId;
        }

        // Destination IP
        // Inherited From oam:Rslt
        // Type is an MO-Defined-Type
        leaf dstIp {
            config "false";
            description "Destination IP";

            // Type is an MO-Defined-Type
            type oam_IpId;
        }

        // The tenant to which this Ep belongs
        // Inherited From oam:Rslt
        // Type is an MO-Defined-Type
        leaf tenant {
            config "false";
            description "Tenant Name";

            // Type is an MO-Defined-Type
            type oam_TenantName;
        }

        // Payload size
        // Inherited From oam:Rslt
        // Type is an MO-Defined-Type
        leaf payloadSz {
            config "false";
            description "Payload Size";

            // Type is an MO-Defined-Type
            type oam_PayloadSz;
        }

        // Number of packets sent
        // Inherited From ping:Rslt
        // Type is an MO-Defined-Type
        leaf sentPkts {
            config "false";
            description "Sent Packets";

            // Type is an MO-Defined-Type
            type ping_Counter;
        }

        // Number of packets received
        // Inherited From ping:Rslt
        // Type is an MO-Defined-Type
        leaf rcvdPkts {
            config "false";
            description "Received Packets";

            // Type is an MO-Defined-Type
            type ping_Counter;
        }

        // Minimum round trip time of all the packets that
        // have been sent in one exec
        // Inherited From ping:Rslt
        // Type is an MO-Defined-Type
        leaf minRtt {
            config "false";
            description "Minimum Round Trip Time";

            // Type is an MO-Defined-Type
            type ping_Rtt;
        }

        // Average round trip time of all the packets that
        // have been sent in one exec
        // Inherited From ping:Rslt
        // Type is an MO-Defined-Type
        leaf avgRtt {
            config "false";
            description "Average Round Trip Time";

            // Type is an MO-Defined-Type
            type ping_Rtt;
        }

        // Maximum round trip time of all the packets that
        // have been sent in one exec
        // Inherited From ping:Rslt
        // Type is an MO-Defined-Type
        leaf maxRtt {
            config "false";
            description "Maximum Round Trip Time";

            // Type is an MO-Defined-Type
            type ping_Rtt;
        }
    }

    grouping ping_RsltTn-group {

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Prof. Name
        // Inherited From oam:Rslt
        // Type is an MO-Defined-Type
        leaf name {
            config "false";
            description "Name";

            // Type is an MO-Defined-Type
            type oam_ProfName;
        }

        // Source Node ID
        // Inherited From oam:Rslt
        // Type is an MO-Defined-Type
        leaf srcNodeId {
            config "false";
            description "Source Node ID";

            // Type is an MO-Defined-Type
            type fabric_NodeId;
        }

        // The vrf in which it is running
        // Inherited From oam:Rslt
        // Type is an MO-Defined-Type
        leaf vrf {
            config "false";
            description "VRF";

            // Type is an MO-Defined-Type
            type oam_Vrf;
        }

        // Source IP
        // Inherited From oam:Rslt
        // Type is an MO-Defined-Type
        leaf srcIp {
            config "false";
            description "Source IP";

            // Type is an MO-Defined-Type
            type oam_IpId;
        }

        // Destination IP
        // Inherited From oam:Rslt
        // Type is an MO-Defined-Type
        leaf dstIp {
            config "false";
            description "Destination IP";

            // Type is an MO-Defined-Type
            type oam_IpId;
        }

        // The tenant to which this Ep belongs
        // Inherited From oam:Rslt
        // Type is an MO-Defined-Type
        leaf tenant {
            config "false";
            description "Tenant Name";

            // Type is an MO-Defined-Type
            type oam_TenantName;
        }

        // Payload size
        // Inherited From oam:Rslt
        // Type is an MO-Defined-Type
        leaf payloadSz {
            config "false";
            description "Payload Size";

            // Type is an MO-Defined-Type
            type oam_PayloadSz;
        }

        // Number of packets sent
        // Inherited From ping:Rslt
        // Type is an MO-Defined-Type
        leaf sentPkts {
            config "false";
            description "Sent Packets";

            // Type is an MO-Defined-Type
            type ping_Counter;
        }

        // Number of packets received
        // Inherited From ping:Rslt
        // Type is an MO-Defined-Type
        leaf rcvdPkts {
            config "false";
            description "Received Packets";

            // Type is an MO-Defined-Type
            type ping_Counter;
        }

        // Minimum round trip time of all the packets that
        // have been sent in one exec
        // Inherited From ping:Rslt
        // Type is an MO-Defined-Type
        leaf minRtt {
            config "false";
            description "Minimum Round Trip Time";

            // Type is an MO-Defined-Type
            type ping_Rtt;
        }

        // Average round trip time of all the packets that
        // have been sent in one exec
        // Inherited From ping:Rslt
        // Type is an MO-Defined-Type
        leaf avgRtt {
            config "false";
            description "Average Round Trip Time";

            // Type is an MO-Defined-Type
            type ping_Rtt;
        }

        // Maximum round trip time of all the packets that
        // have been sent in one exec
        // Inherited From ping:Rslt
        // Type is an MO-Defined-Type
        leaf maxRtt {
            config "false";
            description "Maximum Round Trip Time";

            // Type is an MO-Defined-Type
            type ping_Rtt;
        }
    }

    grouping traceroute_ExecFab-group {

        // Destination Node ID
        // Type is an MO-Defined-Type
        leaf dstNodeId {
            description "Destination Node ID";

            // Type is an MO-Defined-Type
            type fabric_NodeId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: oam:Exec->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Prof. Name
        // Inherited From oam:Exec
        // Type is an MO-Defined-Type
        leaf name {
            description "Name";

            // Type is an MO-Defined-Type
            type oam_ProfName;
        }

        // Endpoint type, this oam test is run for this
        // type of the endpoint
        // Inherited From oam:Exec
        // Type is an MO-Defined-Type
        leaf epT {
            config "false";
            description "Endpoint Type";

            // Type is an MO-Defined-Type
            type oam_EpT;
        }

        // Source Node ID
        // Inherited From oam:Exec
        // Type is an MO-Defined-Type
        leaf srcNodeId {
            description "Source Node ID";

            // Type is an MO-Defined-Type
            type fabric_NodeId;
        }

        // The vrf in which it is running
        // Inherited From oam:Exec
        // Type is an MO-Defined-Type
        leaf vrf {
            description "VRF";

            // Type is an MO-Defined-Type
            type oam_Vrf;
        }

        // Source IP
        // Inherited From oam:Exec
        // Type is an MO-Defined-Type
        leaf srcIp {
            description "Source IP";

            // Type is an MO-Defined-Type
            type oam_IpId;
        }

        // Destination IP
        // Inherited From oam:Exec
        // Type is an MO-Defined-Type
        leaf dstIp {
            description "Destination IP";

            // Type is an MO-Defined-Type
            type oam_IpId;
        }

        // Payload size
        // Inherited From oam:Exec
        // Type is an MO-Defined-Type
        leaf payloadSz {
            description "Payload Size";

            // Type is an MO-Defined-Type
            type oam_PayloadSz;
        }

        // The following are used when the ping/traceroute
        // are done on behalf of the tenant endpoints
        // Inherited From oam:Exec
        // Type is an MO-Defined-Type
        leaf tenant {
            description "Tenant Name";

            // Type is an MO-Defined-Type
            type oam_TenantName;
        }

        // Source MAC
        // Inherited From oam:Exec
        // Type is an MO-Defined-Type
        leaf srcMac {
            description "Source MAC";

            // Type is an MO-Defined-Type
            type oam_MacId;
        }

        // Destination MAC
        // Inherited From oam:Exec
        // Type is an MO-Defined-Type
        leaf dstMac {
            description "Destination MAC";

            // Type is an MO-Defined-Type
            type oam_MacId;
        }
        leaf vtep {
            type address_Ip;
        }
        leaf vtepEncap {
            type string;
        }

        // Runtime status of the task
        // Inherited From oam:Exec
        // Type is an MO-Defined-Type
        leaf operSt {
            config "false";
            description "Completion";

            // Type is an MO-Defined-Type
            type action_OperSt;
        }

        // Max paths that the traceroute should be limited to
        // Inherited From traceroute:AExec
        // Type is an MO-Defined-Type
        leaf maxPaths {
            config "false";
            description "Max Paths";

            // Type is an MO-Defined-Type
            type traceroute_Paths;
        }

        // Max hops that the traceroute should be limited to
        // Inherited From traceroute:AExec
        // Type is an MO-Defined-Type
        leaf maxHops {
            config "false";
            description "Max Hops";

            // Type is an MO-Defined-Type
            type traceroute_Hops;
        }
    }

    grouping traceroute_ExecTn-group {

        // Gateway MAC
        // Type is an MO-Defined-Type
        leaf gwMac {
            description "Gateway MAC";

            // Type is an MO-Defined-Type
            type oam_MacId;
        }
        leaf useGwMac {
            type boolean;
            default "true";
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Modified by Override: oam:Exec->adminSt
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Prof. Name
        // Inherited From oam:Exec
        // Type is an MO-Defined-Type
        leaf name {
            description "Name";

            // Type is an MO-Defined-Type
            type oam_ProfName;
        }

        // Endpoint type, this oam test is run for this
        // type of the endpoint
        // Inherited From oam:Exec
        // Type is an MO-Defined-Type
        leaf epT {
            config "false";
            description "Endpoint Type";

            // Type is an MO-Defined-Type
            type oam_EpT;
        }

        // Source Node ID
        // Inherited From oam:Exec
        // Type is an MO-Defined-Type
        leaf srcNodeId {
            description "Source Node ID";

            // Type is an MO-Defined-Type
            type fabric_NodeId;
        }

        // The vrf in which it is running
        // Inherited From oam:Exec
        // Type is an MO-Defined-Type
        leaf vrf {
            description "VRF";

            // Type is an MO-Defined-Type
            type oam_Vrf;
        }

        // Source IP
        // Inherited From oam:Exec
        // Type is an MO-Defined-Type
        leaf srcIp {
            description "Source IP";

            // Type is an MO-Defined-Type
            type oam_IpId;
        }

        // Destination IP
        // Inherited From oam:Exec
        // Type is an MO-Defined-Type
        leaf dstIp {
            description "Destination IP";

            // Type is an MO-Defined-Type
            type oam_IpId;
        }

        // Payload size
        // Inherited From oam:Exec
        // Type is an MO-Defined-Type
        leaf payloadSz {
            description "Payload Size";

            // Type is an MO-Defined-Type
            type oam_PayloadSz;
        }

        // The following are used when the ping/traceroute
        // are done on behalf of the tenant endpoints
        // Inherited From oam:Exec
        // Type is an MO-Defined-Type
        leaf tenant {
            description "Tenant Name";

            // Type is an MO-Defined-Type
            type oam_TenantName;
        }

        // Source MAC
        // Inherited From oam:Exec
        // Type is an MO-Defined-Type
        leaf srcMac {
            description "Source MAC";

            // Type is an MO-Defined-Type
            type oam_MacId;
        }

        // Destination MAC
        // Inherited From oam:Exec
        // Type is an MO-Defined-Type
        leaf dstMac {
            description "Destination MAC";

            // Type is an MO-Defined-Type
            type oam_MacId;
        }
        leaf vtep {
            type address_Ip;
        }
        leaf vtepEncap {
            type string;
        }

        // Runtime status of the task
        // Inherited From oam:Exec
        // Type is an MO-Defined-Type
        leaf operSt {
            config "false";
            description "Completion";

            // Type is an MO-Defined-Type
            type action_OperSt;
        }

        // Max paths that the traceroute should be limited to
        // Inherited From traceroute:AExec
        // Type is an MO-Defined-Type
        leaf maxPaths {
            config "false";
            description "Max Paths";

            // Type is an MO-Defined-Type
            type traceroute_Paths;
        }

        // Max hops that the traceroute should be limited to
        // Inherited From traceroute:AExec
        // Type is an MO-Defined-Type
        leaf maxHops {
            config "false";
            description "Max Hops";

            // Type is an MO-Defined-Type
            type traceroute_Hops;
        }
    }

    grouping traceroute_RsltFab-group {

        // Destination Node ID
        // Type is an MO-Defined-Type
        leaf dstNodeId {
            config "false";
            description "Destination Node ID";

            // Type is an MO-Defined-Type
            type fabric_NodeId;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Prof. Name
        // Inherited From oam:Rslt
        // Type is an MO-Defined-Type
        leaf name {
            config "false";
            description "Name";

            // Type is an MO-Defined-Type
            type oam_ProfName;
        }

        // Source Node ID
        // Inherited From oam:Rslt
        // Type is an MO-Defined-Type
        leaf srcNodeId {
            config "false";
            description "Source Node ID";

            // Type is an MO-Defined-Type
            type fabric_NodeId;
        }

        // The vrf in which it is running
        // Inherited From oam:Rslt
        // Type is an MO-Defined-Type
        leaf vrf {
            config "false";
            description "VRF";

            // Type is an MO-Defined-Type
            type oam_Vrf;
        }

        // Source IP
        // Inherited From oam:Rslt
        // Type is an MO-Defined-Type
        leaf srcIp {
            config "false";
            description "Source IP";

            // Type is an MO-Defined-Type
            type oam_IpId;
        }

        // Destination IP
        // Inherited From oam:Rslt
        // Type is an MO-Defined-Type
        leaf dstIp {
            config "false";
            description "Destination IP";

            // Type is an MO-Defined-Type
            type oam_IpId;
        }

        // The tenant to which this Ep belongs
        // Inherited From oam:Rslt
        // Type is an MO-Defined-Type
        leaf tenant {
            config "false";
            description "Tenant Name";

            // Type is an MO-Defined-Type
            type oam_TenantName;
        }

        // Payload size
        // Inherited From oam:Rslt
        // Type is an MO-Defined-Type
        leaf payloadSz {
            config "false";
            description "Payload Size";

            // Type is an MO-Defined-Type
            type oam_PayloadSz;
        }

        // Maximum number of hops that the traceroute took to
        // reach the destination
        // Inherited From traceroute:ARslt
        // Type is an MO-Defined-Type
        leaf maxHops {
            config "false";
            description "Max Hops";

            // Type is an MO-Defined-Type
            type traceroute_Hops;
        }

        // Path Group, captures all the paths that were taken by
        // traceroute to the final destination
        container pgrp-items {
            list PathGrp-list {
                config "false";
                key "id";

                // Added containment: Prefix=pgrp
                // Acquired From Package traceroute
                uses traceroute_PathGrp-group;
            }
        }
    }

    grouping traceroute_PathGrp-group {

        // Identifier of the path group
        // Type is an MO-Defined-Type
        leaf id {
            config "false";
            description "ID";

            // Type is an MO-Defined-Type
            type traceroute_PathGrpId;
        }

        // Each path represents a sequence of nodes towards the
        // destination
        container path-items {
            list Path-list {
                config "false";
                key "id";

                // Added containment: Prefix=path
                // Acquired From Package traceroute
                uses traceroute_Path-group;
            }
        }
    }

    grouping traceroute_Path-group {

        // Identifier of the path
        // Type is an MO-Defined-Type
        leaf id {
            config "false";
            description "ID";

            // Type is an MO-Defined-Type
            type traceroute_PathId;
        }

        // Type of the path
        // Type is an MO-Defined-Type
        leaf type {
            config "false";
            description "Type";

            // Type is an MO-Defined-Type
            type traceroute_PathT;
        }

        // Flags
        // Type is an MO-Defined-Type
        leaf flags {
            config "false";
            description "Flags";

            // Type is an MO-Defined-Type
            type traceroute_PathFlags;
        }

        // Node represents a given node in the traceroute path. Each
        // node is identified by the ip address and the order represents
        // its placement in the path
        container node-items {
            list Node-list {
                config "false";
                key "order";

                // Added containment: Prefix=node
                // Acquired From Package traceroute
                uses traceroute_Node-group;
            }
        }
    }

    grouping traceroute_Node-group {

        // Node id
        // Type is an MO-Defined-Type
        leaf order {
            config "false";
            description "Order";

            // Type is an MO-Defined-Type
            type traceroute_Order;
        }
        leaf addr {
            config "false";
            type address_Ip;
        }
        leaf elapsedTime {
            config "false";
            type uint64;
        }

        // Interface id
        // Type is an MO-Defined-Type
        leaf ifId {
            config "false";
            description "Interface ID";

            // Type is an MO-Defined-Type
            type nw_IfId;
        }
    }

    grouping traceroute_RsltTn-group {

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Prof. Name
        // Inherited From oam:Rslt
        // Type is an MO-Defined-Type
        leaf name {
            config "false";
            description "Name";

            // Type is an MO-Defined-Type
            type oam_ProfName;
        }

        // Source Node ID
        // Inherited From oam:Rslt
        // Type is an MO-Defined-Type
        leaf srcNodeId {
            config "false";
            description "Source Node ID";

            // Type is an MO-Defined-Type
            type fabric_NodeId;
        }

        // The vrf in which it is running
        // Inherited From oam:Rslt
        // Type is an MO-Defined-Type
        leaf vrf {
            config "false";
            description "VRF";

            // Type is an MO-Defined-Type
            type oam_Vrf;
        }

        // Source IP
        // Inherited From oam:Rslt
        // Type is an MO-Defined-Type
        leaf srcIp {
            config "false";
            description "Source IP";

            // Type is an MO-Defined-Type
            type oam_IpId;
        }

        // Destination IP
        // Inherited From oam:Rslt
        // Type is an MO-Defined-Type
        leaf dstIp {
            config "false";
            description "Destination IP";

            // Type is an MO-Defined-Type
            type oam_IpId;
        }

        // The tenant to which this Ep belongs
        // Inherited From oam:Rslt
        // Type is an MO-Defined-Type
        leaf tenant {
            config "false";
            description "Tenant Name";

            // Type is an MO-Defined-Type
            type oam_TenantName;
        }

        // Payload size
        // Inherited From oam:Rslt
        // Type is an MO-Defined-Type
        leaf payloadSz {
            config "false";
            description "Payload Size";

            // Type is an MO-Defined-Type
            type oam_PayloadSz;
        }

        // Maximum number of hops that the traceroute took to
        // reach the destination
        // Inherited From traceroute:ARslt
        // Type is an MO-Defined-Type
        leaf maxHops {
            config "false";
            description "Max Hops";

            // Type is an MO-Defined-Type
            type traceroute_Hops;
        }

        // Path Group, captures all the paths that were taken by
        // traceroute to the final destination
        container pgrp-items {
            list PathGrp-list {
                config "false";
                key "id";

                // Added containment: Prefix=pgrp
                // Acquired From Package traceroute
                uses traceroute_PathGrp-group;
            }
        }
    }

    grouping imginstall_Rslt-group {

        // Stage of the install task
        // Type is an MO-Defined-Type
        leaf stage {
            config "false";
            description "Stage";

            // Type is an MO-Defined-Type
            type imginstall_Stage;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }
    }

    grouping eptrk_IpEpExec-group {
        leaf addr {
            type address_Ip;
        }

        // Type is an MO-Defined-Type
        leaf vrf {
            description "VRF";

            // Type is an MO-Defined-Type
            type l3_VrfName;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // IP EP Tracking Results
        container iprslt-items {
            list IpEpRslt-list {
                config "false";
                key "addr vrf";

                // Added containment: Prefix=iprslt
                // Acquired From Package eptrk
                uses eptrk_IpEpRslt-group;
            }
        }
    }

    grouping eptrk_IpEpRslt-group {
        leaf addr {
            type address_Ip;
        }

        // The vrf the EP belongs to
        // Type is an MO-Defined-Type
        leaf vrf {
            config "false";
            description "VRF";

            // Type is an MO-Defined-Type
            type l3_VrfName;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Operational state qualifier
        // Inherited From eptrk:EpRslt
        // Type is an MO-Defined-Type
        leaf operStQual {
            config "false";
            description "Operational State Qualifier";

            // Type is an MO-Defined-Type
            type eptrk_OperStQual;
        }

        // Rel-def from IpEpRslttoIpEpAtt
        container rsipEpRslttoIpEpAtt-items {

            // Added containment as a singleton: Prefix=rsipEpRslttoIpEpAtt
            // Acquired From Package eptrk
            uses eptrk_RsIpEpRslttoIpEpAtt_source-group;
        }
    }

    grouping eptrk_MacEpExec-group {
        leaf addr {
            type address_Mac;
        }
        leaf encap {
            type string;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Admin State of the action
        // Inherited From task:Exec
        // Type is an MO-Defined-Type
        leaf adminSt {
            description "Admin State";

            // Type is an MO-Defined-Type
            type action_AdminSt;
        }

        // Frequency at which tasks are executed
        // Inherited From task:Exec
        // Type is an MO-Defined-Type
        leaf freq {
            description "Task Frequency";

            // Type is an MO-Defined-Type
            type action_Freq;
        }

        // Exec results
        container macrslt-items {
            list MacEpRslt-list {
                key "addr encap";

                // Added containment: Prefix=macrslt
                // Acquired From Package eptrk
                uses eptrk_MacEpRslt-group;
            }
        }
    }

    grouping eptrk_MacEpRslt-group {
        leaf addr {
            type address_Mac;
        }
        leaf encap {
            type string;
        }

        // Inherited From action:Inst
        // Modified by Override: action:LInst->descr
        // Type is an MO-Defined-Type
        leaf descr {
            description "Description";

            // Type is an MO-Defined-Type
            type action_Descr;
        }

        // Time that the task started
        // Inherited From action:Inst
        // Type is an MO-Defined-Type
        leaf startTs {
            config "false";
            description "TBD";

            // Type is an MO-Defined-Type
            type mo_TStamp;
        }

        // Task rule type
        // Inherited From action:LInst
        // Type is an MO-Defined-Type
        leaf type {
            description "TBD";

            // Type is an MO-Defined-Type
            type action_Type;
        }

        // Inherited From action:LInst
        // Type is an MO-Defined-Type
        leaf rSz {
            config "false";
            description "TBD";

            // Type is an MO-Defined-Type
            type action_RetentionSize;
        }

        // Retention time of task results
        // Inherited From action:LInst
        // Type is an MO-Defined-Type
        leaf rTm {
            config "false";
            description "TBD";

            // Type is an MO-Defined-Type
            type action_RetentionTime;
        }
        leaf peerClassId {
            config "false";
            type string;
        }

        // Qualifier for the above status
        // Inherited From task:Rslt
        // Type is an MO-Defined-Type
        leaf qual {
            config "false";
            description "TBD";

            // Type is an MO-Defined-Type
            type action_Qual;
        }
        leaf ack {
            type boolean;
        }

        // Time that the task ended
        // Inherited From task:Rslt
        // Type is an MO-Defined-Type
        leaf endTs {
            config "false";
            description "TBD";

            // Type is an MO-Defined-Type
            type mo_TStamp;
        }

        // Runtime status of the task
        // Inherited From task:Rslt
        // Type is an MO-Defined-Type
        leaf operSt {
            config "false";
            description "Completion";

            // Type is an MO-Defined-Type
            type action_OperSt;
        }

        // Operational state qualifier
        // Inherited From eptrk:EpRslt
        // Type is an MO-Defined-Type
        leaf operStQual {
            config "false";
            description "Operational State Qualifier";

            // Type is an MO-Defined-Type
            type eptrk_OperStQual;
        }

        // Rel-def from MacEpRslttoIpEpAtt
        container rsmacEpRslttoIpEpAtt-items {

            // Abstract containment of rsmacEpRslttoIpEpAtt derived from eptrk:MacEpRslt
            list RsMacEpRslttoIpEpAtt-list {
                config "false";
                key "tDn";

                // Added containment: Prefix=rsmacEpRslttoIpEpAtt
                // Acquired From Package eptrk
                uses eptrk_RsMacEpRslttoIpEpAtt_source-group;
            }
        }
    }

    grouping infra_RtFexBndlGrpToAggrIf_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping infra_RtAccBndlGrpToAggrIf_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping coop_RsCtx2Leaf_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Publisher Id
        // Type is an MO-Defined-Type
        leaf pubId {
            config "false";
            description "Publisher ID";

            // Type is an MO-Defined-Type
            type coop_PubId;
        }

        // Last published timestamp
        // Type is an MO-Defined-Type
        leaf lastPub {
            config "false";
            description "Last Published";

            // Type is an MO-Defined-Type
            type coop_Timestamp;
        }
    }

    grouping coop_RsMrtr2Leaf_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Publisher Id
        // Type is an MO-Defined-Type
        leaf pubId {
            config "false";
            description "Publisher ID";

            // Type is an MO-Defined-Type
            type coop_PubId;
        }

        // Last published timestamp
        // Type is an MO-Defined-Type
        leaf lastPub {
            config "false";
            description "Last Published";

            // Type is an MO-Defined-Type
            type coop_Timestamp;
        }
    }

    grouping datetime_RsNtpProviderToNtpAuth_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping dbgexp_RtDbgexpTsSrc_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping span_RsSessionToDomainRef_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping span_RsSpanSrcToL2CktEpAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Represents state of the relationship
        // Inherited From reln:To
        // Type is an MO-Defined-Type
        leaf state {
            config "false";
            description "State";

            // Type is an MO-Defined-Type
            type reln_State;
        }

        // Represents state qualifier of the relationship
        // Inherited From reln:To
        // Type is an MO-Defined-Type
        leaf stateQual {
            config "false";
            description "State Qualifier";

            // Type is an MO-Defined-Type
            type reln_StateQual;
        }

        // Represents the type of the target
        // - Name based resolution
        // - Explicit resolution
        // Inherited From reln:To
        // Type is an MO-Defined-Type
        leaf tType {
            config "false";
            description "TBD";

            // Type is an MO-Defined-Type
            type reln_TargetType;
        }

        // Represents the type of the Resolver
        // - Mo
        // - Service
        // - Local Shard
        // Inherited From reln:To
        // Type is an MO-Defined-Type
        leaf rType {
            config "false";
            description "TBD";

            // Type is an MO-Defined-Type
            type reln_ResolverType;
        }
        leaf forceResolve {
            config "false";
            type boolean;
            default "true";
        }

        // Source id
        // Type is an MO-Defined-Type
        leaf id {
            config "false";
            description "ID";

            // Type is an MO-Defined-Type
            type span_SrcId;
        }

        // Operational state of the session
        // Type is an MO-Defined-Type
        leaf operSt {
            config "false";
            description "Operational State";

            // Type is an MO-Defined-Type
            type span_OperSt;
        }

        // Operational state qualifier
        // Type is an MO-Defined-Type
        leaf operStQual {
            config "false";
            description "Operational State Qualifier";

            // Type is an MO-Defined-Type
            type span_OperStQual;
        }
    }

    grouping span_RtSpanSpanSrcToL2CktEpAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping traceroutep_RtTraceroutepTrSrc_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping traceroutep_RtTraceroutepTrDst_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping dhcp_RsPseudoIf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping dhcp_RtPseudoIf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fabric_RtOosSlot_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fabric_RtFabricResRadiusEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fabric_RtFabricResLdapEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fabric_RtFabricResTacacsPlusEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fabric_RtFabricResAuthRealm_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fabric_RtFabricResUserEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fabric_RtFabricResPkiEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping l2_RsExtBD_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l2_RsInbandConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l2_RtInbandConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l2_RsExtConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l2_RtExtConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l2_RsBrConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l2_RtBrConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping lldp_RsCtrlrAdjEpToStAdjEp_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping lldp_RtCtrlrAdjEpToStAdjEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping lldp_RsLldpInstPolCons_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping vpc_RsVpcConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping vpc_RtVpcConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping vpc_RsVpcInstPolCons_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
        leaf protGEp {
            config "false";
            type string;
        }
    }

    grouping fv_RsDomDefNs_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fv_RsDomDefNsLocal_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fv_RtFvToRemoteRFltP_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvToRemoteRFltAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvEpDefToPathEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvEpDefToLooseNode_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvEpDefRefToStAdjEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvEpDefRefToL2MacEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvEpDefRefToStAdjEpV6_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RsVNode_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fv_RtFvVNode_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping fv_RsLNode_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvToDomDef_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvDomIfConn_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvDyPathAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvLsNodeAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping fv_RtFvNodePortAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping maint_RtMaintFwinstlsrc_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping isis_RsNhAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping mgmt_RsRtdMgmtConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping mgmt_RtRtdMgmtConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping snmp_RsCommSecPClientGrpAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping snmp_RsCommToCtxAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Operational state
        // Type is an MO-Defined-Type
        leaf operSt {
            config "false";
            description "Operational State";

            // Type is an MO-Defined-Type
            type nw_OSSum;
        }

        // Operational state qualifier
        // Type is an MO-Defined-Type
        leaf operStQual {
            config "false";
            description "Operational State Qualifier";

            // Type is an MO-Defined-Type
            type nw_OSSumQual;
        }
    }

    grouping ospf_RtOspfIfDefToOspfIf_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping ospf_RtOspfIfDefToOspfv3If_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping comm_RtCommKeyRing_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping aaa_RtAaaUserEp_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aaa_RtAaaLoginDomain_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aaa_RtPreLoginBanner_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aaa_RtAaaKeyringRef_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RsVtepAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RtAggregateVtepAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RsVlanMemberAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RtAggregateVlanMemberAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RsMac_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RtMac_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RsVpcIntfEntryAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping aggregate_RtVpcIntfEntryAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping actrl_RsRfltpConn_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping actrl_RsTenConn_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping actrl_RtTenConn_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping analytics_RsRecordPAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping analytics_RsCollectorAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping analytics_RsProfAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping analytics_RsPolicyAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping epm_RsMacEpToIpEpAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping eptrk_RsIpEpRslttoIpEpAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping eptrk_RtIpEpRslttoIpEpAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping eptrk_RsMacEpRslttoIpEpAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping eptrk_RtMacEpRslttoIpEpAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping ipqos_RsPolicyInstToPMap_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping ipqos_RtIpqosPolicyInstToPMap_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping ipqos_RsClassMapToPolicyMap_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping ipqos_RtClassMapToPolicyMap_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsRecord_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsExporter1_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsExporter2_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsMonitor_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsHwProfile_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping flow_RsPmap_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping sts_RsNodeAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping telemetry_RsSensorGroupRel_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
        leaf sampleIntvl {
            type uint64;
        }
    }

    grouping telemetry_RsDestGroupRel_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping ethpm_RsErrDisRecoverPolCons_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping pc_RsMbrIfs_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // channel-group force
        // Type is an MO-Defined-Type
        leaf isMbrForce {
            description "Channel group force";

            // Type is an MO-Defined-Type
            type pc_ChnlGrpForce;
        }
    }

    grouping pc_RtMbrIfs_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping pc_RsLacpPolCons_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping vlan_RsVlanEppAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Represents state of the relationship
        // Inherited From reln:To
        // Type is an MO-Defined-Type
        leaf state {
            config "false";
            description "State";

            // Type is an MO-Defined-Type
            type reln_State;
        }

        // Represents state qualifier of the relationship
        // Inherited From reln:To
        // Type is an MO-Defined-Type
        leaf stateQual {
            config "false";
            description "State Qualifier";

            // Type is an MO-Defined-Type
            type reln_StateQual;
        }

        // Represents the type of the target
        // - Name based resolution
        // - Explicit resolution
        // Inherited From reln:To
        // Type is an MO-Defined-Type
        leaf tType {
            config "false";
            description "TBD";

            // Type is an MO-Defined-Type
            type reln_TargetType;
        }

        // Represents the type of the Resolver
        // - Mo
        // - Service
        // - Local Shard
        // Inherited From reln:To
        // Type is an MO-Defined-Type
        leaf rType {
            config "false";
            description "TBD";

            // Type is an MO-Defined-Type
            type reln_ResolverType;
        }
        leaf forceResolve {
            config "false";
            type boolean;
            default "true";
        }
    }

    grouping vxlan_RsVxlanEppAtt_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Represents state of the relationship
        // Inherited From reln:To
        // Type is an MO-Defined-Type
        leaf state {
            config "false";
            description "State";

            // Type is an MO-Defined-Type
            type reln_State;
        }

        // Represents state qualifier of the relationship
        // Inherited From reln:To
        // Type is an MO-Defined-Type
        leaf stateQual {
            config "false";
            description "State Qualifier";

            // Type is an MO-Defined-Type
            type reln_StateQual;
        }

        // Represents the type of the target
        // - Name based resolution
        // - Explicit resolution
        // Inherited From reln:To
        // Type is an MO-Defined-Type
        leaf tType {
            config "false";
            description "TBD";

            // Type is an MO-Defined-Type
            type reln_TargetType;
        }

        // Represents the type of the Resolver
        // - Mo
        // - Service
        // - Local Shard
        // Inherited From reln:To
        // Type is an MO-Defined-Type
        leaf rType {
            config "false";
            description "TBD";

            // Type is an MO-Defined-Type
            type reln_ResolverType;
        }
        leaf forceResolve {
            config "false";
            type boolean;
            default "true";
        }
    }

    grouping nvo_RsOperSourceInterface_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping nvo_RtOperSourceInterface_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping nvo_RsVni_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }

        // Represents state of the relationship
        // Inherited From reln:To
        // Type is an MO-Defined-Type
        leaf state {
            config "false";
            description "State";

            // Type is an MO-Defined-Type
            type reln_State;
        }

        // Represents state qualifier of the relationship
        // Inherited From reln:To
        // Type is an MO-Defined-Type
        leaf stateQual {
            config "false";
            description "State Qualifier";

            // Type is an MO-Defined-Type
            type reln_StateQual;
        }

        // Represents the type of the target
        // - Name based resolution
        // - Explicit resolution
        // Inherited From reln:To
        // Type is an MO-Defined-Type
        leaf tType {
            config "false";
            description "TBD";

            // Type is an MO-Defined-Type
            type reln_TargetType;
        }

        // Represents the type of the Resolver
        // - Mo
        // - Service
        // - Local Shard
        // Inherited From reln:To
        // Type is an MO-Defined-Type
        leaf rType {
            config "false";
            description "TBD";

            // Type is an MO-Defined-Type
            type reln_ResolverType;
        }
        leaf forceResolve {
            config "false";
            type boolean;
            default "true";
        }
    }

    grouping nvo_RtVni_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping l3_RsCtxToEpP_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l3_RsVrfMbr_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l3_RtVrfMbr_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l3_RsPhysRtdConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l3_RtPhysRtdConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l3_RsProtLbIf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Interface Mode
        // Type is an MO-Defined-Type
        leaf mode {
            description "TBD";

            // Type is an MO-Defined-Type
            type ip_IfMode;
        }
    }

    grouping l3_RsLbIfToLocale_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l3_RsLbIfToOutRef_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping l3_RsEncPhysRtdConf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping l3_RtL3EncPhysRtdConf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping uribv4_RsRouteOwnerToNexthopAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping nw_RsPathToIf_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping nw_RtNwPathToIf_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRegCommAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRegCommAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsExtCommAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtExtCommAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtDstAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtDstAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtDstV6Att_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtDstV6Att_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtNhAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtNhAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtNhV6Att_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtNhV6Att_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtSrcAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtSrcAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtSrcV6Att_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtSrcV6Att_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping rtmap_RsRtAsPathAccAtt_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }

        // Represents state of the relationship
        // Inherited From reln:To
        // Type is an MO-Defined-Type
        leaf state {
            description "State";

            // Type is an MO-Defined-Type
            type reln_State;
        }

        // Represents state qualifier of the relationship
        // Inherited From reln:To
        // Type is an MO-Defined-Type
        leaf stateQual {
            description "State Qualifier";

            // Type is an MO-Defined-Type
            type reln_StateQual;
        }

        // Represents the type of the target
        // - Name based resolution
        // - Explicit resolution
        // Inherited From reln:To
        // Type is an MO-Defined-Type
        leaf tType {
            description "TBD";

            // Type is an MO-Defined-Type
            type reln_TargetType;
        }

        // Represents the type of the Resolver
        // - Mo
        // - Service
        // - Local Shard
        // Inherited From reln:To
        // Type is an MO-Defined-Type
        leaf rType {
            description "TBD";

            // Type is an MO-Defined-Type
            type reln_ResolverType;
        }
        leaf forceResolve {
            type boolean;
            default "true";
        }
    }

    grouping rtmap_RtRtmapRtAsPathAccAtt_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping tunnel_RsTunnelMbrIfs_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping tunnel_RtTunnelTunnelMbrIfs_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping tunnel_RsTunnelToLooseNode_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping tunnel_RtTunnelTunnelToLooseNode_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping eqpt_RsPsuInstPolCons_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping leqpt_RsLsNodeToIf_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping leqpt_RtLsNodeToIf_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping leqpt_RsLsAttLink_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping bfd_RsMbrSess_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping pim_RsRP2Grange_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping synthetic_RsToObj_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping synthetic_RtToObj_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping cnw_RsMbrIfs_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping cnw_RtMbrIfs_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping cnw_RsActiveIf_source-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping cnw_RtActiveIf_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping vns_RtVnsConnToFltInst_target-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping vz_RtVzFwdRFltPAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping vz_RtVzRevRFltPAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping vz_RtVzTabooRFltAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping vz_RtVzRFltAtt_target-group {

        // Target Object's DN
        // Inherited From reln:Inst
        // Type is an MO-Defined-Type
        leaf tDn {
            config "false";
            description "Target-dn";

            // Type is an MO-Defined-Type
            type reln_Dn;
        }

        // Target Object's ClassId
        // Inherited From reln:Inst
        // Type is an MO-Defined-Type
        leaf tCl {
            config "false";
            description "Target-class";

            // Type is an MO-Defined-Type
            type reln_ClassId;
        }
    }

    grouping action_RsLSubjToDomainRef_source-group {

        // Target Object's DN
        // Inherited From reln:Inst
        // Type is an MO-Defined-Type
        leaf tDn {
            description "Target-dn";

            // Type is an MO-Defined-Type
            type reln_Dn;
        }

        // Target Object's ClassId
        // Inherited From reln:Inst
        // Type is an MO-Defined-Type
        leaf tCl {
            description "Target-class";

            // Type is an MO-Defined-Type
            type reln_ClassId;
        }
    }

    grouping datetime_Statistics-group {
        leaf timeReceived {
            config "false";
            type uint32;
        }
        leaf timeToSend {
            config "false";
            type uint32;
        }
        leaf timeReachable {
            config "false";
            type uint32;
        }
        leaf numberSent {
            config "false";
            type uint32;
        }
        leaf numberProcessed {
            config "false";
            type uint32;
        }
        leaf badAuth {
            config "false";
            type uint32;
        }
        leaf bogusOrg {
            config "false";
            type uint32;
        }
        leaf duplicate {
            config "false";
            type uint32;
        }
        leaf badDispersion {
            config "false";
            type uint32;
        }
        leaf badRefTime {
            config "false";
            type uint32;
        }
        leaf candidateOrder {
            config "false";
            type uint8;
        }
    }

    grouping l2_VlanStats-group {
        leaf inUcastOctets {
            config "false";
            type uint64;
        }
        leaf inUcastPkts {
            config "false";
            type uint64;
        }
        leaf inMcastOctets {
            config "false";
            type uint64;
        }
        leaf inMcastPkts {
            config "false";
            type uint64;
        }
        leaf inBcastOctets {
            config "false";
            type uint64;
        }
        leaf inBcastPkts {
            config "false";
            type uint64;
        }
        leaf inL3UcastOctets {
            config "false";
            type uint64;
        }
        leaf inL3UcastPkts {
            config "false";
            type uint64;
        }
        leaf outUcastOctets {
            config "false";
            type uint64;
        }
        leaf outUcastPkts {
            config "false";
            type uint64;
        }
    }

    grouping ac_IngrHit-group {
        leaf fwdPkts {
            config "false";
            type uint64;
        }
        leaf fwdBytes {
            config "false";
            type uint64;
        }
        leaf dropPkts {
            config "false";
            type uint64;
        }
        leaf dropBytes {
            config "false";
            type uint64;
        }
    }

    grouping ac_EgrHit-group {
        leaf fwdPkts {
            config "false";
            type uint64;
        }
        leaf fwdBytes {
            config "false";
            type uint64;
        }
        leaf dropPkts {
            config "false";
            type uint64;
        }
        leaf dropBytes {
            config "false";
            type uint64;
        }
    }

    grouping rmon_IfIn-group {
        leaf octets {
            config "false";
            type uint64;
        }
        leaf ucastPkts {
            config "false";
            type uint64;
        }
        leaf nUcastPkts {
            config "false";
            type uint64;
        }
        leaf discards {
            config "false";
            type uint64;
        }
        leaf errors {
            config "false";
            type uint64;
        }
        leaf unknownProtos {
            config "false";
            type uint64;
        }
        leaf unknownEtype {
            config "false";
            type uint64;
        }
        leaf broadcastPkts {
            config "false";
            type uint64;
        }
        leaf multicastPkts {
            config "false";
            type uint64;
        }
        leaf noBuffer {
            config "false";
            type uint64;
        }
        leaf rateInterval {
            config "false";
            type uint32;
        }
        leaf octetRate {
            config "false";
            type uint64;
        }
        leaf packetRate {
            config "false";
            type uint64;
        }
    }

    grouping rmon_IfOut-group {
        leaf octets {
            config "false";
            type uint64;
        }
        leaf ucastPkts {
            config "false";
            type uint64;
        }
        leaf nUcastPkts {
            config "false";
            type uint64;
        }
        leaf discards {
            config "false";
            type uint64;
        }
        leaf errors {
            config "false";
            type uint64;
        }
        leaf qLen {
            config "false";
            type uint64;
        }
        leaf broadcastPkts {
            config "false";
            type uint64;
        }
        leaf multicastPkts {
            config "false";
            type uint64;
        }
        leaf rateInterval {
            config "false";
            type uint32;
        }
        leaf octetRate {
            config "false";
            type uint64;
        }
        leaf packetRate {
            config "false";
            type uint64;
        }
    }

    grouping rmon_IpIn-group {
        leaf receives {
            config "false";
            type uint64;
        }
        leaf hdrErrors {
            config "false";
            type uint64;
        }
        leaf forwDatagrams {
            config "false";
            type uint64;
        }
        leaf discards {
            config "false";
            type uint64;
        }
    }

    grouping rmon_Dot1d-group {
        leaf basePortDelayExceededDiscards {
            config "false";
            type uint64;
        }
        leaf basePortMtuExceededDiscards {
            config "false";
            type uint64;
        }
        leaf tpPortInFrames {
            config "false";
            type uint64;
        }
        leaf tpPortOutFrames {
            config "false";
            type uint64;
        }
        leaf portInDiscards {
            config "false";
            type uint64;
        }
    }

    grouping rmon_EtherStats-group {
        leaf dropEvents {
            config "false";
            type uint64;
        }
        leaf multicastPkts {
            config "false";
            type uint64;
        }
        leaf broadcastPkts {
            config "false";
            type uint64;
        }
        leaf undersizePkts {
            config "false";
            type uint64;
        }
        leaf fragments {
            config "false";
            type uint64;
        }
        leaf pkts64Octets {
            config "false";
            type uint64;
        }
        leaf pkts65to127Octets {
            config "false";
            type uint64;
        }
        leaf pkts128to255Octets {
            config "false";
            type uint64;
        }
        leaf pkts256to511Octets {
            config "false";
            type uint64;
        }
        leaf pkts512to1023Octets {
            config "false";
            type uint64;
        }
        leaf pkts1024to1518Octets {
            config "false";
            type uint64;
        }
        leaf oversizePkts {
            config "false";
            type uint64;
        }
        leaf jabbers {
            config "false";
            type uint64;
        }
        leaf octets {
            config "false";
            type uint64;
        }
        leaf pkts {
            config "false";
            type uint64;
        }
        leaf collisions {
            config "false";
            type uint64;
        }
        leaf cRCAlignErrors {
            config "false";
            type uint64;
        }
        leaf tXNoErrors {
            config "false";
            type uint64;
        }
        leaf rXNoErrors {
            config "false";
            type uint64;
        }
        leaf rxOversizePkts {
            config "false";
            type uint64;
        }
        leaf txOversizePkts {
            config "false";
            type uint64;
        }
        leaf overrun {
            config "false";
            type uint64;
        }
        leaf underrun {
            config "false";
            type uint64;
        }
        leaf ignored {
            config "false";
            type uint64;
        }
        leaf watchdog {
            config "false";
            type uint64;
        }
        leaf ifdowndrop {
            config "false";
            type uint64;
        }
    }

    grouping rmon_Dot3Stats-group {
        leaf alignmentErrors {
            config "false";
            type uint64;
        }
        leaf fCSErrors {
            config "false";
            type uint64;
        }
        leaf singleCollisionFrames {
            config "false";
            type uint64;
        }
        leaf multipleCollisionFrames {
            config "false";
            type uint64;
        }
        leaf sQETTestErrors {
            config "false";
            type uint64;
        }
        leaf deferredTransmissions {
            config "false";
            type uint64;
        }
        leaf lateCollisions {
            config "false";
            type uint64;
        }
        leaf excessiveCollisions {
            config "false";
            type uint64;
        }
        leaf internalMacTransmitErrors {
            config "false";
            type uint64;
        }
        leaf carrierSenseErrors {
            config "false";
            type uint64;
        }
        leaf frameTooLongs {
            config "false";
            type uint64;
        }
        leaf internalMacReceiveErrors {
            config "false";
            type uint64;
        }
        leaf symbolErrors {
            config "false";
            type uint64;
        }
        leaf controlInUnknownOpcodes {
            config "false";
            type uint64;
        }
        leaf inPauseFrames {
            config "false";
            type uint64;
        }
        leaf outPauseFrames {
            config "false";
            type uint64;
        }
        leaf lostCarrierErrors {
            config "false";
            type uint64;
        }
        leaf noCarrierErrors {
            config "false";
            type uint64;
        }
        leaf inputdribble {
            config "false";
            type uint64;
        }
        leaf babble {
            config "false";
            type uint64;
        }
        leaf runts {
            config "false";
            type uint64;
        }
    }

    grouping rmon_IfHCIn-group {
        leaf octets {
            config "false";
            type uint64;
        }
        leaf ucastPkts {
            config "false";
            type uint64;
        }
        leaf multicastPkts {
            config "false";
            type uint64;
        }
        leaf broadcastPkts {
            config "false";
            type uint64;
        }
    }

    grouping rmon_IfHCOut-group {
        leaf octets {
            config "false";
            type uint64;
        }
        leaf ucastPkts {
            config "false";
            type uint64;
        }
        leaf multicastPkts {
            config "false";
            type uint64;
        }
        leaf broadcastPckts {
            config "false";
            type uint64;
        }
        leaf broadcastPkts {
            config "false";
            type uint64;
        }
    }

    grouping rmon_Ipv6IfStats-group {
        leaf inReceives {
            config "false";
            type uint64;
        }
        leaf inHdrErrors {
            config "false";
            type uint64;
        }
        leaf inAddrErrors {
            config "false";
            type uint64;
        }
        leaf inDiscards {
            config "false";
            type uint64;
        }
        leaf outForwDatagrams {
            config "false";
            type uint64;
        }
        leaf outDiscards {
            config "false";
            type uint64;
        }
        leaf inMcastPkts {
            config "false";
            type uint64;
        }
        leaf outMcastPkts {
            config "false";
            type uint64;
        }
    }

    grouping rmon_IfStorm-group {
        leaf dropBytes {
            config "false";
            type uint64;
        }
    }

    grouping tunnel_IngrTep-group {
        leaf fwdPkts {
            config "false";
            type uint64;
        }
        leaf fwdBytes {
            config "false";
            type uint64;
        }
        leaf dropPkts {
            config "false";
            type uint64;
        }
        leaf dropBytes {
            config "false";
            type uint64;
        }
    }

    grouping tunnel_EgrTep-group {
        leaf fwdPkts {
            config "false";
            type uint64;
        }
        leaf fwdBytes {
            config "false";
            type uint64;
        }
        leaf dropPkts {
            config "false";
            type uint64;
        }
        leaf dropBytes {
            config "false";
            type uint64;
        }
    }

    container System {
        description "System";

        uses System-group;
    }
}
