module cisco-nx-openconfig-bfd-deviations {

  namespace "http://openconfig.net/yang/bfd-deviations";

  prefix "oc-bfd-devs";


  import ietf-inet-types { prefix inet; }
  import ietf-interfaces { prefix if; }
  import ietf-yang-types { prefix yang; }
  import openconfig-bfd { prefix oc-bfd; }
  import openconfig-extensions { prefix oc-ext; }
  import openconfig-inet-types { prefix oc-inet; }
  import openconfig-interfaces { prefix oc-if; }
  import openconfig-policy-types { prefix oc-pol-types; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-bfd module 
     set for Cisco NXOS.
     Copyright (c) 2015-2025 by Cisco Systems, Inc.
     All rights reserved.";

  revision 2025-12-12 {
    description
      "Deviation applicable to NXOS";
  }


  deviation /oc-bfd:bfd/oc-bfd:interfaces/oc-bfd:interface/oc-bfd:config/oc-bfd:desired-minimum-tx-interval {
    deviate add {
            default "50000";
        }
        deviate replace {
            type uint32 {
                range "10000..999000";
            }
        }
  }

  deviation /oc-bfd:bfd/oc-bfd:interfaces/oc-bfd:interface/oc-bfd:config/oc-bfd:detection-multiplier {
    deviate add {
            default "3";
        }
        deviate replace {
            type uint8 {
                range "1..50";
            }
        }
  }

  deviation /oc-bfd:bfd/oc-bfd:interfaces/oc-bfd:interface/oc-bfd:config/oc-bfd:enabled {
    deviate add {
            default "true";
        }
  }

  deviation /oc-bfd:bfd/oc-bfd:interfaces/oc-bfd:interface/oc-bfd:config/oc-bfd:required-minimum-receive {
    deviate add {
            default "50000";
        }
        deviate replace {
            type uint32 {
                range "10000..999000";
            }
        }
  }

  deviation /oc-bfd:bfd/oc-bfd:interfaces/oc-bfd:interface/oc-bfd:interface-ref/oc-bfd:config/oc-bfd:interface {
    //! NOTE_FEATURE_EXIST TRUE
    //! NOTE_DME_DONE      TRUE
    //! NOTE_COMMENT       ""
    deviate not-supported;
  }

  deviation /oc-bfd:bfd/oc-bfd:interfaces/oc-bfd:interface/oc-bfd:interface-ref/oc-bfd:config/oc-bfd:subinterface {
    //! NOTE_FEATURE_EXIST TRUE
    //! NOTE_DME_DONE      TRUE
    //! NOTE_COMMENT       ""
    deviate not-supported;
  }

  deviation /oc-bfd:bfd/oc-bfd:interfaces/oc-bfd:interface/oc-bfd:interface-ref/oc-bfd:state/oc-bfd:interface {
    //! NOTE_FEATURE_EXIST TRUE
    //! NOTE_DME_DONE      TRUE
    //! NOTE_COMMENT       ""
    deviate not-supported;
  }

  deviation /oc-bfd:bfd/oc-bfd:interfaces/oc-bfd:interface/oc-bfd:interface-ref/oc-bfd:state/oc-bfd:subinterface {
    //! NOTE_FEATURE_EXIST TRUE
    //! NOTE_DME_DONE      TRUE
    //! NOTE_COMMENT       ""
    deviate not-supported;
  }

  deviation /oc-bfd:bfd/oc-bfd:interfaces/oc-bfd:interface/oc-bfd:micro-bfd-sessions/oc-bfd:micro-bfd-session/oc-bfd:config/oc-bfd:local-address {
    //! NOTE_FEATURE_EXIST TRUE
    //! NOTE_DME_DONE      TRUE
    //! NOTE_COMMENT       ""
    deviate not-supported;
  }

  deviation /oc-bfd:bfd/oc-bfd:interfaces/oc-bfd:interface/oc-bfd:micro-bfd-sessions/oc-bfd:micro-bfd-session/oc-bfd:config/oc-bfd:member-interface {
    //! NOTE_FEATURE_EXIST TRUE
    //! NOTE_DME_DONE      TRUE
    //! NOTE_COMMENT       ""
    deviate not-supported;
  }

  deviation /oc-bfd:bfd/oc-bfd:interfaces/oc-bfd:interface/oc-bfd:micro-bfd-sessions/oc-bfd:micro-bfd-session/oc-bfd:state/oc-bfd:remote-control-plane-independent {
    //! NOTE_FEATURE_EXIST TRUE
    //! NOTE_DME_DONE      TRUE
    //! NOTE_COMMENT       ""
    deviate not-supported;
  }

  deviation /oc-bfd:bfd/oc-bfd:interfaces/oc-bfd:interface/oc-bfd:peers/oc-bfd:peer/oc-bfd:state/oc-bfd:remote-control-plane-independent {
    //! NOTE_FEATURE_EXIST TRUE
    //! NOTE_DME_DONE      TRUE
    //! NOTE_COMMENT       ""
    deviate not-supported;
  }


}
