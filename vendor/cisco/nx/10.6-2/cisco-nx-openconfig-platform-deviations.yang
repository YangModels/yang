module cisco-nx-openconfig-platform-deviations {

  namespace "http://openconfig.net/yang/platform-deviations";

  prefix "oc-platform-devs";


  import openconfig-alarm-types { prefix oc-alarm-types; }
  import openconfig-extensions { prefix oc-ext; }
  import openconfig-platform-types { prefix oc-platform-types; }
  import openconfig-platform { prefix oc-platform; }
  import openconfig-types { prefix oc-types; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-platform module 
     set for Cisco NXOS.
     Copyright (c) 2015-2025 by Cisco Systems, Inc.
     All rights reserved.";

  revision 2025-12-12 {
    description
      "Deviation applicable to NXOS";
  }


  deviation /oc-platform:components/oc-platform:component/oc-platform:chassis/oc-platform:utilization/oc-platform:resources/oc-platform:resource {
    //! NOTE_FEATURE_EXIST TRUE
    //! NOTE_DME_DONE      TRUE
    //! NOTE_COMMENT       ""
    deviate not-supported;
  }

  deviation /oc-platform:components/oc-platform:component/oc-platform:config/oc-platform:name {
    //! NOTE_FEATURE_EXIST TRUE
    //! NOTE_DME_DONE      TRUE
    //! NOTE_COMMENT       ""
    deviate not-supported;
  }

  deviation /oc-platform:components/oc-platform:component/oc-platform:integrated-circuit/oc-platform:utilization/oc-platform:resources/oc-platform:resource {
    //! NOTE_FEATURE_EXIST TRUE
    //! NOTE_DME_DONE      TRUE
    //! NOTE_COMMENT       ""
    deviate not-supported;
  }

  deviation /oc-platform:components/oc-platform:component/oc-platform:properties/oc-platform:property {
    //! NOTE_FEATURE_EXIST TRUE
    //! NOTE_DME_DONE      TRUE
    //! NOTE_COMMENT       ""
    deviate not-supported;
  }

  deviation /oc-platform:components/oc-platform:component/oc-platform:state/oc-platform:base-mac-address {
    //! NOTE_FEATURE_EXIST TRUE
    //! NOTE_DME_DONE      TRUE
    //! NOTE_COMMENT       ""
    deviate not-supported;
  }

  deviation /oc-platform:components/oc-platform:component/oc-platform:state/oc-platform:clei-code {
    //! NOTE_FEATURE_EXIST TRUE
    //! NOTE_DME_DONE      TRUE
    //! NOTE_COMMENT       ""
    deviate not-supported;
  }

  deviation /oc-platform:components/oc-platform:component/oc-platform:state/oc-platform:firmware-version {
    //! NOTE_FEATURE_EXIST TRUE
    //! NOTE_DME_DONE      TRUE
    //! NOTE_COMMENT       ""
    deviate not-supported;
  }

  deviation /oc-platform:components/oc-platform:component/oc-platform:state/oc-platform:last-reboot-reason {
    //! NOTE_FEATURE_EXIST TRUE
    //! NOTE_DME_DONE      TRUE
    //! NOTE_COMMENT       ""
    deviate not-supported;
  }

  deviation /oc-platform:components/oc-platform:component/oc-platform:state/oc-platform:last-reboot-time {
    //! NOTE_FEATURE_EXIST TRUE
    //! NOTE_DME_DONE      TRUE
    //! NOTE_COMMENT       ""
    deviate not-supported;
  }

  deviation /oc-platform:components/oc-platform:component/oc-platform:state/oc-platform:last-switchover-reason/oc-platform:details {
    //! NOTE_FEATURE_EXIST TRUE
    //! NOTE_DME_DONE      TRUE
    //! NOTE_COMMENT       ""
    deviate not-supported;
  }

  deviation /oc-platform:components/oc-platform:component/oc-platform:state/oc-platform:last-switchover-reason/oc-platform:trigger {
    //! NOTE_FEATURE_EXIST TRUE
    //! NOTE_DME_DONE      TRUE
    //! NOTE_COMMENT       ""
    deviate not-supported;
  }

  deviation /oc-platform:components/oc-platform:component/oc-platform:state/oc-platform:last-switchover-time {
    //! NOTE_FEATURE_EXIST TRUE
    //! NOTE_DME_DONE      TRUE
    //! NOTE_COMMENT       ""
    deviate not-supported;
  }

  deviation /oc-platform:components/oc-platform:component/oc-platform:state/oc-platform:parent {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:advisory-non-fatal-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:bad-dllp-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:bad-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:hdr-log-overflow-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:internal-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:receiver-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:relay-rollover-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:replay-timeout-errors {
    //! NOTE_FEATURE_EXIST TRUE
    //! NOTE_DME_DONE      TRUE
    //! NOTE_COMMENT       ""
    deviate not-supported;
  }

  deviation /oc-platform:components/oc-platform:component/oc-platform:state/oc-platform:pcie/oc-platform:correctable-errors/oc-platform:total-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:acs-violation-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:atomic-op-blocked-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:blocked-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:completion-abort-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:completion-timeout-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:data-link-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:ecrc-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:flow-control-protocol-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:internal-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:malformed-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:poisoned-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:receiver-overflow-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:surprise-down-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:tlp-prefix-blocked-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:total-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:undefined-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:unexpected-completion-errors {
    //! NOTE_FEATURE_EXIST TRUE
    //! NOTE_DME_DONE      TRUE
    //! NOTE_COMMENT       ""
    deviate not-supported;
  }

  deviation /oc-platform:components/oc-platform:component/oc-platform:state/oc-platform:pcie/oc-platform:fatal-errors/oc-platform:unsupported-request-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:acs-violation-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:atomic-op-blocked-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:blocked-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:completion-abort-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:completion-timeout-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:data-link-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:ecrc-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:flow-control-protocol-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:internal-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:malformed-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:poisoned-tlp-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:receiver-overflow-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:surprise-down-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:tlp-prefix-blocked-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:total-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:undefined-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:unexpected-completion-errors {
    //! NOTE_FEATURE_EXIST TRUE
    //! NOTE_DME_DONE      TRUE
    //! NOTE_COMMENT       ""
    deviate not-supported;
  }

  deviation /oc-platform:components/oc-platform:component/oc-platform:state/oc-platform:pcie/oc-platform:non-fatal-errors/oc-platform:unsupported-request-errors {
    //! NOTE_FEATURE_EXIST TRUE
    //! NOTE_DME_DONE      TRUE
    //! NOTE_COMMENT       ""
    deviate not-supported;
  }

  deviation /oc-platform:components/oc-platform:component/oc-platform:state/oc-platform:redundant-role {
    //! NOTE_FEATURE_EXIST TRUE
    //! NOTE_DME_DONE      TRUE
    //! NOTE_COMMENT       ""
    deviate not-supported;
  }

  deviation /oc-platform:components/oc-platform:component/oc-platform:state/oc-platform:switchover-ready {
    //! NOTE_FEATURE_EXIST TRUE
    //! NOTE_DME_DONE      TRUE
    //! NOTE_COMMENT       ""
    deviate not-supported;
  }

  deviation /oc-platform:components/oc-platform:component/oc-platform:state/oc-platform:temperature/oc-platform:avg {
    //! NOTE_FEATURE_EXIST TRUE
    //! NOTE_DME_DONE      TRUE
    //! NOTE_COMMENT       ""
    deviate not-supported;
  }

  deviation /oc-platform:components/oc-platform:component/oc-platform:state/oc-platform:temperature/oc-platform:interval {
    //! NOTE_FEATURE_EXIST TRUE
    //! NOTE_DME_DONE      TRUE
    //! NOTE_COMMENT       ""
    deviate not-supported;
  }

  deviation /oc-platform:components/oc-platform:component/oc-platform:state/oc-platform:temperature/oc-platform:max {
    //! NOTE_FEATURE_EXIST TRUE
    //! NOTE_DME_DONE      TRUE
    //! NOTE_COMMENT       ""
    deviate not-supported;
  }

  deviation /oc-platform:components/oc-platform:component/oc-platform:state/oc-platform:temperature/oc-platform:max-time {
    //! NOTE_FEATURE_EXIST TRUE
    //! NOTE_DME_DONE      TRUE
    //! NOTE_COMMENT       ""
    deviate not-supported;
  }

  deviation /oc-platform:components/oc-platform:component/oc-platform:state/oc-platform:temperature/oc-platform:min {
    //! NOTE_FEATURE_EXIST TRUE
    //! NOTE_DME_DONE      TRUE
    //! NOTE_COMMENT       ""
    deviate not-supported;
  }

  deviation /oc-platform:components/oc-platform:component/oc-platform:state/oc-platform:temperature/oc-platform:min-time {
    //! NOTE_FEATURE_EXIST TRUE
    //! NOTE_DME_DONE      TRUE
    //! NOTE_COMMENT       ""
    deviate not-supported;
  }

  deviation /oc-platform:components/oc-platform:component/oc-platform:subcomponents/oc-platform:subcomponent {
    //! NOTE_FEATURE_EXIST TRUE
    //! NOTE_DME_DONE      TRUE
    //! NOTE_COMMENT       ""
    deviate not-supported;
  }


}
