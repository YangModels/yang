module cisco-nx-openconfig-network-instance-deviations {

  namespace "http://openconfig.net/yang/network-instance-deviations";

  prefix "oc-netinst-devs";


  import iana-if-type { prefix ianaift; }
  import ietf-inet-types { prefix inet; }
  import ietf-interfaces { prefix if; }
  import ietf-yang-types { prefix yang; }
  import openconfig-acl { prefix oc-acl; }
  import openconfig-aft-types { prefix oc-aftt; }
  import openconfig-aft { prefix oc-aft; }
  import openconfig-bfd { prefix oc-bfd; }
  import openconfig-bgp-types { prefix oc-bgp-types; }
  import openconfig-bgp { prefix oc-bgp; }
  import openconfig-defined-sets { prefix oc-sets; }
  import openconfig-evpn-types { prefix oc-evpn-types; }
  import openconfig-evpn { prefix oc-evpn; }
  import openconfig-extensions { prefix oc-ext; }
  import openconfig-if-aggregate { prefix oc-lag; }
  import openconfig-if-ethernet { prefix oc-eth; }
  import openconfig-igmp-types { prefix oc-igmp-types; }
  import openconfig-igmp { prefix oc-igmp; }
  import openconfig-inet-types { prefix oc-inet; }
  import openconfig-interfaces { prefix oc-if; }
  import openconfig-isis-lsdb-types { prefix oc-isis-lsdb-types; }
  import openconfig-isis-types { prefix oc-isis-types; }
  import openconfig-isis { prefix oc-isis; }
  import openconfig-keychain-types { prefix oc-keychain-types; }
  import openconfig-keychain { prefix oc-keychain; }
  import openconfig-local-routing { prefix oc-loc-rt; }
  import openconfig-mpls-ldp { prefix oc-ldp; }
  import openconfig-mpls-rsvp { prefix oc-rsvp; }
  import openconfig-mpls-sr { prefix oc-mpls-sr; }
  import openconfig-mpls-types { prefix oc-mplst; }
  import openconfig-mpls { prefix oc-mpls; }
  import openconfig-network-instance-l3 { prefix oc-ni-l3; }
  import openconfig-network-instance-types { prefix oc-ni-types; }
  import openconfig-network-instance { prefix oc-netinst; }
  import openconfig-ospf-types { prefix oc-ospf-types; }
  import openconfig-ospfv2 { prefix oc-ospfv2; }
  import openconfig-packet-match-types { prefix oc-pkt-match-types; }
  import openconfig-packet-match { prefix oc-pkt-match; }
  import openconfig-pcep { prefix oc-pcep; }
  import openconfig-pim-types { prefix oc-pim-types; }
  import openconfig-pim { prefix oc-pim; }
  import openconfig-policy-forwarding { prefix oc-pf; }
  import openconfig-policy-types { prefix oc-pol-types; }
  import openconfig-rib-bgp-types { prefix oc-bgprib-types; }
  import openconfig-rib-bgp { prefix oc-rib-bgp; }
  import openconfig-routing-policy { prefix oc-rpol; }
  import openconfig-segment-routing-types { prefix oc-srt; }
  import openconfig-segment-routing { prefix oc-sr; }
  import openconfig-srte-policy { prefix oc-srte; }
  import openconfig-types { prefix oc-types; }
  import openconfig-vlan-types { prefix oc-vlan-types; }
  import openconfig-vlan { prefix oc-vlan; }
  import openconfig-yang-types { prefix oc-yang; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-network-instance module 
     set for Cisco NXOS.
     Copyright (c) 2015-2025 by Cisco Systems, Inc.
     All rights reserved.";

  revision 2025-12-12 {
    description
      "Deviation applicable to NXOS";
  }


  deviation /oc-netinst:network-instances/oc-netinst:network-instance/oc-netinst:afts/oc-netinst:ethernet/oc-netinst:mac-entry {
    //! NOTE_FEATURE_EXIST TRUE
    //! NOTE_DME_DONE      TRUE
    //! NOTE_COMMENT       ""
    deviate not-supported;
  }

  deviation /oc-netinst:network-instances/oc-netinst:network-instance/oc-netinst:afts/oc-netinst:ipv4-unicast/oc-netinst:ipv4-entry {
    //! NOTE_FEATURE_EXIST TRUE
    //! NOTE_DME_DONE      TRUE
    //! NOTE_COMMENT       ""
    deviate not-supported;
  }

  deviation /oc-netinst:network-instances/oc-netinst:network-instance/oc-netinst:afts/oc-netinst:ipv6-unicast/oc-netinst:ipv6-entry {
    //! NOTE_FEATURE_EXIST TRUE
    //! NOTE_DME_DONE      TRUE
    //! NOTE_COMMENT       ""
    deviate not-supported;
  }

  deviation /oc-netinst:network-instances/oc-netinst:network-instance/oc-netinst:afts/oc-netinst:mpls/oc-netinst:label-entry {
    //! NOTE_FEATURE_EXIST TRUE
    //! NOTE_DME_DONE      TRUE
    //! NOTE_COMMENT       ""
    deviate not-supported;
  }

  deviation /oc-netinst:network-instances/oc-netinst:network-instance/oc-netinst:afts/oc-netinst:next-hop-groups/oc-netinst:next-hop-group {
    //! NOTE_FEATURE_EXIST TRUE
    //! NOTE_DME_DONE      TRUE
    //! NOTE_COMMENT       ""
    deviate not-supported;
  }

  deviation /oc-netinst:network-instances/oc-netinst:network-instance/oc-netinst:afts/oc-netinst:next-hops/oc-netinst:next-hop {
    //! NOTE_FEATURE_EXIST TRUE
    //! NOTE_DME_DONE      TRUE
    //! NOTE_COMMENT       ""
    deviate not-supported;
  }

  deviation /oc-netinst:network-instances/oc-netinst:network-instance/oc-netinst:afts/oc-netinst:policy-forwarding/oc-netinst:policy-forwarding-entry {
    //! NOTE_FEATURE_EXIST TRUE
    //! NOTE_DME_DONE      TRUE
    //! NOTE_COMMENT       ""
    deviate not-supported;
  }

  deviation /oc-netinst:network-instances/oc-netinst:network-instance/oc-netinst:afts/oc-netinst:state-synced/oc-netinst:state/oc-netinst:ipv4-unicast {
    //! NOTE_FEATURE_EXIST TRUE
    //! NOTE_DME_DONE      TRUE
    //! NOTE_COMMENT       ""
    deviate not-supported;
  }

  deviation /oc-netinst:network-instances/oc-netinst:network-instance/oc-netinst:afts/oc-netinst:state-synced/oc-netinst:state/oc-netinst:ipv6-unicast {
    //! NOTE_FEATURE_EXIST TRUE
    //! NOTE_DME_DONE      TRUE
    //! NOTE_COMMENT       ""
    deviate not-supported;
  }

  deviation /oc-netinst:network-instances/oc-netinst:network-instance/oc-netinst:config/oc-netinst:fallback-network-instance {
    //! NOTE_FEATURE_EXIST TRUE
    //! NOTE_DME_DONE      TRUE
    //! NOTE_COMMENT       ""
    deviate not-supported;
  }

  deviation /oc-netinst:network-instances/oc-netinst:network-instance/oc-netinst:config/oc-netinst:router-id {
    //! NOTE_FEATURE_EXIST TRUE
    //! NOTE_DME_DONE      TRUE
    //! NOTE_COMMENT       ""
    deviate not-supported;
  }

  deviation /oc-netinst:network-instances/oc-netinst:network-instance/oc-netinst:connection-points/oc-netinst:connection-point {
    //! NOTE_FEATURE_EXIST TRUE
    //! NOTE_DME_DONE      TRUE
    //! NOTE_COMMENT       ""
    deviate not-supported;
  }

  deviation /oc-netinst:network-instances/oc-netinst:network-instance/oc-netinst:encapsulation/oc-netinst:config/oc-netinst:control-word {
    //! NOTE_FEATURE_EXIST TRUE
    //! NOTE_DME_DONE      TRUE
    //! NOTE_COMMENT       ""
    deviate not-supported;
  }

  deviation /oc-netinst:network-instances/oc-netinst:network-instance/oc-netinst:encapsulation/oc-netinst:config/oc-netinst:encapsulation-type {
    //! NOTE_FEATURE_EXIST TRUE
    //! NOTE_DME_DONE      TRUE
    //! NOTE_COMMENT       ""
    deviate not-supported;
  }

  deviation /oc-netinst:network-instances/oc-netinst:network-instance/oc-netinst:encapsulation/oc-netinst:config/oc-netinst:label-allocation-mode {
    //! NOTE_FEATURE_EXIST TRUE
    //! NOTE_DME_DONE      TRUE
    //! NOTE_COMMENT       ""
    deviate not-supported;
  }

  deviation /oc-netinst:network-instances/oc-netinst:network-instance/oc-netinst:encapsulation/oc-netinst:state/oc-netinst:control-word {
    //! NOTE_FEATURE_EXIST TRUE
    //! NOTE_DME_DONE      TRUE
    //! NOTE_COMMENT       ""
    deviate not-supported;
  }

  deviation /oc-netinst:network-instances/oc-netinst:network-instance/oc-netinst:encapsulation/oc-netinst:state/oc-netinst:encapsulation-type {
    //! NOTE_FEATURE_EXIST TRUE
    //! NOTE_DME_DONE      TRUE
    //! NOTE_COMMENT       ""
    deviate not-supported;
  }

  deviation /oc-netinst:network-instances/oc-netinst:network-instance/oc-netinst:encapsulation/oc-netinst:state/oc-netinst:label-allocation-mode {
    //! NOTE_FEATURE_EXIST TRUE
    //! NOTE_DME_DONE      TRUE
    //! NOTE_COMMENT       ""
    deviate not-supported;
  }

  deviation /oc-netinst:network-instances/oc-netinst:network-instance/oc-netinst:evpn/oc-netinst:ethernet-segments/oc-netinst:ethernet-segment {
    //! NOTE_FEATURE_EXIST TRUE
    //! NOTE_DME_DONE      TRUE
    //! NOTE_COMMENT       ""
    deviate not-supported;
  }

  deviation /oc-netinst:network-instances/oc-netinst:network-instance/oc-netinst:evpn/oc-netinst:evpn-instances/oc-netinst:evpn-instance {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:config/oc-netinst:arp-suppression {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:config/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:config/oc-netinst:enable {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:config/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:state/oc-netinst:arp-suppression {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:state/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:state/oc-netinst:enable {
    //! NOTE_FEATURE_EXIST TRUE
    //! NOTE_DME_DONE      TRUE
    //! NOTE_COMMENT       ""
    deviate not-supported;
  }

  deviation /oc-netinst:network-instances/oc-netinst:network-instance/oc-netinst:fdb/oc-netinst:arp-proxy/oc-netinst:state/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:config/oc-netinst:anycast-gateway-mac {
    //! NOTE_FEATURE_EXIST TRUE
    //! NOTE_DME_DONE      TRUE
    //! NOTE_COMMENT       ""
    deviate not-supported;
  }

  deviation /oc-netinst:network-instances/oc-netinst:network-instance/oc-netinst:fdb/oc-netinst:config/oc-netinst:flood-unknown-unicast-supression {
    //! NOTE_FEATURE_EXIST TRUE
    //! NOTE_DME_DONE      TRUE
    //! NOTE_COMMENT       ""
    deviate not-supported;
  }

  deviation /oc-netinst:network-instances/oc-netinst:network-instance/oc-netinst:fdb/oc-netinst:l2rib/oc-netinst:mac-ip-table/oc-netinst:entries/oc-netinst:entry {
    //! NOTE_FEATURE_EXIST TRUE
    //! NOTE_DME_DONE      TRUE
    //! NOTE_COMMENT       ""
    deviate not-supported;
  }

  deviation /oc-netinst:network-instances/oc-netinst:network-instance/oc-netinst:fdb/oc-netinst:l2rib/oc-netinst:mac-ip-table/oc-netinst:next-hops/oc-netinst:next-hop {
    //! NOTE_FEATURE_EXIST TRUE
    //! NOTE_DME_DONE      TRUE
    //! NOTE_COMMENT       ""
    deviate not-supported;
  }

  deviation /oc-netinst:network-instances/oc-netinst:network-instance/oc-netinst:fdb/oc-netinst:l2rib/oc-netinst:mac-table/oc-netinst:entries/oc-netinst:entry {
    //! NOTE_FEATURE_EXIST TRUE
    //! NOTE_DME_DONE      TRUE
    //! NOTE_COMMENT       ""
    deviate not-supported;
  }

  deviation /oc-netinst:network-instances/oc-netinst:network-instance/oc-netinst:fdb/oc-netinst:l2rib/oc-netinst:mac-table/oc-netinst:next-hops/oc-netinst:next-hop {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:config/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:config/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:config/oc-netinst:mac-mobility {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:config/oc-netinst:mac-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:config/oc-netinst:mac-mobility-window {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:state/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:state/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:state/oc-netinst:mac-mobility {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:state/oc-netinst:mac-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-mobility/oc-netinst:state/oc-netinst:mac-mobility-window {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-table/oc-netinst:entries/oc-netinst:entry/oc-netinst:config/oc-netinst:mac-address {
    deviate replace {
          type string {
            pattern '^[0-9A-F]{2}(:[0-9A-F]{2}){5}$';
          }
        }
  }

  deviation /oc-netinst:network-instances/oc-netinst:network-instance/oc-netinst:fdb/oc-netinst:mac-table/oc-netinst:entries/oc-netinst:entry/oc-netinst:interface/oc-netinst:interface-ref/oc-netinst:config/oc-netinst:subinterface {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-table/oc-netinst:entries/oc-netinst:entry/oc-netinst:state/oc-netinst:evi {
    //! NOTE_FEATURE_EXIST TRUE
    //! NOTE_DME_DONE      TRUE
    //! NOTE_COMMENT       ""
    deviate not-supported;
  }

  deviation /oc-netinst:network-instances/oc-netinst:network-instance/oc-netinst:fdb/oc-netinst:mac-table/oc-netinst:entries/oc-netinst:entry/oc-netinst:state/oc-netinst:mac-address {
    deviate replace {
          type string {
            pattern '^[0-9A-F]{2}(:[0-9A-F]{2}){5}$';
          }
        }
  }

  deviation /oc-netinst:network-instances/oc-netinst:network-instance/oc-netinst:fdb/oc-netinst:nd-proxy/oc-netinst:config/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:config/oc-netinst:enable {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:config/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:config/oc-netinst:nd-suppression {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:state/oc-netinst:duplicate-ip-detection-interval {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:state/oc-netinst:enable {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:state/oc-netinst:ip-mobility-threshold {
    //! NOTE_FEATURE_EXIST TRUE
    //! NOTE_DME_DONE      TRUE
    //! NOTE_COMMENT       ""
    deviate not-supported;
  }

  deviation /oc-netinst:network-instances/oc-netinst:network-instance/oc-netinst:fdb/oc-netinst:nd-proxy/oc-netinst:state/oc-netinst:nd-suppression {
    //! NOTE_FEATURE_EXIST TRUE
    //! NOTE_DME_DONE      TRUE
    //! NOTE_COMMENT       ""
    deviate not-supported;
  }

  deviation /oc-netinst:network-instances/oc-netinst:network-instance/oc-netinst:fdb/oc-netinst:state/oc-netinst:anycast-gateway-mac {
    //! NOTE_FEATURE_EXIST TRUE
    //! NOTE_DME_DONE      TRUE
    //! NOTE_COMMENT       ""
    deviate not-supported;
  }

  deviation /oc-netinst:network-instances/oc-netinst:network-instance/oc-netinst:fdb/oc-netinst:state/oc-netinst:flood-unknown-unicast-supression {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:config/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:config/oc-netinst:export-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:config/oc-netinst:import-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:state/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:state/oc-netinst:export-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:apply-policy/oc-netinst:state/oc-netinst:import-policy {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:import-export-policy/oc-netinst:config/oc-netinst:export-route-target {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:import-export-policy/oc-netinst:config/oc-netinst:import-route-target {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:import-export-policy/oc-netinst:state/oc-netinst:export-route-target {
    //! NOTE_FEATURE_EXIST TRUE
    //! NOTE_DME_DONE      TRUE
    //! NOTE_COMMENT       ""
    deviate not-supported;
  }

  deviation /oc-netinst:network-instances/oc-netinst:network-instance/oc-netinst:inter-instance-policies/oc-netinst:import-export-policy/oc-netinst:state/oc-netinst:import-route-target {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:config/oc-netinst:associated-address-families {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:config/oc-netinst:irb-anycast-gateway {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:config/oc-netinst:mac-pinning {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:state/oc-netinst:associated-address-families {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:state/oc-netinst:irb-anycast-gateway {
    //! NOTE_FEATURE_EXIST TRUE
    //! NOTE_DME_DONE      TRUE
    //! NOTE_COMMENT       ""
    deviate not-supported;
  }

  deviation /oc-netinst:network-instances/oc-netinst:network-instance/oc-netinst:interfaces/oc-netinst:interface/oc-netinst:state/oc-netinst:mac-pinning {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:config/oc-netinst:null-label {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:config/oc-netinst:pw-encapsulation {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:config/oc-netinst:ttl-propagation {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:interface-attributes/oc-netinst:interface {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:reserved-label-blocks/oc-netinst:reserved-label-block {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:state/oc-netinst:null-label {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:state/oc-netinst:pw-encapsulation {
    //! NOTE_FEATURE_EXIST TRUE
    //! NOTE_DME_DONE      TRUE
    //! NOTE_COMMENT       ""
    deviate not-supported;
  }

  deviation /oc-netinst:network-instances/oc-netinst:network-instance/oc-netinst:mpls/oc-netinst:global/oc-netinst:state/oc-netinst:ttl-propagation {
    //! NOTE_FEATURE_EXIST TRUE
    //! NOTE_DME_DONE      TRUE
    //! NOTE_COMMENT       ""
    deviate not-supported;
  }

  deviation /oc-netinst:network-instances/oc-netinst:network-instance/oc-netinst:mpls/oc-netinst:lsps/oc-netinst:constrained-path/oc-netinst:named-explicit-paths/oc-netinst:named-explicit-path {
    //! NOTE_FEATURE_EXIST TRUE
    //! NOTE_DME_DONE      TRUE
    //! NOTE_COMMENT       ""
    deviate not-supported;
  }

  deviation /oc-netinst:network-instances/oc-netinst:network-instance/oc-netinst:mpls/oc-netinst:lsps/oc-netinst:constrained-path/oc-netinst:tunnels/oc-netinst:tunnel {
    //! NOTE_FEATURE_EXIST TRUE
    //! NOTE_DME_DONE      TRUE
    //! NOTE_COMMENT       ""
    deviate not-supported;
  }

  deviation /oc-netinst:network-instances/oc-netinst:network-instance/oc-netinst:mpls/oc-netinst:lsps/oc-netinst:static-lsps/oc-netinst:static-lsp {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:authentication/oc-netinst:config/oc-netinst:authentication-key {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:authentication/oc-netinst:config/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:authentication/oc-netinst:state/oc-netinst:authentication-key {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:authentication/oc-netinst:state/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:config/oc-netinst:lsr-id {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:config/oc-netinst:forwarding-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:config/oc-netinst:helper-enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:config/oc-netinst:reconnect-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:config/oc-netinst:recovery-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:state/oc-netinst:forwarding-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:state/oc-netinst:helper-enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:state/oc-netinst:reconnect-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:graceful-restart/oc-netinst:state/oc-netinst:recovery-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:global/oc-netinst:state/oc-netinst:lsr-id {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:interface-attributes/oc-netinst:config/oc-netinst:hello-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:interface-attributes/oc-netinst:config/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:interface-attributes/oc-netinst:interfaces/oc-netinst:interface {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:interface-attributes/oc-netinst:state/oc-netinst:hello-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:interface-attributes/oc-netinst:state/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:neighbors/oc-netinst:neighbor {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:address-families/oc-netinst:address-family {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:config/oc-netinst:hello-accept {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:config/oc-netinst:hello-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:config/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:state/oc-netinst:hello-accept {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:state/oc-netinst:hello-holdtime {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:ldp/oc-netinst:targeted/oc-netinst:state/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:config/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:config/oc-netinst:recovery-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:config/oc-netinst:restart-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:state/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:state/oc-netinst:recovery-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:graceful-restart/oc-netinst:state/oc-netinst:restart-time {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:hellos/oc-netinst:config/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:hellos/oc-netinst:config/oc-netinst:refresh-reduction {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:hellos/oc-netinst:state/oc-netinst:hello-interval {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:hellos/oc-netinst:state/oc-netinst:refresh-reduction {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:soft-preemption/oc-netinst:config/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:soft-preemption/oc-netinst:config/oc-netinst:soft-preemption-timeout {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:soft-preemption/oc-netinst:state/oc-netinst:enable {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:soft-preemption/oc-netinst:state/oc-netinst:soft-preemption-timeout {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:authentication-fail {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:bad-checksum {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:bad-packet-format {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:bad-packet-length {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:out-of-order {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:received-nack {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:transmit-failure {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:transmit-queue-full {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:unknown-ack {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:errors/oc-netinst:unknown-nack {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-ack-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-hello-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-path-error-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-path-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-path-tear-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-reservation-error-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-reservation-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-reservation-tear-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:in-srefresh-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-ack-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-hello-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-path-error-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-path-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-path-tear-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-reservation-error-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-reservation-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-reservation-tear-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:out-srefresh-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:path-timeouts {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:rate-limited-messages {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:global/oc-netinst:state/oc-netinst:counters/oc-netinst:reservation-timeouts {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:interface-attributes/oc-netinst:interface {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:neighbors/oc-netinst:neighbor {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:rsvp-te/oc-netinst:sessions/oc-netinst:session {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:segment-routing/oc-netinst:aggregate-sid-counters/oc-netinst:aggregate-sid-counter {
    //! NOTE_FEATURE_EXIST TRUE
    //! NOTE_DME_DONE      TRUE
    //! NOTE_COMMENT       ""
    deviate not-supported;
  }

  deviation /oc-netinst:network-instances/oc-netinst:network-instance/oc-netinst:mpls/oc-netinst:signaling-protocols/oc-netinst:segment-routing/oc-netinst:interfaces/oc-netinst:interface {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:mpls-admin-groups/oc-netinst:admin-group {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:srlgs/oc-netinst:srlg {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:config/oc-netinst:cleanup-delay {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:config/oc-netinst:install-delay {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:config/oc-netinst:reoptimize-timer {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:state/oc-netinst:cleanup-delay {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:state/oc-netinst:install-delay {
    //! NOTE_FEATURE_EXIST TRUE
    //! NOTE_DME_DONE      TRUE
    //! NOTE_COMMENT       ""
    deviate not-supported;
  }

  deviation /oc-netinst:network-instances/oc-netinst:network-instance/oc-netinst:mpls/oc-netinst:te-global-attributes/oc-netinst:te-lsp-timers/oc-netinst:state/oc-netinst:reoptimize-timer {
    //! NOTE_FEATURE_EXIST TRUE
    //! NOTE_DME_DONE      TRUE
    //! NOTE_COMMENT       ""
    deviate not-supported;
  }

  deviation /oc-netinst:network-instances/oc-netinst:network-instance/oc-netinst:mpls/oc-netinst:te-interface-attributes/oc-netinst:interface {
    //! NOTE_FEATURE_EXIST TRUE
    //! NOTE_DME_DONE      TRUE
    //! NOTE_COMMENT       ""
    deviate not-supported;
  }

  deviation /oc-netinst:network-instances/oc-netinst:network-instance/oc-netinst:policy-forwarding/oc-netinst:interfaces/oc-netinst:interface {
    //! NOTE_FEATURE_EXIST TRUE
    //! NOTE_DME_DONE      TRUE
    //! NOTE_COMMENT       ""
    deviate not-supported;
  }

  deviation /oc-netinst:network-instances/oc-netinst:network-instance/oc-netinst:policy-forwarding/oc-netinst:path-selection-groups/oc-netinst:path-selection-group {
    //! NOTE_FEATURE_EXIST TRUE
    //! NOTE_DME_DONE      TRUE
    //! NOTE_COMMENT       ""
    deviate not-supported;
  }

  deviation /oc-netinst:network-instances/oc-netinst:network-instance/oc-netinst:policy-forwarding/oc-netinst:policies/oc-netinst:policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:add-paths/oc-netinst:config/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:add-paths/oc-netinst:state/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:config/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:config/oc-netinst:send-default-route {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:state/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv4-unicast/oc-netinst:state/oc-netinst:send-default-route {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:config/oc-netinst:send-default-route {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:ipv6-unicast/oc-netinst:state/oc-netinst:send-default-route {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-evpn/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l2vpn-vpls/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:advertise-inactive-routes {
    deviate replace {
          default "true";
        }
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:always-compare-med {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:enable-aigp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:external-compare-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:ignore-as-path-length {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:config/oc-netinst:ignore-next-hop-igp-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:state/oc-netinst:always-compare-med {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:state/oc-netinst:enable-aigp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:state/oc-netinst:external-compare-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:state/oc-netinst:ignore-as-path-length {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:route-selection-options/oc-netinst:state/oc-netinst:ignore-next-hop-igp-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv4/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:srte-policy-ipv6/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:config/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:state/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:afi-safis/oc-netinst:afi-safi/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:default-route-distance/oc-netinst:config/oc-netinst:external-route-distance {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:default-route-distance/oc-netinst:config/oc-netinst:internal-route-distance {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:default-route-distance/oc-netinst:state/oc-netinst:external-route-distance {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:default-route-distance/oc-netinst:state/oc-netinst:internal-route-distance {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:dynamic-neighbor-prefixes/oc-netinst:dynamic-neighbor-prefix {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:graceful-restart/oc-netinst:config/oc-netinst:enabled {
    deviate add {
          default "true";
        }
  }

  deviation /oc-netinst:network-instances/oc-netinst:network-instance/oc-netinst:protocols/oc-netinst:protocol/oc-netinst:bgp/oc-netinst:global/oc-netinst:graceful-restart/oc-netinst:config/oc-netinst:helper-only {
    deviate add {
          default "false";
        }
  }

  deviation /oc-netinst:network-instances/oc-netinst:network-instance/oc-netinst:protocols/oc-netinst:protocol/oc-netinst:bgp/oc-netinst:global/oc-netinst:graceful-restart/oc-netinst:config/oc-netinst:restart-time {
    deviate add {
          default "120";
        }
  }

  deviation /oc-netinst:network-instances/oc-netinst:network-instance/oc-netinst:protocols/oc-netinst:protocol/oc-netinst:bgp/oc-netinst:global/oc-netinst:graceful-restart/oc-netinst:config/oc-netinst:stale-routes-time {
    deviate add {
          default "300";
        }
  }

  deviation /oc-netinst:network-instances/oc-netinst:network-instance/oc-netinst:protocols/oc-netinst:protocol/oc-netinst:bgp/oc-netinst:global/oc-netinst:route-selection-options/oc-netinst:config/oc-netinst:advertise-inactive-routes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:route-selection-options/oc-netinst:config/oc-netinst:enable-aigp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:route-selection-options/oc-netinst:state/oc-netinst:advertise-inactive-routes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:route-selection-options/oc-netinst:state/oc-netinst:enable-aigp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:ebgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:ebgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:ibgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:ibgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:global/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:eligible-prefix-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:eligible-prefix-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l2vpn-vpls/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv4/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:srte-policy-ipv6/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes/oc-netinst:installed {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes/oc-netinst:received-pre-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:use-multiple-paths/oc-netinst:ebgp/oc-netinst:config/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:use-multiple-paths/oc-netinst:ebgp/oc-netinst:state/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:afi-safis/oc-netinst:afi-safi/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:config/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:config/oc-netinst:export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:config/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:state/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:state/oc-netinst:export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:apply-policy/oc-netinst:state/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:as-path-options/oc-netinst:config/oc-netinst:replace-peer-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:as-path-options/oc-netinst:state/oc-netinst:replace-peer-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:config/oc-netinst:neighbor-port {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:config/oc-netinst:peer-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:config/oc-netinst:route-flap-damping {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:ebgp-multihop/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:ebgp-multihop/oc-netinst:config/oc-netinst:multihop-ttl {
    deviate add {
          default "1";
        }
  }

  deviation /oc-netinst:network-instances/oc-netinst:network-instance/oc-netinst:protocols/oc-netinst:protocol/oc-netinst:bgp/oc-netinst:neighbors/oc-netinst:neighbor/oc-netinst:error-handling/oc-netinst:config/oc-netinst:treat-as-withdraw {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:error-handling/oc-netinst:state/oc-netinst:erroneous-update-messages {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:error-handling/oc-netinst:state/oc-netinst:treat-as-withdraw {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:graceful-restart/oc-netinst:config/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:graceful-restart/oc-netinst:config/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:graceful-restart/oc-netinst:config/oc-netinst:stale-routes-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:graceful-restart/oc-netinst:state/oc-netinst:local-restarting {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:logging-options/oc-netinst:config/oc-netinst:log-neighbor-state-changes {
    deviate replace {
          default "false";
        }
  }

  deviation /oc-netinst:network-instances/oc-netinst:network-instance/oc-netinst:protocols/oc-netinst:protocol/oc-netinst:bgp/oc-netinst:neighbors/oc-netinst:neighbor/oc-netinst:state/oc-netinst:last-prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:state/oc-netinst:neighbor-port {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:state/oc-netinst:route-flap-damping {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:timers/oc-netinst:config/oc-netinst:connect-retry {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:timers/oc-netinst:config/oc-netinst:hold-time {
    deviate replace {
          default "180";
        }
  }

  deviation /oc-netinst:network-instances/oc-netinst:network-instance/oc-netinst:protocols/oc-netinst:protocol/oc-netinst:bgp/oc-netinst:neighbors/oc-netinst:neighbor/oc-netinst:timers/oc-netinst:config/oc-netinst:keepalive-interval {
    deviate replace {
          default "60";
        }
  }

  deviation /oc-netinst:network-instances/oc-netinst:network-instance/oc-netinst:protocols/oc-netinst:protocol/oc-netinst:bgp/oc-netinst:neighbors/oc-netinst:neighbor/oc-netinst:timers/oc-netinst:config/oc-netinst:minimum-advertisement-interval {
    deviate replace {
          default "0";
        }
  }

  deviation /oc-netinst:network-instances/oc-netinst:network-instance/oc-netinst:protocols/oc-netinst:protocol/oc-netinst:bgp/oc-netinst:neighbors/oc-netinst:neighbor/oc-netinst:timers/oc-netinst:config/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:timers/oc-netinst:state/oc-netinst:connect-retry {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:timers/oc-netinst:state/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:transport/oc-netinst:config/oc-netinst:local-address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:transport/oc-netinst:config/oc-netinst:mtu-discovery {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:transport/oc-netinst:config/oc-netinst:tcp-mss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:transport/oc-netinst:state/oc-netinst:mtu-discovery {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:transport/oc-netinst:state/oc-netinst:tcp-mss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:use-multiple-paths/oc-netinst:ebgp/oc-netinst:config/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:use-multiple-paths/oc-netinst:ebgp/oc-netinst:state/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:neighbors/oc-netinst:neighbor/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:eligible-prefix-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:eligible-prefix-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:send-max {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:extended-next-hop-encoding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-vpls/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit-received/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:config/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:config/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:config/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:state/oc-netinst:max-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:state/oc-netinst:prefix-limit-exceeded {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:state/oc-netinst:prevent-teardown {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6/oc-netinst:prefix-limit/oc-netinst:state/oc-netinst:warning-threshold-pct {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ebgp/oc-netinst:config/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ebgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ebgp/oc-netinst:state/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ebgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ibgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ibgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:config/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:config/oc-netinst:export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:config/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:state/oc-netinst:default-export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:state/oc-netinst:export-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:apply-policy/oc-netinst:state/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:as-path-options/oc-netinst:config/oc-netinst:replace-peer-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:as-path-options/oc-netinst:state/oc-netinst:replace-peer-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:config/oc-netinst:peer-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:config/oc-netinst:route-flap-damping {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:ebgp-multihop/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:ebgp-multihop/oc-netinst:config/oc-netinst:multihop-ttl {
    deviate add {
          default "1";
        }
  }

  deviation /oc-netinst:network-instances/oc-netinst:network-instance/oc-netinst:protocols/oc-netinst:protocol/oc-netinst:bgp/oc-netinst:peer-groups/oc-netinst:peer-group/oc-netinst:error-handling/oc-netinst:config/oc-netinst:treat-as-withdraw {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:error-handling/oc-netinst:state/oc-netinst:treat-as-withdraw {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:graceful-restart/oc-netinst:config/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:graceful-restart/oc-netinst:config/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:graceful-restart/oc-netinst:config/oc-netinst:stale-routes-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:logging-options/oc-netinst:config/oc-netinst:log-neighbor-state-changes {
    deviate replace {
          default "false";
        }
  }

  deviation /oc-netinst:network-instances/oc-netinst:network-instance/oc-netinst:protocols/oc-netinst:protocol/oc-netinst:bgp/oc-netinst:peer-groups/oc-netinst:peer-group/oc-netinst:state/oc-netinst:peer-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:state/oc-netinst:route-flap-damping {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:state/oc-netinst:total-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:state/oc-netinst:total-prefixes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:timers/oc-netinst:config/oc-netinst:connect-retry {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:timers/oc-netinst:config/oc-netinst:hold-time {
    deviate replace {
          default "180";
        }
  }

  deviation /oc-netinst:network-instances/oc-netinst:network-instance/oc-netinst:protocols/oc-netinst:protocol/oc-netinst:bgp/oc-netinst:peer-groups/oc-netinst:peer-group/oc-netinst:timers/oc-netinst:config/oc-netinst:keepalive-interval {
    deviate replace {
          default "60";
        }
  }

  deviation /oc-netinst:network-instances/oc-netinst:network-instance/oc-netinst:protocols/oc-netinst:protocol/oc-netinst:bgp/oc-netinst:peer-groups/oc-netinst:peer-group/oc-netinst:timers/oc-netinst:config/oc-netinst:minimum-advertisement-interval {
    deviate replace {
          default "0";
        }
  }

  deviation /oc-netinst:network-instances/oc-netinst:network-instance/oc-netinst:protocols/oc-netinst:protocol/oc-netinst:bgp/oc-netinst:peer-groups/oc-netinst:peer-group/oc-netinst:timers/oc-netinst:config/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:timers/oc-netinst:state/oc-netinst:connect-retry {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:timers/oc-netinst:state/oc-netinst:restart-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:transport/oc-netinst:config/oc-netinst:local-address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:transport/oc-netinst:config/oc-netinst:mtu-discovery {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:transport/oc-netinst:config/oc-netinst:tcp-mss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:transport/oc-netinst:state/oc-netinst:mtu-discovery {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:transport/oc-netinst:state/oc-netinst:tcp-mss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ebgp/oc-netinst:config/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ebgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ebgp/oc-netinst:state/oc-netinst:allow-multiple-as {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ebgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ibgp/oc-netinst:config/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:ibgp/oc-netinst:state/oc-netinst:maximum-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:peer-groups/oc-netinst:peer-group/oc-netinst:use-multiple-paths/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:rib/oc-netinst:afi-safis/oc-netinst:afi-safi {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:rib/oc-netinst:attr-sets/oc-netinst:attr-set {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:rib/oc-netinst:communities/oc-netinst:community {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:bgp/oc-netinst:rib/oc-netinst:ext-communities/oc-netinst:ext-community {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:config/oc-netinst:default-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:igmp/oc-netinst:global/oc-netinst:ssm/oc-netinst:mappings/oc-netinst:mapping {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:igmp/oc-netinst:interfaces/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:config/oc-netinst:afi-name {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:config/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:config/oc-netinst:safi-name {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:multi-topology/oc-netinst:config/oc-netinst:afi-name {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:multi-topology/oc-netinst:config/oc-netinst:safi-name {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:afi-safi/oc-netinst:af/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:authentication-check {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:csnp-enable-on-p2p-links {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:fast-flooding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:hello-padding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:iid-tlv {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:instance {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:level-capability {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:max-ecmp-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:maximum-area-addresses {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:net {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:config/oc-netinst:poi-tlv {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:graceful-restart/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:graceful-restart/oc-netinst:config/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:graceful-restart/oc-netinst:state/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:igp-shortcuts/oc-netinst:afi {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level1-to-level2/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level1-to-level2/oc-netinst:config/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level1-to-level2/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level1-to-level2/oc-netinst:state/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level2-to-level1/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level2-to-level1/oc-netinst:config/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level2-to-level1/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:inter-level-propagation-policies/oc-netinst:level2-to-level1/oc-netinst:state/oc-netinst:import-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:attached-bit/oc-netinst:config/oc-netinst:ignore-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:attached-bit/oc-netinst:config/oc-netinst:suppress-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:attached-bit/oc-netinst:state/oc-netinst:ignore-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:attached-bit/oc-netinst:state/oc-netinst:suppress-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:config/oc-netinst:advertise-high-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:config/oc-netinst:set-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:config/oc-netinst:set-bit-on-boot {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:reset-triggers/oc-netinst:reset-trigger/oc-netinst:config/oc-netinst:delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:reset-triggers/oc-netinst:reset-trigger/oc-netinst:config/oc-netinst:reset-trigger {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:lsp-bit/oc-netinst:overload-bit/oc-netinst:reset-triggers/oc-netinst:reset-trigger/oc-netinst:state/oc-netinst:delay {
    deviate replace {
            type uint16 {
                range "5..65535";
            }
        }
  }

  deviation /oc-netinst:network-instances/oc-netinst:network-instance/oc-netinst:protocols/oc-netinst:protocol/oc-netinst:isis/oc-netinst:global/oc-netinst:lsp-bit/oc-netinst:overload-bit/oc-netinst:state/oc-netinst:advertise-high-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:mpls/oc-netinst:igp-ldp-sync/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:mpls/oc-netinst:igp-ldp-sync/oc-netinst:config/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:mpls/oc-netinst:igp-ldp-sync/oc-netinst:state/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:nsr/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:nsr/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:reference-bandwidth/oc-netinst:config/oc-netinst:reference-bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:segment-routing/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:segment-routing/oc-netinst:config/oc-netinst:srgb {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:segment-routing/oc-netinst:config/oc-netinst:srlb {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:segment-routing/oc-netinst:state/oc-netinst:srgb {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:segment-routing/oc-netinst:state/oc-netinst:srlb {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:authentication-check {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:csnp-enable-on-p2p-links {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:fast-flooding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:hello-padding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:iid-tlv {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:max-ecmp-paths {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:state/oc-netinst:poi-tlv {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:config/oc-netinst:lsp-lifetime-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:config/oc-netinst:lsp-refresh-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:config/oc-netinst:lsp-first-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:config/oc-netinst:lsp-max-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:config/oc-netinst:lsp-second-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:state/oc-netinst:adaptive-timer {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:state/oc-netinst:lsp-first-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:state/oc-netinst:lsp-max-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:lsp-generation/oc-netinst:state/oc-netinst:lsp-second-wait-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:config/oc-netinst:spf-first-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:config/oc-netinst:spf-hold-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:config/oc-netinst:spf-second-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:state/oc-netinst:adaptive-timer {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:state/oc-netinst:spf-first-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:state/oc-netinst:spf-hold-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:spf/oc-netinst:state/oc-netinst:spf-second-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:timers/oc-netinst:state/oc-netinst:lsp-refresh-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:global/oc-netinst:transport/oc-netinst:config/oc-netinst:lsp-mtu-size {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:afi-safi/oc-netinst:af {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:config/oc-netinst:auth-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:config/oc-netinst:auth-password {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:config/oc-netinst:auth-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:config/oc-netinst:keychain {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:state/oc-netinst:auth-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:state/oc-netinst:auth-password {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:state/oc-netinst:auth-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:authentication/oc-netinst:state/oc-netinst:keychain {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:bfd/oc-netinst:config/oc-netinst:bfd-tlv {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:adj-changes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:adj-number {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:auth-fails {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:auth-type-fails {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:id-field-len-mismatches {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:init-fails {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:lan-dis-changes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:max-area-address-mismatches {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:circuit-counters/oc-netinst:state/oc-netinst:rejected-adj {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:config/oc-netinst:circuit-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:config/oc-netinst:hello-padding {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:config/oc-netinst:interface-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:config/oc-netinst:passive {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:enable-bfd/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:interface-ref/oc-netinst:config/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:interface-ref/oc-netinst:config/oc-netinst:subinterface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:interface-ref/oc-netinst:state/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:interface-ref/oc-netinst:state/oc-netinst:subinterface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:adjacencies/oc-netinst:adjacency/oc-netinst:state/oc-netinst:nlpid {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:adjacencies/oc-netinst:adjacency/oc-netinst:state/oc-netinst:up-timestamp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:afi-safi/oc-netinst:af {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:config/oc-netinst:level-number {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:config/oc-netinst:passive {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:config/oc-netinst:priority {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:auth-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:auth-password {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:auth-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:keychain {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:esh/oc-netinst:state/oc-netinst:dropped {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:esh/oc-netinst:state/oc-netinst:processed {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:esh/oc-netinst:state/oc-netinst:received {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:esh/oc-netinst:state/oc-netinst:retransmit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:esh/oc-netinst:state/oc-netinst:sent {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:ish/oc-netinst:state/oc-netinst:dropped {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:ish/oc-netinst:state/oc-netinst:processed {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:ish/oc-netinst:state/oc-netinst:received {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:ish/oc-netinst:state/oc-netinst:retransmit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:packet-counters/oc-netinst:ish/oc-netinst:state/oc-netinst:sent {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:timers/oc-netinst:config/oc-netinst:hello-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:levels/oc-netinst:level/oc-netinst:timers/oc-netinst:config/oc-netinst:hello-multiplier {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:mpls/oc-netinst:igp-ldp-sync/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:mpls/oc-netinst:igp-ldp-sync/oc-netinst:config/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:mpls/oc-netinst:igp-ldp-sync/oc-netinst:state/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:timers/oc-netinst:config/oc-netinst:csnp-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:timers/oc-netinst:config/oc-netinst:lsp-pacing-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:interfaces/oc-netinst:interface/oc-netinst:timers/oc-netinst:state/oc-netinst:csnp-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:auth-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:auth-password {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:auth-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:disable-csnp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:disable-lsp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:disable-psnp {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:authentication/oc-netinst:config/oc-netinst:keychain {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:config/oc-netinst:authentication-check {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:config/oc-netinst:level-number {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:config/oc-netinst:metric-style {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:flags/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:flags/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv4-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv4-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv6-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv6-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:tag64/oc-netinst:state/oc-netinst:tag64 {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:available-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:available-bandwidth/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:bandwidth-constraints/oc-netinst:bandwidth-constraint {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:extended-admin-group/oc-netinst:state/oc-netinst:extended-admin-group {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv6-interface-address/oc-netinst:state/oc-netinst:address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv6-neighbor-address/oc-netinst:state/oc-netinst:address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:lan-adjacency-sids/oc-netinst:lan-adjacency-sid/oc-netinst:state/oc-netinst:neighbor-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-attributes/oc-netinst:state/oc-netinst:local-protection {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-delay-variation/oc-netinst:state/oc-netinst:delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-delay/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-delay/oc-netinst:state/oc-netinst:delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-id/oc-netinst:state/oc-netinst:local {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-id/oc-netinst:state/oc-netinst:remote {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-loss/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-loss/oc-netinst:state/oc-netinst:link-loss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-protection-type/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:min-max-link-delay/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:min-max-link-delay/oc-netinst:state/oc-netinst:max-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:min-max-link-delay/oc-netinst:state/oc-netinst:min-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:residual-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:unconstrained-lsp/oc-netinst:state/oc-netinst:count {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:unconstrained-lsp/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:utilized-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:utilized-bandwidth/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:instance-ids/oc-netinst:instance-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-external-reachability/oc-netinst:prefixes/oc-netinst:prefix {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:delay-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:delay-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:error-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:error-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:expense-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability/oc-netinst:prefixes/oc-netinst:prefix/oc-netinst:expense-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-srlgs/oc-netinst:ipv4-srlg {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:flags/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:flags/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv4-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv4-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv6-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv6-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:tag64/oc-netinst:state/oc-netinst:tag64 {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-srlgs/oc-netinst:ipv6-srlg {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-te-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-alias-id/oc-netinst:state/oc-netinst:alias-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:delay-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:delay-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:error-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:error-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:expense-metric/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability/oc-netinst:neighbors/oc-netinst:neighbor/oc-netinst:expense-metric/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:isis-neighbor-attribute/oc-netinst:neighbors/oc-netinst:neighbor {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:lsp-buffer-size/oc-netinst:state/oc-netinst:size {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv4-reachability/oc-netinst:prefixes/oc-netinst:prefix {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:flags/oc-netinst:state/oc-netinst:flags {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:flags/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:ipv4-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:ipv4-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:ipv6-source-router-id/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:ipv6-source-router-id/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability/oc-netinst:prefixes/oc-netinst:prefix/oc-netinst:subtlvs/oc-netinst:subtlv/oc-netinst:tag64/oc-netinst:state/oc-netinst:tag64 {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isis-neighbor-attribute/oc-netinst:neighbors/oc-netinst:neighbor {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:available-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:available-bandwidth/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:bandwidth-constraints/oc-netinst:bandwidth-constraint {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:extended-admin-group/oc-netinst:state/oc-netinst:extended-admin-group {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:ipv6-interface-address/oc-netinst:state/oc-netinst:address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:ipv6-neighbor-address/oc-netinst:state/oc-netinst:address {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:lan-adjacency-sids/oc-netinst:lan-adjacency-sid/oc-netinst:state/oc-netinst:neighbor-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-attributes/oc-netinst:state/oc-netinst:local-protection {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-delay-variation/oc-netinst:state/oc-netinst:delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-delay/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-delay/oc-netinst:state/oc-netinst:delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-id/oc-netinst:state/oc-netinst:local {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-id/oc-netinst:state/oc-netinst:remote {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-loss/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-loss/oc-netinst:state/oc-netinst:link-loss {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:link-protection-type/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:min-max-link-delay/oc-netinst:state/oc-netinst:a-bit {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:min-max-link-delay/oc-netinst:state/oc-netinst:max-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:min-max-link-delay/oc-netinst:state/oc-netinst:min-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:residual-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:unconstrained-lsp/oc-netinst:state/oc-netinst:count {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:unconstrained-lsp/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:utilized-bandwidth/oc-netinst:state/oc-netinst:bandwidth {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn/oc-netinst:neighbors/oc-netinst:neighbor/oc-netinst:instances/oc-netinst:instance/oc-netinst:subtlvs/oc-netinst:subtlv/oc-netinst:utilized-bandwidth/oc-netinst:state/oc-netinst:type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:purge-oi/oc-netinst:state/oc-netinst:received-system-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:purge-oi/oc-netinst:state/oc-netinst:source-system-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:purge-oi/oc-netinst:state/oc-netinst:system-id-count {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:router-capabilities/oc-netinst:capability/oc-netinst:subtlvs/oc-netinst:subtlv/oc-netinst:segment-routing-algorithms/oc-netinst:state/oc-netinst:algorithm {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:route-preference/oc-netinst:config/oc-netinst:external-route-preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:route-preference/oc-netinst:config/oc-netinst:internal-route-preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:route-preference/oc-netinst:state/oc-netinst:external-route-preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:route-preference/oc-netinst:state/oc-netinst:internal-route-preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:auth-fails {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:auth-type-fails {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:corrupted-lsps {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:database-overloads {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:exceed-max-seq-nums {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:id-len-mismatch {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:lsp-errors {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:manual-address-drop-from-areas {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:max-area-address-mismatches {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:own-lsp-purges {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:part-changes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:seq-num-skips {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:system-level-counters/oc-netinst:state/oc-netinst:spf-runs {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:config/oc-netinst:ipv4-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:config/oc-netinst:ipv6-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:state/oc-netinst:ipv4-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:isis/oc-netinst:levels/oc-netinst:level/oc-netinst:traffic-engineering/oc-netinst:state/oc-netinst:ipv6-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:local-aggregates/oc-netinst:aggregate {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:config/oc-netinst:hide-network {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:config/oc-netinst:priority {
    deviate add {
          default "1";
        }
  }

  deviation /oc-netinst:network-instances/oc-netinst:network-instance/oc-netinst:protocols/oc-netinst:protocol/oc-netinst:ospfv2/oc-netinst:areas/oc-netinst:area/oc-netinst:interfaces/oc-netinst:interface/oc-netinst:enable-bfd/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:enable-bfd/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:interface-ref/oc-netinst:state/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:interface-ref/oc-netinst:state/oc-netinst:subinterface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:lsa-filter/oc-netinst:config/oc-netinst:all {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:lsa-filter/oc-netinst:state/oc-netinst:all {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:config/oc-netinst:traffic-engineering-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:igp-ldp-sync/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:igp-ldp-sync/oc-netinst:config/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:igp-ldp-sync/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:igp-ldp-sync/oc-netinst:state/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:igp-ldp-sync/oc-netinst:state/oc-netinst:synchronized {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:mpls/oc-netinst:state/oc-netinst:traffic-engineering-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:neighbors/oc-netinst:neighbor {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:authentication-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:hide-network {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:multi-area-adjacency-primary {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:network-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:passive {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:state/oc-netinst:priority {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:config/oc-netinst:dead-interval {
    deviate add {
          default "0";
        }
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:config/oc-netinst:hello-interval {
    deviate add {
          default "10";
        }
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:config/oc-netinst:retransmission-interval {
    deviate add {
          default "5";
        }
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:state/oc-netinst:dead-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:state/oc-netinst:hello-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:interfaces/oc-netinst:interface/oc-netinst:timers/oc-netinst:state/oc-netinst:retransmission-interval {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:lsdb/oc-netinst:lsa-types/oc-netinst:lsa-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:lsdb/oc-netinst:state/oc-netinst:identifier {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:mpls/oc-netinst:config/oc-netinst:traffic-engineering-enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:mpls/oc-netinst:state/oc-netinst:traffic-engineering-enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:state/oc-netinst:identifier {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:adjacency-state {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:backup-designated-router {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:dead-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:designated-router {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:last-established-time {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:optional-capabilities {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:priority {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:remote-router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:retransmission-queue-length {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:areas/oc-netinst:area/oc-netinst:virtual-links/oc-netinst:virtual-link/oc-netinst:state/oc-netinst:state-changes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:config/oc-netinst:hide-transit-only-networks {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:config/oc-netinst:igp-shortcuts {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:config/oc-netinst:summary-route-cost-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:graceful-restart/oc-netinst:config/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:graceful-restart/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:graceful-restart/oc-netinst:state/oc-netinst:helper-only {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:inter-area-propagation-policies/oc-netinst:inter-area-propagation-policy {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:config/oc-netinst:traffic-engineering-extensions {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:igp-ldp-sync/oc-netinst:config/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:igp-ldp-sync/oc-netinst:config/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:igp-ldp-sync/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:igp-ldp-sync/oc-netinst:state/oc-netinst:post-session-up-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:mpls/oc-netinst:state/oc-netinst:traffic-engineering-extensions {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:state/oc-netinst:hide-transit-only-networks {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:state/oc-netinst:igp-shortcuts {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:state/oc-netinst:log-adjacency-changes {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:state/oc-netinst:summary-route-cost-mode {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:lsa-generation/oc-netinst:config/oc-netinst:initial-delay {
    deviate add {
          default "0";
        }
  }

  deviation /oc-netinst:network-instances/oc-netinst:network-instance/oc-netinst:protocols/oc-netinst:protocol/oc-netinst:ospfv2/oc-netinst:global/oc-netinst:timers/oc-netinst:lsa-generation/oc-netinst:config/oc-netinst:maximum-delay {
    deviate add {
          default "5000";
        }
  }

  deviation /oc-netinst:network-instances/oc-netinst:network-instance/oc-netinst:protocols/oc-netinst:protocol/oc-netinst:ospfv2/oc-netinst:global/oc-netinst:timers/oc-netinst:lsa-generation/oc-netinst:state/oc-netinst:initial-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:lsa-generation/oc-netinst:state/oc-netinst:maximum-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:lsa-generation/oc-netinst:state/oc-netinst:timer-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:max-metric/oc-netinst:state/oc-netinst:include {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:max-metric/oc-netinst:state/oc-netinst:set {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:max-metric/oc-netinst:state/oc-netinst:timeout {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:max-metric/oc-netinst:state/oc-netinst:trigger {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:spf/oc-netinst:config/oc-netinst:initial-delay {
    deviate add {
          default "200";
        }
  }

  deviation /oc-netinst:network-instances/oc-netinst:network-instance/oc-netinst:protocols/oc-netinst:protocol/oc-netinst:ospfv2/oc-netinst:global/oc-netinst:timers/oc-netinst:spf/oc-netinst:config/oc-netinst:maximum-delay {
    deviate add {
          default "5000";
        }
  }

  deviation /oc-netinst:network-instances/oc-netinst:network-instance/oc-netinst:protocols/oc-netinst:protocol/oc-netinst:ospfv2/oc-netinst:global/oc-netinst:timers/oc-netinst:spf/oc-netinst:state/oc-netinst:initial-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:spf/oc-netinst:state/oc-netinst:maximum-delay {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:ospfv2/oc-netinst:global/oc-netinst:timers/oc-netinst:spf/oc-netinst:state/oc-netinst:timer-type {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pcep/oc-netinst:path-computation-servers/oc-netinst:path-computation-server {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:config/oc-netinst:maximum-groups {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:rendezvous-points/oc-netinst:rendezvous-point {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:sources-joined/oc-netinst:source {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:ssm/oc-netinst:config/oc-netinst:ssm-ranges {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:ssm/oc-netinst:state/oc-netinst:ssm-ranges {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:state/oc-netinst:counters/oc-netinst:bootstrap-messages {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:state/oc-netinst:counters/oc-netinst:hello-messages {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:state/oc-netinst:counters/oc-netinst:join-prune-messages {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:state/oc-netinst:maximum-groups {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:global/oc-netinst:state/oc-netinst:neighbor-count {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:pim/oc-netinst:interfaces/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:state/oc-netinst:default-metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:state/oc-netinst:identifier {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:state/oc-netinst:name {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:config/oc-netinst:description {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:config/oc-netinst:set-tag {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:config/oc-netinst:preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:config/oc-netinst:recurse {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:enable-bfd/oc-netinst:state/oc-netinst:enabled {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:interface-ref/oc-netinst:state/oc-netinst:interface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:interface-ref/oc-netinst:state/oc-netinst:subinterface {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:state/oc-netinst:index {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:state/oc-netinst:metric {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:state/oc-netinst:next-hop {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:state/oc-netinst:preference {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:next-hops/oc-netinst:next-hop/oc-netinst:state/oc-netinst:recurse {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:state/oc-netinst:description {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:state/oc-netinst:prefix {
    //! NOTE_FEATURE_EXIST TRUE
    //! NOTE_DME_DONE      TRUE
    //! NOTE_COMMENT       ""
    deviate not-supported;
  }

  deviation /oc-netinst:network-instances/oc-netinst:network-instance/oc-netinst:protocols/oc-netinst:protocol/oc-netinst:static-routes/oc-netinst:static/oc-netinst:state/oc-netinst:set-tag {
    //! NOTE_FEATURE_EXIST TRUE
    //! NOTE_DME_DONE      TRUE
    //! NOTE_COMMENT       ""
    deviate not-supported;
  }

  deviation /oc-netinst:network-instances/oc-netinst:network-instance/oc-netinst:segment-routing/oc-netinst:srgbs/oc-netinst:srgb {
    //! NOTE_FEATURE_EXIST TRUE
    //! NOTE_DME_DONE      TRUE
    //! NOTE_COMMENT       ""
    deviate not-supported;
  }

  deviation /oc-netinst:network-instances/oc-netinst:network-instance/oc-netinst:segment-routing/oc-netinst:srlbs/oc-netinst:srlb {
    //! NOTE_FEATURE_EXIST TRUE
    //! NOTE_DME_DONE      TRUE
    //! NOTE_COMMENT       ""
    deviate not-supported;
  }

  deviation /oc-netinst:network-instances/oc-netinst:network-instance/oc-netinst:segment-routing/oc-netinst:te-policies/oc-netinst:te-policy {
    //! NOTE_FEATURE_EXIST TRUE
    //! NOTE_DME_DONE      TRUE
    //! NOTE_COMMENT       ""
    deviate not-supported;
  }

  deviation /oc-netinst:network-instances/oc-netinst:network-instance/oc-netinst:state/oc-netinst:fallback-network-instance {
    //! NOTE_FEATURE_EXIST TRUE
    //! NOTE_DME_DONE      TRUE
    //! NOTE_COMMENT       ""
    deviate not-supported;
  }

  deviation /oc-netinst:network-instances/oc-netinst:network-instance/oc-netinst:state/oc-netinst:router-id {
    //! NOTE_FEATURE_EXIST TRUE
    //! NOTE_DME_DONE      TRUE
    //! NOTE_COMMENT       ""
    deviate not-supported;
  }

  deviation /oc-netinst:network-instances/oc-netinst:network-instance/oc-netinst:table-connections/oc-netinst:table-connection/oc-netinst:config/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:table-connections/oc-netinst:table-connection/oc-netinst:config/oc-netinst:disable-metric-propagation {
    //! NOTE_FEATURE_EXIST TRUE
    //! NOTE_DME_DONE      TRUE
    //! NOTE_COMMENT       ""
    deviate not-supported;
  }

  deviation /oc-netinst:network-instances/oc-netinst:network-instance/oc-netinst:table-connections/oc-netinst:table-connection/oc-netinst:config/oc-netinst:import-policy {
    deviate add {
          max-elements "1";
        }
  }

  deviation /oc-netinst:network-instances/oc-netinst:network-instance/oc-netinst:table-connections/oc-netinst:table-connection/oc-netinst:state/oc-netinst:default-import-policy {
    //! NOTE_FEATURE_EXIST TRUE
    //! NOTE_DME_DONE      TRUE
    //! NOTE_COMMENT       ""
    deviate not-supported;
  }

  deviation /oc-netinst:network-instances/oc-netinst:network-instance/oc-netinst:table-connections/oc-netinst:table-connection/oc-netinst:state/oc-netinst:disable-metric-propagation {
    //! NOTE_FEATURE_EXIST TRUE
    //! NOTE_DME_DONE      TRUE
    //! NOTE_COMMENT       ""
    deviate not-supported;
  }

  deviation /oc-netinst:network-instances/oc-netinst:network-instance/oc-netinst:table-connections/oc-netinst:table-connection/oc-netinst:state/oc-netinst:import-policy {
    deviate add {
          max-elements "1";
        }
  }

  deviation /oc-netinst:network-instances/oc-netinst:network-instance/oc-netinst:tables/oc-netinst:table {
    //! NOTE_FEATURE_EXIST TRUE
    //! NOTE_DME_DONE      TRUE
    //! NOTE_COMMENT       ""
    deviate not-supported;
  }


}
