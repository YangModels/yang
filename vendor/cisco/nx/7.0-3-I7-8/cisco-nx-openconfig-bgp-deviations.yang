module cisco-nx-openconfig-bgp-deviations {

  namespace "http://openconfig.net/yang/bgp-deviations";

  prefix "oc-bgp-devs";

  import openconfig_bgp { prefix oc-bgp; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-bgp module 
     set for Cisco NXOS.
     Copyright (c) 2015-2017 by Cisco Systems, Inc.
     All rights reserved.";

  revision "2017-04-20" {
    description
      "Initial revision applicable to NXOS";
  }

  deviation oc-bgp:/bgp/peer-groups/peer-group/oc-bgp-mp:use-multiple-paths/oc-bgp-mp:config/oc-bgp-mp:enabled {
    deviate "not-supported"; 
  }
  deviation oc-bgp:/bgp/peer-groups/peer-group/oc-bgp-mp:use-multiple-paths/oc-bgp-mp:state/oc-bgp-mp:enabled {
    deviate "not-supported"; 
  }
  deviation oc-bgp:/bgp/peer-groups/peer-group/oc-bgp-mp:use-multiple-paths/oc-bgp-mp:ebgp/oc-bgp-mp:config/oc-bgp-mp:allow-multiple-as {
    deviate "not-supported"; 
  }
  deviation oc-bgp:/bgp/peer-groups/peer-group/oc-bgp-mp:use-multiple-paths/oc-bgp-mp:ebgp/oc-bgp-mp:config/oc-bgp-mp:maximum-paths {
    deviate "not-supported"; 
  }
  deviation oc-bgp:/bgp/peer-groups/peer-group/oc-bgp-mp:use-multiple-paths/oc-bgp-mp:ebgp/oc-bgp-mp:state/oc-bgp-mp:allow-multiple-as {
    deviate "not-supported"; 
  }
  deviation oc-bgp:/bgp/peer-groups/peer-group/oc-bgp-mp:use-multiple-paths/oc-bgp-mp:ebgp/oc-bgp-mp:state/oc-bgp-mp:maximum-paths {
    deviate "not-supported"; 
  }
  deviation oc-bgp:/bgp/peer-groups/peer-group/oc-bgp-mp:use-multiple-paths/oc-bgp-mp:ibgp/oc-bgp-mp:config/oc-bgp-mp:maximum-paths {
    deviate "not-supported"; 
  }
  deviation oc-bgp:/bgp/peer-groups/peer-group/oc-bgp-mp:use-multiple-paths/oc-bgp-mp:ibgp/oc-bgp-mp:state/oc-bgp-mp:maximum-paths {
    deviate "not-supported"; 
  }
  deviation oc-bgp:/bgp/neighbors/neighbor/oc-bgp-mp:use-multiple-paths/oc-bgp-mp:config/oc-bgp-mp:enabled {
    deviate "not-supported"; 
  }
  deviation oc-bgp:/bgp/neighbors/neighbor/oc-bgp-mp:use-multiple-paths/oc-bgp-mp:state/oc-bgp-mp:enabled {
    deviate "not-supported"; 
  }
  deviation oc-bgp:/bgp/neighbors/neighbor/oc-bgp-mp:use-multiple-paths/oc-bgp-mp:ebgp/oc-bgp-mp:config/oc-bgp-mp:allow-multiple-as {
    deviate "not-supported"; 
  }
  deviation oc-bgp:/bgp/neighbors/neighbor/oc-bgp-mp:use-multiple-paths/oc-bgp-mp:ebgp/oc-bgp-mp:state/oc-bgp-mp:allow-multiple-as {
    deviate "not-supported"; 
  }
  deviation oc-bgp:/bgp/peer-groups/peer-group/afi-safis/afi-safi/oc-bgp-mp:use-multiple-paths/oc-bgp-mp:config/oc-bgp-mp:enabled {
    deviate "not-supported"; 
  }
  deviation oc-bgp:/bgp/peer-groups/peer-group/afi-safis/afi-safi/oc-bgp-mp:use-multiple-paths/oc-bgp-mp:state/oc-bgp-mp:enabled {
    deviate "not-supported"; 
  }
  deviation oc-bgp:/bgp/peer-groups/peer-group/afi-safis/afi-safi/oc-bgp-mp:use-multiple-paths/oc-bgp-mp:ebgp/oc-bgp-mp:config/oc-bgp-mp:allow-multiple-as {
    deviate "not-supported"; 
  }
  deviation oc-bgp:/bgp/peer-groups/peer-group/afi-safis/afi-safi/oc-bgp-mp:use-multiple-paths/oc-bgp-mp:ebgp/oc-bgp-mp:config/oc-bgp-mp:maximum-paths {
    deviate "not-supported"; 
  }
  deviation oc-bgp:/bgp/peer-groups/peer-group/afi-safis/afi-safi/oc-bgp-mp:use-multiple-paths/oc-bgp-mp:ebgp/oc-bgp-mp:state/oc-bgp-mp:allow-multiple-as {
    deviate "not-supported"; 
  }
  deviation oc-bgp:/bgp/peer-groups/peer-group/afi-safis/afi-safi/oc-bgp-mp:use-multiple-paths/oc-bgp-mp:ebgp/oc-bgp-mp:state/oc-bgp-mp:maximum-paths {
    deviate "not-supported"; 
  }
  deviation oc-bgp:/bgp/peer-groups/peer-group/afi-safis/afi-safi/oc-bgp-mp:use-multiple-paths/oc-bgp-mp:ibgp/oc-bgp-mp:config/oc-bgp-mp:maximum-paths {
    deviate "not-supported"; 
  }
  deviation oc-bgp:/bgp/peer-groups/peer-group/afi-safis/afi-safi/oc-bgp-mp:use-multiple-paths/oc-bgp-mp:ibgp/oc-bgp-mp:state/oc-bgp-mp:maximum-paths {
    deviate "not-supported"; 
  }
  deviation oc-bgp:/bgp/neighbors/neighbor/afi-safis/afi-safi/oc-bgp-mp:use-multiple-paths/oc-bgp-mp:config/oc-bgp-mp:enabled {
    deviate "not-supported"; 
  }
  deviation oc-bgp:/bgp/neighbors/neighbor/afi-safis/afi-safi/oc-bgp-mp:use-multiple-paths/oc-bgp-mp:state/oc-bgp-mp:enabled {
    deviate "not-supported"; 
  }
  deviation oc-bgp:/bgp/neighbors/neighbor/afi-safis/afi-safi/oc-bgp-mp:use-multiple-paths/oc-bgp-mp:ebgp/oc-bgp-mp:config/oc-bgp-mp:allow-multiple-as {
    deviate "not-supported"; 
  }
  deviation oc-bgp:/bgp/neighbors/neighbor/afi-safis/afi-safi/oc-bgp-mp:use-multiple-paths/oc-bgp-mp:ebgp/oc-bgp-mp:state/oc-bgp-mp:allow-multiple-as {
    deviate "not-supported"; 
  }
  deviation oc-bgp:/bgp/global/afi-safis/afi-safi/oc-bgp-mp:route-selection-options/oc-bgp-mp:config/oc-bgp-mp:always-compare-med {
    deviate "not-supported"; 
  }
  deviation oc-bgp:/bgp/global/afi-safis/afi-safi/oc-bgp-mp:route-selection-options/oc-bgp-mp:config/oc-bgp-mp:ignore-as-path-length {
    deviate "not-supported"; 
  }
  deviation oc-bgp:/bgp/global/afi-safis/afi-safi/oc-bgp-mp:route-selection-options/oc-bgp-mp:config/oc-bgp-mp:external-compare-router-id {
    deviate "not-supported"; 
  }
  deviation oc-bgp:/bgp/global/afi-safis/afi-safi/oc-bgp-mp:route-selection-options/oc-bgp-mp:config/oc-bgp-mp:enable-aigp {
    deviate "not-supported"; 
  }
  deviation oc-bgp:/bgp/global/afi-safis/afi-safi/oc-bgp-mp:route-selection-options/oc-bgp-mp:config/oc-bgp-mp:ignore-next-hop-igp-metric {
    deviate "not-supported"; 
  }
  deviation oc-bgp:/bgp/global/afi-safis/afi-safi/oc-bgp-mp:route-selection-options/oc-bgp-mp:state/oc-bgp-mp:enable-aigp {
    deviate "not-supported"; 
  }
  deviation oc-bgp:/bgp/global/afi-safis/afi-safi/oc-bgp-mp:route-selection-options/oc-bgp-mp:state/oc-bgp-mp:ignore-next-hop-igp-metric {
    deviate "not-supported"; 
  }
  deviation oc-bgp:/bgp/global/afi-safis/afi-safi/oc-bgp-mp:use-multiple-paths/oc-bgp-mp:config/oc-bgp-mp:enabled {
    deviate "not-supported"; 
  }
  deviation oc-bgp:/bgp/global/afi-safis/afi-safi/oc-bgp-mp:use-multiple-paths/oc-bgp-mp:state/oc-bgp-mp:enabled {
    deviate "not-supported"; 
  }
  deviation oc-bgp:/bgp/global/afi-safis/afi-safi/oc-bgp-mp:use-multiple-paths/oc-bgp-mp:ebgp/oc-bgp-mp:config/oc-bgp-mp:allow-multiple-as {
    deviate "not-supported"; 
  }
  deviation oc-bgp:/bgp/global/afi-safis/afi-safi/oc-bgp-mp:use-multiple-paths/oc-bgp-mp:ebgp/oc-bgp-mp:state/oc-bgp-mp:allow-multiple-as {
    deviate "not-supported"; 
  }
  deviation oc-bgp:/bgp/peer-groups/peer-group/afi-safis/afi-safi/oc-bgp-mp:route-selection-options/oc-bgp-mp:config/oc-bgp-mp:always-compare-med {
    deviate "not-supported"; 
  }
  deviation oc-bgp:/bgp/peer-groups/peer-group/afi-safis/afi-safi/oc-bgp-mp:route-selection-options/oc-bgp-mp:config/oc-bgp-mp:ignore-as-path-length {
    deviate "not-supported"; 
  }
  deviation oc-bgp:/bgp/peer-groups/peer-group/afi-safis/afi-safi/oc-bgp-mp:route-selection-options/oc-bgp-mp:config/oc-bgp-mp:external-compare-router-id {
    deviate "not-supported"; 
  }
  deviation oc-bgp:/bgp/peer-groups/peer-group/afi-safis/afi-safi/oc-bgp-mp:route-selection-options/oc-bgp-mp:config/oc-bgp-mp:enable-aigp {
    deviate "not-supported"; 
  }
  deviation oc-bgp:/bgp/peer-groups/peer-group/afi-safis/afi-safi/oc-bgp-mp:route-selection-options/oc-bgp-mp:config/oc-bgp-mp:ignore-next-hop-igp-metric {
    deviate "not-supported"; 
  }
  deviation oc-bgp:/bgp/peer-groups/peer-group/afi-safis/afi-safi/oc-bgp-mp:route-selection-options/oc-bgp-mp:state/oc-bgp-mp:always-compare-med {
    deviate "not-supported"; 
  }
  deviation oc-bgp:/bgp/peer-groups/peer-group/afi-safis/afi-safi/oc-bgp-mp:route-selection-options/oc-bgp-mp:state/oc-bgp-mp:ignore-as-path-length {
    deviate "not-supported"; 
  }
  deviation oc-bgp:/bgp/peer-groups/peer-group/afi-safis/afi-safi/oc-bgp-mp:route-selection-options/oc-bgp-mp:state/oc-bgp-mp:external-compare-router-id {
    deviate "not-supported"; 
  }
  deviation oc-bgp:/bgp/peer-groups/peer-group/afi-safis/afi-safi/oc-bgp-mp:route-selection-options/oc-bgp-mp:state/oc-bgp-mp:enable-aigp {
    deviate "not-supported"; 
  }
  deviation oc-bgp:/bgp/peer-groups/peer-group/afi-safis/afi-safi/oc-bgp-mp:route-selection-options/oc-bgp-mp:state/oc-bgp-mp:ignore-next-hop-igp-metric {
    deviate "not-supported"; 
  }
  deviation oc-bgp:/bgp/neighbors/neighbor/config/oc-bgp:enabled {
    deviate "not-supported"; 
  }
  deviation oc-bgp:/bgp/neighbors/neighbor/state/oc-bgp:enabled {
    deviate "not-supported"; 
  }
  deviation oc-bgp:/bgp/neighbors/neighbor/state/oc-bgp-op:session-state {
    deviate "not-supported"; 
  }
  deviation oc-bgp:/bgp/neighbors/neighbor/state/oc-bgp-op:last-established {
    deviate "not-supported"; 
  }
  deviation oc-bgp:/bgp/neighbors/neighbor/state/oc-bgp-op:established-transitions {
    deviate "not-supported"; 
  }
  deviation oc-bgp:/bgp/neighbors/neighbor/state/oc-bgp-op:supported-capabilities {
    deviate "not-supported"; 
  }
  deviation oc-bgp:/bgp/neighbors/oc-bgp:neighbor/state/oc-bgp:messages/oc-bgp:sent/oc-bgp-op:UPDATE {
    deviate "not-supported"; 
  }
  deviation oc-bgp:/bgp/neighbors/oc-bgp:neighbor/state/oc-bgp:messages/oc-bgp:sent/oc-bgp-op:NOTIFICATION {
    deviate "not-supported"; 
  }
  deviation oc-bgp:/bgp/neighbors/oc-bgp:neighbor/state/oc-bgp:messages/oc-bgp:received/oc-bgp-op:UPDATE {
    deviate "not-supported"; 
  }
  deviation oc-bgp:/bgp/neighbors/oc-bgp:neighbor/state/oc-bgp:messages/oc-bgp:received/oc-bgp-op:NOTIFICATION {
    deviate "not-supported"; 
  }
  deviation oc-bgp:/bgp/neighbors/oc-bgp:neighbor/state/oc-bgp:queues/oc-bgp-op:input {
    deviate "not-supported"; 
  }
  deviation oc-bgp:/bgp/neighbors/oc-bgp:neighbor/state/oc-bgp:queues/oc-bgp-op:output {
    deviate "not-supported"; 
  }
  deviation oc-bgp:/oc-bgp:bgp/oc-bgp:neighbors/neighbor/timers/state/oc-bgp-op:uptime {
    deviate "not-supported"; 
  }
  deviation oc-bgp:/oc-bgp:bgp/oc-bgp:neighbors/neighbor/timers/state/oc-bgp-op:negotiated-hold-time {
    deviate "not-supported"; 
  }
  deviation oc-bgp:/bgp/neighbors/neighbor/error-handling/state/oc-bgp-op:erroneous-update-messages {
    deviate "not-supported"; 
  }
  deviation oc-bgp:/bgp/neighbors/neighbor/graceful-restart/state/oc-bgp-op:peer-restart-time {
    deviate "not-supported"; 
  }
  deviation oc-bgp:/bgp/neighbors/neighbor/graceful-restart/state/oc-bgp-op:peer-restarting {
    deviate "not-supported"; 
  }
  deviation oc-bgp:/bgp/neighbors/neighbor/graceful-restart/state/oc-bgp-op:local-restarting {
    deviate "not-supported"; 
  }
  deviation oc-bgp:/bgp/neighbors/neighbor/graceful-restart/state/oc-bgp-op:mode {
    deviate "not-supported"; 
  }
  deviation oc-bgp:/bgp/peer-groups/peer-group/state/oc-bgp-op:total-paths {
    deviate "not-supported"; 
  }
  deviation oc-bgp:/bgp/peer-groups/peer-group/state/oc-bgp-op:total-prefixes {
    deviate "not-supported"; 
  }
  deviation oc-bgp:/bgp/global/afi-safis/afi-safi/state/oc-bgp-op:total-paths {
    deviate "not-supported"; 
  }
  deviation oc-bgp:/bgp/global/afi-safis/afi-safi/state/oc-bgp-op:total-prefixes {
    deviate "not-supported"; 
  }
  deviation oc-bgp:/bgp/neighbors/neighbor/afi-safis/afi-safi/state/oc-bgp-op:active {
    deviate "not-supported"; 
  }
  deviation oc-bgp:/bgp/neighbors/neighbor/afi-safis/afi-safi/state/oc-bgp-op:prefixes/oc-bgp-op:received {
    deviate "not-supported"; 
  }
  deviation oc-bgp:/bgp/neighbors/neighbor/afi-safis/afi-safi/state/oc-bgp-op:prefixes/oc-bgp-op:sent {
    deviate "not-supported"; 
  }
  deviation oc-bgp:/bgp/neighbors/neighbor/afi-safis/afi-safi/state/oc-bgp-op:prefixes/oc-bgp-op:installed {
    deviate "not-supported"; 
  }
  deviation oc-bgp:/bgp/neighbors/neighbor/afi-safis/afi-safi/graceful-restart/state/oc-bgp-op:received {
    deviate "not-supported"; 
  }
  deviation oc-bgp:/bgp/neighbors/neighbor/afi-safis/afi-safi/graceful-restart/state/oc-bgp-op:advertised {
    deviate "not-supported"; 
  }
  deviation oc-bgp:bgp/oc-bgp:global/oc-bgp:state/oc-bgp-op:total-paths {
    deviate "not-supported"; 
  }
  deviation oc-bgp:bgp/oc-bgp:global/oc-bgp:state/oc-bgp-op:total-prefixes {
    deviate "not-supported"; 
  }
  deviation oc-bgp:bgp/oc-bgp:global/oc-bgp-mp:route-selection-options/oc-bgp-mp:config/oc-bgp-mp:advertise-inactive-routes {
    deviate "not-supported"; 
  }
  deviation oc-bgp:bgp/oc-bgp:global/oc-bgp-mp:route-selection-options/oc-bgp-mp:config/oc-bgp-mp:enable-aigp {
    deviate "not-supported"; 
  }
  deviation oc-bgp:bgp/oc-bgp:global/oc-bgp-mp:route-selection-options/oc-bgp-mp:config/oc-bgp-mp:ignore-next-hop-igp-metric {
    deviate "not-supported"; 
  }
  deviation oc-bgp:bgp/oc-bgp:global/oc-bgp-mp:route-selection-options/oc-bgp-mp:state/oc-bgp-mp:advertise-inactive-routes {
    deviate "not-supported"; 
  }
  deviation oc-bgp:bgp/oc-bgp:global/oc-bgp-mp:route-selection-options/oc-bgp-mp:state/oc-bgp-mp:enable-aigp {
    deviate "not-supported"; 
  }
  deviation oc-bgp:bgp/oc-bgp:global/oc-bgp-mp:route-selection-options/oc-bgp-mp:state/oc-bgp-mp:ignore-next-hop-igp-metric {
    deviate "not-supported"; 
  }
  deviation oc-bgp:bgp/oc-bgp:global/oc-bgp:confederation/oc-bgp:config/oc-bgp:enabled {
    deviate "not-supported"; 
  }
  deviation oc-bgp:bgp/oc-bgp:global/oc-bgp:confederation/oc-bgp:config/oc-bgp:member-as {
    deviate "not-supported"; 
  }
  deviation oc-bgp:bgp/oc-bgp:global/oc-bgp:confederation/oc-bgp:state/oc-bgp:member-as {
    deviate "not-supported"; 
  }
  deviation oc-bgp:bgp/oc-bgp:global/oc-bgp-mp:use-multiple-paths/oc-bgp-mp:config/oc-bgp-mp:enabled {
    deviate "not-supported"; 
  }
  deviation oc-bgp:bgp/oc-bgp:global/oc-bgp-mp:use-multiple-paths/oc-bgp-mp:state/oc-bgp-mp:enabled {
    deviate "not-supported"; 
  }
  deviation oc-bgp:bgp/oc-bgp:global/oc-bgp-mp:use-multiple-paths/oc-bgp-mp:ebgp/oc-bgp-mp:config/oc-bgp-mp:allow-multiple-as {
    deviate "not-supported"; 
  }
  deviation oc-bgp:bgp/oc-bgp:global/oc-bgp-mp:use-multiple-paths/oc-bgp-mp:ebgp/oc-bgp-mp:state/oc-bgp-mp:allow-multiple-as {
    deviate "not-supported"; 
  }
  deviation oc-bgp:bgp/oc-bgp:global/oc-bgp:afi-safis/oc-bgp-mp:afi-safi/oc-bgp-mp:graceful-restart/oc-bgp-mp:config/oc-bgp-mp:enabled {
    deviate "not-supported"; 
  }
  deviation oc-bgp:bgp/oc-bgp:global/oc-bgp:afi-safis/oc-bgp-mp:afi-safi/oc-bgp-mp:config/oc-bgp-mp:enabled {
    deviate "not-supported"; 
  }
  deviation oc-bgp:bgp/oc-bgp:global/oc-bgp:afi-safis/oc-bgp-mp:afi-safi/oc-rpol:apply-policy/oc-rpol:config/oc-rpol:import-policy {
    deviate "not-supported"; 
  }
  deviation oc-bgp:bgp/oc-bgp:global/oc-bgp:afi-safis/oc-bgp-mp:afi-safi/oc-rpol:apply-policy/oc-rpol:config/oc-rpol:default-import-policy {
    deviate "not-supported"; 
  }
  deviation oc-bgp:bgp/oc-bgp:global/oc-bgp:afi-safis/oc-bgp-mp:afi-safi/oc-rpol:apply-policy/oc-rpol:config/oc-rpol:export-policy {
    deviate "not-supported"; 
  }
  deviation oc-bgp:bgp/oc-bgp:global/oc-bgp:afi-safis/oc-bgp-mp:afi-safi/oc-rpol:apply-policy/oc-rpol:config/oc-rpol:default-export-policy {
    deviate "not-supported"; 
  }
  deviation oc-bgp:bgp/oc-bgp:global/oc-bgp:afi-safis/oc-bgp-mp:afi-safi/oc-rpol:apply-policy/oc-rpol:state/oc-rpol:import-policy {
    deviate "not-supported"; 
  }
  deviation oc-bgp:bgp/oc-bgp:global/oc-bgp:afi-safis/oc-bgp-mp:afi-safi/oc-rpol:apply-policy/oc-rpol:state/oc-rpol:default-import-policy {
    deviate "not-supported"; 
  }
  deviation oc-bgp:bgp/oc-bgp:global/oc-bgp:afi-safis/oc-bgp-mp:afi-safi/oc-rpol:apply-policy/oc-rpol:state/oc-rpol:export-policy {
    deviate "not-supported"; 
  }
  deviation oc-bgp:bgp/oc-bgp:global/oc-bgp:afi-safis/oc-bgp-mp:afi-safi/oc-rpol:apply-policy/oc-rpol:state/oc-rpol:default-export-policy {
    deviate "not-supported"; 
  }
  deviation oc-bgp:bgp/oc-bgp:global/oc-bgp:afi-safis/oc-bgp-mp:afi-safi/oc-bgp-mp:ipv4-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:ipv4-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:ipv4-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:ipv4-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:ipv4-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:ipv4-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:ipv4-unicast/oc-bgp-mp:config/oc-bgp-mp:send-default-route {
    deviate "not-supported"; 
  }
  deviation oc-bgp:bgp/oc-bgp:global/oc-bgp:afi-safis/oc-bgp-mp:afi-safi/oc-bgp-mp:ipv4-unicast/oc-bgp-mp:state/oc-bgp-mp:send-default-route {
    deviate "not-supported"; 
  }
  deviation oc-bgp:bgp/oc-bgp:global/oc-bgp:afi-safis/oc-bgp-mp:afi-safi/oc-bgp-mp:ipv6-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:ipv6-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:ipv6-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:ipv6-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:ipv6-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:ipv6-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:ipv6-unicast/oc-bgp-mp:config/oc-bgp-mp:send-default-route {
    deviate "not-supported"; 
  }
  deviation oc-bgp:bgp/oc-bgp:global/oc-bgp:afi-safis/oc-bgp-mp:afi-safi/oc-bgp-mp:ipv6-unicast/oc-bgp-mp:state/oc-bgp-mp:send-default-route {
    deviate "not-supported"; 
  }
  deviation oc-bgp:bgp/oc-bgp:global/oc-bgp:afi-safis/oc-bgp-mp:afi-safi/oc-bgp-mp:ipv4-labeled-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:ipv4-labeled-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:ipv4-labeled-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:ipv4-labeled-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:ipv4-labeled-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:ipv4-labeled-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:ipv6-labeled-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:ipv6-labeled-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:ipv6-labeled-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:ipv6-labeled-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:ipv6-labeled-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:ipv6-labeled-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l3vpn-ipv4-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l3vpn-ipv4-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l3vpn-ipv4-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l3vpn-ipv4-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l3vpn-ipv4-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l3vpn-ipv4-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l3vpn-ipv6-unicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l3vpn-ipv6-unicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l3vpn-ipv6-unicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l3vpn-ipv6-unicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l3vpn-ipv6-unicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l3vpn-ipv6-unicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l3vpn-ipv4-multicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l3vpn-ipv4-multicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l3vpn-ipv4-multicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l3vpn-ipv4-multicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l3vpn-ipv4-multicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l3vpn-ipv4-multicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l3vpn-ipv6-multicast/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l3vpn-ipv6-multicast/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l3vpn-ipv6-multicast/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l3vpn-ipv6-multicast/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l3vpn-ipv6-multicast/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l3vpn-ipv6-multicast/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l2vpn-vpls/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l2vpn-vpls/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l2vpn-vpls/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l2vpn-vpls/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l2vpn-vpls/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l2vpn-vpls/oc-bgp-mp:prefix-limit/oc-bgp-mp:state/oc-bgp-mp:restart-timer {
    deviate "not-supported"; 
  }
  deviation oc-bgp:bgp/oc-bgp:global/oc-bgp:afi-safis/oc-bgp-mp:afi-safi/oc-bgp-mp:l2vpn-evpn/oc-bgp-mp:prefix-limit/oc-bgp-mp:config/oc-bgp-mp:max-prefixes {
    deviate "not-supported"; 
  }
  deviation oc-bgp:bgp/oc-bgp:global/oc-bgp:afi-safis/oc-bgp-mp:afi-safi/oc-bgp-mp:l2vpn-evpn/oc-bgp-mp:prefix-limit/oc-bgp-mp:config/oc-bgp-mp:shutdown-threshold-pct {
    deviate "not-supported"; 
  }
  deviation oc-bgp:bgp/oc-bgp:global/oc-bgp:afi-safis/oc-bgp-mp:afi-safi/oc-bgp-mp:l2vpn-evpn/oc-bgp-mp:prefix-limit/oc-bgp-mp:config/oc-bgp-mp:restart-timer {
    deviate "not-supported"; 
  }
  deviation oc-bgp:bgp/oc-bgp:global/oc-bgp:afi-safis/oc-bgp-mp:afi-safi/oc-bgp-mp:l2vpn-evpn/oc-bgp-mp:prefix-limit/oc-bgp-mp:state/oc-bgp-mp:max-prefixes {
    deviate "not-supported"; 
  }
  deviation oc-bgp:bgp/oc-bgp:global/oc-bgp:afi-safis/oc-bgp-mp:afi-safi/oc-bgp-mp:l2vpn-evpn/oc-bgp-mp:prefix-limit/oc-bgp-mp:state/oc-bgp-mp:shutdown-threshold-pct {
    deviate "not-supported"; 
  }
  deviation oc-bgp:bgp/oc-bgp:global/oc-bgp:afi-safis/oc-bgp-mp:afi-safi/oc-bgp-mp:l2vpn-evpn/oc-bgp-mp:prefix-limit/oc-bgp-mp:state/oc-bgp-mp:restart-timer {
    deviate "not-supported"; 
  }
  deviation oc-bgp:bgp/oc-bgp:global/oc-rpol:apply-policy/oc-rpol:config/oc-rpol:import-policy {
    deviate "not-supported"; 
  }
  deviation oc-bgp:bgp/oc-bgp:global/oc-rpol:apply-policy/oc-rpol:config/oc-rpol:default-import-policy {
    deviate "not-supported"; 
  }
  deviation oc-bgp:bgp/oc-bgp:global/oc-rpol:apply-policy/oc-rpol:config/oc-rpol:export-policy {
    deviate "not-supported"; 
  }
  deviation oc-bgp:bgp/oc-bgp:global/oc-rpol:apply-policy/oc-rpol:config/oc-rpol:default-export-policy {
    deviate "not-supported"; 
  }
  deviation oc-bgp:bgp/oc-bgp:global/oc-rpol:apply-policy/oc-rpol:state/oc-rpol:import-policy {
    deviate "not-supported"; 
  }
  deviation oc-bgp:bgp/oc-bgp:global/oc-rpol:apply-policy/oc-rpol:state/oc-rpol:default-import-policy {
    deviate "not-supported"; 
  }
  deviation oc-bgp:bgp/oc-bgp:global/oc-rpol:apply-policy/oc-rpol:state/oc-rpol:export-policy {
    deviate "not-supported"; 
  }
  deviation oc-bgp:bgp/oc-bgp:global/oc-rpol:apply-policy/oc-rpol:state/oc-rpol:default-export-policy {
    deviate "not-supported"; 
  }
  deviation oc-bgp:bgp/oc-bgp:neighbors/oc-bgp:neighbor/oc-bgp:config/oc-bgp:peer-type {
    deviate "not-supported"; 
  }
  deviation oc-bgp:bgp/oc-bgp:neighbors/oc-bgp:neighbor/oc-bgp:config/oc-bgp:route-flap-damping {
    deviate "not-supported"; 
  }
  deviation oc-bgp:bgp/oc-bgp:neighbors/oc-bgp:neighbor/oc-bgp:state/oc-bgp:peer-type {
    deviate "not-supported"; 
  }
  deviation oc-bgp:bgp/oc-bgp:neighbors/oc-bgp:neighbor/oc-bgp:state/oc-bgp:route-flap-damping {
    deviate "not-supported"; 
  }
  deviation oc-bgp:bgp/oc-bgp:neighbors/oc-bgp:neighbor/oc-bgp:timers/oc-bgp:config/oc-bgp:connect-retry {
    deviate "not-supported"; 
  }
  deviation oc-bgp:bgp/oc-bgp:neighbors/oc-bgp:neighbor/oc-bgp:timers/oc-bgp:state/oc-bgp:connect-retry {
    deviate "not-supported"; 
  }
  deviation oc-bgp:bgp/oc-bgp:neighbors/oc-bgp:neighbor/oc-bgp:transport/oc-bgp:config/oc-bgp:tcp-mss {
    deviate "not-supported"; 
  }
  deviation oc-bgp:bgp/oc-bgp:neighbors/oc-bgp:neighbor/oc-bgp:transport/oc-bgp:config/oc-bgp:mtu-discovery {
    deviate "not-supported"; 
  }
  deviation oc-bgp:bgp/oc-bgp:neighbors/oc-bgp:neighbor/oc-bgp:transport/oc-bgp:config/oc-bgp:local-address {
    deviate "not-supported"; 
  }
  deviation oc-bgp:bgp/oc-bgp:neighbors/oc-bgp:neighbor/oc-bgp:transport/oc-bgp:state/oc-bgp:tcp-mss {
    deviate "not-supported"; 
  }
  deviation oc-bgp:bgp/oc-bgp:neighbors/oc-bgp:neighbor/oc-bgp:transport/oc-bgp:state/oc-bgp:mtu-discovery {
    deviate "not-supported"; 
  }
  deviation oc-bgp:bgp/oc-bgp:neighbors/oc-bgp:neighbor/oc-bgp:error-handling/oc-bgp:config/oc-bgp:treat-as-withdraw {
    deviate "not-supported"; 
  }
  deviation oc-bgp:bgp/oc-bgp:neighbors/oc-bgp:neighbor/oc-bgp:error-handling/oc-bgp:state/oc-bgp:treat-as-withdraw {
    deviate "not-supported"; 
  }
  deviation oc-bgp:bgp/oc-bgp:neighbors/oc-bgp:neighbor/oc-bgp:ebgp-multihop/oc-bgp:config/oc-bgp:enabled {
    deviate "not-supported"; 
  }
  deviation oc-bgp:bgp/oc-bgp:neighbors/oc-bgp:neighbor/oc-bgp:as-path-options/oc-bgp:config/oc-bgp:replace-peer-as {
    deviate "not-supported"; 
  }
  deviation oc-bgp:bgp/oc-bgp:neighbors/oc-bgp:neighbor/oc-bgp:as-path-options/oc-bgp:state/oc-bgp:replace-peer-as {
    deviate "not-supported"; 
  }
  deviation oc-bgp:bgp/oc-bgp:neighbors/oc-bgp:neighbor/oc-bgp:add-paths/oc-bgp:config/oc-bgp:receive {
    deviate "not-supported"; 
  }
  deviation oc-bgp:bgp/oc-bgp:neighbors/oc-bgp:neighbor/oc-bgp:add-paths/oc-bgp:config/oc-bgp:send-max {
    deviate "not-supported"; 
  }
  deviation oc-bgp:bgp/oc-bgp:neighbors/oc-bgp:neighbor/oc-bgp:add-paths/oc-bgp:config/oc-bgp:eligible-prefix-policy {
    deviate "not-supported"; 
  }
  deviation oc-bgp:bgp/oc-bgp:neighbors/oc-bgp:neighbor/oc-bgp:add-paths/oc-bgp:state/oc-bgp:receive {
    deviate "not-supported"; 
  }
  deviation oc-bgp:bgp/oc-bgp:neighbors/oc-bgp:neighbor/oc-bgp:add-paths/oc-bgp:state/oc-bgp:send-max {
    deviate "not-supported"; 
  }
  deviation oc-bgp:bgp/oc-bgp:neighbors/oc-bgp:neighbor/oc-bgp:add-paths/oc-bgp:state/oc-bgp:eligible-prefix-policy {
    deviate "not-supported"; 
  }
  deviation oc-bgp:bgp/oc-bgp:neighbors/oc-bgp:neighbor/oc-bgp:afi-safis/oc-bgp-mp:afi-safi/oc-bgp-mp:graceful-restart/oc-bgp-mp:config/oc-bgp-mp:enabled {
    deviate "not-supported"; 
  }
  deviation oc-bgp:bgp/oc-bgp:neighbors/oc-bgp:neighbor/oc-bgp:afi-safis/oc-bgp-mp:afi-safi/oc-bgp-mp:config/oc-bgp-mp:enabled {
    deviate "not-supported"; 
  }
  deviation oc-bgp:bgp/oc-bgp:neighbors/oc-bgp:neighbor/oc-bgp:afi-safis/oc-bgp-mp:afi-safi/oc-rpol:apply-policy/oc-rpol:config/oc-rpol:import-policy {
    deviate "not-supported"; 
  }
  deviation oc-bgp:bgp/oc-bgp:neighbors/oc-bgp:neighbor/oc-bgp:afi-safis/oc-bgp-mp:afi-safi/oc-rpol:apply-policy/oc-rpol:config/oc-rpol:default-import-policy {
    deviate "not-supported"; 
  }
  deviation oc-bgp:bgp/oc-bgp:neighbors/oc-bgp:neighbor/oc-bgp:afi-safis/oc-bgp-mp:afi-safi/oc-rpol:apply-policy/oc-rpol:config/oc-rpol:export-policy {
    deviate "not-supported"; 
  }
  deviation oc-bgp:bgp/oc-bgp:neighbors/oc-bgp:neighbor/oc-bgp:afi-safis/oc-bgp-mp:afi-safi/oc-rpol:apply-policy/oc-rpol:config/oc-rpol:default-export-policy {
    deviate "not-supported"; 
  }
  deviation oc-bgp:bgp/oc-bgp:neighbors/oc-bgp:neighbor/oc-bgp:afi-safis/oc-bgp-mp:afi-safi/oc-rpol:apply-policy/oc-rpol:state/oc-rpol:import-policy {
    deviate "not-supported"; 
  }
  deviation oc-bgp:bgp/oc-bgp:neighbors/oc-bgp:neighbor/oc-bgp:afi-safis/oc-bgp-mp:afi-safi/oc-rpol:apply-policy/oc-rpol:state/oc-rpol:default-import-policy {
    deviate "not-supported"; 
  }
  deviation oc-bgp:bgp/oc-bgp:neighbors/oc-bgp:neighbor/oc-bgp:afi-safis/oc-bgp-mp:afi-safi/oc-rpol:apply-policy/oc-rpol:state/oc-rpol:export-policy {
    deviate "not-supported"; 
  }
  deviation oc-bgp:bgp/oc-bgp:neighbors/oc-bgp:neighbor/oc-bgp:afi-safis/oc-bgp-mp:afi-safi/oc-rpol:apply-policy/oc-rpol:state/oc-rpol:default-export-policy {
    deviate "not-supported"; 
  }
  deviation oc-bgp:bgp/oc-bgp:neighbors/oc-bgp:neighbor/oc-bgp:graceful-restart/oc-bgp:config/oc-bgp:enabled {
    deviate "not-supported"; 
  }
  deviation oc-bgp:bgp/oc-bgp:neighbors/oc-bgp:neighbor/oc-bgp:graceful-restart/oc-bgp:config/oc-bgp:restart-time {
    deviate "not-supported"; 
  }
  deviation oc-bgp:bgp/oc-bgp:neighbors/oc-bgp:neighbor/oc-bgp:graceful-restart/oc-bgp:config/oc-bgp:stale-routes-time {
    deviate "not-supported"; 
  }
  deviation oc-bgp:bgp/oc-bgp:neighbors/oc-bgp:neighbor/oc-bgp:graceful-restart/oc-bgp:config/oc-bgp:helper-only {
    deviate "not-supported"; 
  }
  deviation oc-bgp:bgp/oc-bgp:neighbors/oc-bgp:neighbor/oc-rpol:apply-policy/oc-rpol:config/oc-rpol:import-policy {
    deviate "not-supported"; 
  }
  deviation oc-bgp:bgp/oc-bgp:neighbors/oc-bgp:neighbor/oc-rpol:apply-policy/oc-rpol:config/oc-rpol:default-import-policy {
    deviate "not-supported"; 
  }
  deviation oc-bgp:bgp/oc-bgp:neighbors/oc-bgp:neighbor/oc-rpol:apply-policy/oc-rpol:config/oc-rpol:export-policy {
    deviate "not-supported"; 
  }
  deviation oc-bgp:bgp/oc-bgp:neighbors/oc-bgp:neighbor/oc-rpol:apply-policy/oc-rpol:config/oc-rpol:default-export-policy {
    deviate "not-supported"; 
  }
  deviation oc-bgp:bgp/oc-bgp:neighbors/oc-bgp:neighbor/oc-rpol:apply-policy/oc-rpol:state/oc-rpol:import-policy {
    deviate "not-supported"; 
  }
  deviation oc-bgp:bgp/oc-bgp:neighbors/oc-bgp:neighbor/oc-rpol:apply-policy/oc-rpol:state/oc-rpol:default-import-policy {
    deviate "not-supported"; 
  }
  deviation oc-bgp:bgp/oc-bgp:neighbors/oc-bgp:neighbor/oc-rpol:apply-policy/oc-rpol:state/oc-rpol:export-policy {
    deviate "not-supported"; 
  }
  deviation oc-bgp:bgp/oc-bgp:neighbors/oc-bgp:neighbor/oc-rpol:apply-policy/oc-rpol:state/oc-rpol:default-export-policy {
    deviate "not-supported"; 
  }
  deviation oc-bgp:bgp/oc-bgp:peer-groups/oc-bgp:peer-group/oc-bgp:config/oc-bgp:peer-type {
    deviate "not-supported"; 
  }
  deviation oc-bgp:bgp/oc-bgp:peer-groups/oc-bgp:peer-group/oc-bgp:config/oc-bgp:route-flap-damping {
    deviate "not-supported"; 
  }
  deviation oc-bgp:bgp/oc-bgp:peer-groups/oc-bgp:peer-group/oc-bgp:state/oc-bgp:peer-type {
    deviate "not-supported"; 
  }
  deviation oc-bgp:bgp/oc-bgp:peer-groups/oc-bgp:peer-group/oc-bgp:state/oc-bgp:route-flap-damping {
    deviate "not-supported"; 
  }
  deviation oc-bgp:bgp/oc-bgp:peer-groups/oc-bgp:peer-group/oc-bgp:timers/oc-bgp:config/oc-bgp:connect-retry {
    deviate "not-supported"; 
  }
  deviation oc-bgp:bgp/oc-bgp:peer-groups/oc-bgp:peer-group/oc-bgp:timers/oc-bgp:state/oc-bgp:connect-retry {
    deviate "not-supported"; 
  }
  deviation oc-bgp:bgp/oc-bgp:peer-groups/oc-bgp:peer-group/oc-bgp:transport/oc-bgp:config/oc-bgp:tcp-mss {
    deviate "not-supported"; 
  }
  deviation oc-bgp:bgp/oc-bgp:peer-groups/oc-bgp:peer-group/oc-bgp:transport/oc-bgp:config/oc-bgp:mtu-discovery {
    deviate "not-supported"; 
  }
  deviation oc-bgp:bgp/oc-bgp:peer-groups/oc-bgp:peer-group/oc-bgp:transport/oc-bgp:config/oc-bgp:local-address {
    deviate "not-supported"; 
  }
  deviation oc-bgp:bgp/oc-bgp:peer-groups/oc-bgp:peer-group/oc-bgp:transport/oc-bgp:state/oc-bgp:tcp-mss {
    deviate "not-supported"; 
  }
  deviation oc-bgp:bgp/oc-bgp:peer-groups/oc-bgp:peer-group/oc-bgp:transport/oc-bgp:state/oc-bgp:mtu-discovery {
    deviate "not-supported"; 
  }
  deviation oc-bgp:bgp/oc-bgp:peer-groups/oc-bgp:peer-group/oc-bgp:transport/oc-bgp:state/oc-bgp:local-address {
    deviate "not-supported"; 
  }
  deviation oc-bgp:bgp/oc-bgp:peer-groups/oc-bgp:peer-group/oc-bgp:error-handling/oc-bgp:config/oc-bgp:treat-as-withdraw {
    deviate "not-supported"; 
  }
  deviation oc-bgp:bgp/oc-bgp:peer-groups/oc-bgp:peer-group/oc-bgp:error-handling/oc-bgp:state/oc-bgp:treat-as-withdraw {
    deviate "not-supported"; 
  }
  deviation oc-bgp:bgp/oc-bgp:peer-groups/oc-bgp:peer-group/oc-bgp:ebgp-multihop/oc-bgp:config/oc-bgp:enabled {
    deviate "not-supported"; 
  }
  deviation oc-bgp:bgp/oc-bgp:peer-groups/oc-bgp:peer-group/oc-bgp:route-reflector/oc-bgp:config/oc-bgp:route-reflector-client {
    deviate "not-supported"; 
  }
  deviation oc-bgp:bgp/oc-bgp:peer-groups/oc-bgp:peer-group/oc-bgp:route-reflector/oc-bgp:state/oc-bgp:route-reflector-client {
    deviate "not-supported"; 
  }
  deviation oc-bgp:bgp/oc-bgp:peer-groups/oc-bgp:peer-group/oc-bgp:as-path-options/oc-bgp:config/oc-bgp:allow-own-as {
    deviate "not-supported"; 
  }
  deviation oc-bgp:bgp/oc-bgp:peer-groups/oc-bgp:peer-group/oc-bgp:as-path-options/oc-bgp:config/oc-bgp:replace-peer-as {
    deviate "not-supported"; 
  }
  deviation oc-bgp:bgp/oc-bgp:peer-groups/oc-bgp:peer-group/oc-bgp:as-path-options/oc-bgp:state/oc-bgp:allow-own-as {
    deviate "not-supported"; 
  }
  deviation oc-bgp:bgp/oc-bgp:peer-groups/oc-bgp:peer-group/oc-bgp:as-path-options/oc-bgp:state/oc-bgp:replace-peer-as {
    deviate "not-supported"; 
  }
  deviation oc-bgp:bgp/oc-bgp:peer-groups/oc-bgp:peer-group/oc-bgp:add-paths/oc-bgp:config/oc-bgp:receive {
    deviate "not-supported"; 
  }
  deviation oc-bgp:bgp/oc-bgp:peer-groups/oc-bgp:peer-group/oc-bgp:add-paths/oc-bgp:config/oc-bgp:send-max {
    deviate "not-supported"; 
  }
  deviation oc-bgp:bgp/oc-bgp:peer-groups/oc-bgp:peer-group/oc-bgp:add-paths/oc-bgp:config/oc-bgp:eligible-prefix-policy {
    deviate "not-supported"; 
  }
  deviation oc-bgp:bgp/oc-bgp:peer-groups/oc-bgp:peer-group/oc-bgp:add-paths/oc-bgp:state/oc-bgp:receive {
    deviate "not-supported"; 
  }
  deviation oc-bgp:bgp/oc-bgp:peer-groups/oc-bgp:peer-group/oc-bgp:add-paths/oc-bgp:state/oc-bgp:send-max {
    deviate "not-supported"; 
  }
  deviation oc-bgp:bgp/oc-bgp:peer-groups/oc-bgp:peer-group/oc-bgp:add-paths/oc-bgp:state/oc-bgp:eligible-prefix-policy {
    deviate "not-supported"; 
  }
  deviation oc-bgp:bgp/oc-bgp:peer-groups/oc-bgp:peer-group/oc-bgp:afi-safis/oc-bgp-mp:afi-safi/oc-bgp-mp:graceful-restart/oc-bgp-mp:config/oc-bgp-mp:enabled {
    deviate "not-supported"; 
  }
  deviation oc-bgp:bgp/oc-bgp:peer-groups/oc-bgp:peer-group/oc-bgp:afi-safis/oc-bgp-mp:afi-safi/oc-bgp-mp:config/oc-bgp-mp:enabled {
    deviate "not-supported"; 
  }
  deviation oc-bgp:bgp/oc-bgp:peer-groups/oc-bgp:peer-group/oc-bgp:afi-safis/oc-bgp-mp:afi-safi/oc-rpol:apply-policy/oc-rpol:config/oc-rpol:import-policy {
    deviate "not-supported"; 
  }
  deviation oc-bgp:bgp/oc-bgp:peer-groups/oc-bgp:peer-group/oc-bgp:afi-safis/oc-bgp-mp:afi-safi/oc-rpol:apply-policy/oc-rpol:config/oc-rpol:default-import-policy {
    deviate "not-supported"; 
  }
  deviation oc-bgp:bgp/oc-bgp:peer-groups/oc-bgp:peer-group/oc-bgp:afi-safis/oc-bgp-mp:afi-safi/oc-rpol:apply-policy/oc-rpol:config/oc-rpol:export-policy {
    deviate "not-supported"; 
  }
  deviation oc-bgp:bgp/oc-bgp:peer-groups/oc-bgp:peer-group/oc-bgp:afi-safis/oc-bgp-mp:afi-safi/oc-rpol:apply-policy/oc-rpol:config/oc-rpol:default-export-policy {
    deviate "not-supported"; 
  }
  deviation oc-bgp:bgp/oc-bgp:peer-groups/oc-bgp:peer-group/oc-bgp:afi-safis/oc-bgp-mp:afi-safi/oc-rpol:apply-policy/oc-rpol:state/oc-rpol:import-policy {
    deviate "not-supported"; 
  }
  deviation oc-bgp:bgp/oc-bgp:peer-groups/oc-bgp:peer-group/oc-bgp:afi-safis/oc-bgp-mp:afi-safi/oc-rpol:apply-policy/oc-rpol:state/oc-rpol:default-import-policy {
    deviate "not-supported"; 
  }
  deviation oc-bgp:bgp/oc-bgp:peer-groups/oc-bgp:peer-group/oc-bgp:afi-safis/oc-bgp-mp:afi-safi/oc-rpol:apply-policy/oc-rpol:state/oc-rpol:export-policy {
    deviate "not-supported"; 
  }
  deviation oc-bgp:bgp/oc-bgp:peer-groups/oc-bgp:peer-group/oc-bgp:afi-safis/oc-bgp-mp:afi-safi/oc-rpol:apply-policy/oc-rpol:state/oc-rpol:default-export-policy {
    deviate "not-supported"; 
  }
  deviation oc-bgp:bgp/oc-bgp:peer-groups/oc-bgp:peer-group/oc-bgp:graceful-restart/oc-bgp:config/oc-bgp:enabled {
    deviate "not-supported"; 
  }
  deviation oc-bgp:bgp/oc-bgp:peer-groups/oc-bgp:peer-group/oc-bgp:graceful-restart/oc-bgp:config/oc-bgp:restart-time {
    deviate "not-supported"; 
  }
  deviation oc-bgp:bgp/oc-bgp:peer-groups/oc-bgp:peer-group/oc-bgp:graceful-restart/oc-bgp:config/oc-bgp:stale-routes-time {
    deviate "not-supported"; 
  }
  deviation oc-bgp:bgp/oc-bgp:peer-groups/oc-bgp:peer-group/oc-bgp:graceful-restart/oc-bgp:config/oc-bgp:helper-only {
    deviate "not-supported"; 
  }
  deviation oc-bgp:bgp/oc-bgp:peer-groups/oc-bgp:peer-group/oc-rpol:apply-policy/oc-rpol:config/oc-rpol:import-policy {
    deviate "not-supported"; 
  }
  deviation oc-bgp:bgp/oc-bgp:peer-groups/oc-bgp:peer-group/oc-rpol:apply-policy/oc-rpol:config/oc-rpol:default-import-policy {
    deviate "not-supported"; 
  }
  deviation oc-bgp:bgp/oc-bgp:peer-groups/oc-bgp:peer-group/oc-rpol:apply-policy/oc-rpol:config/oc-rpol:export-policy {
    deviate "not-supported"; 
  }
  deviation oc-bgp:bgp/oc-bgp:peer-groups/oc-bgp:peer-group/oc-rpol:apply-policy/oc-rpol:config/oc-rpol:default-export-policy {
    deviate "not-supported"; 
  }
  deviation oc-bgp:bgp/oc-bgp:peer-groups/oc-bgp:peer-group/oc-rpol:apply-policy/oc-rpol:state/oc-rpol:import-policy {
    deviate "not-supported"; 
  }
  deviation oc-bgp:bgp/oc-bgp:peer-groups/oc-bgp:peer-group/oc-rpol:apply-policy/oc-rpol:state/oc-rpol:default-import-policy {
    deviate "not-supported"; 
  }
  deviation oc-bgp:bgp/oc-bgp:peer-groups/oc-bgp:peer-group/oc-rpol:apply-policy/oc-rpol:state/oc-rpol:export-policy {
    deviate "not-supported"; 
  }
  deviation oc-bgp:bgp/oc-bgp:peer-groups/oc-bgp:peer-group/oc-rpol:apply-policy/oc-rpol:state/oc-rpol:default-export-policy {
    deviate "not-supported"; 
  }

/* Mapped to device model
 *     Device Model Target: /top:System/top:bgp-items/top:inst-items/top:dom-items/top:Dom-list/top:rtrId
 * Transformation Function: conv_oc_nx_glob_router_id 
 */
  deviation oc-bgp:bgp/oc-bgp:global/oc-bgp:config/oc-bgp:router-id {
    deviate add {
      default "0.0.0.0";
    }
  }

/* Mapped to device model
 *     Device Model Target: /top:System/top:bgp-items/top:inst-items/top:dom-items/top:Dom-list/top:af-items/top:DomAf-list/top:adminDist-items/top:eDist
 * Transformation Function: conv_oc_nx_glob_route_distance 
 */
  deviation oc-bgp:bgp/oc-bgp:global/oc-bgp:default-route-distance/oc-bgp:config/oc-bgp:external-route-distance {
    deviate add {
      default "20";
    }
  }

/* Mapped to device model
 *     Device Model Target: /top:System/top:bgp-items/top:inst-items/top:dom-items/top:Dom-list/top:af-items/top:DomAf-list/top:adminDist-items/top:iDist
 * Transformation Function: conv_oc_nx_glob_route_distance 
 */
  deviation oc-bgp:bgp/oc-bgp:global/oc-bgp:default-route-distance/oc-bgp:config/oc-bgp:internal-route-distance {
    deviate add {
      default "200";
    }
  }

/* Mapped to device model
 *     Device Model Target: /top:System/top:bgp-items/top:inst-items/top:dom-items/top:Dom-list/top:gr-items/top:ctrl
 * Transformation Function: conv_oc_nx_glob_gr_enabled 
 */
  deviation oc-bgp:bgp/oc-bgp:global/oc-bgp:graceful-restart/oc-bgp:config/oc-bgp:enabled {
    deviate add {
      default "true";
    }
  }

/* Mapped to device model
 *     Device Model Target: /top:System/top:bgp-items/top:inst-items/top:dom-items/top:Dom-list/top:gr-items/top:restartIntvl
 * Transformation Function: conv_oc_nx_glob_gr_restart_time 
 */
  deviation oc-bgp:bgp/oc-bgp:global/oc-bgp:graceful-restart/oc-bgp:config/oc-bgp:restart-time {
    deviate add {
      default "120";
    }
  }

/* Mapped to device model
 *     Device Model Target: /top:System/top:bgp-items/top:inst-items/top:dom-items/top:Dom-list/top:gr-items/top:staleIntvl
 * Transformation Function: conv_oc_nx_glob_gr_stale_route_time 
 */
  deviation oc-bgp:bgp/oc-bgp:global/oc-bgp:graceful-restart/oc-bgp:config/oc-bgp:stale-routes-time {
    deviate add {
      default "300";
    }
  }

/* Mapped to device model
 *     Device Model Target: /top:System/top:bgp-items/top:inst-items/top:dom-items/top:Dom-list/top:gr-items/top:ctrl
 * Transformation Function: conv_oc_nx_glob_gr_helper_only 
 */
  deviation oc-bgp:bgp/oc-bgp:global/oc-bgp:graceful-restart/oc-bgp:config/oc-bgp:helper-only {
    deviate add {
      default "false";
    }
  }

/* Mapped to device model
 *     Device Model Target: /top:System/top:bgp-items/top:inst-items/top:dom-items/top:Dom-list/top:peer-items/top:Peer-list/top:holdIntvl
 * Transformation Function: conv_oc_nx_peer_hold_time 
 */
  deviation oc-bgp:bgp/oc-bgp:neighbors/oc-bgp:neighbor/oc-bgp:timers/oc-bgp:config/oc-bgp:hold-time {
    deviate replace {
      default "180";
    }
  }

/* Mapped to device model
 *     Device Model Target: /top:System/top:bgp-items/top:inst-items/top:dom-items/top:Dom-list/top:peer-items/top:Peer-list/top:kaIntvl
 * Transformation Function: conv_oc_nx_peer_keepalive_interval 
 */
  deviation oc-bgp:bgp/oc-bgp:neighbors/oc-bgp:neighbor/oc-bgp:timers/oc-bgp:config/oc-bgp:keepalive-interval {
    deviate replace {
      default "60";
    }
  }

/* Mapped to device model
 *     Device Model Target: /top:System/top:bgp-items/top:inst-items/top:dom-items/top:Dom-list/top:peer-items/top:Peer-list/top:af-items/top:PeerAf-list/top:advIntvl
 * Transformation Function: conv_oc_nx_peer_min_advertisement_interval 
 */
  deviation oc-bgp:bgp/oc-bgp:neighbors/oc-bgp:neighbor/oc-bgp:timers/oc-bgp:config/oc-bgp:minimum-advertisement-interval {
    deviate replace {
      default "0";
    }
  }

/* Mapped to device model
 *     Device Model Target: /top:System/top:bgp-items/top:inst-items/top:dom-items/top:Dom-list/top:peer-items/top:Peer-list/top:logNbrChgs
 * Transformation Function: conv_oc_nx_peer_log_state_changes 
 */
  deviation oc-bgp:bgp/oc-bgp:neighbors/oc-bgp:neighbor/oc-bgp:logging-options/oc-bgp:config/oc-bgp:log-neighbor-state-changes {
    deviate replace {
      default "false";
    }
  }

/* Mapped to device model
 *     Device Model Target: /top:System/top:bgp-items/top:inst-items/top:dom-items/top:Dom-list/top:peer-items/top:Peer-list/top:ttl
 * Transformation Function: conv_oc_nx_peer_ebgp_multihop_ttl 
 */
  deviation oc-bgp:bgp/oc-bgp:neighbors/oc-bgp:neighbor/oc-bgp:ebgp-multihop/oc-bgp:config/oc-bgp:multihop-ttl {
    deviate add {
      default "1";
    }
  }

/* Mapped to device model
 *     Device Model Target: /top:System/top:bgp-items/top:inst-items/top:dom-items/top:Dom-list/top:peercont-items/top:PeerCont-list/top:holdIntvl
 * Transformation Function: conv_oc_nx_peer_group_hold_time 
 */
  deviation oc-bgp:bgp/oc-bgp:peer-groups/oc-bgp:peer-group/oc-bgp:timers/oc-bgp:config/oc-bgp:hold-time {
    deviate replace {
      default "180";
    }
  }

/* Mapped to device model
 *     Device Model Target: /top:System/top:bgp-items/top:inst-items/top:dom-items/top:Dom-list/top:peercont-items/top:PeerCont-list/top:kaIntvl
 * Transformation Function: conv_oc_nx_peer_group_keepalive_interval 
 */
  deviation oc-bgp:bgp/oc-bgp:peer-groups/oc-bgp:peer-group/oc-bgp:timers/oc-bgp:config/oc-bgp:keepalive-interval {
    deviate replace {
      default "60";
    }
  }

/* Mapped to device model
 *     Device Model Target: /top:System/top:bgp-items/top:inst-items/top:dom-items/top:Dom-list/top:peercont-items/top:PeerCont-list/top:af-items/top:PeerAf-list/top:advIntvl
 * Transformation Function: conv_oc_nx_peer_group_min_advertisement_interval 
 */
  deviation oc-bgp:bgp/oc-bgp:peer-groups/oc-bgp:peer-group/oc-bgp:timers/oc-bgp:config/oc-bgp:minimum-advertisement-interval {
    deviate replace {
      default "0";
    }
  }

/* Mapped to device model
 *     Device Model Target: /top:System/top:bgp-items/top:inst-items/top:dom-items/top:Dom-list/top:peercont-items/top:PeerCont-list/top:logNbrChgs
 * Transformation Function: conv_oc_nx_peer_group_log_state_changes 
 */
  deviation oc-bgp:bgp/oc-bgp:peer-groups/oc-bgp:peer-group/oc-bgp:logging-options/oc-bgp:config/oc-bgp:log-neighbor-state-changes {
    deviate replace {
      default "false";
    }
  }

/* Mapped to device model
 *     Device Model Target: /top:System/top:bgp-items/top:inst-items/top:dom-items/top:Dom-list/top:peercont-items/top:PeerCont-list/top:ttl
 * Transformation Function: conv_oc_nx_peer_group_ebgp_multihop_ttl 
 */
  deviation oc-bgp:bgp/oc-bgp:peer-groups/oc-bgp:peer-group/oc-bgp:ebgp-multihop/oc-bgp:config/oc-bgp:multihop-ttl {
    deviate add {
      default "1";
    }
  }
  
/* Mapped to device model
 *     Device Model Target: /top:System/top:bgp-items/top:inst-items/top:dom-items/top:Dom-list/top:pathctrl-items/top:compRtrId
 * Transformation Function: conv_oc_nx_glob_ext_compare_router_id 
 */
  deviation oc-bgp:bgp/oc-bgp:global/oc-bgp:route-selection-options/oc-bgp:config/oc-bgp:external-compare-router-id {
    deviate replace {
      default "false";
    }
  }

}
