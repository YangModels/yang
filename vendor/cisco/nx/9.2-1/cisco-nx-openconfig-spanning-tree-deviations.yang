module cisco-nx-openconfig-spanning-tree-deviations {

  namespace "http://openconfig.net/yang/spanning-tree-deviations";

  prefix "oc-stp-devs";

  import openconfig-spanning-tree { prefix oc-stp; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-spanning-tree module 
     set for Cisco NXOS.
     Copyright (c) 2015-2017 by Cisco Systems, Inc.
     All rights reserved.";

  revision "2018-02-07" {
    description
      "Initial revision applicable to NXOS";
  }

  deviation /oc-stp:stp/oc-stp:global/oc-stp:config/oc-stp:etherchannel-misconfig-guard {
    deviate "not-supported"; 
  }
  deviation /oc-stp:stp/oc-stp:global/oc-stp:config/oc-stp:bpduguard-timeout-recovery {
    deviate "not-supported"; 
  }
  deviation /oc-stp:stp/oc-stp:global/oc-stp:state/oc-stp:enabled-protocol {
    deviate "not-supported"; 
  }
  deviation /oc-stp:stp/oc-stp:global/oc-stp:state/oc-stp:bridge-assurance {
    deviate "not-supported"; 
  }
  deviation /oc-stp:stp/oc-stp:global/oc-stp:state/oc-stp:etherchannel-misconfig-guard {
    deviate "not-supported"; 
  }
  deviation /oc-stp:stp/oc-stp:global/oc-stp:state/oc-stp:bpduguard-timeout-recovery {
    deviate "not-supported"; 
  }
  deviation /oc-stp:stp/oc-stp:global/oc-stp:state/oc-stp:loop-guard {
    deviate "not-supported"; 
  }
  deviation /oc-stp:stp/oc-stp:global/oc-stp:state/oc-stp:bpdu-guard {
    deviate "not-supported"; 
  }
  deviation /oc-stp:stp/oc-stp:global/oc-stp:state/oc-stp:bpdu-filter {
    deviate "not-supported"; 
  }
  deviation /oc-stp:stp/oc-stp:rstp/oc-stp:config/oc-stp:hello-time {
    deviate "not-supported"; 
  }
  deviation /oc-stp:stp/oc-stp:rstp/oc-stp:config/oc-stp:max-age {
    deviate "not-supported"; 
  }
  deviation /oc-stp:stp/oc-stp:rstp/oc-stp:config/oc-stp:forwarding-delay {
    deviate "not-supported"; 
  }
  deviation /oc-stp:stp/oc-stp:rstp/oc-stp:config/oc-stp:hold-count {
    deviate "not-supported"; 
  }
  deviation /oc-stp:stp/oc-stp:rstp/oc-stp:config/oc-stp:bridge-priority {
    deviate "not-supported"; 
  }
  deviation /oc-stp:stp/oc-stp:rstp/oc-stp:state/oc-stp:hello-time {
    deviate "not-supported"; 
  }
  deviation /oc-stp:stp/oc-stp:rstp/oc-stp:state/oc-stp:max-age {
    deviate "not-supported"; 
  }
  deviation /oc-stp:stp/oc-stp:rstp/oc-stp:state/oc-stp:forwarding-delay {
    deviate "not-supported"; 
  }
  deviation /oc-stp:stp/oc-stp:rstp/oc-stp:state/oc-stp:hold-count {
    deviate "not-supported"; 
  }
  deviation /oc-stp:stp/oc-stp:rstp/oc-stp:state/oc-stp:bridge-priority {
    deviate "not-supported"; 
  }
  deviation /oc-stp:stp/oc-stp:rstp/oc-stp:state/oc-stp:bridge-address {
    deviate "not-supported"; 
  }
  deviation /oc-stp:stp/oc-stp:rstp/oc-stp:state/oc-stp:designated-root-priority {
    deviate "not-supported"; 
  }
  deviation /oc-stp:stp/oc-stp:rstp/oc-stp:state/oc-stp:designated-root-address {
    deviate "not-supported"; 
  }
  deviation /oc-stp:stp/oc-stp:rstp/oc-stp:state/oc-stp:root-port {
    deviate "not-supported"; 
  }
  deviation /oc-stp:stp/oc-stp:rstp/oc-stp:state/oc-stp:root-cost {
    deviate "not-supported"; 
  }
  deviation /oc-stp:stp/oc-stp:rstp/oc-stp:state/oc-stp:hold-time {
    deviate "not-supported"; 
  }
  deviation /oc-stp:stp/oc-stp:rstp/oc-stp:state/oc-stp:topology-changes {
    deviate "not-supported"; 
  }
  deviation /oc-stp:stp/oc-stp:rstp/oc-stp:state/oc-stp:time-since-topology-change {
    deviate "not-supported"; 
  }
  deviation /oc-stp:stp/oc-stp:rstp/oc-stp:interfaces/oc-stp:interface {
    deviate "not-supported"; 
  }
  deviation /oc-stp:stp/oc-stp:mstp/oc-stp:config/oc-stp:hold-count {
    deviate "not-supported"; 
  }
  deviation /oc-stp:stp/oc-stp:mstp/oc-stp:state/oc-stp:name {
    deviate "not-supported"; 
  }
  deviation /oc-stp:stp/oc-stp:mstp/oc-stp:state/oc-stp:revision {
    deviate "not-supported"; 
  }
  deviation /oc-stp:stp/oc-stp:mstp/oc-stp:state/oc-stp:max-hop {
    deviate "not-supported"; 
  }
  deviation /oc-stp:stp/oc-stp:mstp/oc-stp:state/oc-stp:hello-time {
    deviate "not-supported"; 
  }
  deviation /oc-stp:stp/oc-stp:mstp/oc-stp:state/oc-stp:max-age {
    deviate "not-supported"; 
  }
  deviation /oc-stp:stp/oc-stp:mstp/oc-stp:state/oc-stp:forwarding-delay {
    deviate "not-supported"; 
  }
  deviation /oc-stp:stp/oc-stp:mstp/oc-stp:state/oc-stp:hold-count {
    deviate "not-supported"; 
  }
  deviation /oc-stp:stp/oc-stp:mstp/oc-stp:mst-instances/oc-stp:mst-instance/oc-stp:state/oc-stp:mst-id {
    deviate "not-supported"; 
  }
  deviation /oc-stp:stp/oc-stp:mstp/oc-stp:mst-instances/oc-stp:mst-instance/oc-stp:state/oc-stp:vlan {
    deviate "not-supported"; 
  }
  deviation /oc-stp:stp/oc-stp:mstp/oc-stp:mst-instances/oc-stp:mst-instance/oc-stp:state/oc-stp:bridge-priority {
    deviate "not-supported"; 
  }
  deviation /oc-stp:stp/oc-stp:mstp/oc-stp:mst-instances/oc-stp:mst-instance/oc-stp:state/oc-stp:bridge-address {
    deviate "not-supported"; 
  }
  deviation /oc-stp:stp/oc-stp:mstp/oc-stp:mst-instances/oc-stp:mst-instance/oc-stp:state/oc-stp:designated-root-priority {
    deviate "not-supported"; 
  }
  deviation /oc-stp:stp/oc-stp:mstp/oc-stp:mst-instances/oc-stp:mst-instance/oc-stp:state/oc-stp:designated-root-address {
    deviate "not-supported"; 
  }
  deviation /oc-stp:stp/oc-stp:mstp/oc-stp:mst-instances/oc-stp:mst-instance/oc-stp:state/oc-stp:root-port {
    deviate "not-supported"; 
  }
  deviation /oc-stp:stp/oc-stp:mstp/oc-stp:mst-instances/oc-stp:mst-instance/oc-stp:state/oc-stp:root-cost {
    deviate "not-supported"; 
  }
  deviation /oc-stp:stp/oc-stp:mstp/oc-stp:mst-instances/oc-stp:mst-instance/oc-stp:state/oc-stp:hold-time {
    deviate "not-supported"; 
  }
  deviation /oc-stp:stp/oc-stp:mstp/oc-stp:mst-instances/oc-stp:mst-instance/oc-stp:state/oc-stp:topology-changes {
    deviate "not-supported"; 
  }
  deviation /oc-stp:stp/oc-stp:mstp/oc-stp:mst-instances/oc-stp:mst-instance/oc-stp:state/oc-stp:time-since-topology-change {
    deviate "not-supported"; 
  }
  deviation /oc-stp:stp/oc-stp:mstp/oc-stp:mst-instances/oc-stp:mst-instance/oc-stp:interfaces/oc-stp:interface/oc-stp:state/oc-stp:name {
    deviate "not-supported"; 
  }
  deviation /oc-stp:stp/oc-stp:mstp/oc-stp:mst-instances/oc-stp:mst-instance/oc-stp:interfaces/oc-stp:interface/oc-stp:state/oc-stp:cost {
    deviate "not-supported"; 
  }
  deviation /oc-stp:stp/oc-stp:mstp/oc-stp:mst-instances/oc-stp:mst-instance/oc-stp:interfaces/oc-stp:interface/oc-stp:state/oc-stp:port-priority {
    deviate "not-supported"; 
  }
  deviation /oc-stp:stp/oc-stp:mstp/oc-stp:mst-instances/oc-stp:mst-instance/oc-stp:interfaces/oc-stp:interface/oc-stp:state/oc-stp:port-num {
    deviate "not-supported"; 
  }
  deviation /oc-stp:stp/oc-stp:mstp/oc-stp:mst-instances/oc-stp:mst-instance/oc-stp:interfaces/oc-stp:interface/oc-stp:state/oc-stp:role {
    deviate "not-supported"; 
  }
  deviation /oc-stp:stp/oc-stp:mstp/oc-stp:mst-instances/oc-stp:mst-instance/oc-stp:interfaces/oc-stp:interface/oc-stp:state/oc-stp:port-state {
    deviate "not-supported"; 
  }
  deviation /oc-stp:stp/oc-stp:mstp/oc-stp:mst-instances/oc-stp:mst-instance/oc-stp:interfaces/oc-stp:interface/oc-stp:state/oc-stp:designated-root-priority {
    deviate "not-supported"; 
  }
  deviation /oc-stp:stp/oc-stp:mstp/oc-stp:mst-instances/oc-stp:mst-instance/oc-stp:interfaces/oc-stp:interface/oc-stp:state/oc-stp:designated-root-address {
    deviate "not-supported"; 
  }
  deviation /oc-stp:stp/oc-stp:mstp/oc-stp:mst-instances/oc-stp:mst-instance/oc-stp:interfaces/oc-stp:interface/oc-stp:state/oc-stp:designated-cost {
    deviate "not-supported"; 
  }
  deviation /oc-stp:stp/oc-stp:mstp/oc-stp:mst-instances/oc-stp:mst-instance/oc-stp:interfaces/oc-stp:interface/oc-stp:state/oc-stp:designated-bridge-priority {
    deviate "not-supported"; 
  }
  deviation /oc-stp:stp/oc-stp:mstp/oc-stp:mst-instances/oc-stp:mst-instance/oc-stp:interfaces/oc-stp:interface/oc-stp:state/oc-stp:designated-bridge-address {
    deviate "not-supported"; 
  }
  deviation /oc-stp:stp/oc-stp:mstp/oc-stp:mst-instances/oc-stp:mst-instance/oc-stp:interfaces/oc-stp:interface/oc-stp:state/oc-stp:designated-port-priority {
    deviate "not-supported"; 
  }
  deviation /oc-stp:stp/oc-stp:mstp/oc-stp:mst-instances/oc-stp:mst-instance/oc-stp:interfaces/oc-stp:interface/oc-stp:state/oc-stp:designated-port-num {
    deviate "not-supported"; 
  }
  deviation /oc-stp:stp/oc-stp:mstp/oc-stp:mst-instances/oc-stp:mst-instance/oc-stp:interfaces/oc-stp:interface/oc-stp:state/oc-stp:forward-transisitions {
    deviate "not-supported"; 
  }
  deviation /oc-stp:stp/oc-stp:mstp/oc-stp:mst-instances/oc-stp:mst-instance/oc-stp:interfaces/oc-stp:interface/oc-stp:state/oc-stp:counters/oc-stp:bpdu-sent {
    deviate "not-supported"; 
  }
  deviation /oc-stp:stp/oc-stp:mstp/oc-stp:mst-instances/oc-stp:mst-instance/oc-stp:interfaces/oc-stp:interface/oc-stp:state/oc-stp:counters/oc-stp:bpdu-received {
    deviate "not-supported"; 
  }
  deviation /oc-stp:stp/oc-stp:rapid-pvst/oc-stp:vlan/oc-stp:config/oc-stp:hold-count {
    deviate "not-supported"; 
  }
  deviation /oc-stp:stp/oc-stp:rapid-pvst/oc-stp:vlan/oc-stp:state/oc-stp:vlan-id {
    deviate "not-supported"; 
  }
  deviation /oc-stp:stp/oc-stp:rapid-pvst/oc-stp:vlan/oc-stp:state/oc-stp:hello-time {
    deviate "not-supported"; 
  }
  deviation /oc-stp:stp/oc-stp:rapid-pvst/oc-stp:vlan/oc-stp:state/oc-stp:max-age {
    deviate "not-supported"; 
  }
  deviation /oc-stp:stp/oc-stp:rapid-pvst/oc-stp:vlan/oc-stp:state/oc-stp:forwarding-delay {
    deviate "not-supported"; 
  }
  deviation /oc-stp:stp/oc-stp:rapid-pvst/oc-stp:vlan/oc-stp:state/oc-stp:hold-count {
    deviate "not-supported"; 
  }
  deviation /oc-stp:stp/oc-stp:rapid-pvst/oc-stp:vlan/oc-stp:state/oc-stp:bridge-priority {
    deviate "not-supported"; 
  }
  deviation /oc-stp:stp/oc-stp:rapid-pvst/oc-stp:vlan/oc-stp:state/oc-stp:bridge-address {
    deviate "not-supported"; 
  }
  deviation /oc-stp:stp/oc-stp:rapid-pvst/oc-stp:vlan/oc-stp:state/oc-stp:designated-root-priority {
    deviate "not-supported"; 
  }
  deviation /oc-stp:stp/oc-stp:rapid-pvst/oc-stp:vlan/oc-stp:state/oc-stp:designated-root-address {
    deviate "not-supported"; 
  }
  deviation /oc-stp:stp/oc-stp:rapid-pvst/oc-stp:vlan/oc-stp:state/oc-stp:root-port {
    deviate "not-supported"; 
  }
  deviation /oc-stp:stp/oc-stp:rapid-pvst/oc-stp:vlan/oc-stp:state/oc-stp:root-cost {
    deviate "not-supported"; 
  }
  deviation /oc-stp:stp/oc-stp:rapid-pvst/oc-stp:vlan/oc-stp:state/oc-stp:hold-time {
    deviate "not-supported"; 
  }
  deviation /oc-stp:stp/oc-stp:rapid-pvst/oc-stp:vlan/oc-stp:state/oc-stp:topology-changes {
    deviate "not-supported"; 
  }
  deviation /oc-stp:stp/oc-stp:rapid-pvst/oc-stp:vlan/oc-stp:state/oc-stp:time-since-topology-change {
    deviate "not-supported"; 
  }
  deviation /oc-stp:stp/oc-stp:rapid-pvst/oc-stp:vlan/oc-stp:interfaces/oc-stp:interface/oc-stp:state/oc-stp:name {
    deviate "not-supported"; 
  }
  deviation /oc-stp:stp/oc-stp:rapid-pvst/oc-stp:vlan/oc-stp:interfaces/oc-stp:interface/oc-stp:state/oc-stp:cost {
    deviate "not-supported"; 
  }
  deviation /oc-stp:stp/oc-stp:rapid-pvst/oc-stp:vlan/oc-stp:interfaces/oc-stp:interface/oc-stp:state/oc-stp:port-priority {
    deviate "not-supported"; 
  }
  deviation /oc-stp:stp/oc-stp:rapid-pvst/oc-stp:vlan/oc-stp:interfaces/oc-stp:interface/oc-stp:state/oc-stp:port-num {
    deviate "not-supported"; 
  }
  deviation /oc-stp:stp/oc-stp:rapid-pvst/oc-stp:vlan/oc-stp:interfaces/oc-stp:interface/oc-stp:state/oc-stp:role {
    deviate "not-supported"; 
  }
  deviation /oc-stp:stp/oc-stp:rapid-pvst/oc-stp:vlan/oc-stp:interfaces/oc-stp:interface/oc-stp:state/oc-stp:port-state {
    deviate "not-supported"; 
  }
  deviation /oc-stp:stp/oc-stp:rapid-pvst/oc-stp:vlan/oc-stp:interfaces/oc-stp:interface/oc-stp:state/oc-stp:designated-root-priority {
    deviate "not-supported"; 
  }
  deviation /oc-stp:stp/oc-stp:rapid-pvst/oc-stp:vlan/oc-stp:interfaces/oc-stp:interface/oc-stp:state/oc-stp:designated-root-address {
    deviate "not-supported"; 
  }
  deviation /oc-stp:stp/oc-stp:rapid-pvst/oc-stp:vlan/oc-stp:interfaces/oc-stp:interface/oc-stp:state/oc-stp:designated-cost {
    deviate "not-supported"; 
  }
  deviation /oc-stp:stp/oc-stp:rapid-pvst/oc-stp:vlan/oc-stp:interfaces/oc-stp:interface/oc-stp:state/oc-stp:designated-bridge-priority {
    deviate "not-supported"; 
  }
  deviation /oc-stp:stp/oc-stp:rapid-pvst/oc-stp:vlan/oc-stp:interfaces/oc-stp:interface/oc-stp:state/oc-stp:designated-bridge-address {
    deviate "not-supported"; 
  }
  deviation /oc-stp:stp/oc-stp:rapid-pvst/oc-stp:vlan/oc-stp:interfaces/oc-stp:interface/oc-stp:state/oc-stp:designated-port-priority {
    deviate "not-supported"; 
  }
  deviation /oc-stp:stp/oc-stp:rapid-pvst/oc-stp:vlan/oc-stp:interfaces/oc-stp:interface/oc-stp:state/oc-stp:designated-port-num {
    deviate "not-supported"; 
  }
  deviation /oc-stp:stp/oc-stp:rapid-pvst/oc-stp:vlan/oc-stp:interfaces/oc-stp:interface/oc-stp:state/oc-stp:forward-transisitions {
    deviate "not-supported"; 
  }
  deviation /oc-stp:stp/oc-stp:rapid-pvst/oc-stp:vlan/oc-stp:interfaces/oc-stp:interface/oc-stp:state/oc-stp:counters/oc-stp:bpdu-sent {
    deviate "not-supported"; 
  }
  deviation /oc-stp:stp/oc-stp:rapid-pvst/oc-stp:vlan/oc-stp:interfaces/oc-stp:interface/oc-stp:state/oc-stp:counters/oc-stp:bpdu-received {
    deviate "not-supported"; 
  }
  deviation /oc-stp:stp/oc-stp:interfaces/oc-stp:interface/oc-stp:state/oc-stp:name {
    deviate "not-supported"; 
  }
  deviation /oc-stp:stp/oc-stp:interfaces/oc-stp:interface/oc-stp:state/oc-stp:edge-port {
    deviate "not-supported"; 
  }
  deviation /oc-stp:stp/oc-stp:interfaces/oc-stp:interface/oc-stp:state/oc-stp:link-type {
    deviate "not-supported"; 
  }
  deviation /oc-stp:stp/oc-stp:interfaces/oc-stp:interface/oc-stp:state/oc-stp:guard {
    deviate "not-supported"; 
  }
  deviation /oc-stp:stp/oc-stp:interfaces/oc-stp:interface/oc-stp:state/oc-stp:bpdu-guard {
    deviate "not-supported"; 
  }
  deviation /oc-stp:stp/oc-stp:interfaces/oc-stp:interface/oc-stp:state/oc-stp:bpdu-filter {
    deviate "not-supported"; 
  }

}
