module cisco-nx-openconfig-system-deviations {

  namespace "http://openconfig.net/yang/system-deviations";

  prefix "oc-sys-devs";

  import openconfig-system { prefix oc-sys; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-system module 
     set for Cisco NXOS.
     Copyright (c) 2019 by Cisco Systems, Inc.
     All rights reserved.";

  revision "2019-08-21" {
    description
      "Initial revision applicable to NXOS";
  }

  deviation /oc-sys:system/oc-sys:config/oc-sys:hostname {
    deviate "not-supported"; 
  }
  deviation /oc-sys:system/oc-sys:config/oc-sys:domain-name {
    deviate "not-supported"; 
  }
  deviation /oc-sys:system/oc-sys:config/oc-sys:login-banner {
    deviate "not-supported"; 
  }
  deviation /oc-sys:system/oc-sys:config/oc-sys:motd-banner {
    deviate "not-supported"; 
  }
  deviation /oc-sys:system/oc-sys:state/oc-sys:hostname {
    deviate "not-supported"; 
  }
  deviation /oc-sys:system/oc-sys:state/oc-sys:domain-name {
    deviate "not-supported"; 
  }
  deviation /oc-sys:system/oc-sys:state/oc-sys:login-banner {
    deviate "not-supported"; 
  }
  deviation /oc-sys:system/oc-sys:state/oc-sys:motd-banner {
    deviate "not-supported"; 
  }
  deviation /oc-sys:system/oc-sys:state/oc-sys:current-datetime {
    deviate "not-supported"; 
  }
  deviation /oc-sys:system/oc-sys:state/oc-sys:boot-time {
    deviate "not-supported"; 
  }
  deviation /oc-sys:system/oc-sys:clock/oc-sys:config/oc-sys:timezone-name {
    deviate "not-supported"; 
  }
  deviation /oc-sys:system/oc-sys:clock/oc-sys:state/oc-sys:timezone-name {
    deviate "not-supported"; 
  }
  deviation /oc-sys:system/oc-sys:dns/oc-sys:config/oc-sys:search {
    deviate "not-supported"; 
  }
  deviation /oc-sys:system/oc-sys:dns/oc-sys:state/oc-sys:search {
    deviate "not-supported"; 
  }
  deviation /oc-sys:system/oc-sys:dns/oc-sys:servers/oc-sys:server {
    deviate "not-supported"; 
  }
  deviation /oc-sys:system/oc-sys:dns/oc-sys:host-entries/oc-sys:host-entry {
    deviate "not-supported"; 
  }
  deviation /oc-sys:system/oc-sys:ntp/oc-sys:config/oc-sys:enabled {
    deviate "not-supported"; 
  }
  deviation /oc-sys:system/oc-sys:ntp/oc-sys:config/oc-sys:ntp-source-address {
    deviate "not-supported"; 
  }
  deviation /oc-sys:system/oc-sys:ntp/oc-sys:config/oc-sys:enable-ntp-auth {
    deviate "not-supported"; 
  }
  deviation /oc-sys:system/oc-sys:ntp/oc-sys:state/oc-sys:enabled {
    deviate "not-supported"; 
  }
  deviation /oc-sys:system/oc-sys:ntp/oc-sys:state/oc-sys:ntp-source-address {
    deviate "not-supported"; 
  }
  deviation /oc-sys:system/oc-sys:ntp/oc-sys:state/oc-sys:enable-ntp-auth {
    deviate "not-supported"; 
  }
  deviation /oc-sys:system/oc-sys:ntp/oc-sys:state/oc-sys:auth-mismatch {
    deviate "not-supported"; 
  }
  deviation /oc-sys:system/oc-sys:ntp/oc-sys:ntp-keys/oc-sys:ntp-key {
    deviate "not-supported"; 
  }
  deviation /oc-sys:system/oc-sys:ntp/oc-sys:servers/oc-sys:server {
    deviate "not-supported"; 
  }
  deviation /oc-sys:system/oc-sys:ssh-server/oc-sys:config/oc-sys:protocol-version {
    deviate "not-supported"; 
  }
  deviation /oc-sys:system/oc-sys:ssh-server/oc-sys:config/oc-sys:rate-limit {
    deviate "not-supported"; 
  }
  deviation /oc-sys:system/oc-sys:ssh-server/oc-sys:state/oc-sys:enable {
    deviate "not-supported"; 
  }
  deviation /oc-sys:system/oc-sys:ssh-server/oc-sys:state/oc-sys:protocol-version {
    deviate "not-supported"; 
  }
  deviation /oc-sys:system/oc-sys:ssh-server/oc-sys:state/oc-sys:timeout {
    deviate "not-supported"; 
  }
  deviation /oc-sys:system/oc-sys:ssh-server/oc-sys:state/oc-sys:rate-limit {
    deviate "not-supported"; 
  }
  deviation /oc-sys:system/oc-sys:ssh-server/oc-sys:state/oc-sys:session-limit {
    deviate "not-supported"; 
  }
  deviation /oc-sys:system/oc-sys:telnet-server/oc-sys:config/oc-sys:enable {
    deviate "not-supported"; 
  }
  deviation /oc-sys:system/oc-sys:telnet-server/oc-sys:config/oc-sys:timeout {
    deviate "not-supported"; 
  }
  deviation /oc-sys:system/oc-sys:telnet-server/oc-sys:config/oc-sys:rate-limit {
    deviate "not-supported"; 
  }
  deviation /oc-sys:system/oc-sys:telnet-server/oc-sys:config/oc-sys:session-limit {
    deviate "not-supported"; 
  }
  deviation /oc-sys:system/oc-sys:telnet-server/oc-sys:state/oc-sys:enable {
    deviate "not-supported"; 
  }
  deviation /oc-sys:system/oc-sys:telnet-server/oc-sys:state/oc-sys:timeout {
    deviate "not-supported"; 
  }
  deviation /oc-sys:system/oc-sys:telnet-server/oc-sys:state/oc-sys:rate-limit {
    deviate "not-supported"; 
  }
  deviation /oc-sys:system/oc-sys:telnet-server/oc-sys:state/oc-sys:session-limit {
    deviate "not-supported"; 
  }
  deviation /oc-sys:system/oc-sys:logging/oc-sys:console/oc-sys:selectors/oc-sys:selector {
    deviate "not-supported"; 
  }
  deviation /oc-sys:system/oc-sys:logging/oc-sys:remote-servers/oc-sys:remote-server {
    deviate "not-supported"; 
  }
  deviation /oc-sys:system/oc-sys:aaa/oc-sys:authentication/oc-sys:config/oc-sys:authentication-method {
    deviate "not-supported"; 
  }
  deviation /oc-sys:system/oc-sys:aaa/oc-sys:authentication/oc-sys:state/oc-sys:authentication-method {
    deviate "not-supported"; 
  }
  deviation /oc-sys:system/oc-sys:aaa/oc-sys:authentication/oc-sys:admin-user/oc-sys:config/oc-sys:admin-password {
    deviate "not-supported"; 
  }
  deviation /oc-sys:system/oc-sys:aaa/oc-sys:authentication/oc-sys:admin-user/oc-sys:config/oc-sys:admin-password-hashed {
    deviate "not-supported"; 
  }
  deviation /oc-sys:system/oc-sys:aaa/oc-sys:authentication/oc-sys:admin-user/oc-sys:state/oc-sys:admin-password {
    deviate "not-supported"; 
  }
  deviation /oc-sys:system/oc-sys:aaa/oc-sys:authentication/oc-sys:admin-user/oc-sys:state/oc-sys:admin-password-hashed {
    deviate "not-supported"; 
  }
  deviation /oc-sys:system/oc-sys:aaa/oc-sys:authentication/oc-sys:admin-user/oc-sys:state/oc-sys:admin-username {
    deviate "not-supported"; 
  }
  deviation /oc-sys:system/oc-sys:aaa/oc-sys:authentication/oc-sys:users/oc-sys:user {
    deviate "not-supported"; 
  }
  deviation /oc-sys:system/oc-sys:aaa/oc-sys:authorization/oc-sys:config/oc-sys:authorization-method {
    deviate "not-supported"; 
  }
  deviation /oc-sys:system/oc-sys:aaa/oc-sys:authorization/oc-sys:state/oc-sys:authorization-method {
    deviate "not-supported"; 
  }
  deviation /oc-sys:system/oc-sys:aaa/oc-sys:authorization/oc-sys:events/oc-sys:event {
    deviate "not-supported"; 
  }
  deviation /oc-sys:system/oc-sys:aaa/oc-sys:accounting/oc-sys:config/oc-sys:accounting-method {
    deviate "not-supported"; 
  }
  deviation /oc-sys:system/oc-sys:aaa/oc-sys:accounting/oc-sys:state/oc-sys:accounting-method {
    deviate "not-supported"; 
  }
  deviation /oc-sys:system/oc-sys:aaa/oc-sys:accounting/oc-sys:events/oc-sys:event {
    deviate "not-supported"; 
  }
  deviation /oc-sys:system/oc-sys:aaa/oc-sys:server-groups/oc-sys:server-group/oc-sys:state/oc-sys:name {
    deviate "not-supported"; 
  }
  deviation /oc-sys:system/oc-sys:aaa/oc-sys:server-groups/oc-sys:server-group/oc-sys:state/oc-sys:type {
    deviate "not-supported"; 
  }
  deviation /oc-sys:system/oc-sys:aaa/oc-sys:server-groups/oc-sys:server-group/oc-sys:servers/oc-sys:server/oc-sys:config/oc-sys:name {
    deviate "not-supported"; 
  }
  deviation /oc-sys:system/oc-sys:aaa/oc-sys:server-groups/oc-sys:server-group/oc-sys:servers/oc-sys:server/oc-sys:state/oc-sys:name {
    deviate "not-supported"; 
  }
  deviation /oc-sys:system/oc-sys:aaa/oc-sys:server-groups/oc-sys:server-group/oc-sys:servers/oc-sys:server/oc-sys:state/oc-sys:address {
    deviate "not-supported"; 
  }
  deviation /oc-sys:system/oc-sys:aaa/oc-sys:server-groups/oc-sys:server-group/oc-sys:servers/oc-sys:server/oc-sys:state/oc-sys:timeout {
    deviate "not-supported"; 
  }
  deviation /oc-sys:system/oc-sys:aaa/oc-sys:server-groups/oc-sys:server-group/oc-sys:servers/oc-sys:server/oc-sys:state/oc-sys:connection-opens {
    deviate "not-supported"; 
  }
  deviation /oc-sys:system/oc-sys:aaa/oc-sys:server-groups/oc-sys:server-group/oc-sys:servers/oc-sys:server/oc-sys:state/oc-sys:connection-closes {
    deviate "not-supported"; 
  }
  deviation /oc-sys:system/oc-sys:aaa/oc-sys:server-groups/oc-sys:server-group/oc-sys:servers/oc-sys:server/oc-sys:state/oc-sys:connection-aborts {
    deviate "not-supported"; 
  }
  deviation /oc-sys:system/oc-sys:aaa/oc-sys:server-groups/oc-sys:server-group/oc-sys:servers/oc-sys:server/oc-sys:state/oc-sys:connection-failures {
    deviate "not-supported"; 
  }
  deviation /oc-sys:system/oc-sys:aaa/oc-sys:server-groups/oc-sys:server-group/oc-sys:servers/oc-sys:server/oc-sys:state/oc-sys:connection-timeouts {
    deviate "not-supported"; 
  }
  deviation /oc-sys:system/oc-sys:aaa/oc-sys:server-groups/oc-sys:server-group/oc-sys:servers/oc-sys:server/oc-sys:state/oc-sys:messages-sent {
    deviate "not-supported"; 
  }
  deviation /oc-sys:system/oc-sys:aaa/oc-sys:server-groups/oc-sys:server-group/oc-sys:servers/oc-sys:server/oc-sys:state/oc-sys:messages-received {
    deviate "not-supported"; 
  }
  deviation /oc-sys:system/oc-sys:aaa/oc-sys:server-groups/oc-sys:server-group/oc-sys:servers/oc-sys:server/oc-sys:state/oc-sys:errors-received {
    deviate "not-supported"; 
  }
  deviation /oc-sys:system/oc-sys:aaa/oc-sys:server-groups/oc-sys:server-group/oc-sys:servers/oc-sys:server/oc-sys:tacacs/oc-sys:config/oc-sys:source-address {
    deviate "not-supported"; 
  }
  deviation /oc-sys:system/oc-sys:aaa/oc-sys:server-groups/oc-sys:server-group/oc-sys:servers/oc-sys:server/oc-sys:tacacs/oc-sys:state/oc-sys:port {
    deviate "not-supported"; 
  }
  deviation /oc-sys:system/oc-sys:aaa/oc-sys:server-groups/oc-sys:server-group/oc-sys:servers/oc-sys:server/oc-sys:tacacs/oc-sys:state/oc-sys:secret-key {
    deviate "not-supported"; 
  }
  deviation /oc-sys:system/oc-sys:aaa/oc-sys:server-groups/oc-sys:server-group/oc-sys:servers/oc-sys:server/oc-sys:tacacs/oc-sys:state/oc-sys:source-address {
    deviate "not-supported"; 
  }
  deviation /oc-sys:system/oc-sys:aaa/oc-sys:server-groups/oc-sys:server-group/oc-sys:servers/oc-sys:server/oc-sys:radius/oc-sys:config/oc-sys:auth-port {
    deviate "not-supported"; 
  }
  deviation /oc-sys:system/oc-sys:aaa/oc-sys:server-groups/oc-sys:server-group/oc-sys:servers/oc-sys:server/oc-sys:radius/oc-sys:config/oc-sys:acct-port {
    deviate "not-supported"; 
  }
  deviation /oc-sys:system/oc-sys:aaa/oc-sys:server-groups/oc-sys:server-group/oc-sys:servers/oc-sys:server/oc-sys:radius/oc-sys:config/oc-sys:secret-key {
    deviate "not-supported"; 
  }
  deviation /oc-sys:system/oc-sys:aaa/oc-sys:server-groups/oc-sys:server-group/oc-sys:servers/oc-sys:server/oc-sys:radius/oc-sys:config/oc-sys:source-address {
    deviate "not-supported"; 
  }
  deviation /oc-sys:system/oc-sys:aaa/oc-sys:server-groups/oc-sys:server-group/oc-sys:servers/oc-sys:server/oc-sys:radius/oc-sys:config/oc-sys:retransmit-attempts {
    deviate "not-supported"; 
  }
  deviation /oc-sys:system/oc-sys:aaa/oc-sys:server-groups/oc-sys:server-group/oc-sys:servers/oc-sys:server/oc-sys:radius/oc-sys:state/oc-sys:auth-port {
    deviate "not-supported"; 
  }
  deviation /oc-sys:system/oc-sys:aaa/oc-sys:server-groups/oc-sys:server-group/oc-sys:servers/oc-sys:server/oc-sys:radius/oc-sys:state/oc-sys:acct-port {
    deviate "not-supported"; 
  }
  deviation /oc-sys:system/oc-sys:aaa/oc-sys:server-groups/oc-sys:server-group/oc-sys:servers/oc-sys:server/oc-sys:radius/oc-sys:state/oc-sys:secret-key {
    deviate "not-supported"; 
  }
  deviation /oc-sys:system/oc-sys:aaa/oc-sys:server-groups/oc-sys:server-group/oc-sys:servers/oc-sys:server/oc-sys:radius/oc-sys:state/oc-sys:source-address {
    deviate "not-supported"; 
  }
  deviation /oc-sys:system/oc-sys:aaa/oc-sys:server-groups/oc-sys:server-group/oc-sys:servers/oc-sys:server/oc-sys:radius/oc-sys:state/oc-sys:retransmit-attempts {
    deviate "not-supported"; 
  }
  deviation /oc-sys:system/oc-sys:aaa/oc-sys:server-groups/oc-sys:server-group/oc-sys:servers/oc-sys:server/oc-sys:radius/oc-sys:state/oc-sys:counters/oc-sys:retried-access-requests {
    deviate "not-supported"; 
  }
  deviation /oc-sys:system/oc-sys:aaa/oc-sys:server-groups/oc-sys:server-group/oc-sys:servers/oc-sys:server/oc-sys:radius/oc-sys:state/oc-sys:counters/oc-sys:access-accepts {
    deviate "not-supported"; 
  }
  deviation /oc-sys:system/oc-sys:aaa/oc-sys:server-groups/oc-sys:server-group/oc-sys:servers/oc-sys:server/oc-sys:radius/oc-sys:state/oc-sys:counters/oc-sys:access-rejects {
    deviate "not-supported"; 
  }
  deviation /oc-sys:system/oc-sys:aaa/oc-sys:server-groups/oc-sys:server-group/oc-sys:servers/oc-sys:server/oc-sys:radius/oc-sys:state/oc-sys:counters/oc-sys:timeout-access-requests {
    deviate "not-supported"; 
  }
  deviation /oc-sys:system/oc-sys:memory/oc-sys:state/oc-sys:physical {
    deviate "not-supported"; 
  }
  deviation /oc-sys:system/oc-sys:memory/oc-sys:state/oc-sys:reserved {
    deviate "not-supported"; 
  }
}
