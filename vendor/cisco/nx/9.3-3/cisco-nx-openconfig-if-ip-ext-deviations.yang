module cisco-nx-openconfig-if-ip-ext-deviations {

  namespace "http://openconfig.net/yang/interfaces/ip-ext-deviations";

  prefix "oc-ip-ext-devs";

  import openconfig-if-ip-ext { prefix oc-ip-ext; }
  import openconfig-interfaces {prefix oc-if;}
  import openconfig-if-ip {prefix oc-ip; } 

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-if-ip-ext module 
     set for Cisco NXOS.
     Copyright (c) 2015-2016 by Cisco Systems, Inc.
     All rights reserved.";

  revision "2018-02-23" {
    description
      "Initial revision applicable to NXOS";
  }

  deviation /oc-if:interfaces/oc-if:interface/oc-if:subinterfaces/oc-if:subinterface/oc-ip:ipv6/oc-ip-ext:autoconf/oc-ip-ext:config/oc-ip-ext:create-temporary-addresses {
    deviate "not-supported"; 
  }
  deviation /oc-if:interfaces/oc-if:interface/oc-if:subinterfaces/oc-if:subinterface/oc-ip:ipv6/oc-ip-ext:autoconf/oc-ip-ext:config/oc-ip-ext:temporary-valid-lifetime {
    deviate "not-supported"; 
  }
  deviation /oc-if:interfaces/oc-if:interface/oc-if:subinterfaces/oc-if:subinterface/oc-ip:ipv6/oc-ip-ext:autoconf/oc-ip-ext:config/oc-ip-ext:temporary-preferred-lifetime {
    deviate "not-supported"; 
  }
  deviation /oc-if:interfaces/oc-if:interface/oc-if:subinterfaces/oc-if:subinterface/oc-ip:ipv6/oc-ip-ext:autoconf/oc-ip-ext:state/oc-ip-ext:create-global-addresses {
    deviate "not-supported"; 
  }
  deviation /oc-if:interfaces/oc-if:interface/oc-if:subinterfaces/oc-if:subinterface/oc-ip:ipv6/oc-ip-ext:autoconf/oc-ip-ext:state/oc-ip-ext:create-temporary-addresses {
    deviate "not-supported"; 
  }
  deviation /oc-if:interfaces/oc-if:interface/oc-if:subinterfaces/oc-if:subinterface/oc-ip:ipv6/oc-ip-ext:autoconf/oc-ip-ext:state/oc-ip-ext:temporary-valid-lifetime {
    deviate "not-supported"; 
  }
  deviation /oc-if:interfaces/oc-if:interface/oc-if:subinterfaces/oc-if:subinterface/oc-ip:ipv6/oc-ip-ext:autoconf/oc-ip-ext:state/oc-ip-ext:temporary-preferred-lifetime {
    deviate "not-supported"; 
  }

  deviation /oc-if:interfaces/oc-if:interface/oc-if:subinterfaces/oc-if:subinterface/oc-ip:ipv6/oc-ip-ext:autoconf/oc-ip-ext:config/oc-ip-ext:create-global-addresses {
    deviate replace {
      default "false";
    }
  }

}
