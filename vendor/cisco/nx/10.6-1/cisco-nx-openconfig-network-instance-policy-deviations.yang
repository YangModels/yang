module cisco-nx-openconfig-network-instance-policy-deviations {

  namespace "http://openconfig.net/yang/network-instance/policy-deviations";

  prefix "oc-ni-pol-devs";

  import openconfig-network-instance-policy { prefix oc-ni-pol; }
  import openconfig-policy-types { prefix oc-pol-types; }
  import openconfig-routing-policy { prefix oc-rpol; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-network-instance-policy module 
     set for Cisco NXOS.
     Copyright (c) 2015-2017, 2020 by Cisco Systems, Inc.
     All rights reserved.";

  revision "2020-02-21" {
    description
      "Initial revision applicable to NXOS";
  }

/* Mapped to device model
 *     Device Model Target: /top:System/top:rpm-items/top:rtmap-items/top:Rule-list/top:ent-items/top:Entry-list/top:msrcprot-items/top:MatchSrcProto-list/top:proto
 * Transformation Function: oc_proto_identifier_to_src_proto 
 */
  deviation /oc-rpol:routing-policy/oc-rpol:policy-definitions/oc-rpol:policy-definition/oc-rpol:statements/oc-rpol:statement/oc-rpol:conditions/oc-ni-pol:match-protocol-instance/oc-ni-pol:config/oc-ni-pol:protocol-identifier {
    deviate add {
      must "../oc-ni-pol:protocol-identifier='oc-pol-types:BGP' or ../oc-ni-pol:protocol-identifier='oc-pol-types:ISIS' or ../oc-ni-pol:protocol-identifier='oc-pol-types:OSPF' or ../oc-ni-pol:protocol-identifier='oc-pol-types:OSPF3' or ../oc-ni-pol:protocol-identifier='oc-pol-types:STATIC' or ../oc-ni-pol:protocol-identifier='oc-pol-types:DIRECTLY_CONNECTED' or ../oc-ni-pol:protocol-identifier='oc-pol-types:LOCAL_AGGREGATE'" {
        error-message "Only supports BGP, ISIS, OSPF, OSPF3, STATIC, DIRECTLY_CONNECTED and LOCAL_AGGREGATE on device model";
      }
    }
  }

}
