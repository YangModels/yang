module cisco-nx-openconfig-routing-policy-deviations {

  namespace "http://openconfig.net/yang/routing-policy-deviations";

  prefix "oc-rpol-devs";

  import openconfig_routing_policy { prefix oc-rpol; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-routing-policy module 
     set for Cisco NXOS.
     Copyright (c) 2015-2016 by Cisco Systems, Inc.
     All rights reserved.";

  revision "2017-05-24" {
    description
      "Initial revision applicable to NXOS";
  }

  deviation oc-rpol:routing-policy/oc-rpol:defined-sets/oc-rpol:prefix-sets/oc-rpol:prefix-set/oc-rpol:state/oc-rpol:prefix-set-name {
    deviate "not-supported"; 
  }
  deviation oc-rpol:routing-policy/oc-rpol:defined-sets/oc-rpol:prefix-sets/oc-rpol:prefix-set/oc-rpol:prefixes/oc-rpol:prefix {
    deviate "not-supported"; 
  }
  deviation oc-rpol:routing-policy/oc-rpol:defined-sets/oc-rpol:prefix-sets/oc-rpol:prefix-set/oc-rpol:prefixes/oc-rpol:prefix/oc-rpol:ip-prefix {
    deviate "not-supported"; 
  }
  deviation oc-rpol:routing-policy/oc-rpol:defined-sets/oc-rpol:prefix-sets/oc-rpol:prefix-set/oc-rpol:prefixes/oc-rpol:prefix/oc-rpol:masklength-range {
    deviate "not-supported"; 
  }
  deviation oc-rpol:routing-policy/oc-rpol:defined-sets/oc-rpol:prefix-sets/oc-rpol:prefix-set/oc-rpol:prefixes/oc-rpol:prefix/oc-rpol:config/oc-rpol:ip-prefix {
    deviate "not-supported"; 
  }
  deviation oc-rpol:routing-policy/oc-rpol:defined-sets/oc-rpol:prefix-sets/oc-rpol:prefix-set/oc-rpol:prefixes/oc-rpol:prefix/oc-rpol:config/oc-rpol:masklength-range {
    deviate "not-supported"; 
  }
  deviation oc-rpol:routing-policy/oc-rpol:defined-sets/oc-rpol:prefix-sets/oc-rpol:prefix-set/oc-rpol:prefixes/oc-rpol:prefix/oc-rpol:state/oc-rpol:ip-prefix {
    deviate "not-supported"; 
  }
  deviation oc-rpol:routing-policy/oc-rpol:defined-sets/oc-rpol:prefix-sets/oc-rpol:prefix-set/oc-rpol:prefixes/oc-rpol:prefix/oc-rpol:state/oc-rpol:masklength-range {
    deviate "not-supported"; 
  }
  deviation oc-rpol:routing-policy/oc-rpol:defined-sets/oc-rpol:neighbor-sets/oc-rpol:neighbor-set {
    deviate "not-supported"; 
  }
  deviation oc-rpol:routing-policy/oc-rpol:defined-sets/oc-rpol:neighbor-sets/oc-rpol:neighbor-set/oc-rpol:neighbor-set-name {
    deviate "not-supported"; 
  }
  deviation oc-rpol:routing-policy/oc-rpol:defined-sets/oc-rpol:neighbor-sets/oc-rpol:neighbor-set/oc-rpol:config/oc-rpol:neighbor-set-name {
    deviate "not-supported"; 
  }
  deviation oc-rpol:routing-policy/oc-rpol:defined-sets/oc-rpol:neighbor-sets/oc-rpol:neighbor-set/oc-rpol:config/oc-rpol:address {
    deviate "not-supported"; 
  }
  deviation oc-rpol:routing-policy/oc-rpol:defined-sets/oc-rpol:neighbor-sets/oc-rpol:neighbor-set/oc-rpol:state/oc-rpol:neighbor-set-name {
    deviate "not-supported"; 
  }
  deviation oc-rpol:routing-policy/oc-rpol:defined-sets/oc-rpol:neighbor-sets/oc-rpol:neighbor-set/oc-rpol:state/oc-rpol:address {
    deviate "not-supported"; 
  }
  deviation oc-rpol:routing-policy/oc-rpol:defined-sets/oc-rpol:tag-sets/oc-rpol:tag-set {
    deviate "not-supported"; 
  }
  deviation oc-rpol:routing-policy/oc-rpol:defined-sets/oc-rpol:tag-sets/oc-rpol:tag-set/oc-rpol:tag-set-name {
    deviate "not-supported"; 
  }
  deviation oc-rpol:routing-policy/oc-rpol:defined-sets/oc-rpol:tag-sets/oc-rpol:tag-set/oc-rpol:config/oc-rpol:tag-set-name {
    deviate "not-supported"; 
  }
  deviation oc-rpol:routing-policy/oc-rpol:defined-sets/oc-rpol:tag-sets/oc-rpol:tag-set/oc-rpol:config/oc-rpol:tag-value {
    deviate "not-supported"; 
  }
  deviation oc-rpol:routing-policy/oc-rpol:defined-sets/oc-rpol:tag-sets/oc-rpol:tag-set/oc-rpol:state/oc-rpol:tag-set-name {
    deviate "not-supported"; 
  }
  deviation oc-rpol:routing-policy/oc-rpol:defined-sets/oc-rpol:tag-sets/oc-rpol:tag-set/oc-rpol:state/oc-rpol:tag-value {
    deviate "not-supported"; 
  }
  deviation oc-rpol:routing-policy/oc-rpol:policy-definitions/oc-rpol:policy-definition/oc-rpol:state/oc-rpol:name {
    deviate "not-supported"; 
  }
  deviation oc-rpol:routing-policy/oc-rpol:policy-definitions/oc-rpol:policy-definition/oc-rpol:statements/oc-rpol:statement/oc-rpol:state/oc-rpol:name {
    deviate "not-supported"; 
  }
  deviation oc-rpol:routing-policy/oc-rpol:policy-definitions/oc-rpol:policy-definition/oc-rpol:statements/oc-rpol:statement/oc-rpol:conditions/oc-rpol:config/oc-rpol:call-policy {
    deviate "not-supported"; 
  }
  deviation oc-rpol:routing-policy/oc-rpol:policy-definitions/oc-rpol:policy-definition/oc-rpol:statements/oc-rpol:statement/oc-rpol:conditions/oc-rpol:config/oc-rpol:install-protocol-eq {
    deviate "not-supported"; 
  }
  deviation oc-rpol:routing-policy/oc-rpol:policy-definitions/oc-rpol:policy-definition/oc-rpol:statements/oc-rpol:statement/oc-rpol:conditions/oc-rpol:state/oc-rpol:call-policy {
    deviate "not-supported"; 
  }
  deviation oc-rpol:routing-policy/oc-rpol:policy-definitions/oc-rpol:policy-definition/oc-rpol:statements/oc-rpol:statement/oc-rpol:conditions/oc-rpol:state/oc-rpol:install-protocol-eq {
    deviate "not-supported"; 
  }
  deviation oc-rpol:routing-policy/oc-rpol:policy-definitions/oc-rpol:policy-definition/oc-rpol:statements/oc-rpol:statement/oc-rpol:conditions/oc-rpol:match-interface/oc-rpol:config/oc-if:interface {
    deviate "not-supported"; 
  }
  deviation oc-rpol:routing-policy/oc-rpol:policy-definitions/oc-rpol:policy-definition/oc-rpol:statements/oc-rpol:statement/oc-rpol:conditions/oc-rpol:match-interface/oc-rpol:config/oc-if:subinterface {
    deviate "not-supported"; 
  }
  deviation oc-rpol:routing-policy/oc-rpol:policy-definitions/oc-rpol:policy-definition/oc-rpol:statements/oc-rpol:statement/oc-rpol:conditions/oc-rpol:match-interface/oc-rpol:state/oc-if:interface {
    deviate "not-supported"; 
  }
  deviation oc-rpol:routing-policy/oc-rpol:policy-definitions/oc-rpol:policy-definition/oc-rpol:statements/oc-rpol:statement/oc-rpol:conditions/oc-rpol:match-interface/oc-rpol:state/oc-if:subinterface {
    deviate "not-supported"; 
  }
  deviation oc-rpol:routing-policy/oc-rpol:policy-definitions/oc-rpol:policy-definition/oc-rpol:statements/oc-rpol:statement/oc-rpol:conditions/oc-rpol:match-prefix-set/oc-rpol:config/oc-rpol:match-set-options {
    deviate "not-supported"; 
  }
  deviation oc-rpol:routing-policy/oc-rpol:policy-definitions/oc-rpol:policy-definition/oc-rpol:statements/oc-rpol:statement/oc-rpol:conditions/oc-rpol:match-prefix-set/oc-rpol:state/oc-rpol:prefix-set {
    deviate "not-supported"; 
  }
  deviation oc-rpol:routing-policy/oc-rpol:policy-definitions/oc-rpol:policy-definition/oc-rpol:statements/oc-rpol:statement/oc-rpol:conditions/oc-rpol:match-prefix-set/oc-rpol:state/oc-rpol:match-set-options {
    deviate "not-supported"; 
  }
  deviation oc-rpol:routing-policy/oc-rpol:policy-definitions/oc-rpol:policy-definition/oc-rpol:statements/oc-rpol:statement/oc-rpol:conditions/oc-rpol:match-neighbor-set/oc-rpol:config/oc-rpol:neighbor-set {
    deviate "not-supported"; 
  }
  deviation oc-rpol:routing-policy/oc-rpol:policy-definitions/oc-rpol:policy-definition/oc-rpol:statements/oc-rpol:statement/oc-rpol:conditions/oc-rpol:match-neighbor-set/oc-rpol:config/oc-rpol:match-set-options {
    deviate "not-supported"; 
  }
  deviation oc-rpol:routing-policy/oc-rpol:policy-definitions/oc-rpol:policy-definition/oc-rpol:statements/oc-rpol:statement/oc-rpol:conditions/oc-rpol:match-neighbor-set/oc-rpol:state/oc-rpol:neighbor-set {
    deviate "not-supported"; 
  }
  deviation oc-rpol:routing-policy/oc-rpol:policy-definitions/oc-rpol:policy-definition/oc-rpol:statements/oc-rpol:statement/oc-rpol:conditions/oc-rpol:match-neighbor-set/oc-rpol:state/oc-rpol:match-set-options {
    deviate "not-supported"; 
  }
  deviation oc-rpol:routing-policy/oc-rpol:policy-definitions/oc-rpol:policy-definition/oc-rpol:statements/oc-rpol:statement/oc-rpol:conditions/oc-rpol:match-tag-set/oc-rpol:config/oc-rpol:match-set-options {
    deviate "not-supported"; 
  }
  deviation oc-rpol:routing-policy/oc-rpol:policy-definitions/oc-rpol:policy-definition/oc-rpol:statements/oc-rpol:statement/oc-rpol:conditions/oc-rpol:match-tag-set/oc-rpol:state/oc-rpol:tag-set {
    deviate "not-supported"; 
  }
  deviation oc-rpol:routing-policy/oc-rpol:policy-definitions/oc-rpol:policy-definition/oc-rpol:statements/oc-rpol:statement/oc-rpol:conditions/oc-rpol:match-tag-set/oc-rpol:state/oc-rpol:match-set-options {
    deviate "not-supported"; 
  }
  deviation oc-rpol:routing-policy/oc-rpol:policy-definitions/oc-rpol:policy-definition/oc-rpol:statements/oc-rpol:statement/oc-rpol:actions/oc-rpol:config/oc-rpol:route-disposition/oc-rpol:accept-route {
    deviate "not-supported"; 
  }
  deviation oc-rpol:routing-policy/oc-rpol:policy-definitions/oc-rpol:policy-definition/oc-rpol:statements/oc-rpol:statement/oc-rpol:actions/oc-rpol:config/oc-rpol:route-disposition/oc-rpol:reject-route {
    deviate "not-supported"; 
  }
  deviation oc-rpol:routing-policy/oc-rpol:policy-definitions/oc-rpol:policy-definition/oc-rpol:statements/oc-rpol:statement/oc-rpol:actions/oc-rpol:state/oc-rpol:route-disposition/oc-rpol:accept-route {
    deviate "not-supported"; 
  }
  deviation oc-rpol:routing-policy/oc-rpol:policy-definitions/oc-rpol:policy-definition/oc-rpol:statements/oc-rpol:statement/oc-rpol:actions/oc-rpol:state/oc-rpol:route-disposition/oc-rpol:reject-route {
    deviate "not-supported"; 
  }
  deviation oc-rpol:routing-policy/oc-rpol:policy-definitions/oc-rpol:policy-definition/oc-rpol:statements/oc-rpol:statement/oc-rpol:actions/oc-rpol:igp-actions/oc-rpol:state/oc-rpol:set-tag {
    deviate "not-supported"; 
  }

/* Mapped to device model
 *     Device Model Target: /top:System/top:rpm-items/top:pfxlistv4-items/top:RuleV4-list
 * Transformation Function: oc_prefix_set_to_low_rule 
 */
  deviation oc-rpol:routing-policy/oc-rpol:defined-sets/oc-rpol:prefix-sets/oc-rpol:prefix-set {
    deviate /* add, replace, or delete */ {
      /* something */ /* "something's value" */;
    }
  }

/* Mapped to device model
 *     Device Model Target: /top:System/top:rpm-items/top:pfxlistv4-items/top:RuleV4-list/top:name
 * Transformation Function: oc_prefix_name_to_rule_prefix_name 
 */
  deviation oc-rpol:routing-policy/oc-rpol:defined-sets/oc-rpol:prefix-sets/oc-rpol:prefix-set/oc-rpol:prefix-set-name {
    deviate /* add, replace, or delete */ {
      /* something */ /* "something's value" */;
    }
  }

/* Mapped to device model
 *     Device Model Target: /top:System/top:rpm-items/top:pfxlistv4-items/top:RuleV4-list/top:name
 * Transformation Function: oc_prefix_name_to_rule_prefix_name_config 
 */
  deviation oc-rpol:routing-policy/oc-rpol:defined-sets/oc-rpol:prefix-sets/oc-rpol:prefix-set/oc-rpol:config/oc-rpol:prefix-set-name {
    deviate /* add, replace, or delete */ {
      /* something */ /* "something's value" */;
    }
  }

/* Mapped to device model
 *     Device Model Target: /top:System/top:rpm-items/top:rtmap-items/top:Rule-list
 * Transformation Function: oc_policy_to_native_rule 
 */
  deviation oc-rpol:routing-policy/oc-rpol:policy-definitions/oc-rpol:policy-definition {
    deviate /* add, replace, or delete */ {
      /* something */ /* "something's value" */;
    }
  }

/* Mapped to device model
 *     Device Model Target: /top:System/top:rpm-items/top:rtmap-items/top:Rule-list/top:name
 * Transformation Function: oc_name_to_native_name 
 */
  deviation oc-rpol:routing-policy/oc-rpol:policy-definitions/oc-rpol:policy-definition/oc-rpol:name {
    deviate /* add, replace, or delete */ {
      /* something */ /* "something's value" */;
    }
  }

/* Mapped to device model
 *     Device Model Target: /top:System/top:rpm-items/top:rtmap-items/top:Rule-list/top:name
 * Transformation Function: oc_name_to_native_name_config 
 */
  deviation oc-rpol:routing-policy/oc-rpol:policy-definitions/oc-rpol:policy-definition/oc-rpol:config/oc-rpol:name {
    deviate /* add, replace, or delete */ {
      /* something */ /* "something's value" */;
    }
  }

/* Mapped to device model
 *     Device Model Target: /top:System/top:rpm-items/top:rtmap-items/top:Rule-list/top:ent-items/top:Entry-list
 * Transformation Function: oc_statement_name_to_entry_order 
 */
  deviation oc-rpol:routing-policy/oc-rpol:policy-definitions/oc-rpol:policy-definition/oc-rpol:statements/oc-rpol:statement {
    deviate /* add, replace, or delete */ {
      /* something */ /* "something's value" */;
    }
  }

/* Mapped to device model
 *     Device Model Target: /top:System/top:rpm-items/top:rtmap-items/top:Rule-list/top:ent-items/top:Entry-list/top:order
 * Transformation Function: oc_name_to_order 
 */
  deviation oc-rpol:routing-policy/oc-rpol:policy-definitions/oc-rpol:policy-definition/oc-rpol:statements/oc-rpol:statement/oc-rpol:name {
    deviate /* add, replace, or delete */ {
      /* something */ /* "something's value" */;
    }
  }

/* Mapped to device model
 *     Device Model Target: /top:System/top:rpm-items/top:rtmap-items/top:Rule-list/top:ent-items/top:Entry-list/top:order
 * Transformation Function: oc_name_to_order_config 
 */
  deviation oc-rpol:routing-policy/oc-rpol:policy-definitions/oc-rpol:policy-definition/oc-rpol:statements/oc-rpol:statement/oc-rpol:config/oc-rpol:name {
    deviate /* add, replace, or delete */ {
      /* something */ /* "something's value" */;
    }
  }

/* Mapped to device model
 *     Device Model Target: /top:System/top:rpm-items/top:rtmap-items/top:Rule-list/top:ent-items/top:Entry-list/top:mrtdst-items/top:rsrtDstAtt-items/top:RsRtDstAtt-list/top:tDn
 * Transformation Function: oc_prefix_to_low_dst_tdn 
 */
  deviation oc-rpol:routing-policy/oc-rpol:policy-definitions/oc-rpol:policy-definition/oc-rpol:statements/oc-rpol:statement/oc-rpol:conditions/oc-rpol:match-prefix-set/oc-rpol:config/oc-rpol:prefix-set {
    deviate /* add, replace, or delete */ {
      /* something */ /* "something's value" */;
    }
  }

/* Mapped to device model
 *     Device Model Target: /top:System/top:rpm-items/top:rtmap-items/top:Rule-list/top:ent-items/top:Entry-list/top:mrttag-items/top:MatchRtTag-list/top:tag
 * Transformation Function: oc_tag_to_low_tag 
 */
  deviation oc-rpol:routing-policy/oc-rpol:policy-definitions/oc-rpol:policy-definition/oc-rpol:statements/oc-rpol:statement/oc-rpol:conditions/oc-rpol:match-tag-set/oc-rpol:config/oc-rpol:tag-set {
    deviate /* add, replace, or delete */ {
      /* something */ /* "something's value" */;
    }
  }

/* Mapped to device model
 *     Device Model Target: /top:System/top:rpm-items/top:rtmap-items/top:Rule-list/top:ent-items/top:Entry-list/top:srttag-items/top:tag
 * Transformation Function: oc_tag_to_native_tag 
 */
  deviation oc-rpol:routing-policy/oc-rpol:policy-definitions/oc-rpol:policy-definition/oc-rpol:statements/oc-rpol:statement/oc-rpol:actions/oc-rpol:igp-actions/oc-rpol:config/oc-rpol:set-tag {
    deviate /* add, replace, or delete */ {
      /* something */ /* "something's value" */;
    }
  }

}
