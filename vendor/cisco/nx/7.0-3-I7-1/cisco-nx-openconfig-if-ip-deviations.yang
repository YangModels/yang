module cisco-nx-openconfig-if-ip-deviations {

  namespace "http://openconfig.net/yang/interfaces/ip-deviations";

  prefix "oc-ip-devs";

  import openconfig_if_ip { prefix oc-ip; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-if-ip module 
     set for Cisco NXOS.
     Copyright (c) 2015-2016 by Cisco Systems, Inc.
     All rights reserved.";

  revision "2017-05-24" {
    description
      "Initial revision applicable to NXOS";
  }

  deviation oc-ip:/oc-if:interfaces/oc-if:interface/oc-if:subinterfaces/oc-if:subinterface/oc-ip:ipv4/oc-ip:addresses/oc-ip:address/oc-ip:state/oc-ip:ip {
    deviate "not-supported"; 
  }
  deviation oc-ip:/oc-if:interfaces/oc-if:interface/oc-if:subinterfaces/oc-if:subinterface/oc-ip:ipv4/oc-ip:addresses/oc-ip:address/oc-ip:state/oc-ip:prefix-length {
    deviate "not-supported"; 
  }
  deviation oc-ip:/oc-if:interfaces/oc-if:interface/oc-if:subinterfaces/oc-if:subinterface/oc-ip:ipv4/oc-ip:addresses/oc-ip:address/oc-ip:state/oc-ip:origin {
    deviate "not-supported"; 
  }
  deviation oc-ip:/oc-if:interfaces/oc-if:interface/oc-if:subinterfaces/oc-if:subinterface/oc-ip:ipv4/oc-ip:neighbors/oc-ip:neighbor/oc-ip:state/oc-ip:ip {
    deviate "not-supported"; 
  }
  deviation oc-ip:/oc-if:interfaces/oc-if:interface/oc-if:subinterfaces/oc-if:subinterface/oc-ip:ipv4/oc-ip:neighbors/oc-ip:neighbor/oc-ip:state/oc-ip:link-layer-address {
    deviate "not-supported"; 
  }
  deviation oc-ip:/oc-if:interfaces/oc-if:interface/oc-if:subinterfaces/oc-if:subinterface/oc-ip:ipv4/oc-ip:neighbors/oc-ip:neighbor/oc-ip:state/oc-ip:origin {
    deviate "not-supported"; 
  }
  deviation oc-ip:/oc-if:interfaces/oc-if:interface/oc-if:subinterfaces/oc-if:subinterface/oc-ip:ipv4/oc-if:unnumbered/oc-if:config/oc-if:enabled {
    deviate "not-supported"; 
  }
  deviation oc-ip:/oc-if:interfaces/oc-if:interface/oc-if:subinterfaces/oc-if:subinterface/oc-ip:ipv4/oc-if:unnumbered/oc-if:state/oc-if:enabled {
    deviate "not-supported"; 
  }
  deviation oc-ip:/oc-if:interfaces/oc-if:interface/oc-if:subinterfaces/oc-if:subinterface/oc-ip:ipv4/oc-if:unnumbered/oc-if:interface-ref/oc-if:config/oc-if:interface {
    deviate "not-supported"; 
  }
  deviation oc-ip:/oc-if:interfaces/oc-if:interface/oc-if:subinterfaces/oc-if:subinterface/oc-ip:ipv4/oc-if:unnumbered/oc-if:interface-ref/oc-if:config/oc-if:subinterface {
    deviate "not-supported"; 
  }
  deviation oc-ip:/oc-if:interfaces/oc-if:interface/oc-if:subinterfaces/oc-if:subinterface/oc-ip:ipv4/oc-if:unnumbered/oc-if:interface-ref/oc-if:state/oc-if:interface {
    deviate "not-supported"; 
  }
  deviation oc-ip:/oc-if:interfaces/oc-if:interface/oc-if:subinterfaces/oc-if:subinterface/oc-ip:ipv4/oc-if:unnumbered/oc-if:interface-ref/oc-if:state/oc-if:subinterface {
    deviate "not-supported"; 
  }
  deviation oc-ip:/oc-if:interfaces/oc-if:interface/oc-if:subinterfaces/oc-if:subinterface/oc-ip:ipv4/oc-ip:config/oc-ip:enabled {
    deviate "not-supported"; 
  }
  deviation oc-ip:/oc-if:interfaces/oc-if:interface/oc-if:subinterfaces/oc-if:subinterface/oc-ip:ipv4/oc-ip:config/oc-ip:mtu {
    deviate "not-supported"; 
  }
  deviation oc-ip:/oc-if:interfaces/oc-if:interface/oc-if:subinterfaces/oc-if:subinterface/oc-ip:ipv4/oc-ip:state/oc-ip:enabled {
    deviate "not-supported"; 
  }
  deviation oc-ip:/oc-if:interfaces/oc-if:interface/oc-if:subinterfaces/oc-if:subinterface/oc-ip:ipv4/oc-ip:state/oc-ip:mtu {
    deviate "not-supported"; 
  }
  deviation oc-ip:/oc-if:interfaces/oc-if:interface/oc-if:subinterfaces/oc-if:subinterface/oc-ip:ipv6/oc-ip:addresses/oc-ip:address/oc-ip:state/oc-ip:ip {
    deviate "not-supported"; 
  }
  deviation oc-ip:/oc-if:interfaces/oc-if:interface/oc-if:subinterfaces/oc-if:subinterface/oc-ip:ipv6/oc-ip:addresses/oc-ip:address/oc-ip:state/oc-ip:prefix-length {
    deviate "not-supported"; 
  }
  deviation oc-ip:/oc-if:interfaces/oc-if:interface/oc-if:subinterfaces/oc-if:subinterface/oc-ip:ipv6/oc-ip:addresses/oc-ip:address/oc-ip:state/oc-ip:origin {
    deviate "not-supported"; 
  }
  deviation oc-ip:/oc-if:interfaces/oc-if:interface/oc-if:subinterfaces/oc-if:subinterface/oc-ip:ipv6/oc-ip:addresses/oc-ip:address/oc-ip:state/oc-ip:status {
    deviate "not-supported"; 
  }
  deviation oc-ip:/oc-if:interfaces/oc-if:interface/oc-if:subinterfaces/oc-if:subinterface/oc-ip:ipv6/oc-ip:neighbors/oc-ip:neighbor/oc-ip:state/oc-ip:ip {
    deviate "not-supported"; 
  }
  deviation oc-ip:/oc-if:interfaces/oc-if:interface/oc-if:subinterfaces/oc-if:subinterface/oc-ip:ipv6/oc-ip:neighbors/oc-ip:neighbor/oc-ip:state/oc-ip:link-layer-address {
    deviate "not-supported"; 
  }
  deviation oc-ip:/oc-if:interfaces/oc-if:interface/oc-if:subinterfaces/oc-if:subinterface/oc-ip:ipv6/oc-ip:neighbors/oc-ip:neighbor/oc-ip:state/oc-ip:origin {
    deviate "not-supported"; 
  }
  deviation oc-ip:/oc-if:interfaces/oc-if:interface/oc-if:subinterfaces/oc-if:subinterface/oc-ip:ipv6/oc-ip:neighbors/oc-ip:neighbor/oc-ip:state/oc-ip:is-router {
    deviate "not-supported"; 
  }
  deviation oc-ip:/oc-if:interfaces/oc-if:interface/oc-if:subinterfaces/oc-if:subinterface/oc-ip:ipv6/oc-ip:neighbors/oc-ip:neighbor/oc-ip:state/oc-ip:neighbor-state {
    deviate "not-supported"; 
  }
  deviation oc-ip:/oc-if:interfaces/oc-if:interface/oc-if:subinterfaces/oc-if:subinterface/oc-ip:ipv6/oc-if:unnumbered/oc-if:config/oc-if:enabled {
    deviate "not-supported"; 
  }
  deviation oc-ip:/oc-if:interfaces/oc-if:interface/oc-if:subinterfaces/oc-if:subinterface/oc-ip:ipv6/oc-if:unnumbered/oc-if:state/oc-if:enabled {
    deviate "not-supported"; 
  }
  deviation oc-ip:/oc-if:interfaces/oc-if:interface/oc-if:subinterfaces/oc-if:subinterface/oc-ip:ipv6/oc-if:unnumbered/oc-if:interface-ref/oc-if:config/oc-if:interface {
    deviate "not-supported"; 
  }
  deviation oc-ip:/oc-if:interfaces/oc-if:interface/oc-if:subinterfaces/oc-if:subinterface/oc-ip:ipv6/oc-if:unnumbered/oc-if:interface-ref/oc-if:config/oc-if:subinterface {
    deviate "not-supported"; 
  }
  deviation oc-ip:/oc-if:interfaces/oc-if:interface/oc-if:subinterfaces/oc-if:subinterface/oc-ip:ipv6/oc-if:unnumbered/oc-if:interface-ref/oc-if:state/oc-if:interface {
    deviate "not-supported"; 
  }
  deviation oc-ip:/oc-if:interfaces/oc-if:interface/oc-if:subinterfaces/oc-if:subinterface/oc-ip:ipv6/oc-if:unnumbered/oc-if:interface-ref/oc-if:state/oc-if:subinterface {
    deviate "not-supported"; 
  }
  deviation oc-ip:/oc-if:interfaces/oc-if:interface/oc-if:subinterfaces/oc-if:subinterface/oc-ip:ipv6/oc-ip:config/oc-ip:enabled {
    deviate "not-supported"; 
  }
  deviation oc-ip:/oc-if:interfaces/oc-if:interface/oc-if:subinterfaces/oc-if:subinterface/oc-ip:ipv6/oc-ip:config/oc-ip:mtu {
    deviate "not-supported"; 
  }
  deviation oc-ip:/oc-if:interfaces/oc-if:interface/oc-if:subinterfaces/oc-if:subinterface/oc-ip:ipv6/oc-ip:state/oc-ip:enabled {
    deviate "not-supported"; 
  }
  deviation oc-ip:/oc-if:interfaces/oc-if:interface/oc-if:subinterfaces/oc-if:subinterface/oc-ip:ipv6/oc-ip:state/oc-ip:mtu {
    deviate "not-supported"; 
  }
  deviation oc-ip:/oc-if:interfaces/oc-if:interface/oc-if:subinterfaces/oc-if:subinterface/oc-ip:ipv6/oc-ip:state/oc-ip:dup-addr-detect-transmits {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:config/oc-ip:accept-mode {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:virtual-router-id {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:virtual-address {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:priority {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:preempt {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:preempt-delay {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:accept-mode {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:advertisement-interval {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:state/oc-ip:current-priority {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:interface-tracking/oc-ip:config/oc-ip:track-interface {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:interface-tracking/oc-ip:config/oc-ip:priority-decrement {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:interface-tracking/oc-ip:state/oc-ip:track-interface {
    deviate "not-supported"; 
  }
  deviation oc-ip:/oc-if:interfaces/oc-if:interface/oc-if:subinterfaces/oc-if:subinterface/oc-ip:ipv4/oc-ip:addresses/oc-ip:address/oc-ip:vrrp/oc-ip:vrrp-group/oc-ip:interface-tracking/oc-ip:state/oc-ip:priority-decrement {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:config/oc-ip:accept-mode {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:virtual-router-id {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:virtual-address {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:priority {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:preempt {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:preempt-delay {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:accept-mode {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:advertisement-interval {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:state/oc-ip:current-priority {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:interface-tracking/oc-ip:config/oc-ip:track-interface {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:interface-tracking/oc-ip:config/oc-ip:priority-decrement {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:interface-tracking/oc-ip:state/oc-ip:track-interface {
    deviate "not-supported"; 
  }
  deviation oc-ip:/oc-if:interfaces/oc-if:interface/oc-if:subinterfaces/oc-if:subinterface/oc-ip:ipv6/oc-ip:addresses/oc-ip:address/oc-ip:vrrp/oc-ip:vrrp-group/oc-ip:interface-tracking/oc-ip:state/oc-ip:priority-decrement {
    deviate "not-supported"; 
  }
  deviation oc-ip:/oc-if:interfaces/oc-if:interface/oc-if:subinterfaces/oc-if:subinterface/oc-ip:ipv6/oc-ip:addresses/oc-ip:address/vrrp/vrrp-group/state/oc-ip:virtual-link-local {
    deviate "not-supported"; 
  }
  deviation oc-ip:/oc-if:interfaces/oc-if:interface/oc-vlan:routed-vlan/oc-ip:ipv4/oc-ip:addresses/oc-ip:address/oc-ip:state/oc-ip:ip {
    deviate "not-supported"; 
  }
  deviation oc-ip:/oc-if:interfaces/oc-if:interface/oc-vlan:routed-vlan/oc-ip:ipv4/oc-ip:addresses/oc-ip:address/oc-ip:state/oc-ip:prefix-length {
    deviate "not-supported"; 
  }
  deviation oc-ip:/oc-if:interfaces/oc-if:interface/oc-vlan:routed-vlan/oc-ip:ipv4/oc-ip:addresses/oc-ip:address/oc-ip:state/oc-ip:origin {
    deviate "not-supported"; 
  }
  deviation oc-ip:/oc-if:interfaces/oc-if:interface/oc-vlan:routed-vlan/oc-ip:ipv4/oc-ip:neighbors/oc-ip:neighbor/oc-ip:state/oc-ip:ip {
    deviate "not-supported"; 
  }
  deviation oc-ip:/oc-if:interfaces/oc-if:interface/oc-vlan:routed-vlan/oc-ip:ipv4/oc-ip:neighbors/oc-ip:neighbor/oc-ip:state/oc-ip:link-layer-address {
    deviate "not-supported"; 
  }
  deviation oc-ip:/oc-if:interfaces/oc-if:interface/oc-vlan:routed-vlan/oc-ip:ipv4/oc-ip:neighbors/oc-ip:neighbor/oc-ip:state/oc-ip:origin {
    deviate "not-supported"; 
  }
  deviation oc-ip:/oc-if:interfaces/oc-if:interface/oc-vlan:routed-vlan/oc-ip:ipv4/oc-if:unnumbered/oc-if:config/oc-if:enabled {
    deviate "not-supported"; 
  }
  deviation oc-ip:/oc-if:interfaces/oc-if:interface/oc-vlan:routed-vlan/oc-ip:ipv4/oc-if:unnumbered/oc-if:state/oc-if:enabled {
    deviate "not-supported"; 
  }
  deviation oc-ip:/oc-if:interfaces/oc-if:interface/oc-vlan:routed-vlan/oc-ip:ipv4/oc-if:unnumbered/oc-if:interface-ref/oc-if:config/oc-if:interface {
    deviate "not-supported"; 
  }
  deviation oc-ip:/oc-if:interfaces/oc-if:interface/oc-vlan:routed-vlan/oc-ip:ipv4/oc-if:unnumbered/oc-if:interface-ref/oc-if:config/oc-if:subinterface {
    deviate "not-supported"; 
  }
  deviation oc-ip:/oc-if:interfaces/oc-if:interface/oc-vlan:routed-vlan/oc-ip:ipv4/oc-if:unnumbered/oc-if:interface-ref/oc-if:state/oc-if:interface {
    deviate "not-supported"; 
  }
  deviation oc-ip:/oc-if:interfaces/oc-if:interface/oc-vlan:routed-vlan/oc-ip:ipv4/oc-if:unnumbered/oc-if:interface-ref/oc-if:state/oc-if:subinterface {
    deviate "not-supported"; 
  }
  deviation oc-ip:/oc-if:interfaces/oc-if:interface/oc-vlan:routed-vlan/oc-ip:ipv4/oc-ip:config/oc-ip:enabled {
    deviate "not-supported"; 
  }
  deviation oc-ip:/oc-if:interfaces/oc-if:interface/oc-vlan:routed-vlan/oc-ip:ipv4/oc-ip:config/oc-ip:mtu {
    deviate "not-supported"; 
  }
  deviation oc-ip:/oc-if:interfaces/oc-if:interface/oc-vlan:routed-vlan/oc-ip:ipv4/oc-ip:state/oc-ip:enabled {
    deviate "not-supported"; 
  }
  deviation oc-ip:/oc-if:interfaces/oc-if:interface/oc-vlan:routed-vlan/oc-ip:ipv4/oc-ip:state/oc-ip:mtu {
    deviate "not-supported"; 
  }
  deviation oc-ip:/oc-if:interfaces/oc-if:interface/oc-vlan:routed-vlan/oc-ip:ipv6/oc-ip:addresses/oc-ip:address/oc-ip:state/oc-ip:ip {
    deviate "not-supported"; 
  }
  deviation oc-ip:/oc-if:interfaces/oc-if:interface/oc-vlan:routed-vlan/oc-ip:ipv6/oc-ip:addresses/oc-ip:address/oc-ip:state/oc-ip:prefix-length {
    deviate "not-supported"; 
  }
  deviation oc-ip:/oc-if:interfaces/oc-if:interface/oc-vlan:routed-vlan/oc-ip:ipv6/oc-ip:addresses/oc-ip:address/oc-ip:state/oc-ip:origin {
    deviate "not-supported"; 
  }
  deviation oc-ip:/oc-if:interfaces/oc-if:interface/oc-vlan:routed-vlan/oc-ip:ipv6/oc-ip:addresses/oc-ip:address/oc-ip:state/oc-ip:status {
    deviate "not-supported"; 
  }
  deviation oc-ip:/oc-if:interfaces/oc-if:interface/oc-vlan:routed-vlan/oc-ip:ipv6/oc-ip:neighbors/oc-ip:neighbor/oc-ip:state/oc-ip:ip {
    deviate "not-supported"; 
  }
  deviation oc-ip:/oc-if:interfaces/oc-if:interface/oc-vlan:routed-vlan/oc-ip:ipv6/oc-ip:neighbors/oc-ip:neighbor/oc-ip:state/oc-ip:link-layer-address {
    deviate "not-supported"; 
  }
  deviation oc-ip:/oc-if:interfaces/oc-if:interface/oc-vlan:routed-vlan/oc-ip:ipv6/oc-ip:neighbors/oc-ip:neighbor/oc-ip:state/oc-ip:origin {
    deviate "not-supported"; 
  }
  deviation oc-ip:/oc-if:interfaces/oc-if:interface/oc-vlan:routed-vlan/oc-ip:ipv6/oc-ip:neighbors/oc-ip:neighbor/oc-ip:state/oc-ip:is-router {
    deviate "not-supported"; 
  }
  deviation oc-ip:/oc-if:interfaces/oc-if:interface/oc-vlan:routed-vlan/oc-ip:ipv6/oc-ip:neighbors/oc-ip:neighbor/oc-ip:state/oc-ip:neighbor-state {
    deviate "not-supported"; 
  }
  deviation oc-ip:/oc-if:interfaces/oc-if:interface/oc-vlan:routed-vlan/oc-ip:ipv6/oc-if:unnumbered/oc-if:config/oc-if:enabled {
    deviate "not-supported"; 
  }
  deviation oc-ip:/oc-if:interfaces/oc-if:interface/oc-vlan:routed-vlan/oc-ip:ipv6/oc-if:unnumbered/oc-if:state/oc-if:enabled {
    deviate "not-supported"; 
  }
  deviation oc-ip:/oc-if:interfaces/oc-if:interface/oc-vlan:routed-vlan/oc-ip:ipv6/oc-if:unnumbered/oc-if:interface-ref/oc-if:config/oc-if:interface {
    deviate "not-supported"; 
  }
  deviation oc-ip:/oc-if:interfaces/oc-if:interface/oc-vlan:routed-vlan/oc-ip:ipv6/oc-if:unnumbered/oc-if:interface-ref/oc-if:config/oc-if:subinterface {
    deviate "not-supported"; 
  }
  deviation oc-ip:/oc-if:interfaces/oc-if:interface/oc-vlan:routed-vlan/oc-ip:ipv6/oc-if:unnumbered/oc-if:interface-ref/oc-if:state/oc-if:interface {
    deviate "not-supported"; 
  }
  deviation oc-ip:/oc-if:interfaces/oc-if:interface/oc-vlan:routed-vlan/oc-ip:ipv6/oc-if:unnumbered/oc-if:interface-ref/oc-if:state/oc-if:subinterface {
    deviate "not-supported"; 
  }
  deviation oc-ip:/oc-if:interfaces/oc-if:interface/oc-vlan:routed-vlan/oc-ip:ipv6/oc-ip:config/oc-ip:enabled {
    deviate "not-supported"; 
  }
  deviation oc-ip:/oc-if:interfaces/oc-if:interface/oc-vlan:routed-vlan/oc-ip:ipv6/oc-ip:config/oc-ip:mtu {
    deviate "not-supported"; 
  }
  deviation oc-ip:/oc-if:interfaces/oc-if:interface/oc-vlan:routed-vlan/oc-ip:ipv6/oc-ip:state/oc-ip:enabled {
    deviate "not-supported"; 
  }
  deviation oc-ip:/oc-if:interfaces/oc-if:interface/oc-vlan:routed-vlan/oc-ip:ipv6/oc-ip:state/oc-ip:mtu {
    deviate "not-supported"; 
  }
  deviation oc-ip:/oc-if:interfaces/oc-if:interface/oc-vlan:routed-vlan/oc-ip:ipv6/oc-ip:state/oc-ip:dup-addr-detect-transmits {
    deviate "not-supported"; 
  }
  deviation oc-ip:/oc-if:interfaces/oc-if:interface/oc-vlan:routed-vlan/oc-ip:ipv4/oc-ip:addresses/oc-ip:address/oc-ip:vrrp/oc-ip:vrrp-group/oc-ip:config/oc-ip:accept-mode {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:virtual-router-id {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:virtual-address {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:priority {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:preempt {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:preempt-delay {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:accept-mode {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:advertisement-interval {
    deviate "not-supported"; 
  }
  deviation oc-ip:/oc-if:interfaces/oc-if:interface/oc-vlan:routed-vlan/oc-ip:ipv4/oc-ip:addresses/oc-ip:address/oc-ip:vrrp/oc-ip:vrrp-group/oc-ip:state/oc-ip:current-priority {
    deviate "not-supported"; 
  }
  deviation oc-ip:/oc-if:interfaces/oc-if:interface/oc-vlan:routed-vlan/oc-ip:ipv4/oc-ip:addresses/oc-ip:address/oc-ip:vrrp/oc-ip:vrrp-group/oc-ip:interface-tracking/oc-ip:config/oc-ip:track-interface {
    deviate "not-supported"; 
  }
  deviation oc-ip:/oc-if:interfaces/oc-if:interface/oc-vlan:routed-vlan/oc-ip:ipv4/oc-ip:addresses/oc-ip:address/oc-ip:vrrp/oc-ip:vrrp-group/oc-ip:interface-tracking/oc-ip:config/oc-ip:priority-decrement {
    deviate "not-supported"; 
  }
  deviation oc-ip:/oc-if:interfaces/oc-if:interface/oc-vlan:routed-vlan/oc-ip:ipv4/oc-ip:addresses/oc-ip:address/oc-ip:vrrp/oc-ip:vrrp-group/oc-ip:interface-tracking/oc-ip:state/oc-ip:track-interface {
    deviate "not-supported"; 
  }
  deviation oc-ip:/oc-if:interfaces/oc-if:interface/oc-vlan:routed-vlan/oc-ip:ipv4/oc-ip:addresses/oc-ip:address/oc-ip:vrrp/oc-ip:vrrp-group/oc-ip:interface-tracking/oc-ip:state/oc-ip:priority-decrement {
    deviate "not-supported"; 
  }
  deviation oc-ip:/oc-if:interfaces/oc-if:interface/oc-vlan:routed-vlan/oc-ip:ipv6/oc-ip:addresses/oc-ip:address/oc-ip:vrrp/oc-ip:vrrp-group/oc-ip:config/oc-ip:accept-mode {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:virtual-router-id {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:virtual-address {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:priority {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:preempt {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:preempt-delay {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:accept-mode {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:advertisement-interval {
    deviate "not-supported"; 
  }
  deviation oc-ip:/oc-if:interfaces/oc-if:interface/oc-vlan:routed-vlan/oc-ip:ipv6/oc-ip:addresses/oc-ip:address/oc-ip:vrrp/oc-ip:vrrp-group/oc-ip:state/oc-ip:current-priority {
    deviate "not-supported"; 
  }
  deviation oc-ip:/oc-if:interfaces/oc-if:interface/oc-vlan:routed-vlan/oc-ip:ipv6/oc-ip:addresses/oc-ip:address/oc-ip:vrrp/oc-ip:vrrp-group/oc-ip:interface-tracking/oc-ip:config/oc-ip:track-interface {
    deviate "not-supported"; 
  }
  deviation oc-ip:/oc-if:interfaces/oc-if:interface/oc-vlan:routed-vlan/oc-ip:ipv6/oc-ip:addresses/oc-ip:address/oc-ip:vrrp/oc-ip:vrrp-group/oc-ip:interface-tracking/oc-ip:config/oc-ip:priority-decrement {
    deviate "not-supported"; 
  }
  deviation oc-ip:/oc-if:interfaces/oc-if:interface/oc-vlan:routed-vlan/oc-ip:ipv6/oc-ip:addresses/oc-ip:address/oc-ip:vrrp/oc-ip:vrrp-group/oc-ip:interface-tracking/oc-ip:state/oc-ip:track-interface {
    deviate "not-supported"; 
  }
  deviation oc-ip:/oc-if:interfaces/oc-if:interface/oc-vlan:routed-vlan/oc-ip:ipv6/oc-ip:addresses/oc-ip:address/oc-ip:vrrp/oc-ip:vrrp-group/oc-ip:interface-tracking/oc-ip:state/oc-ip:priority-decrement {
    deviate "not-supported"; 
  }
  deviation oc-ip:/oc-if:interfaces/oc-if:interface/oc-vlan:routed-vlan/oc-ip:ipv6/oc-ip:addresses/oc-ip:address/vrrp/vrrp-group/state/oc-ip:virtual-link-local {
    deviate "not-supported"; 
  }

/* Mapped to device model
 *     Device Model Target: /top:System/top:ipv4-items/top:inst-items/top:dom-items/top:Dom-list/top:if-items/top:If-list/top:addr-items/top:Addr-list
 * Transformation Function: mapping_ipv4addrlist_condition 
 */
  deviation oc-ip:/oc-if:interfaces/oc-if:interface/oc-if:subinterfaces/oc-if:subinterface/oc-ip:ipv4/oc-ip:addresses/oc-ip:address {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ipv4_addr_ip 
 */
  deviation oc-ip:/oc-if:interfaces/oc-if:interface/oc-if:subinterfaces/oc-if:subinterface/oc-ip:ipv4/oc-ip:addresses/oc-ip:address/oc-ip:ip {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ip_str_to_int 
 */
  deviation oc-ip:/oc-if:interfaces/oc-if:interface/oc-if:subinterfaces/oc-if:subinterface/oc-ip:ipv4/oc-ip:addresses/oc-ip:address/oc-ip:config/oc-ip:ip {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ip_pref_len 
 */
  deviation oc-ip:/oc-if:interfaces/oc-if:interface/oc-if:subinterfaces/oc-if:subinterface/oc-ip:ipv4/oc-ip:addresses/oc-ip:address/oc-ip:config/oc-ip:prefix-length {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list
 * Transformation Function: conv_oc_to_nx_ipv4_neighbor_list 
 */
  deviation oc-ip:/oc-if:interfaces/oc-if:interface/oc-if:subinterfaces/oc-if:subinterface/oc-ip:ipv4/oc-ip:neighbors/oc-ip:neighbor {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:ip
 * Transformation Function: conv_oc_to_nx_neighbor_ip 
 */
  deviation oc-ip:/oc-if:interfaces/oc-if:interface/oc-if:subinterfaces/oc-if:subinterface/oc-ip:ipv4/oc-ip:neighbors/oc-ip:neighbor/oc-ip:ip {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:ip
 * Transformation Function: conv_oc_to_nx_neighbor_config_ip_str_to_int 
 */
  deviation oc-ip:/oc-if:interfaces/oc-if:interface/oc-if:subinterfaces/oc-if:subinterface/oc-ip:ipv4/oc-ip:neighbors/oc-ip:neighbor/oc-ip:config/oc-ip:ip {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:mac
 * Transformation Function: conv_oc_to_nx_neighbor_config_lladdr_str_to_int 
 */
  deviation oc-ip:/oc-if:interfaces/oc-if:interface/oc-if:subinterfaces/oc-if:subinterface/oc-ip:ipv4/oc-ip:neighbors/oc-ip:neighbor/oc-ip:config/oc-ip:link-layer-address {
    deviate /* add, replace, or delete */ {
      /* something */ /* "something's value" */;
    }
  }

/* Mapped to device model
 *     Device Model Target: /top:System/top:ipv6-items/top:inst-items/top:dom-items/top:Dom-list/top:if-items/top:If-list/top:addr-items/top:Addr-list
 * Transformation Function: mapping_ipv6addrlist_iflist_condition 
 */
  deviation oc-ip:/oc-if:interfaces/oc-if:interface/oc-if:subinterfaces/oc-if:subinterface/oc-ip:ipv6/oc-ip:addresses/oc-ip:address {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ipv6_addr_ip 
 */
  deviation oc-ip:/oc-if:interfaces/oc-if:interface/oc-if:subinterfaces/oc-if:subinterface/oc-ip:ipv6/oc-ip:addresses/oc-ip:address/oc-ip:ip {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ip6_str_to_int 
 */
  deviation oc-ip:/oc-if:interfaces/oc-if:interface/oc-if:subinterfaces/oc-if:subinterface/oc-ip:ipv6/oc-ip:addresses/oc-ip:address/oc-ip:config/oc-ip:ip {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ip6_pref_len 
 */
  deviation oc-ip:/oc-if:interfaces/oc-if:interface/oc-if:subinterfaces/oc-if:subinterface/oc-ip:ipv6/oc-ip:addresses/oc-ip:address/oc-ip:config/oc-ip:prefix-length {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list
 * Transformation Function: conv_oc_to_nx_ipv6_neighbor_list 
 */
  deviation oc-ip:/oc-if:interfaces/oc-if:interface/oc-if:subinterfaces/oc-if:subinterface/oc-ip:ipv6/oc-ip:neighbors/oc-ip:neighbor {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:addr
 * Transformation Function: conv_oc_to_nx_neighbor_ip6_ip 
 */
  deviation oc-ip:/oc-if:interfaces/oc-if:interface/oc-if:subinterfaces/oc-if:subinterface/oc-ip:ipv6/oc-ip:neighbors/oc-ip:neighbor/oc-ip:ip {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:addr
 * Transformation Function: conv_oc_to_nx_neighbor_config_ip6_str_to_int 
 */
  deviation oc-ip:/oc-if:interfaces/oc-if:interface/oc-if:subinterfaces/oc-if:subinterface/oc-ip:ipv6/oc-ip:neighbors/oc-ip:neighbor/oc-ip:config/oc-ip:ip {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:neighborMac
 * Transformation Function: neighbor_config_lladdr_str_to_int 
 */
  deviation oc-ip:/oc-if:interfaces/oc-if:interface/oc-if:subinterfaces/oc-if:subinterface/oc-ip:ipv6/oc-ip:neighbors/oc-ip:neighbor/oc-ip:config/oc-ip:link-layer-address {
    deviate /* add, replace, or delete */ {
      /* something */ /* "something's value" */;
    }
  }

/* Mapped to device model
 *     Device Model Target: /top:System/top:nd-items/top:inst-items/top:dom-items/top:Dom-list/top:if-items/top:If-list/top:dadAttempts
 * Transformation Function: conv_oc_to_nx_ipv6_config_dupdet_uint32_to_uint16 
 */
  deviation oc-ip:/oc-if:interfaces/oc-if:interface/oc-if:subinterfaces/oc-if:subinterface/oc-ip:ipv6/oc-ip:config/oc-ip:dup-addr-detect-transmits {
    deviate /* add, replace, or delete */ {
      /* something */ /* "something's value" */;
    }
  }

/* Mapped to device model
 *     Device Model Target: /top:System/top:vrrpv3-items/top:inst-items/top:if-items/top:Interface-list/top:id-items/top:Vr-list
 * Transformation Function: conv_oc_vrgroup_list_v4_to_nx 
 */
  deviation oc-ip:/oc-if:interfaces/oc-if:interface/oc-if:subinterfaces/oc-if:subinterface/oc-ip:ipv4/oc-ip:addresses/oc-ip:address/oc-ip:vrrp/oc-ip:vrrp-group {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_router_id_v4_to_nx 
 */
  deviation oc-ip:/oc-if:interfaces/oc-if:interface/oc-if:subinterfaces/oc-if:subinterface/oc-ip:ipv4/oc-ip:addresses/oc-ip:address/oc-ip:vrrp/oc-ip:vrrp-group/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_config_container_router_id_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_list_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:virtual-address {
    deviate /* add, replace, or delete */ {
      /* something */ /* "something's value" */;
    }
  }

/* Mapped to device model
 *     Device Model Target: /top:System/top:vrrpv3-items/top:inst-items/top:if-items/top:Interface-list/top:id-items/top:Vr-list/top:priCfg
 * Transformation Function: conv_oc_priority_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:priority {
    deviate /* add, replace, or delete */ {
      /* something */ /* "something's value" */;
    }
  }

/* Mapped to device model
 *     Device Model Target: /top:System/top:vrrpv3-items/top:inst-items/top:if-items/top:Interface-list/top:id-items/top:Vr-list/top:preempt
 * Transformation Function: conv_oc_preempt_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:preempt {
    deviate /* add, replace, or delete */ {
      /* something */ /* "something's value" */;
    }
  }

/* Mapped to device model
 *     Device Model Target: /top:System/top:vrrpv3-items/top:inst-items/top:if-items/top:Interface-list/top:id-items/top:Vr-list/top:preemptDelayMin
 * Transformation Function: conv_oc_preDelay_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:preempt-delay {
    deviate /* add, replace, or delete */ {
      /* something */ /* "something's value" */;
    }
  }

/* Mapped to device model
 *     Device Model Target: /top:System/top:vrrpv3-items/top:inst-items/top:if-items/top:Interface-list/top:id-items/top:Vr-list/top:advIntvl
 * Transformation Function: conv_oc_advtimer_v4_to_nx 
 */
  deviation oc-ip:/oc-if:interfaces/oc-if:interface/oc-if:subinterfaces/oc-if:subinterface/oc-ip:ipv4/oc-ip:addresses/oc-ip:address/oc-ip:vrrp/oc-ip:vrrp-group/oc-ip:config/oc-ip:advertisement-interval {
    deviate /* add, replace, or delete */ {
      /* something */ /* "something's value" */;
    }
  }

/* Mapped to device model
 *     Device Model Target: /top:System/top:vrrpv3-items/top:inst-items/top:if-items/top:Interface-list/top:id-items/top:Vr-list
 * Transformation Function: conv_oc_vrgroup_list_v6_to_nx 
 */
  deviation oc-ip:/oc-if:interfaces/oc-if:interface/oc-if:subinterfaces/oc-if:subinterface/oc-ip:ipv6/oc-ip:addresses/oc-ip:address/oc-ip:vrrp/oc-ip:vrrp-group {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_router_id_v6_to_nx 
 */
  deviation oc-ip:/oc-if:interfaces/oc-if:interface/oc-if:subinterfaces/oc-if:subinterface/oc-ip:ipv6/oc-ip:addresses/oc-ip:address/oc-ip:vrrp/oc-ip:vrrp-group/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_config_container_router_id_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_list_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:virtual-address {
    deviate /* add, replace, or delete */ {
      /* something */ /* "something's value" */;
    }
  }

/* Mapped to device model
 *     Device Model Target: /top:System/top:vrrpv3-items/top:inst-items/top:if-items/top:Interface-list/top:id-items/top:Vr-list/top:priCfg
 * Transformation Function: conv_oc_priority_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:priority {
    deviate /* add, replace, or delete */ {
      /* something */ /* "something's value" */;
    }
  }

/* Mapped to device model
 *     Device Model Target: /top:System/top:vrrpv3-items/top:inst-items/top:if-items/top:Interface-list/top:id-items/top:Vr-list/top:preempt
 * Transformation Function: conv_oc_preempt_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:preempt {
    deviate /* add, replace, or delete */ {
      /* something */ /* "something's value" */;
    }
  }

/* Mapped to device model
 *     Device Model Target: /top:System/top:vrrpv3-items/top:inst-items/top:if-items/top:Interface-list/top:id-items/top:Vr-list/top:preemptDelayMin
 * Transformation Function: conv_oc_preDelay_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:preempt-delay {
    deviate /* add, replace, or delete */ {
      /* something */ /* "something's value" */;
    }
  }

/* Mapped to device model
 *     Device Model Target: /top:System/top:vrrpv3-items/top:inst-items/top:if-items/top:Interface-list/top:id-items/top:Vr-list/top:advIntvl
 * Transformation Function: conv_oc_advtimer_v6_to_nx 
 */
  deviation oc-ip:/oc-if:interfaces/oc-if:interface/oc-if:subinterfaces/oc-if:subinterface/oc-ip:ipv6/oc-ip:addresses/oc-ip:address/oc-ip:vrrp/oc-ip:vrrp-group/oc-ip:config/oc-ip:advertisement-interval {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_link_local_v6_to_nx 
 */
  deviation oc-ip:/oc-if:interfaces/oc-if:interface/oc-if:subinterfaces/oc-if:subinterface/oc-ip:ipv6/oc-ip:addresses/oc-ip:address/vrrp/vrrp-group/config/oc-ip:virtual-link-local {
    deviate /* add, replace, or delete */ {
      /* something */ /* "something's value" */;
    }
  }

/* Mapped to device model
 *     Device Model Target: /top:System/top:ipv4-items/top:inst-items/top:dom-items/top:Dom-list/top:if-items/top:If-list/top:addr-items/top:Addr-list
 * Transformation Function: mapping_ipv4addrlist_condition 
 */
  deviation oc-ip:/oc-if:interfaces/oc-if:interface/oc-vlan:routed-vlan/oc-ip:ipv4/oc-ip:addresses/oc-ip:address {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ipv4_addr_ip 
 */
  deviation oc-ip:/oc-if:interfaces/oc-if:interface/oc-vlan:routed-vlan/oc-ip:ipv4/oc-ip:addresses/oc-ip:address/oc-ip:ip {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ip_str_to_int 
 */
  deviation oc-ip:/oc-if:interfaces/oc-if:interface/oc-vlan:routed-vlan/oc-ip:ipv4/oc-ip:addresses/oc-ip:address/oc-ip:config/oc-ip:ip {
    deviate /* add, replace, or delete */ {
      /* something */ /* "something's value" */;
    }
  }

/* Mapped to device model
 *     Device Model Target: /top:System/top:ipv4-items/top:inst-items/top:dom-items/top:Dom-list/top:if-items/top:If-list/top:addr-items/top:Addr-list/top:addr
 * Transformation Function: conv_oc_to_nx_ip_pref_len 
 */
  deviation oc-ip:/oc-if:interfaces/oc-if:interface/oc-vlan:routed-vlan/oc-ip:ipv4/oc-ip:addresses/oc-ip:address/oc-ip:config/oc-ip:prefix-length {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list
 * Transformation Function: conv_oc_to_nx_ipv4_neighbor_list 
 */
  deviation oc-ip:/oc-if:interfaces/oc-if:interface/oc-vlan:routed-vlan/oc-ip:ipv4/oc-ip:neighbors/oc-ip:neighbor {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:ip
 * Transformation Function: conv_oc_to_nx_neighbor_ip 
 */
  deviation oc-ip:/oc-if:interfaces/oc-if:interface/oc-vlan:routed-vlan/oc-ip:ipv4/oc-ip:neighbors/oc-ip:neighbor/oc-ip:ip {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:ip
 * Transformation Function: conv_oc_to_nx_neighbor_config_ip_str_to_int 
 */
  deviation oc-ip:/oc-if:interfaces/oc-if:interface/oc-vlan:routed-vlan/oc-ip:ipv4/oc-ip:neighbors/oc-ip:neighbor/oc-ip:config/oc-ip:ip {
    deviate /* add, replace, or delete */ {
      /* something */ /* "something's value" */;
    }
  }

/* Mapped to device model
 *     Device Model Target: /top:System/top:arp-items/top:inst-items/top:dom-items/top:Dom-list/top:if-items/top:If-list/top:sadj-items/top:StAdjEp-list/top:mac
 * Transformation Function: conv_oc_to_nx_neighbor_config_lladdr_str_to_int 
 */
  deviation oc-ip:/oc-if:interfaces/oc-if:interface/oc-vlan:routed-vlan/oc-ip:ipv4/oc-ip:neighbors/oc-ip:neighbor/oc-ip:config/oc-ip:link-layer-address {
    deviate /* add, replace, or delete */ {
      /* something */ /* "something's value" */;
    }
  }

/* Mapped to device model
 *     Device Model Target: /top:System/top:ipv6-items/top:inst-items/top:dom-items/top:Dom-list/top:if-items/top:If-list/top:addr-items/top:Addr-list
 * Transformation Function: mapping_ipv6addrlist_iflist_condition 
 */
  deviation oc-ip:/oc-if:interfaces/oc-if:interface/oc-vlan:routed-vlan/oc-ip:ipv6/oc-ip:addresses/oc-ip:address {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ipv6_addr_ip 
 */
  deviation oc-ip:/oc-if:interfaces/oc-if:interface/oc-vlan:routed-vlan/oc-ip:ipv6/oc-ip:addresses/oc-ip:address/oc-ip:ip {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ip6_str_to_int 
 */
  deviation oc-ip:/oc-if:interfaces/oc-if:interface/oc-vlan:routed-vlan/oc-ip:ipv6/oc-ip:addresses/oc-ip:address/oc-ip:config/oc-ip:ip {
    deviate /* add, replace, or delete */ {
      /* something */ /* "something's value" */;
    }
  }

/* Mapped to device model
 *     Device Model Target: /top:System/top:ipv6-items/top:inst-items/top:dom-items/top:Dom-list/top:if-items/top:If-list/top:addr-items/top:Addr-list/top:addr
 * Transformation Function: conv_oc_to_nx_ip6_pref_len 
 */
  deviation oc-ip:/oc-if:interfaces/oc-if:interface/oc-vlan:routed-vlan/oc-ip:ipv6/oc-ip:addresses/oc-ip:address/oc-ip:config/oc-ip:prefix-length {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list
 * Transformation Function: conv_oc_to_nx_ipv6_neighbor_list 
 */
  deviation oc-ip:/oc-if:interfaces/oc-if:interface/oc-vlan:routed-vlan/oc-ip:ipv6/oc-ip:neighbors/oc-ip:neighbor {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:addr
 * Transformation Function: conv_oc_to_nx_neighbor_ip6_ip 
 */
  deviation oc-ip:/oc-if:interfaces/oc-if:interface/oc-vlan:routed-vlan/oc-ip:ipv6/oc-ip:neighbors/oc-ip:neighbor/oc-ip:ip {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:addr
 * Transformation Function: conv_oc_to_nx_neighbor_config_ip6_str_to_int 
 */
  deviation oc-ip:/oc-if:interfaces/oc-if:interface/oc-vlan:routed-vlan/oc-ip:ipv6/oc-ip:neighbors/oc-ip:neighbor/oc-ip:config/oc-ip:ip {
    deviate /* add, replace, or delete */ {
      /* something */ /* "something's value" */;
    }
  }

/* Mapped to device model
 *     Device Model Target: /top:System/top:ipv6-items/top:inst-items/top:dom-items/top:Dom-list/top:if-items/top:If-list/top:nghbr-items/top:Neighbor-list/top:neighborMac
 * Transformation Function: neighbor_config_lladdr_str_to_int 
 */
  deviation oc-ip:/oc-if:interfaces/oc-if:interface/oc-vlan:routed-vlan/oc-ip:ipv6/oc-ip:neighbors/oc-ip:neighbor/oc-ip:config/oc-ip:link-layer-address {
    deviate /* add, replace, or delete */ {
      /* something */ /* "something's value" */;
    }
  }

/* Mapped to device model
 *     Device Model Target: /top:System/top:nd-items/top:inst-items/top:dom-items/top:Dom-list/top:if-items/top:If-list/top:dadAttempts
 * Transformation Function: conv_oc_to_nx_ipv6_config_dupdet_uint32_to_uint16 
 */
  deviation oc-ip:/oc-if:interfaces/oc-if:interface/oc-vlan:routed-vlan/oc-ip:ipv6/oc-ip:config/oc-ip:dup-addr-detect-transmits {
    deviate /* add, replace, or delete */ {
      /* something */ /* "something's value" */;
    }
  }

/* Mapped to device model
 *     Device Model Target: /top:System/top:vrrpv3-items/top:inst-items/top:if-items/top:Interface-list/top:id-items/top:Vr-list
 * Transformation Function: conv_oc_vrgroup_list_v4_to_nx 
 */
  deviation oc-ip:/oc-if:interfaces/oc-if:interface/oc-vlan:routed-vlan/oc-ip:ipv4/oc-ip:addresses/oc-ip:address/oc-ip:vrrp/oc-ip:vrrp-group {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_router_id_v4_to_nx 
 */
  deviation oc-ip:/oc-if:interfaces/oc-if:interface/oc-vlan:routed-vlan/oc-ip:ipv4/oc-ip:addresses/oc-ip:address/oc-ip:vrrp/oc-ip:vrrp-group/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_config_container_router_id_v4_to_nx 
 */
  deviation oc-ip:/oc-if:interfaces/oc-if:interface/oc-vlan:routed-vlan/oc-ip:ipv4/oc-ip:addresses/oc-ip:address/oc-ip:vrrp/oc-ip:vrrp-group/oc-ip:config/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_list_v4_to_nx 
 */
  deviation oc-ip:/oc-if:interfaces/oc-if:interface/oc-vlan:routed-vlan/oc-ip:ipv4/oc-ip:addresses/oc-ip:address/oc-ip:vrrp/oc-ip:vrrp-group/oc-ip:config/oc-ip:virtual-address {
    deviate /* add, replace, or delete */ {
      /* something */ /* "something's value" */;
    }
  }

/* Mapped to device model
 *     Device Model Target: /top:System/top:vrrpv3-items/top:inst-items/top:if-items/top:Interface-list/top:id-items/top:Vr-list/top:priCfg
 * Transformation Function: conv_oc_priority_v4_to_nx 
 */
  deviation oc-ip:/oc-if:interfaces/oc-if:interface/oc-vlan:routed-vlan/oc-ip:ipv4/oc-ip:addresses/oc-ip:address/oc-ip:vrrp/oc-ip:vrrp-group/oc-ip:config/oc-ip:priority {
    deviate /* add, replace, or delete */ {
      /* something */ /* "something's value" */;
    }
  }

/* Mapped to device model
 *     Device Model Target: /top:System/top:vrrpv3-items/top:inst-items/top:if-items/top:Interface-list/top:id-items/top:Vr-list/top:preempt
 * Transformation Function: conv_oc_preempt_v4_to_nx 
 */
  deviation oc-ip:/oc-if:interfaces/oc-if:interface/oc-vlan:routed-vlan/oc-ip:ipv4/oc-ip:addresses/oc-ip:address/oc-ip:vrrp/oc-ip:vrrp-group/oc-ip:config/oc-ip:preempt {
    deviate /* add, replace, or delete */ {
      /* something */ /* "something's value" */;
    }
  }

/* Mapped to device model
 *     Device Model Target: /top:System/top:vrrpv3-items/top:inst-items/top:if-items/top:Interface-list/top:id-items/top:Vr-list/top:preemptDelayMin
 * Transformation Function: conv_oc_preDelay_v4_to_nx 
 */
  deviation oc-ip:/oc-if:interfaces/oc-if:interface/oc-vlan:routed-vlan/oc-ip:ipv4/oc-ip:addresses/oc-ip:address/oc-ip:vrrp/oc-ip:vrrp-group/oc-ip:config/oc-ip:preempt-delay {
    deviate /* add, replace, or delete */ {
      /* something */ /* "something's value" */;
    }
  }

/* Mapped to device model
 *     Device Model Target: /top:System/top:vrrpv3-items/top:inst-items/top:if-items/top:Interface-list/top:id-items/top:Vr-list/top:advIntvl
 * Transformation Function: conv_oc_advtimer_v4_to_nx 
 */
  deviation oc-ip:/oc-if:interfaces/oc-if:interface/oc-vlan:routed-vlan/oc-ip:ipv4/oc-ip:addresses/oc-ip:address/oc-ip:vrrp/oc-ip:vrrp-group/oc-ip:config/oc-ip:advertisement-interval {
    deviate /* add, replace, or delete */ {
      /* something */ /* "something's value" */;
    }
  }

/* Mapped to device model
 *     Device Model Target: /top:System/top:vrrpv3-items/top:inst-items/top:if-items/top:Interface-list/top:id-items/top:Vr-list
 * Transformation Function: conv_oc_vrgroup_list_v6_to_nx 
 */
  deviation oc-ip:/oc-if:interfaces/oc-if:interface/oc-vlan:routed-vlan/oc-ip:ipv6/oc-ip:addresses/oc-ip:address/oc-ip:vrrp/oc-ip:vrrp-group {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_router_id_v6_to_nx 
 */
  deviation oc-ip:/oc-if:interfaces/oc-if:interface/oc-vlan:routed-vlan/oc-ip:ipv6/oc-ip:addresses/oc-ip:address/oc-ip:vrrp/oc-ip:vrrp-group/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:id
 * Transformation Function: conv_oc_config_container_router_id_v6_to_nx 
 */
  deviation oc-ip:/oc-if:interfaces/oc-if:interface/oc-vlan:routed-vlan/oc-ip:ipv6/oc-ip:addresses/oc-ip:address/oc-ip:vrrp/oc-ip:vrrp-group/oc-ip:config/oc-ip:virtual-router-id {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_list_v6_to_nx 
 */
  deviation oc-ip:/oc-if:interfaces/oc-if:interface/oc-vlan:routed-vlan/oc-ip:ipv6/oc-ip:addresses/oc-ip:address/oc-ip:vrrp/oc-ip:vrrp-group/oc-ip:config/oc-ip:virtual-address {
    deviate /* add, replace, or delete */ {
      /* something */ /* "something's value" */;
    }
  }

/* Mapped to device model
 *     Device Model Target: /top:System/top:vrrpv3-items/top:inst-items/top:if-items/top:Interface-list/top:id-items/top:Vr-list/top:priCfg
 * Transformation Function: conv_oc_priority_v6_to_nx 
 */
  deviation oc-ip:/oc-if:interfaces/oc-if:interface/oc-vlan:routed-vlan/oc-ip:ipv6/oc-ip:addresses/oc-ip:address/oc-ip:vrrp/oc-ip:vrrp-group/oc-ip:config/oc-ip:priority {
    deviate /* add, replace, or delete */ {
      /* something */ /* "something's value" */;
    }
  }

/* Mapped to device model
 *     Device Model Target: /top:System/top:vrrpv3-items/top:inst-items/top:if-items/top:Interface-list/top:id-items/top:Vr-list/top:preempt
 * Transformation Function: conv_oc_preempt_v6_to_nx 
 */
  deviation oc-ip:/oc-if:interfaces/oc-if:interface/oc-vlan:routed-vlan/oc-ip:ipv6/oc-ip:addresses/oc-ip:address/oc-ip:vrrp/oc-ip:vrrp-group/oc-ip:config/oc-ip:preempt {
    deviate /* add, replace, or delete */ {
      /* something */ /* "something's value" */;
    }
  }

/* Mapped to device model
 *     Device Model Target: /top:System/top:vrrpv3-items/top:inst-items/top:if-items/top:Interface-list/top:id-items/top:Vr-list/top:preemptDelayMin
 * Transformation Function: conv_oc_preDelay_v6_to_nx 
 */
  deviation oc-ip:/oc-if:interfaces/oc-if:interface/oc-vlan:routed-vlan/oc-ip:ipv6/oc-ip:addresses/oc-ip:address/oc-ip:vrrp/oc-ip:vrrp-group/oc-ip:config/oc-ip:preempt-delay {
    deviate /* add, replace, or delete */ {
      /* something */ /* "something's value" */;
    }
  }

/* Mapped to device model
 *     Device Model Target: /top:System/top:vrrpv3-items/top:inst-items/top:if-items/top:Interface-list/top:id-items/top:Vr-list/top:advIntvl
 * Transformation Function: conv_oc_advtimer_v6_to_nx 
 */
  deviation oc-ip:/oc-if:interfaces/oc-if:interface/oc-vlan:routed-vlan/oc-ip:ipv6/oc-ip:addresses/oc-ip:address/oc-ip:vrrp/oc-ip:vrrp-group/oc-ip:config/oc-ip:advertisement-interval {
    deviate /* add, replace, or delete */ {
      /* something */ /* "something's value" */;
    }
  }

/* Mapped to device model
 *     Device Model Target: /top:System/top:vrrpv3-items/top:inst-items/top:if-items/top:Interface-list/top:id-items/top:Vr-list/top:ip
 * Transformation Function: conv_oc_ip_link_local_v6_to_nx 
 */
  deviation oc-ip:/oc-if:interfaces/oc-if:interface/oc-vlan:routed-vlan/oc-ip:ipv6/oc-ip:addresses/oc-ip:address/vrrp/vrrp-group/config/oc-ip:virtual-link-local {
    deviate /* add, replace, or delete */ {
      /* something */ /* "something's value" */;
    }
  }

}
