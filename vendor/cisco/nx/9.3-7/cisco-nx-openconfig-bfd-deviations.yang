module cisco-nx-openconfig-bfd-deviations {

  namespace "http://openconfig.net/yang/bfd-deviations";

  prefix "oc-bfd-devs";

  import openconfig-bfd { prefix oc-bfd; }
  import openconfig-extensions { prefix oc-ext; }
  import openconfig-interfaces { prefix oc-if; }
  import openconfig-if-types { prefix oc-ift; }
  import openconfig-inet-types { prefix oc-inet; }
  import openconfig-network-instance { prefix oc-ni; }
  import openconfig-policy-types { prefix oc-pol-types; }
  import openconfig-types { prefix oc-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-bfd module 
     set for Cisco NXOS.
     Copyright (c) 2015-2017, 2020 by Cisco Systems, Inc.
     All rights reserved.";

  revision "2019-12-02" {
    description
      "Initial revision applicable to NXOS";
  }

  deviation /oc-ni:network-instances/oc-ni:network-instance/oc-ni:protocols/oc-ni:protocol/oc-ni:bgp/oc-ni:peer-groups/oc-ni:peer-group/oc-bfd:enable-bfd/oc-bfd:state/oc-bfd:associated-session {
    deviate "not-supported"; 
  }
  deviation /oc-ni:network-instances/oc-ni:network-instance/oc-ni:protocols/oc-ni:protocol/oc-ni:static-routes/oc-ni:static/oc-ni:next-hops/oc-ni:next-hop/oc-bfd:enable-bfd/oc-bfd:state/oc-bfd:enabled {
    deviate "not-supported"; 
  }
  deviation /oc-bfd:bfd/oc-bfd:interfaces/oc-bfd:interface/oc-bfd:interface-ref/oc-bfd:config/oc-bfd:interface {
    deviate "not-supported"; 
  }
  deviation /oc-bfd:bfd/oc-bfd:interfaces/oc-bfd:interface/oc-bfd:interface-ref/oc-bfd:config/oc-bfd:subinterface {
    deviate "not-supported"; 
  }
  deviation /oc-bfd:bfd/oc-bfd:interfaces/oc-bfd:interface/oc-bfd:interface-ref/oc-bfd:state/oc-bfd:interface {
    deviate "not-supported"; 
  }
  deviation /oc-bfd:bfd/oc-bfd:interfaces/oc-bfd:interface/oc-bfd:interface-ref/oc-bfd:state/oc-bfd:subinterface {
    deviate "not-supported"; 
  }
  deviation /oc-bfd:bfd/oc-bfd:interfaces/oc-bfd:interface/oc-bfd:micro-bfd-sessions/oc-bfd:micro-bfd-session/oc-bfd:config/oc-bfd:local-address {
    deviate "not-supported"; 
  }
  deviation /oc-bfd:bfd/oc-bfd:interfaces/oc-bfd:interface/oc-bfd:micro-bfd-sessions/oc-bfd:micro-bfd-session/oc-bfd:config/oc-bfd:member-interface {
    deviate "not-supported"; 
  }
  deviation /oc-bfd:bfd/oc-bfd:interfaces/oc-bfd:interface/oc-bfd:micro-bfd-sessions/oc-bfd:micro-bfd-session/oc-bfd:state/oc-bfd:remote-control-plane-independent {
    deviate "not-supported"; 
  }
  deviation /oc-bfd:bfd/oc-bfd:interfaces/oc-bfd:interface/oc-bfd:peers/oc-bfd:peer/oc-bfd:state/oc-bfd:remote-control-plane-independent {
    deviate "not-supported"; 
  }


/* Mapped to device model
 *     Device Model Target: /top:System/top:bfd-items/top:inst-items/top:if-items/top:If-list/top:adminSt
 * Transformation Function: conv_oc_nx_enabled 
 */
  deviation /oc-bfd:bfd/oc-bfd:interfaces/oc-bfd:interface/oc-bfd:config/oc-bfd:enabled {
    deviate add {
        default "true";
    }
  }

/* Mapped to device model
 *     Device Model Target: /top:System/top:bfd-items/top:inst-items/top:if-items/top:If-list/top:ifka-items/top:minTxIntvl
 * Transformation Function: conv_oc_nx_desired_min_tx 
 */
  deviation /oc-bfd:bfd/oc-bfd:interfaces/oc-bfd:interface/oc-bfd:config/oc-bfd:desired-minimum-tx-interval {
    deviate add {
        default "50000";
    }
    deviate replace {
        type uint32 {
            range "50000..999000";
        }
    }
  }

/* Mapped to device model
 *     Device Model Target: /top:System/top:bfd-items/top:inst-items/top:if-items/top:If-list/top:ifka-items/top:minRxIntvl
 * Transformation Function: conv_oc_nx_required_min_receive 
 */
  deviation /oc-bfd:bfd/oc-bfd:interfaces/oc-bfd:interface/oc-bfd:config/oc-bfd:required-minimum-receive {
    deviate add {
        default "50000";
    }
    deviate replace {
        type uint32 {
            range "50000..999000";
        }
    }
  }

/* Mapped to device model
 *     Device Model Target: /top:System/top:bfd-items/top:inst-items/top:if-items/top:If-list/top:ifka-items/top:detectMult
 * Transformation Function: conv_oc_nx_detection_multiplier 
 */
  deviation /oc-bfd:bfd/oc-bfd:interfaces/oc-bfd:interface/oc-bfd:config/oc-bfd:detection-multiplier {
    deviate add {
        default "3";
    }
    deviate replace {
        type uint8 {
            range "1..50";
        }
    }
  }
}
