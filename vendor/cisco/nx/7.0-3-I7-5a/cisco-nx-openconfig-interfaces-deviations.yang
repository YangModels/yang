module cisco-nx-openconfig-interfaces-deviations {

  namespace "http://openconfig.net/yang/interfaces-deviations";

  prefix "oc-if-devs";

  import openconfig_interfaces { prefix oc-if; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-interfaces module 
     set for Cisco NXOS.
     Copyright (c) 2015-2016 by Cisco Systems, Inc.
     All rights reserved.";

  revision "2017-09-26" {
    description
      "Initial revision applicable to NXOS";
  }

  deviation oc-if:interfaces/oc-if:interface/oc-if:state/oc-if:type {
    deviate "not-supported";
  }
  deviation oc-if:interfaces/oc-if:interface/oc-if:state/oc-if:last-change {
    deviate "not-supported";
  }
  deviation oc-if:interfaces/oc-if:interface/oc-if:hold-time/oc-if:config/oc-if:down {
    deviate "not-supported"; 
  }
  deviation oc-if:interfaces/oc-if:interface/oc-if:hold-time/oc-if:state/oc-if:down {
    deviate "not-supported"; 
  }
  deviation oc-if:interfaces/oc-if:interface/oc-if:subinterfaces/oc-if:subinterface/oc-if:state/oc-if:last-change {
    deviate "not-supported";
  }
  deviation oc-if:interfaces/oc-if:interface/oc-if:subinterfaces/oc-if:subinterface/oc-if:state/oc-if:counters/oc-if:in-octets {
    deviate "not-supported"; 
  }
  deviation oc-if:interfaces/oc-if:interface/oc-if:subinterfaces/oc-if:subinterface/oc-if:state/oc-if:counters/oc-if:in-unicast-pkts {
    deviate "not-supported"; 
  }
  deviation oc-if:interfaces/oc-if:interface/oc-if:subinterfaces/oc-if:subinterface/oc-if:state/oc-if:counters/oc-if:in-broadcast-pkts {
    deviate "not-supported"; 
  }
  deviation oc-if:interfaces/oc-if:interface/oc-if:subinterfaces/oc-if:subinterface/oc-if:state/oc-if:counters/oc-if:in-multicast-pkts {
    deviate "not-supported"; 
  }
  deviation oc-if:interfaces/oc-if:interface/oc-if:subinterfaces/oc-if:subinterface/oc-if:state/oc-if:counters/oc-if:in-discards {
    deviate "not-supported"; 
  }
  deviation oc-if:interfaces/oc-if:interface/oc-if:subinterfaces/oc-if:subinterface/oc-if:state/oc-if:counters/oc-if:in-errors {
    deviate "not-supported"; 
  }
  deviation oc-if:interfaces/oc-if:interface/oc-if:subinterfaces/oc-if:subinterface/oc-if:state/oc-if:counters/oc-if:in-unknown-protos {
    deviate "not-supported"; 
  }
  deviation oc-if:interfaces/oc-if:interface/oc-if:subinterfaces/oc-if:subinterface/oc-if:state/oc-if:counters/oc-if:out-octets {
    deviate "not-supported"; 
  }
  deviation oc-if:interfaces/oc-if:interface/oc-if:subinterfaces/oc-if:subinterface/oc-if:state/oc-if:counters/oc-if:out-unicast-pkts {
    deviate "not-supported"; 
  }
  deviation oc-if:interfaces/oc-if:interface/oc-if:subinterfaces/oc-if:subinterface/oc-if:state/oc-if:counters/oc-if:out-broadcast-pkts {
    deviate "not-supported"; 
  }
  deviation oc-if:interfaces/oc-if:interface/oc-if:subinterfaces/oc-if:subinterface/oc-if:state/oc-if:counters/oc-if:out-multicast-pkts {
    deviate "not-supported"; 
  }
  deviation oc-if:interfaces/oc-if:interface/oc-if:subinterfaces/oc-if:subinterface/oc-if:state/oc-if:counters/oc-if:out-discards {
    deviate "not-supported"; 
  }
  deviation oc-if:interfaces/oc-if:interface/oc-if:subinterfaces/oc-if:subinterface/oc-if:state/oc-if:counters/oc-if:out-errors {
    deviate "not-supported"; 
  }
  deviation oc-if:interfaces/oc-if:interface/oc-if:subinterfaces/oc-if:subinterface/oc-if:state/oc-if:counters/oc-if:last-clear {
    deviate "not-supported"; 
  }

}
