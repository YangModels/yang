module cisco-nx-openconfig-vlan-deviations {

  namespace "http://openconfig.net/yang/vlan-deviations";

  prefix "oc-vlan-devs";

  import openconfig_vlan { prefix oc-vlan; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-vlan module 
     set for Cisco NXOS.
     Copyright (c) 2015-2016 by Cisco Systems, Inc.
     All rights reserved.";

  revision "2017-09-26" {
    description
      "Initial revision applicable to NXOS";
  }

  deviation oc-vlan:vlans/oc-vlan:vlan/oc-vlan:config/oc-vlan:tpid {
    deviate "not-supported"; 
  }
  deviation oc-vlan:vlans/oc-vlan:vlan/oc-vlan:state/oc-vlan:tpid {
    deviate "not-supported"; 
  }
  deviation oc-vlan:vlans/oc-vlan:vlan/oc-vlan:members/oc-vlan:member {
    deviate "not-supported";
  }
  deviation oc-vlan:vlans/oc-vlan:vlan/oc-vlan:members/oc-vlan:member/oc-if:interface-ref/oc-if:state/oc-if:interface {
    deviate "not-supported";
  }
  deviation oc-vlan:vlans/oc-vlan:vlan/oc-vlan:members/oc-vlan:member/oc-if:interface-ref/oc-if:state/oc-if:subinterface {
    deviate "not-supported"; 
  }
  deviation oc-vlan:/oc-if:interfaces/oc-if:interface/oc-if:subinterfaces/oc-if:subinterface/oc-vlan:vlan/oc-vlan:config/oc-vlan:vlan-id {
    deviate "not-supported";
  }
  deviation oc-vlan:/oc-if:interfaces/oc-if:interface/oc-if:subinterfaces/oc-if:subinterface/oc-vlan:vlan/oc-vlan:state/oc-vlan:vlan-id {
    deviate "not-supported";
  }

}
