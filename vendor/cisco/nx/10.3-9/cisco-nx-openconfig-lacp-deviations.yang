module cisco-nx-openconfig-lacp-deviations {

  namespace "http://openconfig.net/yang/lacp-deviations";

  prefix "oc-lacp-devs";

  import openconfig-lacp { prefix oc-lacp; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-lacp module 
     set for Cisco NXOS.
     Copyright (c) 2015-2017, 2020 by Cisco Systems, Inc.
     All rights reserved.";

  revision "2019-02-25" {
    description
      "Initial revision applicable to NXOS";
  }

  deviation /oc-lacp:lacp/oc-lacp:config/oc-lacp:system-priority {
    deviate add {
    default "32768";
    }
     deviate replace {
           type uint16 {
                range "1 .. 65535";
           }
     }
  }

  deviation /oc-lacp:lacp/oc-lacp:state/oc-lacp:system-priority {
    deviate add {
    default "32768";
    }
     deviate replace {
           type uint16 {
                range "1 .. 65535";
           }
     }
  }

  deviation /oc-lacp:lacp/oc-lacp:interfaces/oc-lacp:interface/oc-lacp:config/oc-lacp:system-id-mac {
    deviate "not-supported";
  }

  deviation /oc-lacp:lacp/oc-lacp:interfaces/oc-lacp:interface/oc-lacp:config/oc-lacp:system-priority {
    deviate "not-supported";
  }

  deviation /oc-lacp:lacp/oc-lacp:interfaces/oc-lacp:interface/oc-lacp:state/oc-lacp:system-id-mac {
    deviate "not-supported";
  }

  deviation /oc-lacp:lacp/oc-lacp:interfaces/oc-lacp:interface/oc-lacp:state/oc-lacp:system-priority {
    deviate "not-supported";
  }
  
  deviation /oc-lacp:lacp/oc-lacp:interfaces/oc-lacp:interface/oc-lacp:members/oc-lacp:member/oc-lacp:state/oc-lacp:system-id {
    deviate "not-supported";
  }

}
