module cisco-nx-openconfig-lldp-deviations {

  namespace "http://openconfig.net/yang/lldp-deviations";

  prefix "oc-lldp-devs";

  import openconfig-lldp { prefix oc-lldp; }
  import openconfig-lldp-types { prefix oc-lldp-types; }

  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-lldp module 
     set for Cisco NXOS.
     Copyright (c) 2015-2017 by Cisco Systems, Inc.
     All rights reserved.";

  revision "2020-05-05" {
    description
      "Initial revision applicable to NXOS";
  }

  deviation /oc-lldp:lldp/oc-lldp:config/oc-lldp:system-name {
    deviate "not-supported"; 
  }
  deviation /oc-lldp:lldp/oc-lldp:config/oc-lldp:system-description {
    deviate "not-supported"; 
  }
  deviation /oc-lldp:lldp/oc-lldp:config/oc-lldp:chassis-id {
    deviate "not-supported"; 
  }
  deviation /oc-lldp:lldp/oc-lldp:config/oc-lldp:chassis-id-type {
    deviate "not-supported"; 
  }
  deviation /oc-lldp:lldp/oc-lldp:state/oc-lldp:system-name {
    deviate "not-supported"; 
  }
  deviation /oc-lldp:lldp/oc-lldp:state/oc-lldp:system-description {
    deviate "not-supported"; 
  }
  deviation /oc-lldp:lldp/oc-lldp:state/oc-lldp:chassis-id {
    deviate "not-supported"; 
  }
  deviation /oc-lldp:lldp/oc-lldp:state/oc-lldp:chassis-id-type {
    deviate "not-supported"; 
  }
  deviation /oc-lldp:lldp/oc-lldp:state/oc-lldp:counters/oc-lldp:tlv-discard {
    deviate "not-supported"; 
  }
  deviation /oc-lldp:lldp/oc-lldp:state/oc-lldp:counters/oc-lldp:last-clear {
    deviate "not-supported"; 
  }
  deviation /oc-lldp:lldp/oc-lldp:state/oc-lldp:counters/oc-lldp:tlv-accepted {
    deviate "not-supported"; 
  }
  deviation /oc-lldp:lldp/oc-lldp:interfaces/oc-lldp:interface/oc-lldp:state/oc-lldp:counters/oc-lldp:tlv-discard {
    deviate "not-supported"; 
  }
  deviation /oc-lldp:lldp/oc-lldp:interfaces/oc-lldp:interface/oc-lldp:state/oc-lldp:counters/oc-lldp:last-clear {
    deviate "not-supported"; 
  }
  deviation /oc-lldp:lldp/oc-lldp:interfaces/oc-lldp:interface/oc-lldp:state/oc-lldp:counters/oc-lldp:frame-error-out {
    deviate "not-supported"; 
  }
  deviation /oc-lldp:lldp/oc-lldp:interfaces/oc-lldp:interface/oc-lldp:neighbors/oc-lldp:neighbor/oc-lldp:state/oc-lldp:age {
    deviate "not-supported"; 
  }
  deviation /oc-lldp:lldp/oc-lldp:interfaces/oc-lldp:interface/oc-lldp:neighbors/oc-lldp:neighbor/oc-lldp:state/oc-lldp:last-update {
    deviate "not-supported"; 
  }
  deviation /oc-lldp:lldp/oc-lldp:interfaces/oc-lldp:interface/oc-lldp:neighbors/oc-lldp:neighbor/oc-lldp:state/oc-lldp:ttl {
    deviate "not-supported"; 
  }
  deviation /oc-lldp:lldp/oc-lldp:interfaces/oc-lldp:interface/oc-lldp:neighbors/oc-lldp:neighbor/oc-lldp:state/oc-lldp:management-address-type {
    deviate "not-supported"; 
  }
  deviation /oc-lldp:lldp/oc-lldp:interfaces/oc-lldp:interface/oc-lldp:neighbors/oc-lldp:neighbor/oc-lldp:custom-tlvs/oc-lldp:tlv {
    deviate "not-supported"; 
  }

/* Mapped to device model
 *     Device Model Target: /top:System/top:fm-items/top:lldp-items/top:adminSt
 * Transformation Function: openconfig_lldp_config_enabled
 */
  deviation /oc-lldp:lldp/oc-lldp:config/oc-lldp:enabled {
    deviate replace {
    default "false";
    }   
  }


/* Mapped to device model
 *     Device Model Target: /top:System/top:lldp-items/top:inst-items/top:txFreq
 * Transformation Function: openconfig_lldp_hello_timer 
 */
  deviation /oc-lldp:lldp/oc-lldp:config/oc-lldp:hello-timer {
    deviate add {
    default "30";
    }   
     deviate replace {
           type uint64 {
                range "1 .. 254";
           }
     }   
    
  }

/* Mapped to device model
 *     Device Model Target: /top:System/top:lldp-items/top:inst-items/top:optTlvSel
 * Transformation Function: openconfig_lldp_suppress_advertisement
 */
  deviation /oc-lldp:lldp/oc-lldp:config/oc-lldp:suppress-tlv-advertisement {
    deviate add {
    must "../oc-lldp:suppress-tlv-advertisement='oc-lldp-types:SYSTEM_NAME' or ../oc-lldp:suppress-tlv-advertisement='oc-lldp-types:SYSTEM_DESCRIPTION' or ../oc-lldp:suppress-tlv-advertisement='oc-lldp-types:SYSTEM_CAPABILITIES' or ../oc-lldp:suppress-tlv-advertisement='oc-lldp-types:PORT_DESCRIPTION' or ../oc-lldp:suppress-tlv-advertisement='oc-lldp-types:MANAGEMENT_ADDRESS'" {
        error-message "Only supports SYSTEM_NAME, SYSTEM_DESCRIPTION, SYSTEM_CAPABILITIES, PORT_DESCRIPTION, MANAGEMENT_ADDRESS on device model";
    }

    }
  }


/* Mapped to device model
 *     Device Model Target: /top:System/top:fm-items/top:lldp-items/top:adminSt
 * Transformation Function: openconfig_lldp_state_enabled 
 */
  deviation /oc-lldp:lldp/oc-lldp:state/oc-lldp:enabled {
    deviate replace {
    default "false";
    }
  }

/* Mapped to device model
 *     Device Model Target: /top:System/top:lldp-items/top:inst-items/top:txFreq
 * Transformation Function: openconfig_lldp_state_hello_timer 
 */
  deviation /oc-lldp:lldp/oc-lldp:state/oc-lldp:hello-timer {
    deviate add {
    default "30";
    }
     deviate replace {
           type uint64 {
                range "1 .. 254";
           }
     }   
  }

/* Mapped to device model
 *     Device Model Target: /top:System/top:lldp-items/top:inst-items/top:optTlvSel
 * Transformation Function: openconfig_lldp_state_suppress_advertisement 
 */
  deviation /oc-lldp:lldp/oc-lldp:state/oc-lldp:suppress-tlv-advertisement {
    deviate add {
    must "../oc-lldp:suppress-tlv-advertisement='oc-lldp-types:SYSTEM_NAME' or ../oc-lldp:suppress-tlv-advertisement='oc-lldp-types:SYSTEM_DESCRIPTION' or ../oc-lldp:suppress-tlv-advertisement='oc-lldp-types:SYSTEM_CAPABILITIES' or ../oc-lldp:suppress-tlv-advertisement='oc-lldp-types:PORT_DESCRIPTION' or ../oc-lldp:suppress-tlv-advertisement='oc-lldp-types:MANAGEMENT_ADDRESS'" {
        error-message "Only supports SYSTEM_NAME, SYSTEM_DESCRIPTION, SYSTEM_CAPABILITIES, PORT_DESCRIPTION, MANAGEMENT_ADDRESS on device model";
    }

    }   
 
  }


/* Mapped to device model
 *     Device Model Target: /top:System/top:lldp-items/top:inst-items/top:if-items/top:If-list/top:adj-items/top:AdjEp-list/top:capability
 * Transformation Function: openconfig_lldp_interface_neighbor_capability_name 
 */
  deviation /oc-lldp:lldp/oc-lldp:interfaces/oc-lldp:interface/oc-lldp:neighbors/oc-lldp:neighbor/oc-lldp:capabilities/oc-lldp:capability/oc-lldp:name {
    deviate add {
    must "../oc-lldp:name='oc-lldp-types:OTHER' or ../oc-lldp:name='oc-lldp-types:REPEATER' or ../oc-lldp:name='oc-lldp-types:MAC_BRIDGE' or ../oc-lldp:name='oc-lldp-types:WLAN_ACCESS_POINT' or ../oc-lldp:name='oc-lldp-types:ROUTER' or ../oc-lldp:name='oc-lldp-types:TELEPHONE' or ../oc-lldp:name='oc-lldp-types:DOCSIS_CABLE_DEVICE' or ../oc-lldp:name='oc-lldp-types:STATION_ONLY'" {
        error-message "Only supports OTHER,REPEATER,MAC_BRIDGE,WLAN_ACCESS_POINT,ROUTER,TELEPHONE,DOCSIS_CABLE_DEVICE,STATION_ONLY on device model"; 
    }
    }
  }

/* Mapped to device model
 *     Device Model Target: /top:System/top:lldp-items/top:inst-items/top:if-items/top:If-list/top:adj-items/top:AdjEp-list/top:capability
 * Transformation Function: openconfig_lldp_interface_neighbor_capability_state_name 
 */
  deviation /oc-lldp:lldp/oc-lldp:interfaces/oc-lldp:interface/oc-lldp:neighbors/oc-lldp:neighbor/oc-lldp:capabilities/oc-lldp:capability/oc-lldp:state/oc-lldp:name {
    deviate add {
    must "../oc-lldp:name='oc-lldp-types:OTHER' or ../oc-lldp:name='oc-lldp-types:REPEATER' or ../oc-lldp:name='oc-lldp-types:MAC_BRIDGE' or ../oc-lldp:name='oc-lldp-types:WLAN_ACCESS_POINT' or ../oc-lldp:name='oc-lldp-types:ROUTER' or ../oc-lldp:name='oc-lldp-types:TELEPHONE' or ../oc-lldp:name='oc-lldp-types:DOCSIS_CABLE_DEVICE' or ../oc-lldp:name='oc-lldp-types:STATION_ONLY'" {
        error-message "Only supports OTHER,REPEATER,MAC_BRIDGE,WLAN_ACCESS_POINT,ROUTER,TELEPHONE,DOCSIS_CABLE_DEVICE,STATION_ONLY on device model";
    }
    }
  }

  deviation /oc-lldp:lldp/oc-lldp:interfaces/oc-lldp:interface/oc-lldp:neighbors/oc-lldp:neighbor/oc-lldp:config {
      deviate "not-supported"; 
  }

}
