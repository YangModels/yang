module cisco-nx-openconfig-ospf-policy-deviations {

  namespace "http://openconfig.net/yang/ospf-policy-deviations";

  prefix "oc-ospf-pol-devs";

  import openconfig-ospf-policy { prefix oc-ospf-pol; }
  import openconfig-routing-policy { prefix oc-rpol; }
  organization "Cisco Systems, Inc.";

  contact
    "Cisco Systems, Inc.
     Customer Service
     Postal: 170 West Tasman Drive
     San Jose, CA 95134
     Tel: +1 800 553-NETS
     E-mail: cs-yang@cisco.com";

  description 
    "This module contains a set of deviations of the openconfig-ospf-policy module 
     set for Cisco NXOS.
     Copyright (c) 2015-2017, 2020 by Cisco Systems, Inc.
     All rights reserved.";

  revision "2018-05-18" {
    description
      "Initial revision applicable to NXOS";
  }

  deviation /oc-rpol:routing-policy/oc-rpol:policy-definitions/oc-rpol:policy-definition/oc-rpol:statements/oc-rpol:statement/oc-rpol:conditions/oc-ospf-pol:ospf-conditions/oc-ospf-pol:config/oc-ospf-pol:area-eq {
    deviate replace {
        type uint32;
    }
  }
  deviation /oc-rpol:routing-policy/oc-rpol:policy-definitions/oc-rpol:policy-definition/oc-rpol:statements/oc-rpol:statement/oc-rpol:conditions/oc-ospf-pol:ospf-conditions/oc-ospf-pol:state/oc-ospf-pol:area-eq {
    deviate replace {
        type uint32;
    }
  }
  deviation /oc-rpol:routing-policy/oc-rpol:policy-definitions/oc-rpol:policy-definition/oc-rpol:statements/oc-rpol:statement/oc-rpol:actions/oc-ospf-pol:ospf-actions/oc-ospf-pol:config/oc-ospf-pol:set-area {
    deviate "not-supported"; 
  }
  deviation /oc-rpol:routing-policy/oc-rpol:policy-definitions/oc-rpol:policy-definition/oc-rpol:statements/oc-rpol:statement/oc-rpol:actions/oc-ospf-pol:ospf-actions/oc-ospf-pol:state/oc-ospf-pol:set-area {
    deviate "not-supported"; 
  }
}
