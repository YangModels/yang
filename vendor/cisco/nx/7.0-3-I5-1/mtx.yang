module mtx {
    yang-version 1;
    namespace "http://www.cisco.com/yang/nxos-dev/";
    prefix mtx;
    organization "Cisco Systems, Inc.";
    contact " Cisco Systems, Inc., Customer Service, Postal: 170 W Tasman Drive, San Jose, CA 95134, Tel: +1 1800 553-NETS, e-mail: nxos-dev-yang@cisco.com";
    description "This module contains the MTX extension definitions";
    reference "60bdf8d38f970733c957ce4bfa80127192a82ba6";
    revision 2016-10-29 {
        description "Initial Revision";
    }
    extension mo-obj-dn {
        argument "Dn";
        description "The mo-obj-dn statement takes as an argument (Dn) that describes the DME Managed Object Distinguished Name (Dn).";
    }
    extension mo-obj-dn-local {
        argument "LocalDn";
        description "The mo-obj-dn-local statement takes as an argument (LocalDn) that describes the local DME Managed Object Distinguished Name (Dn) relative to the containing object.";
    }
    extension mo-prop-name {
        argument "PropName";
        description "The mo-prop-name statement takes as an argument (PropName) that describes the DME Managed Object property name.";
    }
    extension mo-rest-name {
        argument "RestName";
        description "The mo-rest-name statement takes as an argument (RestName) that describes the DME object Name Pkg+MO used by the Rest Interface.";
    }
    extension mo-ref {
        argument "Ref";
        description "The mo-ref statement takes as an argument (Ref) that describes a reference to the source model";
    }
    extension circular-inst {
        argument "grp";
        description "The circular-inst statement takes as an argument that is the grouping to be circularly included as a singleton instance";
    }
    extension circular-list {
        argument "grp";
        description "The circular-list statement takes as an argument that is the grouping to be circularly included as a list - requires mtx:circular-list-key extention within { & }";
    }
    extension circular-list-key {
        argument "key";
        description "The circular-list statement takes as an argument that is the key for the containing circular-list";
    }
    extension compound-key {
        argument "key-template";
        description "The compound-key statement takes as an argument a string contining a key-template for constructing DME-specific compound keys";
    }
    extension require-dme-escape {
        argument "dme-type";
        description "The require-dme-escape statement takes as an argument a string that determines if the input/output value of the MO property must be escaped with brackets in the DME";
    }
    extension rel-def-dn-key {
        argument "convert-dn";
        description "The rel-def-dn-key statement takes as an argument a string that determines if the input/output value of the DN field must be converted to a YANG path";
    }
    extension is-applied-config {
        argument "applied-config";
        description "The is-applied-config statement takes as an argument a string that determines if this property value is an applied config";
    }
}
