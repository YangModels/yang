module cisco-svo-common-otdr-oper-grp {

    yang-version 1.1;
    namespace "http://cisco.com/yang/svo/common-otdr-oper-grp";
    prefix "ccoog";


    organization
        "Cisco Systems, Inc.";

    contact
        "Cisco Systems, Inc. Customer Service Postal: 170 West Tasman
        Drive San Jose, CA 95134 Tel: +1 800 553-NETS E-mail: cs-yang@cisco.com";

    description " CISCO Common Otdr Operational Data
        yang models.";

    revision 2020-12-04 { 
       description "Model version for SVO Release 12.1.0 "; 
       reference cisco-svo-common-otdr-oper-grp.yang; 
    }
 

    typedef Upload-status {
        type enumeration {
            enum not-executed {
                value 0;
                description "upload not executed";
            }
            enum done {
                value 1;
                description "upload done";
            }
            enum failed {
                value 2;
                description "upload failed";
            }
        }
    }
    

    typedef Otdr-status {
        type enumeration {
            enum status-unknown {
                value 0;
                description "Unknown";
            }
            enum status-ok {
                value 1;
                description "Ok";
            }
            enum status-progress {
                value 2;
                description "Progress";
            }
            enum status-failure {
                value 3;
                description "Failure";
            }
            enum status-terminated {
                value 4;
                description "Terminated";
            }
            enum status-not-executed {
                value 5;
                description "Not executed";
            }
            enum status-idle {
                value 6;
                description "Idle";
            }
            enum status-trained {
                value 7;
                description "training ok";
            }

        }
        description "Otdr status";
    }

    typedef Otdr-scan-mode {
        type enumeration {
            enum otdr-scan-auto {
                value 0;
                description "Auto";
            }
        }
        description "Otdr scan mode; to be extended with new modes";
    }

    typedef Direction {
        type enumeration {
            enum "direction-tx" {
                description "Tx";
            }
            enum "direction-rx" {
                description "Rx";
            }
        }
        description "Direction";
    }

    typedef Ots-otdr-data {
        type enumeration {
            enum scan {
                value 1;
                description "Display the list of saved measurements";
            }
            enum base-line {
                value 2;
                description "Display the list of saved baseline";
            }
        }
        description "Ots otdr data";
    }

    typedef Ots-otdr-data-type-details {
        type enumeration {
            enum scan-details {
                value 1;
                description "Displays Scan Details";
            }
            enum base-line-details {
                value 2;
                description "Displays Baseline Details";
            }
        }
        description "Ots otdr data type details";
    }


    grouping HWMOD-OTDR-STATUS-B {
        description "HWMOD OTDR STATUS B";

        leaf direction {
            type Direction;
            config false;
            description "Direction";
        }
        leaf otdr-training-status {
            type Otdr-status;
            config false;
            description "Training Status";
        }
        leaf orl-training-status {
            type Otdr-status;
            config false;
            description "Training Status";
        }
        leaf measurement-status {
            type Otdr-status;
            config false;
            description "Measurement Status";
        }
        leaf progress-pc {
            type uint32;
            config false;
            description "Progress %";
        }
        leaf specific-problem {
            type string;
            config false;
            description "Reason of failure";
        }

        leaf high-reflection-location {
            type decimal64 {
              fraction-digits 4;
            }
            default 0.0;
            description "High Reflection Location in Km";
        }

    }

    grouping HWMOD-OTDR-SCAN-LIST-B {
        description "HWMOD OTDR SCAN LIST B";

        leaf sor-file-id {
             type uint32;
             description "sor file identifier";
        }

        leaf sor-file {
            type string {
                length "0..64";
            }
            description "Sor File Name";
        }
        leaf direction {
            type Direction;
            description "Direction";
        }
        leaf timestamp {
            type string;
            description "Timestamp";
        }
        leaf fiber-end {
            type decimal64 {
              fraction-digits 4;
            }
            description "Fiber end in Km";
        }

        leaf orl {
            type decimal64 {
              fraction-digits 2;
            }
            description "Total Orl in dB";
        }
    }

    grouping otdr-oper {
        description "Otdr Root Info";

        leaf sor-file-upload-status {
            config false;
            type Upload-status;
            description "Status of sor file upload"; 
            default not-executed;
        }

        list data-type {
            config false;
            key "otdr-data-type";
            description "Dispaly data type list";
            
            leaf otdr-data-type {
                type Ots-otdr-data;
                description
                                "Details associated with a particular Data type";
            }

            list otdr-scan {
                config false;
                key "sor-file-id";
                description "otdr scan";
                uses HWMOD-OTDR-SCAN-LIST-B;
            }
        }
        list otdr-status {
            config false;
            key "direction";
            description "otdr status";
            uses HWMOD-OTDR-STATUS-B;
        }
    }
}
