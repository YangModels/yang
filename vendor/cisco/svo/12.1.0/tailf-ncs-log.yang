submodule tailf-ncs-log {
  yang-version 1.1;
  belongs-to tailf-ncs {
    prefix ncs;
  }

  import ietf-yang-types {
    prefix yang;
  }

  import tailf-common {
    prefix tailf;
  }

  organization "Tail-f Systems";

  description
    "This module contains a collection of YANG definitions for
     configuring log data in NCS.

     Copyright 2019 Cisco Systems, Inc.
     All rights reserved.
     Permission is hereby granted to redistribute this file without
     modification.";

  revision 2019-04-09 {
    description
      "Released as part of NCS-5.1.

       Removed leaf 'result' from purge action.";
  }

  revision 2016-11-24 {
    description
      "Released as part of NCS-4.3.

       Initial revision.";
  }

  /*
   * Log entry levels
   */

  typedef log-entry-level-t {
    type enumeration {
      enum all {
        tailf:code-name log-entry-level-all;
        value 1;
      }
      enum trace {
        tailf:code-name log-entry-level-trace;
        value 2;
      }
      enum debug {
        tailf:code-name log-entry-level-debug;
        value 3;
      }
      enum info {
        tailf:code-name log-entry-level-info;
        value 4;
      }
      enum warn {
        tailf:code-name log-entry-level-warn;
        value 5;
      }
      enum error {
        tailf:code-name log-entry-level-error;
        value 6;
      }
    }
    description
      "Levels used for identifying the severity of an event.
       Levels are organized from least specific to most where
       'all' is least specific and 'error' is most specific.";
  }

  /*
   * Log entry identities
   */

  typedef log-entry-t {
    description
      "This leaf identifies the specific log entry.";
    type identityref {
      base log-entry;
    }
  }

  identity log-entry {
    description
      "This is a base type from which all log entries can be derived.

       All code that adds log-entries must always provide their own
       identity, derived from this one.";
  }

  identity service-modified {
    description
      "When a service is modified, we log with this log entry type";
    base log-entry;
  }

  identity device-modified {
    description
      "When a device is modified and has a service backpointer,
       we log with this log entry type";
    base log-entry;
  }

  /*
   * Groupings
   */

  grouping log-data {
    description
      "NCS or user specific code may choose to populate a log entry
       to indicate important events associated with it.";
    container log {
      config false;
      tailf:cdb-oper {
        tailf:persistent true;
      }

      tailf:action purge {
        tailf:info "Remove log entries";
        tailf:actionpoint ncsinternal {
          tailf:internal;
        }
        description
          "This action requests to delete log entries from the log-entry
           list according to the supplied criteria.";
        input {
          uses filter-input;
        }
        output {
          leaf purged-log-entries {
            type uint16;
          }
        }
      }

      list log-entry {
        key when;
        leaf when {
          type yang:date-and-time;
        }
        leaf type {
          description
            "What type of log entry is this.";
          type log-entry-t;
          mandatory true;
        }
        leaf level {
          description
            "What level this log entry has.";
          type log-entry-level-t;
          mandatory true;
        }
        leaf message {
          type string;
        }
      }
    }
  }

  grouping filter-input {
    leaf type {
      type log-entry-t;
    }
    leaf level {
      type log-entry-level-t;
    }
    container older-than {
      presence "Age specification";
      description
        "Matches the 'when' leaf in the log entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }
}
