module cisco-svo-xconnect {
    yang-version 1.1;
    namespace "http://cisco.com/yang/svo/xconnect";
    prefix svo-xconn;

    import tailf-common { prefix tailf; }
    import cisco-svo-xconnect-grp { prefix csxcg; }
    import tailf-ncs { prefix ncs; }
    
    organization
        "Cisco Systems, Inc.";

    contact
        "Cisco Systems, Inc.
       Customer Service
       
       Postal: 170 West Tasman Drive
       San Jose, CA 95134
       
       Tel: +1 800 553-NETS
       
       E-mail: cs-yang@cisco.com";

    description
        "YANG definition for SVO optical cross connections";

    revision 2020-12-04 { 
       description "Model version for SVO Release 12.1.0 "; 
       reference cisco-svo-xconnect.yang; 
    }


    augment /ncs:services {
    	description "Optical XConnect service augment";
    	
    	list oxc-alarmable-object {
    		tailf:hidden full;
    		key "object-index object-device";
    		config false;
    		description "Internal map of alarmable objects - used to map low level alarm to high level object";
    		
    		leaf object-index {
                type uint32;
                description "NCS2K och-term interface index";
    		}
    		
    		leaf object-device {
    			type string; 
    			description "Device to which the object belong";
    		}
    		
    		leaf parent-oxc-name {
    			type string;
    			config false;
    			description "Name of the parent Crossonnection";
    		}
    		
    		leaf object-xpath {
    			type string;
    			config false;
    			description "Xpath of the high level alarmable object";
    		}
    	}
    	
        list oxc {
			key "connection-name";
            description "cross connection list";

            uses ncs:service-data;
            ncs:servicepoint "Oxc-servicepoint";

            uses csxcg:oxc-grp {
                refine path1/internal-path/monitoring/optical-power {
                    tailf:callpoint oxc-hl-live-data;
                }
                refine path2/internal-path/monitoring/optical-power {
                    tailf:callpoint oxc-hl-live-data;
                }                
            }

            tailf:validate oxc_validator {
                tailf:dependency ".";
            }
        }
        tailf:action oxc-sync-from-devices {
            tailf:info "Perform OXC sync-from from devices";
            tailf:actionpoint syncfromdevices;
        }
    }
}
