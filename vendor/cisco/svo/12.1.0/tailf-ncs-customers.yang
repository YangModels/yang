submodule tailf-ncs-customers {
  yang-version 1.1;
  belongs-to tailf-ncs {
    prefix ncs;
  }

  import tailf-common {
    prefix tailf;
  }

  organization "Tail-f Systems";

  description
    "This submodule contains a collection of YANG definitions
     for configuring customers.

     Copyright 2019 Cisco Systems, Inc.
     All rights reserved.
     Permission is hereby granted to redistribute this file without
     modification.";

  revision 2012-08-30 {
    description
      "Released as part of NCS-2.0.";
  }

  container customers {
    tailf:info "Customers using services";
    list customer {
      tailf:info "Show customers";
      key id;
      reference "TMForumPhaseVIII::SID Phase VIII::Customer Domain";

      leaf id {
        tailf:info "Unique customer id";
        type string;
        reference "Customer ABE::id";
      }
      leaf rank {
        tailf:info "Customer rank";
        type uint8;
        reference "Customer ABE::rank";
      }
      leaf status {
        tailf:info "Customer status";
        type enumeration {
          enum active;
          enum inactive;
          enum prospective;
        }
        reference "Customer ABE::status";
      }
      leaf-list customer-service {
        tailf:info "Customer facing services";
        type string;
        config false;
        description
          "A list of references to /services/customer-service.";
        tailf:callpoint ncs {
          tailf:internal;
        }
      }
      container properties {
        tailf:info "Specific customer properties";
        description
        "This container can be augmented with specific customer
         properties.";
      }
    }
  }

}
