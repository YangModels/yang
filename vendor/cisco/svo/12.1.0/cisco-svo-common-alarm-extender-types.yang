module cisco-svo-common-alarm-extender-types {
  yang-version 1.1;
  namespace "http://cisco.com/yang/svo/common-alarm-extender-types";
  prefix alext-types;

  organization 
    "Cisco Systems, Inc.";

  contact 
    "Cisco Systems, Inc.
     Customer Service
     
     Postal: 170 West Tasman Drive
     San Jose, CA 95134
     
     Tel: +1 800 553-NETS
     
     E-mail: cs-yang@cisco.com";

  description "
    CISCO Common Types for dry contacts alarms";

    revision 2020-12-04 { 
       description "Model version for SVO Release 12.1.0 "; 
       reference cisco-svo-common-alarm-extender-types.yang; 
    }
 
  
  typedef alarm-type {
    type enumeration {
      enum "ENV_ALM_NORMAL" {
        description "External";
      }
      enum "ENV_ALM_AIRCOMPR" {
        description "Compressor Failure";
      }
      enum "ENV_ALM_AIRCOND" {
        description "Air Cond Fail";
      }
      enum "ENV_ALM_AIRDRYR" {
        description "Air Dryer Fail";
      }
      enum "ENV_ALM_BATDSCHRG" {
        description "Battery Discharge";
      }
      enum "ENV_ALM_BATTERY" {
        description "Battery Fail";
      }
      enum "ENV_ALM_CLFAN" {
        description "Cool Fan Fail";
      }
      enum "ENV_ALM_CPMAJOR" {
        description "Ctrl PwrMaj fail";
      }
      enum "ENV_ALM_CPMINOR" {
        description "Ctrl PwrMin fail";
      }
      enum "ENV_ALM_ENGINE" {
        description "Engine fail";
      }
      enum "ENV_ALM_ENGOPRG" {
        description "Engine Operating";
      }
      enum "ENV_ALM_EXPLGS" {
        description "Explosive Gas";
      }
      enum "ENV_ALM_FIRDETR" {
        description "Fire Detector fail";
      }
      enum "ENV_ALM_FIRE" {
        description "Fire";
      }
      enum "ENV_ALM_FLOOD" {
        description "Flood";
      }
      enum "ENV_ALM_FUSE" {
        description "Fuse fail";
      }
      enum "ENV_ALM_GEN" {
        description "Generator Fail";
      }
      enum "ENV_ALM_HIAIR" {
        description "High airflow";
      }
      enum "ENV_ALM_HIHUM" {
        description "High Humidity";
      }
      enum "ENV_ALM_HITEMP" {
        description "High Temp";
      }
      enum "ENV_ALM_HIWTR" {
        description "High water";
      }
      enum "ENV_ALM_INTRUDER" {
        description "Intrusion";
      }
      enum "ENV_ALM_LWBATVG" {
        description "Low Batt";
      }
      enum "ENV_ALM_LWFUEL" {
        description "Low fuel";
      }
      enum "ENV_ALM_LWHUM" {
        description "Low Humidity";
      }
      enum "ENV_ALM_LWPRES" {
        description "Low Cable Press";
      }
      enum "ENV_ALM_LWTEMP" {
        description "Low Temp";
      }
      enum "ENV_ALM_LWWTR" {
        description "Low Water";
      }
      enum "ENV_ALM_MISC" {
        description "Misc";
      }
      enum "ENV_ALM_OPENDR" {
        description "Open Door";
      }
      enum "ENV_ALM_POWER" {
        description "Comm. Pwr Fail";
      }
      enum "ENV_ALM_PUMP" {
        description "Pump Fail";
      }
      enum "ENV_ALM_PWR48" {
        description "48 Power supp fail";
      }
      enum "ENV_ALM_RECT" {
        description "Rectifier fail";
      }
      enum "ENV_ALM_RECTHI" {
        description "Rectifier high volt";
      }
      enum "ENV_ALM_RECTLO" {
        description "Rectifier low volt";
      }
      enum "ENV_ALM_SMOKE" {
        description "Smoke";
      }
      enum "ENV_ALM_TOXICGAS" {
        description "Toxic Gas";
      }
      enum "ENV_ALM_VENT" {
        description "Ventilation fail";
      }
      enum "ENV_ALM_ENGTRANS" {
        description "Standby engine transfer";
      }
      enum "ENV_ALM_FUELLEAK" {
        description "Fuel leak";
      }
      enum "ENV_ALM_GASALARM" {
        description "Explosive gas";
      }
      enum "ENV_ALM_HATCH" {
        description "CEV hatch fail";
      }
      enum "ENV_ALM_LEVELCON" {
        description "Level converter";
      }
      enum "ENV_ALM_LVDADSL" {
        description "Secondary ADSL low voltage disconnect";
      }
      enum "ENV_ALM_LVDBYPAS" {
        description "Low voltage disconnect bypass";
      }
      enum "ENV_ALM_PWR_139" {
        description "-139V power converter";
      }
      enum "ENV_ALM_PWR_190" {
        description "-190V power converter";
      }
      enum "ENV_ALM_PWRMJ" {
        description "Power supply major";
      }
      enum "ENV_ALM_PWRMN" {
        description "Power supply minor";
      }
      enum "ENV_ALM_RINGGENMJ" {
        description "Ringing generator major";
      }
      enum "ENV_ALM_RINGGENMN" {
        description "Ringing generator minor";
      }
      enum "ENV_ALM_RTACADSL" {
        description "AC or AC/rectifier power fail DCL equipment critical site";
      }
      enum "ENV_ALM_RTACCRIT" {
        description "AC or AC/rectifier power fail DCL equipment";
      }
      enum "ENV_ALM_RTACPWR" {
        description "Commercial AC fail, site equipped with standby engine";
      }
      enum "ENV_ALM_RTACPWRENG" {
        description "AC power loss distributed power RT bay";
      }
      enum "ENV_ALM_RTBAYPWR" {
        description "Retrieve standby engine, commercial AC restored";
      }
      enum "ENV_ALM_RTRVENG" {
        description "Retrieve standby engine, commercial AC";
      }
      enum "ENV_ALM_TEMP" {
        description "temp";
      }
      enum "ENV_ALM_TREPEATER" {
        description "TREPEATER T-repeater shelf";
      }
      enum "ENV_ALM_USERDEFINED1" {
        description "Not Available";
      }
      enum "ENV_ALM_USERDEFINED2" {
        description "Not Available";
      }
      enum "ENV_ALM_USERDEFINED3" {
        description "Not Available";
      }
      enum "ENV_ALM_USERDEFINED4" {
        description "Not Available";
      }
      enum "ENV_ALM_USERDEFINED5" {
        description "Not Available";
      }
      enum "ENV_ALM_USERDEFINED6" {
        description "Not Available";
      }
      enum "ENV_ALM_USERDEFINED7" {
        description "Not Available";
      }
      enum "ENV_ALM_USERDEFINED8" {
        description "Not Available";
      }
      enum "ENV_ALM_USERDEFINED9" {
        description "Not Available";
      }
      enum "ENV_ALM_USERDEFINED10" {
        description "Not Available";
      }
      enum "ENV_ALM_USERDEFINED11" {
        description "Not Available";
      }
      enum "ENV_ALM_USERDEFINED12" {
        description "Not Available";
      }
      enum "ENV_ALM_USERDEFINED13" {
        description "Not Available";
      }
      enum "ENV_ALM_USERDEFINED14" {
        description "Not Available";
      }
      enum "ENV_ALM_USERDEFINED15" {
        description "Not Available";
      }
      enum "ENV_ALM_USERDEFINED16" {
        description "Not Available";
      }
      enum "ENV_ALM_USERDEFINED17" {
        description "Not Available";
      }
      enum "ENV_ALM_USERDEFINED18" {
        description "Not Available";
      }
      enum "ENV_ALM_USERDEFINED19" {
        description "Not Available";
      }
      enum "ENV_ALM_USERDEFINED20" {
        description "Not Available";
      }
      enum "ENV_ALM_USERDEFINED21" {
        description "Not Available";
      }
      enum "ENV_ALM_USERDEFINED22" {
        description "Not Available";
      }
      enum "ENV_ALM_USERDEFINED23" {
        description "Not Available";
      }
      enum "ENV_ALM_USERDEFINED24" {
        description "Not Available";
      }
      enum "ENV_ALM_USERDEFINED25" {
        description "Not Available";
      }
      enum "ENV_ALM_USERDEFINED26" {
        description "Not Available";
      }
      enum "ENV_ALM_USERDEFINED27" {
        description "Not Available";
      }
      enum "ENV_ALM_USERDEFINED28" {
        description "Not Available";
      }
      enum "ENV_ALM_USERDEFINED29" {
        description "Not Available";
      }
      enum "ENV_ALM_USERDEFINED30" {
        description "Not Available";
      }
      enum "ENV_ALM_USERDEFINED31" {
        description "Not Available";
      }
      enum "ENV_ALM_USERDEFINED32" {
        description "Not Available";
      }
      enum "ENV_ALM_USERDEFINED33" {
        description "Not Available";
      }
      enum "ENV_ALM_USERDEFINED34" {
        description "Not Available";
      }
      enum "ENV_ALM_USERDEFINED35" {
        description "Not Available";
      }
      enum "ENV_ALM_USERDEFINED36" {
        description "Not Available";
      }
      enum "ENV_ALM_USERDEFINED37" {
        description "Not Available";
      }
      enum "ENV_ALM_USERDEFINED38" {
        description "Not Available";
      }
      enum "ENV_ALM_USERDEFINED39" {
        description "Not Available";
      }
      enum "ENV_ALM_USERDEFINED40" {
        description "Not Available";
      }
      enum "ENV_ALM_USERDEFINED41" {
        description "Not Available";
      }
      enum "ENV_ALM_USERDEFINED42" {
        description "Not Available";
      }
      enum "ENV_ALM_USERDEFINED43" {
        description "Not Available";
      }
      enum "ENV_ALM_USERDEFINED44" {
        description "Not Available";
      }
      enum "ENV_ALM_USERDEFINED45" {
        description "Not Available";
      }
      enum "ENV_ALM_USERDEFINED46" {
        description "Not Available";
      }
      enum "ENV_ALM_USERDEFINED47" {
        description "Not Available";
      }
      enum "ENV_ALM_USERDEFINED48" {
        description "Not Available";
      }
      enum "ENV_ALM_USERDEFINED49" {
        description "Not Available";
      }
      enum "ENV_ALM_USERDEFINED50" {
        description "Not Available";
      }
    }
    description "External Alarm Type";
  }
  
  typedef external-control-type {
    type enumeration {
      enum "ENV_CTL_NONE" {
        description "Not used";
      }
      enum "ENV_CTL_AIRCOND" {
        description "Air conditioning";
      }
      enum "ENV_CTL_ENGINE" {
        description "Engine";
      }
      enum "ENV_CTL_FAN" {
        description "Fan";
      }
      enum "ENV_CTL_GEN" {
        description "Generator";
      }
      enum "ENV_CTL_HEAT" {
        description "Heat";
      }
      enum "ENV_CTL_LIGHT" {
        description "Light";
      }
      enum "ENV_CTL_MISC" {
        description "Misc";
      }
      enum "ENV_CTL_SPKLR" {
        description "Sprinkler";
      }
    }
    description "External Control Type";
  }
  
  typedef virtual-wire {
    type enumeration {
      enum "VIRT_WIRE_NONE" {
        description "Not used";
      }
      enum "VIRT_WIRE_1" {
        description "Virtual Wire 1";
      }
      enum "VIRT_WIRE_2" {
        description "Virtual Wire 2";
      }
      enum "VIRT_WIRE_3" {
        description "Virtual Wire 3";
      }
      enum "VIRT_WIRE_4" {
        description "Virtual Wire 4";
      }
    }
    description "External Control Type";
  }
  
  typedef severity-t {
    type enumeration {
      enum "NOT_REPORTED" {
        description "Not Reported";
      }
      enum "NOT_ALARMED" {
        description "Not Alarmed";
      }
      enum "MINOR" {
        description "Minor";
      }
      enum "MAJOR" {
        description "MAJOR";
      }
      enum "CRITICAL" {
        description "Critical";
      }
    }
    description "severity types";
  }
 
  typedef trigger-type-t {
    type enumeration {
      enum "TGR_TYPE_LOCAL_ALARM_LEVEL" {
        description "Trigger Type local alarm level";
      }
      enum "TGR_TYPE_REMOTE_ALARM_LEVEL" {
        description "Trigger Type Remote alarm level";
      }
      enum "TGR_TYPE_VIRTUAL_WIRE" {
        description "Trigger type Virtual wire level";
      }
    }
    description "trigger types";
  }

  typedef alarm-severity-rank-t {
    type enumeration {
      enum "HIGHWATER_NO_ALARMS" {
        description "alarm severity rank highwater no alarms";
      }
      enum "HIGHWATER_NOT_REPORTED" {
        description "alarm severity rank highwater not reported";
      }
      enum "HIGHWATER_NOT_ALARMED" {
        description "alarm severity rank highwater not alarmed";
      }
      enum "HIGHWATER_MINOR" {
        description "alarm severity rank highwater minor";
      }
      enum "HIGHWATER_MAJOR" {
        description "alarm severity rank highwater major";
      }
      enum "HIGHWATER_CRITICAL" {
        description "alarm severity rank highwater critical";
      }
    }
    description "alarm severity rank";
  }
  
  typedef trigger-info-t {
    type enumeration {
      enum "LOCAL_HIGHWATER_NO_ALARMS" {
        description "alarm severity rank highwater no alarms";
      }
      enum "LOCAL_HIGHWATER_NOT_REPORTED" {
        description "alarm severity rank highwater not reported";
      }
      enum "LOCAL_HIGHWATER_NOT_ALARMED" {
        description "alarm severity rank highwater not alarmed";
      }
      enum "LOCAL_HIGHWATER_MINOR" {
        description "alarm severity rank highwater minor";
      }
      enum "LOCAL_HIGHWATER_MAJOR" {
        description "alarm severity rank highwater major";
      }
      enum "LOCAL_HIGHWATER_CRITICAL" {
        description "alarm severity rank highwater critical";
      }
      enum "REMOTE_HIGHWATER_NO_ALARMS" {
        description "alarm severity rank highwater no alarms";
      }
      enum "REMOTE_HIGHWATER_NOT_REPORTED" {
        description "alarm severity rank highwater not reported";
      }
      enum "REMOTE_HIGHWATER_NOT_ALARMED" {
        description "alarm severity rank highwater not alarmed";
      }
      enum "REMOTE_HIGHWATER_MINOR" {
        description "alarm severity rank highwater minor";
      }
      enum "REMOTE_HIGHWATER_MAJOR" {
        description "alarm severity rank highwater major";
      }
      enum "REMOTE_HIGHWATER_CRITICAL" {
        description "alarm severity rank highwater critical";
      }
      enum "TRIGGER_INFO_VIRT_WIRE_NONE" {
        description "Not used";
      }
      enum "TRIGGER_INFO_VIRT_WIRE_1" {
        description "Virtual Wire 1";
      }
      enum "TRIGGER_INFO_VIRT_WIRE_2" {
        description "Virtual Wire 2";
      }
      enum "TRIGGER_INFO_VIRT_WIRE_3" {
        description "Virtual Wire 3";
      }
      enum "TRIGGER_INFO_VIRT_WIRE_4" {
        description "Virtual Wire 4";
      }
    }
    description "trigger Info Type ";
  }
 
}
