module cisco-svo-common-base-opt-grp {
    yang-version 1.1;
    namespace "http://cisco.com/yang/svo/common-base-opt-grp";
    prefix ccbog;

    import cisco-svo-common-types { prefix cct; }
    import ietf-yang-types { prefix yang; }

    organization
        "Cisco Systems, Inc.";

    contact
        "Cisco Systems, Inc.
     Customer Service

     Postal: 170 West Tasman Drive
     San Jose, CA 95134

     Tel: +1 800 553-NETS

     E-mail: cs-yang@cisco.com";

    description "
    Cisco Common Types, used inside both,
    the equipment and the network modules and them
    submodules.";

    revision 2020-12-04 { 
       description "Model version for SVO Release 12.1.0 "; 
       reference cisco-svo-common-base-opt-grp.yang; 
    }
 


    grouping och-power-thresholds-grp {
        description "Thresholds to detect Optical Channel Power alarms";
        leaf power-high {
            type cct:dbm-threshold-t;
            units "dBm";
            description "High Power Value";
        }
        leaf power-low {
            type cct:dbm-threshold-t;
            units "dBm";
            description "Low Power Value";
        }
    }

    grouping cd-range-grp {
        description "A Chromatic Dispersion interval";
        leaf cd-high {
            type cct:cd-working-range-t;
            units "ps/nm";
            description "CD Interval upper value";
        }
        leaf cd-low {
            type cct:cd-working-range-t;
            units "ps/nm";
            description "CD Interval lower value";
        }
    }

    grouping power-failure-low-threshold-grp {
        description "Threshold to detect Optical Power fail alarm";
        leaf power-failure-low {
            type cct:any-threshold-t;
            units "dBm or mW";
            description "Power Failure Low Value";
        }
    }
    
    grouping psd-failure-low-threshold-grp {
        description "Threshold to detect Optical Power fail alarm (PSD)";
        leaf power-failure-low {
            type cct:psd-threshold-t;
            units "dBm";
            description "Power Failure Low Value";
        }
    }

    grouping laser-bias-high-threshold-grp {
        description "Threshold to detect excessive Laser Bias";
        leaf laser-bias-hi {
            type cct:laser-bias-threshold-t;
            description "Laser Bias High threshold %";
        }
    }

    grouping rpc-status {
        description "Response Status";
        leaf status {
            type identityref {
                base cct:rpc-response-status;
            }
            description "Status code";
        }
        leaf message {
            type string;
            description "Descriptive Error or Message";
        }
    }

    // Feasibility Metric Types Definition

    grouping feasibility-limit-list {
        list feasibility-limit {
            key "id";
            description "Feasibility limit power / osnr pair";
            leaf id {
                type uint32;
                description "Unique Identifier";
            }
            leaf power {
                type decimal64 {
                    fraction-digits 2;
                }
                units "dB";
                description "Feasibility power";
            }
            leaf osnr {
                type decimal64 {
                    fraction-digits 2;
                }
                description "Feasibility Signal / Noise";
            }
        }
        description "
      Ordered list of feasibility limits
      (should match order of supported FEC types
      given in fec-type-list).
    ";
    }

    grouping ber-grp {
        leaf sf-ber {
            type enumeration {
                enum "1E-3";
                enum "1E-4";
                enum "1E-5";
            }
            description "signal failure - Bit Error Ratio .";
        }
        leaf sd-ber {
            type enumeration {
                enum "1E-5";
                enum "1E-6";
                enum "1E-7";
                enum "1E-8";
                enum "1E-9";
            }
            description "signal degradation - Bit Error Ratio .";
        }
    }
    
	grouping manual-raman-calibration-four-corners-grp {
        
        leaf pump-1-low-power {
            type cct:dbm-t;
            mandatory true;
            description 
              "measured incoming power with only Pump 1 on at low power level";
        }

        leaf pump-1-high-power {
            type cct:dbm-t;
            mandatory true;
            description 
              "measured incoming power with only Pump 1 on at high power level";
        }

        leaf pump-2-low-power {
            type cct:dbm-t;
            mandatory true;
            description 
              "measured incoming power with only Pump 2 on at low power level";
        }

        leaf pump-2-high-power {
            type cct:dbm-t;
            mandatory true;
            description 
              "measured incoming power with only Pump 2 on at high power level";
        }	

	}
	
    grouping automatic-raman-calibration-report-grp {
        list report {
            key "time-stamp";

            leaf time-stamp {
                type yang:date-and-time;
                description
                   "Time stamp of calibration";
            }

            leaf status {
                type cct:raman-automatic-calib-status-t;
                description
                   "Status of automatic Raman Calibration";
            }

            leaf raman-noise-floor {
                type cct:dbm-t;
                description
                  "Power level of noise floor generated by Raman Amplification";
            }

            leaf incoming-power-with-pumps-off {
                type cct:dbm-t;
                description
                  "Power level of probe signal with raman pumps off";
            }

            leaf incoming-power-with-pumps-on {
                type cct:dbm-t;
                description
                  "Power level of probe signal with raman pumps on (combined with
                                raman noise floor)";
            }

            leaf power-source {
                type cct:raman-automatic-calib-pwr-src-t;
                description
                  "Type of power source used for calibration";
            }

            leaf calibration-gain {
                type cct:gain-t;
                description
                  "Raman gain obtained with calibration total pumps power";
            }

            leaf calibration-total-pumps-power {
                type cct:mw-t;
                description
                  "Reference total pump power used through-out the calibration procedure";
            }

            leaf target-gain {
                type cct:gain-t;
                description
                  "Target raman gain";
            }

            leaf obtained-gain {
                type cct:gain-t;
                description
                  "Obtained gain";
            }

            leaf target-tilt {
                type cct:tilt-t;
                description
                  "Target spectrum tilt";
            }

            leaf obtained-tilt {
                type cct:tilt-t;
                description
                  "Obtained spectrum tilt";
            }

            leaf result {
                type cct:raman-calib-result-t;
                description
                  "Calibration result versus target gain and tilt";
            }
        }
    }
}
