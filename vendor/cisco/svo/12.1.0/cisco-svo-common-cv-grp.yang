module cisco-svo-common-cv-grp {
    yang-version 1.1;
    namespace "http://cisco.com/yang/svo/common-cv-grp";
    prefix "cccv";

    import cisco-svo-common-equipment-types { prefix ccet; }
    import cisco-svo-common-types { prefix cct; }
    import cisco-svo-common-base-opt-grp { prefix ccbog; }
   
    organization
        "Cisco Systems, Inc.";

    contact
        "Cisco Systems, Inc. Customer Service Postal: 170 West Tasman
        Drive San Jose, CA 95134 Tel: +1 800 553-NETS E-mail: cs-yang@cisco.com";

    description " Cisco Common Sync Interface, used inside both, SVO and NCS2K yang models.";

    revision 2020-12-04 { 
       description "Model version for SVO Release 12.1.0 "; 
       reference cisco-svo-common-cv-grp.yang; 
    }
 

    grouping cv-config-grp {
      description "Connection Verification config";
      leaf enabling-status {
        type cct:cv-enabling-status-t;
        default enabled;
        config true;
        description "Enable/Disable Connection Verification";
      }

      leaf degrade-threshold {
        type cct:insertion-loss-t;
        default 1.50;
        config true;
        description "Default excess loss degrade threshold after that we have a degrade";
      }

      leaf fail-threshold {
        type cct:insertion-loss-t;
        default 4.00;
        config true;
        description "Default excess loss degrade threshold after that we have a fail";
      }
    }

    grouping cv-action-link-parameters-grp {
      description "Connection Verification action link parameters";
        list internal-link {
          key "src-port-name dst-port-name";
          description "Internal patchcord";
          leaf src-port-name {
            type leafref {
              path "../../../../../internal-link/src-port-name";
            }
            description "Identifier of the source portname in the format uid/[slot-id/]port-id.";
          }

          leaf dst-port-name {
            type leafref {
              path "../../../../../internal-link[src-port-name=current()/../src-port-name]/dst-port-name";
            }
            description "Identifier of the destination portname in the format uid/[slot-id/]port-id.";
          }
        }
    }

    grouping cv-action-single-link-parameters-grp {
      description "Connection Verification action single link parameters";
        container internal-link {
          description "Internal patchcord";
          leaf src-port-name {
            type leafref {
              path "../../../../../internal-link/src-port-name";
            }
            description "Identifier of the source portname in the format uid/[slot-id/]port-id.";
          }

          leaf dst-port-name {
            type leafref {
              path "../../../../../internal-link[src-port-name=current()/../src-port-name]/dst-port-name";
            }
            description "Identifier of the destination portname in the format uid/[slot-id/]port-id.";
          }
        }
    }

    grouping combined-loss-info-list-grp {
      description "Combined loss info list group";
 
      leaf combined-excess-insertion-loss {
        type cct:attenuation-t;
        description "Combined Excess loss of internallink versus its expected loss; 0 means insertion loss is within specification";
      }

      list internal-link {
        key "src-port-name dst-port-name";
        description "Internal patchcord";

        leaf src-port-name {
          type ccet:port-name-t;
          description
            "Identifier of the source portname in the format uid/[slot-id/]port-id.";
        }

        leaf dst-port-name {
          type ccet:port-name-t;
          description
            "Identifier of the destination portname in the format uid/[slot-id/]port-id.";
        }
      }
      leaf loopback-port-name {
        type ccet:port-name-t;
        description
          "Identifier of the loopback portname in the format uid/[slot-id/]port-id.";
      }
    }

    grouping combined-loss-info-response-grp {
      description "Combined loss info Response group";
      container combined-loss-info-response {
        description "Combined loss info Response container";
        uses ccbog:rpc-status;
        uses combined-loss-info-list-grp;
      }
    }

    grouping cv-actions-grp {
      description "Connection Verification Action group";
      container commands {
        description "Connection Verification Action commands container";

        action verify-connectivity {
          description "Action to start connectivity verification on all links";

          output {
            uses ccbog:rpc-status;
          }
        }

        action verify-loss {
          description "Action to start loss verification on all links";

          output {
            uses ccbog:rpc-status;
          }
        }

        action terminate-running-cv {
          description "Action to terminate current running connection verification";

          output {
            uses ccbog:rpc-status;
          }
        }

        action verify-link-connectivity {
          description "Action to start Connection Verification on a list of links";

          input {
            uses cv-action-link-parameters-grp;
            must "count(internal-link) > 0";
         }

          output {
            uses ccbog:rpc-status;
          }
        }

        action verify-link-loss {
          description "Action to start loss verification on a list of links";
  
          input {
            uses cv-action-link-parameters-grp;
            must "count(internal-link) > 0";
          }

          output {
            uses ccbog:rpc-status;
          }
        }
 
        action ack-link-loss-alarm {
          description "Action to acknowledge loss alarm of specified links";
 
          input {
            uses cv-action-link-parameters-grp;
            must "count(internal-link) > 0";
          }

          output {
            uses ccbog:rpc-status;
          }
        }

        action clear-ack-link-loss-alarm {
          description "Action to clear the acknowledge of loss alarm of specified links";
 
          input {
            uses cv-action-link-parameters-grp;
            must "count(internal-link) > 0";
          }

          output {
            uses ccbog:rpc-status;
          }
        }

        action retrieve-combined-link-loss-info {
          description "Action to start loss verification on a list of links";
  
          input {
            uses cv-action-single-link-parameters-grp;
          }

          output {
            uses combined-loss-info-response-grp;
          }
        }

        action refresh-cv-info {
          description "Action to start the refresh of all the operational data within the SVO with the current backend CV links data";

          output {
            uses ccbog:rpc-status;
          }
        }

        action enable-link-cv {
          description "Action to enable connection verification for the specified links";
 
          input {
            uses cv-action-link-parameters-grp;
            must "count(internal-link) > 0";
          }

          output {
            uses ccbog:rpc-status;
          }
        }

        action disable-link-cv {
          description "Action to disable connection verification for the specified links";
 
          input {
            uses cv-action-link-parameters-grp;
            must "count(internal-link) > 0";
          }

          output {
            uses ccbog:rpc-status;
          }
        }

      }
    }

    grouping connection-verification-grp {
      description "Connection Verification grouping";
      container connection-verification {
        description "Connection Verification";
        uses cv-config-grp;
        uses cv-actions-grp {
          when "(enabling-status = enabled)";
        }
      }
   }
}
