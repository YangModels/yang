module cisco-svo-node-functionalities-internal {
    yang-version 1.1;
    namespace "http://cisco.com/yang/svo/node-funct-int";
    prefix svo-node-funct-int;

    import tailf-common { prefix tailf; }
    import ietf-inet-types { prefix inet; }    
    import cisco-svo-common-base-opt-grp { prefix ccbog; }

    organization
        "Cisco Systems, Inc.";

    contact
        "Cisco Systems, Inc. Customer Service Postal: 170 West Tasman
        Drive San Jose, CA 95134 Tel: +1 800 553-NETS E-mail: cs-yang@cisco.com";

   
    description 
       "Yang definition of types and action for manage internal non public operations";

    revision 2020-12-04 { 
       description "Model version for SVO Release 12.1.0 "; 
       reference cisco-svo-node-functionalities-internal.yang; 
    }
    
    tailf:export cli; //none cli netconf  
      
    typedef protocol-type {
        description "Defines the supported protocols for download of package";
        type enumeration {
            enum "sftp" {
                value 1;
            }
        }
    }
    
    grouping upload-download-input-param {
        leaf file-name {
            description "The backup filename to download on the system";
            type string;
        }
        
        leaf protocol {
            type protocol-type;
            description
                        "Protocol to be used to download the package";
        }
        
        choice credential {
            case user-password {
                leaf user {
                    type string;
                    description "user name to be used to download the package";
                }
                leaf password {
                    type string;
                    tailf:suppress-echo true;
                    description "password to be used to download the package";
                }
            }
            case authgroup {
                leaf group-name {
                    type string;
                    description "authorization group configured for download";
                }
            }
        }
    }
    
    container svo-node-function {  
                  
         container commands {
                     
           tailf:action move-uploaded-file {
                tailf:info "Move file from source to destination directory based on operation type";
                description "Move file from source to destination directory based on operation type";
                tailf:actionpoint move-uploaded-file;
                input {
                	leaf-list file-path {
                       description "The backup filename to move on the system";
                       type string;
                    }
                    
                    leaf operation-type {
			            type move-op-type;
			            description "Give information for destination operation";
			        }
                }

                output {
                    uses ccbog:rpc-status;
                }
            }
                     
           tailf:action execute-otdr-ml {
                tailf:info "activate one external downloaded SOR file";
                description "activate one external downloaded SOR file";
                tailf:actionpoint execute-otdr-ml;
                input {
                	leaf sor-file-name {
                       description "sor file that will be parsed by otdr-ml";
                       type string;
          				mandatory true;
                    } 
                    leaf json-destination-path {
                       description "path of destination of the json file, if not present use the SVO sor system path";
                       type string;
                    }                    
                }

                output {
                    uses ccbog:rpc-status;
                }
            }
                     
           tailf:action otdr-upgrade-ml {
                tailf:info "upgrade the ml library";
                description "upgrade the ml library";
                tailf:actionpoint otdr-upgrade-ml;
                input {
                	leaf remote-file-path {
            			type inet:uri;
            			description "Remote file path. A URI for the remote file path. Format:sftp://user[:password]@host[:port]/path.
                           				Ex: sftp://test:verify@[2001:db8:0:1::10]:22/home/user/sample";
            			tailf:info "Remote file path. A URI for the remote file path. Format:sftp://user[:password]@host[:port]/path.
                           				Ex: sftp://test:verify@[2001:db8:0:1::10]:22/home/user/sample";
                    }
                    
                    uses upload-download-input-param;
                    
                    leaf post-upgrade-script {
                    	type string;
            			description "Name of an optional script that shall be automatically run by the system";
            			tailf:info "Name of an optional script that shall be automatically run by the system";
                    }
                }

                output {
                    uses ccbog:rpc-status;
                }
            }           
        }
    }
      
    typedef move-op-type {
        type enumeration {
          
            enum "backup-restore" {
                description "Move operation for Backup&Restore.";
            }
              
            enum "capabilities" {
                description "Move operation for Backup&Restore.";
            }       
        }
        description "The destination of move operation";
    }

}
