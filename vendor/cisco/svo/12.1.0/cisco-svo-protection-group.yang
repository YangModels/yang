module cisco-svo-protection-group {
    yang-version 1.1;
    namespace "http://cisco.com/yang/svo/protection-group";
    prefix svo-prt-grp;

    import cisco-svo-common-protection-group { prefix cprt-grp; }
    import cisco-svo-common-protection-group-oper-grp { prefix coprt-grp; }
    import cisco-svo-common-equipment-types { prefix ccet; }

    organization
        "Cisco Systems, Inc.";

    contact
        "Cisco Systems, Inc. Customer Service Postal: 170 West Tasman
        Drive San Jose, CA 95134 Tel: +1 800 553-NETS E-mail: cs-yang@cisco.com";

    description "
    YANG model definition for SVO Protection Groups";

    revision 2020-12-04 { 
       description "Model version for SVO Release 12.1.0 "; 
       reference cisco-svo-protection-group.yang; 
    }
 

    grouping svo-protection-grps {
        list protection-group {
            key "ref-interface";

			leaf ref-interface {
				type ccet:port-name-t;
				description "The reference interface for the protection-group";
			}

            uses cprt-grp:protection-group-config-grp;
            uses coprt-grp:protection-group-oper-grp;
            uses cprt-grp:protection-group-action-grp;
        }
    }
}
