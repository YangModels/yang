module cisco-svo-common-interface-live-grp {

    yang-version 1.1;
    namespace "http://cisco.com/yang/svo/common-interface-live-grp";
    prefix "ccilg";

    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description " Cisco Common Interface Live Data";

    revision 2020-12-04 { 
       description "Model version for SVO Release 12.1.0 "; 
       reference cisco-svo-common-interface-live-grp.yang; 
    }
 

    grouping optical-transport-live-data {
      description "OTS Interface live data grouping";
      leaf optical-power {
        type cct:pwr-oper-t;
        config false;
        description "Signal Optical power";
       }

       leaf osc-power {
         type cct:dbm-oper-t;
         config false;
         description "OSC optical power";
       }
    }
}
