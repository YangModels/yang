module cisco-svo-alarms-dictionary {
    namespace "http://cisco.com/yang/svo/alarms-dictionary";
    prefix svo-al-dict;

    import tailf-common { prefix tailf; }

    import tailf-ncs-alarms { prefix al; }

    import cisco-svo-alarms { prefix svo-al; }
    import cisco-svo-alarm-type { prefix svo-al-t; }

    organization "Cisco Systems";

    description
        "This module defines the structure for representing an alarm dictionary entry and augments the alarms
        section with an action for retrieving the alarm dictionary conditions";

    revision 2020-12-04 { 
       description "Model version for SVO Release 12.1.0 "; 
       reference cisco-svo-alarms-dictionary.yang; 
    }
 


    typedef resource-t {
      type enumeration {
        enum system;
        enum backplane;
        enum bits;
        enum card;
        enum ecu;
        enum envalarm;
        enum eth;
        enum ext-synchref;
        enum fan-tray;
        enum fc;
        enum lcd-flash;
        enum ms-eth;
        enum ne;
        enum ne-synchref;
        enum oxc;
        enum och;
        enum ocn;
        enum oduk;
        enum opt;
        enum otuk;
        enum passive-shelf;
        enum port;
        enum ppm;
        enum pwr;
        enum shelf;
        enum stmn;
        enum usb-flash;
        enum raman-amplifier;
        enum otdr;
        enum zr-plus;
      }
      description "Indicates the alarmable resources";
    }

    grouping input-group {
      choice input-selection {
        description
          "input selection for retrieving alarm dictionary elements";
        case all-selection {
          description "Retrieve all alarms";
          leaf include-transient {
            type boolean;
            description
              "include or not the transient alarms";
            default false;
          }
        }
        case resource-selection {
          description "Retrieve all alarms with given resources selection";
          leaf-list resource {
            type resource-t;
            description
              "resource type (all means every resources when applicable)";
          }
        }
        case condition-selection {
          description "Retrieve all alarms with type name that contains the given condition-name";
          leaf condition-name {
            type string;
            description
              "condition name to find as substring";
          }
        }
        case identity-selection {
          description "Retrieve with the given type";
          leaf condition-type {
            type svo-al-t:svo-alarm-type-t;
            description
              "type of alarm (no alarm-transien)";
          }
        }
      }
    }

    grouping condition-list {
      container conditions {
        list condition {
          key "condition-name";
          description "The list of conditions retrieved from the alarm dictionary";

          leaf condition-name {
            type string;
            mandatory true;
            description "name of the condition (the same as the alarm-type tag)";
          }  

          leaf alarm-text {
            type string;
            mandatory true;
            description "alarm description from the dictionary";
          }  

          leaf direction {
            type svo-al:direction-t;
            description
             "Indicates is the Alarm direction (Transmit/Receive/NA)";
          }

          leaf location {
            type svo-al:location-t;
            description
              "Indicates is the Alarm location (Far/Near/NA)";
          }

          leaf sa-severity {
            type al:severity-t;
            description "The severity (Service Affecting) of the condition.";
          }

          leaf nsa-severity {
            type al:severity-t;
             description "The severity (Not Service Affecting) of the condition.";
          }

          leaf-list resources {
            type resource-t;
            description "List of possible resources affected by this alarm";
          }

          leaf release-info {
            type string;
            description "Some information about, the supported implementation
                         of this alarm ad the supported releases";
          }
        }
      }
    }

    grouping available-resources-group {
      leaf-list available-resources {
        type resource-t;
        description "List of all available resources for the alarms";
      }
    }

    augment /al:alarms {

      tailf:action retrieve-dictionary {
        description "Retrieve the Alarm Dictionary Information";
        tailf:info "Retrieve the Alarm Dictionary Information";

        tailf:actionpoint retrieve-dictionary-point;

        input {
          uses input-group;
        }
        output {
          uses condition-list;
        }
      }

      tailf:action retrieve-dictionary-resources {
        description "Retrieve the Alarm Dictionary Resources";
        tailf:info "Retrieve the Alarm Dictionary Resources";

        tailf:actionpoint retrieve-dictionary-point;

        output {
          uses available-resources-group;
        }
      }
    }
}
