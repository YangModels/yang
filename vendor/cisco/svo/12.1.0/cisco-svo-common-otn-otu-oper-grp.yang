module cisco-svo-common-otn-otu-oper-grp {

	yang-version 1.1;
	namespace "http://cisco.com/yang/svo/common-otn-otu-oper-grp";
	prefix cotuog;

	import cisco-svo-common-otn-oper-grp { prefix ccotnog; }

	organization 
	"Cisco Systems, Inc.";

	contact 
	"Cisco Systems, Inc.
	Customer Service

	Postal: 170 West Tasman Drive
	San Jose, CA 95134

	Tel: +1 800 553-NETS

	E-mail: cs-yang@cisco.com";

	description "
	This module defines the OpticalChannel interface Operational.";

    revision 2020-12-04 { 
       description "Model version for SVO Release 12.1.0 "; 
       reference cisco-svo-common-otn-otu-oper-grp.yang; 
    }
 

	grouping proactive-protection-oper-grp {
   	    description "Proactive Protection read-only Parameters";
       	leaf supports-proactive-protection {
      		type boolean;
	      	config false;
    	  	description "True if Proactive Protection is supported on the interface";
    	}
       	leaf supports-proactive-protection-forwarding {
      		type boolean;
	      	config false;
    	  	description "True if the interface can be configured to block or forward Proactive Protection";
    	}
	}

	grouping otn-otu-oper-group {
		uses ccotnog:otu-attributes;

		container proactive-protection {
			uses cotuog:proactive-protection-oper-grp;
		}

		container optical-transport-unit {
 			container tti {
				uses ccotnog:tti-oper-grp;
			}
			container synchronization {
				uses ccotnog:sync-oper-grp;
			}
		}
	}
}
