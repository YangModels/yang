/*
* Generated by python main_svo_generator.py
* Source: alarm_dictionary
*/
submodule cisco-svo-pm-tca-alarm-types {

  belongs-to cisco-svo-alarm-tca-type {
    prefix svo-al-tca-t;
  }

  include cisco-svo-alarm-tca-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the pm tca alarm types";

    revision 2020-12-04 { 
       description "Model version for SVO Release 12.1.0 "; 
       reference cisco-svo-pm-tca-alarm-types.yang; 
    }
 

  identity pm-tca-alarm-type {
    description "Root of pm tca alarm type";
    base svo-al-tca-t:svo-alarm-tca-type;
  }

  identity T-CVL {
    description "Performance Monitor Threshold Crossing Alert";
    base pm-tca-alarm-type;
  }

  identity T-CVS {
    description "Performance Monitor Threshold Crossing Alert";
    base pm-tca-alarm-type;
  }

  identity T-ESL {
    description "Performance Monitor Threshold Crossing Alert";
    base pm-tca-alarm-type;
  }

  identity T-ESS {
    description "Performance Monitor Threshold Crossing Alert";
    base pm-tca-alarm-type;
  }

  identity T-SEFS {
    description "Performance Monitor Threshold Crossing Alert";
    base pm-tca-alarm-type;
  }

  identity T-SESL {
    description "Performance Monitor Threshold Crossing Alert";
    base pm-tca-alarm-type;
  }

  identity T-SESS {
    description "Performance Monitor Threshold Crossing Alert";
    base pm-tca-alarm-type;
  }

  identity T-UASL {
    description "Performance Monitor Threshold Crossing Alert";
    base pm-tca-alarm-type;
  }

  identity T-RS-BBE {
    description "Performance Monitor Threshold Crossing Alert";
    base pm-tca-alarm-type;
  }

  identity T-BBEL {
    description "Performance Monitor Threshold Crossing Alert";
    base pm-tca-alarm-type;
  }

  identity T-MS-ES {
    description "Performance Monitor Threshold Crossing Alert";
    base pm-tca-alarm-type;
  }

  identity T-RS-ES {
    description "Performance Monitor Threshold Crossing Alert";
    base pm-tca-alarm-type;
  }

  identity T-MS-SES {
    description "Performance Monitor Threshold Crossing Alert";
    base pm-tca-alarm-type;
  }

  identity T-RS-SES {
    description "Performance Monitor Threshold Crossing Alert";
    base pm-tca-alarm-type;
  }

  identity T-MS-UAS {
    description "Performance Monitor Threshold Crossing Alert";
    base pm-tca-alarm-type;
  }

  identity T-MS-FC {
    description "Performance Monitor Threshold Crossing Alert";
    base pm-tca-alarm-type;
  }

  identity T-RS-OFS {
    description "Performance Monitor Threshold Crossing Alert";
    base pm-tca-alarm-type;
  }

  identity T-MS-BBE {
    description "Performance Monitor Threshold Crossing Alert";
    base pm-tca-alarm-type;
  }

  identity T-BBES {
    description "Performance Monitor Threshold Crossing Alert";
    base pm-tca-alarm-type;
  }

  identity T-UASS {
    description "Performance Monitor Threshold Crossing Alert";
    base pm-tca-alarm-type;
  }

  identity T-RS-SESR {
    description "Performance Monitor Threshold Crossing Alert";
    base pm-tca-alarm-type;
  }

  identity T-RS-BBER {
    description "Performance Monitor Threshold Crossing Alert";
    base pm-tca-alarm-type;
  }

  identity T-RS-UAS {
    description "Performance Monitor Threshold Crossing Alert";
    base pm-tca-alarm-type;
  }

  identity T-MS-ESR {
    description "Performance Monitor Threshold Crossing Alert";
    base pm-tca-alarm-type;
  }

  identity T-MS-SESR {
    description "Performance Monitor Threshold Crossing Alert";
    base pm-tca-alarm-type;
  }

  identity T-MS-BBER {
    description "Performance Monitor Threshold Crossing Alert";
    base pm-tca-alarm-type;
  }

  identity T-BBE-SM {
    description "Performance Monitor Threshold Crossing Alert";
    base pm-tca-alarm-type;
  }

  identity T-BBE-PM {
    description "Performance Monitor Threshold Crossing Alert";
    base pm-tca-alarm-type;
  }

  identity T-BBE-TCM1 {
    description "Performance Monitor Threshold Crossing Alert";
    base pm-tca-alarm-type;
  }

  identity T-BBE-TCM2 {
    description "Performance Monitor Threshold Crossing Alert";
    base pm-tca-alarm-type;
  }

  identity T-BBER-SM {
    description "Performance Monitor Threshold Crossing Alert";
    base pm-tca-alarm-type;
  }

  identity T-BBER-PM {
    description "Performance Monitor Threshold Crossing Alert";
    base pm-tca-alarm-type;
  }

  identity T-BBER-TCM1 {
    description "Performance Monitor Threshold Crossing Alert";
    base pm-tca-alarm-type;
  }

  identity T-BBER-TCM2 {
    description "Performance Monitor Threshold Crossing Alert";
    base pm-tca-alarm-type;
  }

  identity T-BIEC {
    description "Performance Monitor Threshold Crossing Alert";
    base pm-tca-alarm-type;
  }

  identity T-TX-PWR-MIN {
    description "Performance Monitor Threshold Crossing Alert";
    base pm-tca-alarm-type;
  }

  identity T-RX-PWR-MIN {
    description "Performance Monitor Threshold Crossing Alert";
    base pm-tca-alarm-type;
  }

  identity T-RX-TEMP-MIN {
    description "Performance Monitor Threshold Crossing Alert";
    base pm-tca-alarm-type;
  }

  identity T-LASER-BIAS-MIN {
    description "Performance Monitor Threshold Crossing Alert";
    base pm-tca-alarm-type;
  }

  identity T-LASER-TEMP-MIN {
    description "Performance Monitor Threshold Crossing Alert";
    base pm-tca-alarm-type;
  }

  identity T-VOA-MIN {
    description "Performance Monitor Threshold Crossing Alert";
    base pm-tca-alarm-type;
  }

  identity T-GAIN-MIN {
    description "Performance Monitor Threshold Crossing Alert";
    base pm-tca-alarm-type;
  }

  identity T-GAIN-MAX {
    description "Performance Monitor Threshold Crossing Alert";
    base pm-tca-alarm-type;
  }

  identity T-TX-PWR-MAX {
    description "Performance Monitor Threshold Crossing Alert";
    base pm-tca-alarm-type;
  }

  identity T-RX-PWR-MAX {
    description "Performance Monitor Threshold Crossing Alert";
    base pm-tca-alarm-type;
  }

  identity T-RX-TEMP-MAX {
    description "Performance Monitor Threshold Crossing Alert";
    base pm-tca-alarm-type;
  }

  identity T-LASER-BIAS-MAX {
    description "Performance Monitor Threshold Crossing Alert";
    base pm-tca-alarm-type;
  }

  identity T-LASER-TEMP-MAX {
    description "Performance Monitor Threshold Crossing Alert";
    base pm-tca-alarm-type;
  }

  identity T-VOA-MAX {
    description "Performance Monitor Threshold Crossing Alert";
    base pm-tca-alarm-type;
  }

  identity T-BIT-EC {
    description "Performance Monitor Threshold Crossing Alert";
    base pm-tca-alarm-type;
  }

  identity T-BYTE-EC {
    description "Performance Monitor Threshold Crossing Alert";
    base pm-tca-alarm-type;
  }

  identity T-UNC-WORDS {
    description "Performance Monitor Threshold Crossing Alert";
    base pm-tca-alarm-type;
  }

  identity T-GAIN-AVG {
    description "Performance Monitor Threshold Crossing Alert";
    base pm-tca-alarm-type;
  }

  identity T-PWR-AVG {
    description "Performance Monitor Threshold Crossing Alert";
    base pm-tca-alarm-type;
  }

  identity T-VOA-AVG {
    description "Performance Monitor Threshold Crossing Alert";
    base pm-tca-alarm-type;
  }

  identity T-PWR-MAX {
    description "Performance Monitor Threshold Crossing Alert";
    base pm-tca-alarm-type;
  }

  identity T-PWR-MIN {
    description "Performance Monitor Threshold Crossing Alert";
    base pm-tca-alarm-type;
  }

  identity T-ES-SM {
    description "Performance Monitor Threshold Crossing Alert";
    base pm-tca-alarm-type;
  }

  identity T-ES-PM {
    description "Performance Monitor Threshold Crossing Alert";
    base pm-tca-alarm-type;
  }

  identity T-SES-SM {
    description "Performance Monitor Threshold Crossing Alert";
    base pm-tca-alarm-type;
  }

  identity T-UAS-SM {
    description "Performance Monitor Threshold Crossing Alert";
    base pm-tca-alarm-type;
  }

  identity T-FC-SM {
    description "Performance Monitor Threshold Crossing Alert";
    base pm-tca-alarm-type;
  }

  identity T-ESR-SM {
    description "Performance Monitor Threshold Crossing Alert";
    base pm-tca-alarm-type;
  }

  identity T-SESR-SM {
    description "Performance Monitor Threshold Crossing Alert";
    base pm-tca-alarm-type;
  }

  identity T-SES-PM {
    description "Performance Monitor Threshold Crossing Alert";
    base pm-tca-alarm-type;
  }

  identity T-UAS-PM {
    description "Performance Monitor Threshold Crossing Alert";
    base pm-tca-alarm-type;
  }

  identity T-FC-PM {
    description "Performance Monitor Threshold Crossing Alert";
    base pm-tca-alarm-type;
  }

  identity T-ESR-PM {
    description "Performance Monitor Threshold Crossing Alert";
    base pm-tca-alarm-type;
  }

  identity T-SESR-PM {
    description "Performance Monitor Threshold Crossing Alert";
    base pm-tca-alarm-type;
  }

  identity T-ES-TCM1 {
    description "Performance Monitor Threshold Crossing Alert";
    base pm-tca-alarm-type;
  }

  identity T-SES-TCM1 {
    description "Performance Monitor Threshold Crossing Alert";
    base pm-tca-alarm-type;
  }

  identity T-UAS-TCM1 {
    description "Performance Monitor Threshold Crossing Alert";
    base pm-tca-alarm-type;
  }

  identity T-FC-TCM1 {
    description "Performance Monitor Threshold Crossing Alert";
    base pm-tca-alarm-type;
  }

  identity T-ESR-TCM1 {
    description "Performance Monitor Threshold Crossing Alert";
    base pm-tca-alarm-type;
  }

  identity T-SESR-TCM1 {
    description "Performance Monitor Threshold Crossing Alert";
    base pm-tca-alarm-type;
  }

  identity T-ES-TCM2 {
    description "Performance Monitor Threshold Crossing Alert";
    base pm-tca-alarm-type;
  }

  identity T-SES-TCM2 {
    description "Performance Monitor Threshold Crossing Alert";
    base pm-tca-alarm-type;
  }

  identity T-UAS-TCM2 {
    description "Performance Monitor Threshold Crossing Alert";
    base pm-tca-alarm-type;
  }

  identity T-FC-TCM2 {
    description "Performance Monitor Threshold Crossing Alert";
    base pm-tca-alarm-type;
  }

  identity T-ESR-TCM2 {
    description "Performance Monitor Threshold Crossing Alert";
    base pm-tca-alarm-type;
  }

  identity T-SESR-TCM2 {
    description "Performance Monitor Threshold Crossing Alert";
    base pm-tca-alarm-type;
  }

  identity T-OPR-AVG {
    description "Performance Monitor Threshold Crossing Alert";
    base pm-tca-alarm-type;
  }

  identity T-OPR-MAX {
    description "Performance Monitor Threshold Crossing Alert";
    base pm-tca-alarm-type;
  }

  identity T-OPR-MIN {
    description "Performance Monitor Threshold Crossing Alert";
    base pm-tca-alarm-type;
  }

  identity T-OPT-AVG {
    description "Performance Monitor Threshold Crossing Alert";
    base pm-tca-alarm-type;
  }

  identity T-OPT-MAX {
    description "Performance Monitor Threshold Crossing Alert";
    base pm-tca-alarm-type;
  }

  identity T-OPT-MIN {
    description "Performance Monitor Threshold Crossing Alert";
    base pm-tca-alarm-type;
  }

  identity T-OPWR-AVG {
    description "Performance Monitor Threshold Crossing Alert";
    base pm-tca-alarm-type;
  }

  identity T-OPWR-MAX {
    description "Performance Monitor Threshold Crossing Alert";
    base pm-tca-alarm-type;
  }

  identity T-OPWR-MIN {
    description "Performance Monitor Threshold Crossing Alert";
    base pm-tca-alarm-type;
  }

  identity T-RS-ESR {
    description "Performance Monitor Threshold Crossing Alert";
    base pm-tca-alarm-type;
  }

  identity T-MS-LOSS {
    description "Performance Monitor Threshold Crossing Alert";
    base pm-tca-alarm-type;
  }

  identity T-OSC-PWR-MIN {
    description "Performance Monitor Threshold Crossing Alert";
    base pm-tca-alarm-type;
  }

  identity T-OSC-PWR-MAX {
    description "Performance Monitor Threshold Crossing Alert";
    base pm-tca-alarm-type;
  }

  identity T-OSC-PWR-AVG {
    description "Performance Monitor Threshold Crossing Alert";
    base pm-tca-alarm-type;
  }

  identity T-OSNR-MIN {
    description "Performance Monitor Threshold Crossing Alert";
    base pm-tca-alarm-type;
  }

  identity T-OSNR-MAX {
    description "Performance Monitor Threshold Crossing Alert";
    base pm-tca-alarm-type;
  }

  identity T-OSNR-AVG {
    description "Performance Monitor Threshold Crossing Alert";
    base pm-tca-alarm-type;
  }

  identity T-PMD-MIN {
    description "Performance Monitor Threshold Crossing Alert";
    base pm-tca-alarm-type;
  }

  identity T-DGD-MAX {
    description "Performance Monitor Threshold Crossing Alert";
    base pm-tca-alarm-type;
  }

  identity T-PMD-AVG {
    description "Performance Monitor Threshold Crossing Alert";
    base pm-tca-alarm-type;
  }

  identity T-CHROM-DISP {
    description "Performance Monitor Threshold Crossing Alert";
    base pm-tca-alarm-type;
  }

  identity T-CDPM-MIN {
    description "Performance Monitor Threshold Crossing Alert";
    base pm-tca-alarm-type;
  }

  identity T-CDPM-MAX {
    description "Performance Monitor Threshold Crossing Alert";
    base pm-tca-alarm-type;
  }

  identity T-CDPM-AVG {
    description "Performance Monitor Threshold Crossing Alert";
    base pm-tca-alarm-type;
  }

  identity T-SOPMD-MIN {
    description "Performance Monitor Threshold Crossing Alert";
    base pm-tca-alarm-type;
  }

  identity T-SOPMD-MAX {
    description "Performance Monitor Threshold Crossing Alert";
    base pm-tca-alarm-type;
  }

  identity T-SOPMD-AVG {
    description "Performance Monitor Threshold Crossing Alert";
    base pm-tca-alarm-type;
  }

  identity T-PCR-MIN {
    description "Performance Monitor Threshold Crossing Alert";
    base pm-tca-alarm-type;
  }

  identity T-PCR-MAX {
    description "Performance Monitor Threshold Crossing Alert";
    base pm-tca-alarm-type;
  }

  identity T-PCR-AVG {
    description "Performance Monitor Threshold Crossing Alert";
    base pm-tca-alarm-type;
  }

  identity T-PDL-MIN {
    description "Performance Monitor Threshold Crossing Alert";
    base pm-tca-alarm-type;
  }

  identity T-PDL-MAX {
    description "Performance Monitor Threshold Crossing Alert";
    base pm-tca-alarm-type;
  }

  identity T-PDL-AVG {
    description "Performance Monitor Threshold Crossing Alert";
    base pm-tca-alarm-type;
  }

  identity T-rxPauseFrames {
    description "Performance Monitor Threshold Crossing Alert";
    base pm-tca-alarm-type;
  }

  identity T-txPauseFrames {
    description "Performance Monitor Threshold Crossing Alert";
    base pm-tca-alarm-type;
  }

  identity T-rxPktsDroppedInternalCongestion {
    description "Performance Monitor Threshold Crossing Alert";
    base pm-tca-alarm-type;
  }

  identity T-txPktsDroppedInternalCongestion {
    description "Performance Monitor Threshold Crossing Alert";
    base pm-tca-alarm-type;
  }

  identity T-rxControlFrames {
    description "Performance Monitor Threshold Crossing Alert";
    base pm-tca-alarm-type;
  }

  identity T-rxUnknownOpcodeFrames {
    description "Performance Monitor Threshold Crossing Alert";
    base pm-tca-alarm-type;
  }

  identity T-gfpStatsRoundTripLatencyUSec {
    description "Performance Monitor Threshold Crossing Alert";
    base pm-tca-alarm-type;
  }

}
