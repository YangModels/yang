module cisco-svo-common-action-param-grp {
    yang-version 1.1;
    namespace "http://cisco.com/yang/svo/common-action-param-grp";
    prefix ccapg;

    import cisco-svo-common-types { prefix cct;}
    import org-openroadm-common-optical-channel-types { prefix org-openroadm-common-optical-channel-types; revision-date 2018-05-30; }
    import cisco-svo-common-equipment-types { prefix ccet; }
    
    organization
        "Cisco Systems, Inc.";

    contact
        "Cisco Systems, Inc. Customer Service Postal: 170 West Tasman
        Drive San Jose, CA 95134 Tel: +1 800 553-NETS E-mail: cs-yang@cisco.com";

    description " Cisco Common Action Parameters groupings";

    revision 2020-12-04 { 
       description "Model version for SVO Release 12.1.0 "; 
       reference cisco-svo-common-action-param-grp.yang; 
    }
 
 
	
    grouping raw-power-data-grp {
    	description "Raw Power Data for OTS Interfaces with OCM capability";
	    list power-data {
	        key "frequency";
	        description "List of raw power data";
	        leaf frequency {
	            type org-openroadm-common-optical-channel-types:frequency-THz;
	            mandatory true;
	            description "slice begin frequency [THz]";
	        }
	        leaf optical-power {
	            type cct:dbm-t;
	            mandatory true;
	            description "Signal Optical power for a specific slice";
	        }
	    }
    }
    
    grouping unidir-raw-power-data-grp {
        description "Raw Power Data with OCM capability for a direction on a degree";
        
        leaf if-name {
            type ccet:port-name-t;
            description "The name of the OTS interface.";
        }
        
        uses raw-power-data-grp;
    }   
}
