module cisco-svo-common-if-ethernet-csmacd-grp {
  yang-version 1.1;
  namespace "http://cisco.com/yang/svo/common-if-ethernet-csmacd-grp";
  prefix ncciecg;
  
  import cisco-svo-common-if-ethernet-csmacd-oper-grp { prefix ccifethog; }
  import cisco-svo-common-interface-grp { prefix ccig;}
  import cisco-svo-common-types { prefix ct; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines Ethernet Interfaces";

    revision 2020-12-04 { 
       description "Model version for SVO Release 12.1.0 "; 
       reference cisco-svo-common-if-ethernet-csmacd-grp.yang; 
    }
 

  typedef mapping-mode-t {
    type enumeration {
      enum GFP;
      enum CBR;
    }
    description "Mapping mode for Ethernet/FC payloads";
  }
  
  grouping eth-attributes {
    leaf speed {
      type uint32;
      description
        "Set speed of the interface, unit mbps. 
         This is for ETH facility. ";
    }
    leaf fec {
      type enumeration {
        enum "NA";
        enum "Auto";
        enum "On";
        enum "Off";
      }
      description
        "Forward Error Correction Choices. ";
    }
    leaf duplex {
      type enumeration {
        enum "half" {
          value 0;
          description
            "half duplex";
        }
        enum "full" {
          value 1;
          description
            "full duplex";
        }
      }
      default "full";
      description
        "Set duplex selections.";
    }
    leaf mtu {
      type uint32 {
        range "64..9700";
      }
      default "1522";
      description
        "Set Maximum Frame Size.";
    }
    leaf mapping {
      type mapping-mode-t;
    }
    leaf auto-negotiation {
      type enumeration {
        enum "enabled" {
          value 1;
          description
            "Auto Negotiation enabled";
        }
        enum "disabled" {
          value 0;
          description
            "Auto Negotiation disabled";
        }
      }
      default "disabled";
      description
        "Set Auto Negotiation: Enabled/Disabled.";
    }

    leaf squelch-mode {
      type ct:squelch-ethernet-t;
      default "Squelch";
    }

    leaf squelch-hold-off-time {
      type ct:squelch-hold-off-time-t;
      default "Disable";
    }
  }

  grouping ethernet-csmacd-grp {
    container ethernet {
      description
        "Ethernet Interfaces";
      uses eth-attributes;
      uses ccifethog:eth-oper-attributes;
      uses ccig:maintenance-loopback;
    }
  }
}
