module cisco-svo-common-otdr-grp {
    yang-version 1.1;
    namespace "http://cisco.com/yang/svo/common-otdr-grp";
    prefix "ccog";

    organization
        "Cisco Systems, Inc.";

    contact
        "Cisco Systems, Inc. Customer Service Postal: 170 West Tasman
        Drive San Jose, CA 95134 Tel: +1 800 553-NETS E-mail: cs-yang@cisco.com";

    description " CISCO Common Otdr Config
        yang models.";

    revision 2020-12-04 { 
       description "Model version for SVO Release 12.1.0 "; 
       reference cisco-svo-common-otdr-grp.yang; 
    }
 

   grouping otdrs-conf {
     container otdr-node-configuration {
        leaf absolute-loss-threshold {
           type decimal64 {
             fraction-digits 1;
             range "0.1..30.0";
           }
            default 2.0;
            description "Otdr loss absolute threshold:valid for all otdrs of the device";
         } 
         leaf absolute-reflection-threshold {
            type decimal64 {
            fraction-digits 1;
            range "-50.0..0.0";
          }
            default -30.0;
            description "Otdr reflection absolute threshold:valid for all otdr of the device";
         }
     }
  }



    grouping otdr-conf {
      description "Grouping for OTDR configs";
        container sector-autosector {
            description "Mode Auto";
            leaf loss-sensitivity {
                 type decimal64 {
                    fraction-digits 2;
                    range "0.40..5.00";
                 }

              default 1.50;
              description
                                "Otdr Loss Sensitivity, supported values [40 ,500] in db * 100";
            }
            leaf reflection-sensitivity {
                 type decimal64 {
                   fraction-digits 2;
                   range "-40.00..-14.00";
                 }

                default -30.00;
                description
                                "Otdr Reflection Sensitivity, supported values [-4000,-1400] in
                                units of db * 100";
            }
        }

    }
}
