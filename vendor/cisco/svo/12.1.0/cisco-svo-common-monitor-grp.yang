module cisco-svo-common-monitor-grp {
    yang-version 1.1;
    namespace "http://cisco.com/yang/svo/common-monitor-grp";
    prefix "ccmg";

    import cisco-svo-common-types { prefix cct; }
    import cisco-ncs2k-equipment-types { prefix cet; }

    organization
        "Cisco Systems, Inc.";

    contact
        "Cisco Systems, Inc. Customer Service Postal: 170 West Tasman
        Drive San Jose, CA 95134 Tel: +1 800 553-NETS E-mail: cs-yang@cisco.com";

    description " Cisco Common Monitor Config";

    revision 2020-12-04 { 
       description "Model version for SVO Release 12.1.0 "; 
       reference cisco-svo-common-monitor-grp.yang; 
    }
 
    
    grouping voltage-threshold-grp {
    	description "Chassis Voltage thresholds grouping";

      container voltage-thresholds {
    	  description "Voltage thresholds";

          leaf  extreme-high-voltage {
            type cct:vdc-th-t;
            must "(current() <= ../high-voltage)";
            config true;
            description "Extreme high voltage threshold";
         }
         leaf  high-voltage {
            type cct:vdc-th-t;
            must "current() < ../low-voltage and current() >= ../extreme-high-voltage";
            config true;
            description "high voltage threshold";
         }
         leaf  extreme-low-voltage {
            type cct:vdc-th-t;
            must "(current() >= ../low-voltage)";
            config true;
            description "Extreme low voltage threshold";
         }
         leaf  low-voltage {
            type cct:vdc-th-t;
            must "(current() <= ../extreme-low-voltage) and (current() > ../high-voltage)";
            config true;
            description "low voltage threshold";
        }
      }
    }

    grouping psu-config-grp {
    	description "PSU config grouping";

      list psu-config {
        key psu-id;
        description "List of the PSU";

        leaf psu-id {
          type cct:psu-id-t;
          description "PSU identifier";
        }

        leaf psu-config-type {
          type cct:psu-config-type-t;
          description "PSU Config type";
        }
      }
    }

    grouping cooling-profile-grp {
    	description "Chassis cooling profile grouping";
         leaf cooling-profile {
            type cct:cooling-profile-t;
            config true;
            description "cooling profile";
        }
    }

    grouping monitor-config-params-grp {
    	description "Chassis monitor configuration parameters grouping";

      uses voltage-threshold-grp {
        when "../chassis-type = 'cet:NCS2006-ANSI' or ../chassis-type = 'cet:NCS2006-ETSI'";
      }
      uses psu-config-grp {
        when "../chassis-type = 'cet:NCS2015-ANSI' or ../chassis-type = 'cet:NCS2015-ETSI'";
      }
    }
    
}
