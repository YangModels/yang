module cisco-svo-common-interface-types {
  yang-version 1.1;
  namespace "http://cisco.com/yang/svo/common-interface-types";
  prefix "ccit";

  import org-openroadm-interfaces { prefix or-if; revision-date 2018-09-28; }

  organization
      "Cisco Systems, Inc.";

  contact
      "Cisco Systems, Inc. Customer Service Postal: 170 West Tasman
      Drive San Jose, CA 95134 Tel: +1 800 553-NETS E-mail: cs-yang@cisco.com";

  description "Cisco Common Interface Config Types";

    revision 2020-12-04 { 
       description "Model version for SVO Release 12.1.0 "; 
       reference cisco-svo-common-interface-types.yang; 
    }
 

  identity oscCommunicationChannel {
    base or-if:interface-type;
    description "Osc Communication channel";
  }

  identity udcCommunicationChannel {
    base or-if:interface-type;
    description "Udc Communication channel";
  }
  
  
}
