module cisco-svo-common-interface-grp {
    yang-version 1.1;
    namespace "http://cisco.com/yang/svo/common-interface-grp";
    prefix "ccig";
    
    import ietf-inet-types { prefix inet; }
    import cisco-svo-common-types { prefix cct; }    
    import cisco-svo-common-base-opt-grp { prefix ccbog; }


    organization
        "Cisco Systems, Inc.";

    contact
        "Cisco Systems, Inc. Customer Service Postal: 170 West Tasman
        Drive San Jose, CA 95134 Tel: +1 800 553-NETS E-mail: cs-yang@cisco.com";

    description " Cisco Common Interface Config group";

    revision 2020-12-04 { 
       description "Model version for SVO Release 12.1.0 "; 
       reference cisco-svo-common-interface-grp.yang; 
    }
 

    grouping interface-common-config-grp {
    	description "Interface common configuration paramters grouping";
        leaf description {
            type string;
            description "A textual description of the interface.";
        }

        leaf admin-state {
            type cct:admin-state-t;
            description "Admin State";
        }

        leaf alias {
            type string {
              length "0..80";
            }
            description "Interface alias";
        }

        leaf circuit-id {
            type string {
                length "0..45";
            }
            description "circuit identifier/user label, can be used in alarm correlation and/or connection management ";
        }
    }

    
    grouping optical-transport-config-params-grp {
    	description "OTS Interface configuration parameters grouping";
    	
        leaf optical-psd-setpoint {
        	type cct:power-spectral-density-t;
        	description "Optical power setpoint expressed as Power Spectral Density"; 
        }
    	    	
    	container optical-power-thresholds {
            uses ccbog:power-failure-low-threshold-grp;
            description "Optical signal power thresholds";
        }

        container osc-power-thresholds {
            uses ccbog:power-failure-low-threshold-grp;
            description "Service Channel power thresholds";
        }
    	    	
        leaf attenuator {
            type cct:attenuator-t;
            description "Attenuator to be set on an optical inferface";
        }

    }
 
    grouping variable-optical-attenuator-config-param-grp {
        leaf attenuation-setpoint {
            type cct:attenuation-t;
            description "Attenuation setpoint for the Variable Optical Attenuator (VOA)";
        }
        
        leaf attenuation-offset {
            type cct:attenuation-t;
            description "Attenuation offset for the Variable Optical Attenuator (VOA) 
                        - used to manually tweak the VOA when controlled based on optical psd setpoint";
        }       
			
	    description "Configuration for the internal Variable Optical Attenuator (VOA); 
			         the interface itself is the output of the VOA";
    }

    typedef loopback-type-t {
        type enumeration {
            enum "Disabled" {
                description "Loopback Disabled. No loopback";
            }
            enum "Terminal" {
                description "Loopback in the terminal direction. It's an Inward loopback and continue";
            }
            enum "Facility" {
                description "Loopback in the facility direction. It's a Line loopback and continue";
            }
            enum "Terminal-Drop" {
                description "Loopback in the terminal direction. It's an Inward loopback and drop";
            }
            enum "Facility-Drop" {
                description "Loopback in the facility direction. It's a Line loopback and drop";
            }
        }
        description "Loopback type (or direction).";
    }    
        
	grouping maintenance-loopback {
      container maint-loopback {
        leaf loop-type {
          type loopback-type-t;
          default "Disabled";
          description
            "Set Loopback type (or direction).";
        }
      }
    }
	
    grouping gcc-config-grp {
        description "GCC Interface config data grouping";

        container gcc {
          description "GCC Interface definitions";
            leaf channel {
                type cct:gcc-channel-t;
                mandatory true;
                description "Gcc channel type";
            }

            leaf speed {
                type uint32;
                units Kbps;
                mandatory true;
                description "Gcc data rate espressed in Kbps";
            }

            leaf ospf-enable {
                type boolean;
                default true;
                description "OSPF enable flag";
            }

            leaf foreign-ip {
                type inet:ip-address;
                description "Ip address of foreign node";
            }
        }
    }
    
}
