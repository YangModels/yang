/*
* Generated by python main_svo_generator.py
* Source: alarm_dictionary
*/
submodule cisco-devices-alarm-types {

  belongs-to cisco-svo-alarm-type {
    prefix svo-al-t;
  }

  include cisco-svo-alarm-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the alarm types";
  
  revision 2020-12-04 {
    description 
      "Released as part of SVO Release 12.1.
        added alarm: ENC-CERT-EXP
        added alarm: FPGA-CRC-AUDIT
        added alarm: FPGA-DWLD-FAIL
        added alarm: FPGA-DWLD-PROGRESS
        added alarm: FPGA-EMPTY
        added alarm: FPGA-VER-MISMATCH
        added alarm: LOAM
        added alarm: LOBL
        added alarm: LOCALFECDEGSER
        added alarm: LOL
        added alarm: PEER-CSF
        added alarm: TRUNK-PAYLOAD-MISM
      ";
  }

  revision 2019-10-10 {
    description "Initial revision";
    reference cisco-devices-alarm-types.yang;
  }


  identity ACT-SOFT-VERIF-FAIL {
    description "Active Volume Software Signature Verification Failed";
    base svo-al-t:svo-alarm-type;
  }

  identity ADD-OPWR-HDEG {
    description "Port Add Power Degrade High";
    base svo-al-t:svo-alarm-type;
  }

  identity ADD-OPWR-HFAIL {
    description "Port Add Power Fail High";
    base svo-al-t:svo-alarm-type;
  }

  identity ADD-OPWR-LDEG {
    description "Port Add Power Degrade Low";
    base svo-al-t:svo-alarm-type;
  }

  identity ADD-OPWR-LFAIL {
    description "Port Add Power Fail Low";
    base svo-al-t:svo-alarm-type;
  }

  identity AIS {
    description "Alarm Indication Signal";
    base svo-al-t:svo-alarm-type;
  }

  identity AIS-L {
    description "Alarm Indication Signal Line";
    base svo-al-t:svo-alarm-type;
  }

  identity ALS {
    description "Automatic Laser Shutdown";
    base svo-al-t:svo-alarm-type;
  }

  identity ALS-DISABLED {
    description "Auto Laser Shutdown Disabled";
    base svo-al-t:svo-alarm-type;
  }

  identity AMPLI-INIT {
    description "Optical Amplifier Initialization";
    base svo-al-t:svo-alarm-type;
  }

  identity APC-CORR-SKIPPED {
    description "Automatic Power Control Correction Skipped";
    base svo-al-t:svo-alarm-type;
  }

  identity APC-DISABLED {
    description "Automatic Power Control Disabled";
    base svo-al-t:svo-alarm-type;
  }

  identity APC-END {
    description "Manual Requested Automatic Power Control run Completed";
    base svo-al-t:svo-alarm-type;
  }

  identity APC-OUT-OF-RANGE {
    description "APC Cannot Set Value Due To Range Limits";
    base svo-al-t:svo-alarm-type;
  }

  identity APC-WRONG-GAIN {
    description "APC Wrong Gain Set Point";
    base svo-al-t:svo-alarm-type;
  }

  identity APS-NO-RESPONSE {
    description "APS Signal Mismatch";
    base svo-al-t:svo-alarm-type;
  }

  identity APS-PROV-MISM {
    description "APS Protection Type Mismatch";
    base svo-al-t:svo-alarm-type;
  }

  identity AS-CMD {
    description "Alarms Suppressed By User Command";
    base svo-al-t:svo-alarm-type;
  }

  identity AS-MT {
    description "Alarms Suppressed For Maintenance";
    base svo-al-t:svo-alarm-type;
  }

  identity AUD-LOG-LOSS {
    description "Audit Log 100 Percent Full - Oldest records will be lost";
    base svo-al-t:svo-alarm-type;
  }

  identity AUD-LOG-LOW {
    description "Audit Log 80 Percent Full";
    base svo-al-t:svo-alarm-type;
  }

  identity AUTH-EC {
    description "Payload Authetication Error Count";
    base svo-al-t:svo-alarm-type;
  }

  identity AUTOLSROFF {
    description "Automatic Laser Shutoff Due To High Temperature";
    base svo-al-t:svo-alarm-type;
  }

  identity AUTORESET {
    description "Automatic System Reset";
    base svo-al-t:svo-alarm-type;
  }

  identity AWG-DEG {
    description "AWG Temperature Degrade";
    base svo-al-t:svo-alarm-type;
  }

  identity AWG-FAIL {
    description "AWG Temperature Failure";
    base svo-al-t:svo-alarm-type;
  }

  identity AWG-OVERTEMP {
    description "AWG Over-Temperature";
    base svo-al-t:svo-alarm-type;
  }

  identity AWG-WARM-UP {
    description "AWG Warm Up";
    base svo-al-t:svo-alarm-type;
  }

  identity B-AUTH-EC {
    description "Backward Auth Error Count";
    base svo-al-t:svo-alarm-type;
  }

  identity BAD-DB-DETECTED {
    description "Bad Database Detected And Database Load Failed";
    base svo-al-t:svo-alarm-type;
  }

  identity BAT-FAIL {
    description "Battery Failure";
    base svo-al-t:svo-alarm-type;
  }

  identity BDI {
    description "Backward Defect Indication";
    base svo-al-t:svo-alarm-type;
  }

  identity BERT-ENBL {
    description "BERT Enabled";
    base svo-al-t:svo-alarm-type;
  }

  identity BERT-SYNC-FAIL {
    description "BERT Synchronization Status Failed";
    base svo-al-t:svo-alarm-type;
  }

  identity BKUPMEMP {
    description "Primary Non-Volatile Backup Memory Failure";
    base svo-al-t:svo-alarm-type;
  }

  identity BP-LPBKFACILITY {
    description "Back-panel Facility Loopback";
    base svo-al-t:svo-alarm-type;
  }

  identity BP-LPBKTERMINAL {
    description "Back-panel Terminal Loopback";
    base svo-al-t:svo-alarm-type;
  }

  identity CANNOT-BE-EQUALIZED {
    description "Incoming signal cannot be equalized";
    base svo-al-t:svo-alarm-type;
  }

  identity CARD-UNREACHABLE {
    description "RemoteCard Not Reachable For Key Exchange. Retrying ...";
    base svo-al-t:svo-alarm-type;
  }

  identity CARLOSS {
    description "Carrier Loss On The LAN";
    base svo-al-t:svo-alarm-type;
  }

  identity CASETEMP-DEG {
    description "Case Temperature Degrade";
    base svo-al-t:svo-alarm-type;
  }

  identity CD {
    description "Chromatic Dispersion";
    base svo-al-t:svo-alarm-type;
  }

  identity CHAN-PWR-THRESHOLD-CHECK {
    description "Channel Power would fall below threshold value";
    base svo-al-t:svo-alarm-type;
  }

  identity CLDRESTART {
    description "Cold Restart";
    base svo-al-t:svo-alarm-type;
  }

  identity COMM-FAIL {
    description "Plug-in Module Communication Failure";
    base svo-al-t:svo-alarm-type;
  }

  identity COMP-CARD-MISSING {
    description "Companion Card Missing";
    base svo-al-t:svo-alarm-type;
  }

  identity CONTBUS-A-18 {
    description "Controller Card A To DCC A Processor Communication Failure";
    base svo-al-t:svo-alarm-type;
  }

  identity CONTBUS-B-18 {
    description "Controller Card B To DCC B Processor Communication Failure";
    base svo-al-t:svo-alarm-type;
  }

  identity CONTBUS-CLK-A {
    description "Clock Bus Failure - Shelf Controller A";
    base svo-al-t:svo-alarm-type;
  }

  identity CONTBUS-CLK-B {
    description "Clock Bus Failure - Shelf Controller B";
    base svo-al-t:svo-alarm-type;
  }

  identity CONTBUS-DISABLED {
    description "Slot Commmunication Disabled";
    base svo-al-t:svo-alarm-type;
  }

  identity CONTBUS-IO-A {
    description "Peer To Peer Slot Communication Failure";
    base svo-al-t:svo-alarm-type;
  }

  identity CONTBUS-IO-B {
    description "Peer To Peer Slot Communication Failure";
    base svo-al-t:svo-alarm-type;
  }

  identity COOL-MISM {
    description "Cooling Profile Mismatch";
    base svo-al-t:svo-alarm-type;
  }

  identity CPP-INCAPABLE {
    description "Card/Ports Unable To Provide Protection";
    base svo-al-t:svo-alarm-type;
  }

  identity DATAFLT {
    description "Software Fault - Data Integrity Fault";
    base svo-al-t:svo-alarm-type;
  }

  identity DBOSYNC {
    description "Standby Database Out of Sync";
    base svo-al-t:svo-alarm-type;
  }

  identity DCU-LOSS-FAIL {
    description "DCU Loss Failure";
    base svo-al-t:svo-alarm-type;
  }

  identity DISK-SPACE-FULL {
    description "No Space Left On Device";
    base svo-al-t:svo-alarm-type;
  }

  identity DISK-SPACE-LOW {
    description "Low Disk Space Remaining On Device";
    base svo-al-t:svo-alarm-type;
  }

  identity DSP-COMM-FAIL {
    description "DSP Communication Failure";
    base svo-al-t:svo-alarm-type;
  }

  identity DSP-FAIL {
    description "DSP Failure";
    base svo-al-t:svo-alarm-type;
  }

  identity DUP-IPADDR {
    description "IP Address A1ready In Use Within The Same DCC Area";
    base svo-al-t:svo-alarm-type;
  }

  identity DUP-NODENAME {
    description "Node name already in use within the same DCC Area";
    base svo-al-t:svo-alarm-type;
  }

  identity DUP-SHELF-ID {
    description "Duplicated Shelf Identifier";
    base svo-al-t:svo-alarm-type;
  }

  identity EHIBATVG {
    description "Extreme High Volt";
    base svo-al-t:svo-alarm-type;
  }

  identity ELWBATVG {
    description "Extreme Low Volt";
    base svo-al-t:svo-alarm-type;
  }

  identity ENC-CERT-EXP {
    description "MIC cert is expired switch to LSC";
    base svo-al-t:svo-alarm-type;
  }

  identity EOC {
    description "SDCC Termination Failure";
    base svo-al-t:svo-alarm-type;
  }

  identity EOC-E {
    description "Ethernet OSC Termination Failure";
    base svo-al-t:svo-alarm-type;
  }

  identity EPROM-SUDI-SN-MISMATCH {
    description "Card Serial Number and Certificate Serial Number Mismatch";
    base svo-al-t:svo-alarm-type;
  }

  identity EQPT {
    description "Equipment Failure";
    base svo-al-t:svo-alarm-type;
  }

  identity EQPT-DEGRADE {
    description "Equipment Degrade";
    base svo-al-t:svo-alarm-type;
  }

  identity EQPT-DIAG {
    description "Diagnostic Failure";
    base svo-al-t:svo-alarm-type;
  }

  identity EQPT-FAIL {
    description "Board Failure";
    base svo-al-t:svo-alarm-type;
  }

  identity EQPT-FPGA-IMAGE-AVAILABLE {
    description "Different FPGA Image Available";
    base svo-al-t:svo-alarm-type;
  }

  identity EQPT-MISS {
    description "Replaceable Equipment/Unit is Missing";
    base svo-al-t:svo-alarm-type;
  }

  identity ETH-LINKLOSS {
    description "Rear Panel Ethernet Link Removed";
    base svo-al-t:svo-alarm-type;
  }

  identity EVAL-LIC {
    description "Evaluation License Is In Use";
    base svo-al-t:svo-alarm-type;
  }

  identity EXT {
    description "Failure Detected External To The NE";
    base svo-al-t:svo-alarm-type;
  }

  identity FAILTOSW {
    description "Failure To Switch To Protection";
    base svo-al-t:svo-alarm-type;
  }

  identity FAN {
    description "Fan Failure";
    base svo-al-t:svo-alarm-type;
  }

  identity FANDEGRADE {
    description "Partial Fan Failure";
    base svo-al-t:svo-alarm-type;
  }

  identity FC-DE-NES {
    description "Fibre Channel Distance Extension Function Not Established";
    base svo-al-t:svo-alarm-type;
  }

  identity FC-NO-CREDITS {
    description "Fibre Channel Distance Extension Credit Starvation";
    base svo-al-t:svo-alarm-type;
  }

  identity FDI {
    description "Forward Defect Indication";
    base svo-al-t:svo-alarm-type;
  }

  identity FEED-MISMATCH {
    description "Feed Not Available/Improper Connection";
    base svo-al-t:svo-alarm-type;
  }

  identity FIBERTEMP-DEG {
    description "Fiber Temperature Degrade";
    base svo-al-t:svo-alarm-type;
  }

  identity FIRMWARE-UPG {
    description "Firmware Upgrade In Progress";
    base svo-al-t:svo-alarm-type;
  }

  identity FIRMWARE-UPG-FAIL {
    description "Firmware Upgrade Failed";
    base svo-al-t:svo-alarm-type;
  }

  identity FOIC-GIDM {
    description "FOIC Group ID mismatch defect";
    base svo-al-t:svo-alarm-type;
  }

  identity FOIC-LDI-LD {
    description "FOIC Link Degrade indicator - Local Degrade";
    base svo-al-t:svo-alarm-type;
  }

  identity FOIC-LDI-RD {
    description "FOIC Link Degrade indicator- Remote Degrade";
    base svo-al-t:svo-alarm-type;
  }

  identity FOIC-LOF-LOM {
    description "FOIC Loss of Frame loss of Multiframe";
    base svo-al-t:svo-alarm-type;
  }

  identity FOIC-LOL {
    description "FOIC Loss of Lock Detect";
    base svo-al-t:svo-alarm-type;
  }

  identity FOIC-LOM {
    description "FOIC Loss of Multiframe Indication";
    base svo-al-t:svo-alarm-type;
  }

  identity FOIC-PMM {
    description "FOIC Phy Map mismatch Alarm";
    base svo-al-t:svo-alarm-type;
  }

  identity FOIC-RPF {
    description "FOIC Remote Phy Fault Detect";
    base svo-al-t:svo-alarm-type;
  }

  identity FPGA-CRC-AUDIT {
    description "Fpga Crc Audit Fail";
    base svo-al-t:svo-alarm-type;
  }

  identity FPGA-DWLD-FAIL {
    description "Fpga Download Fail";
    base svo-al-t:svo-alarm-type;
  }

  identity FPGA-DWLD-PROGRESS {
    description "Fpga Download Progress";
    base svo-al-t:svo-alarm-type;
  }

  identity FPGA-EMPTY {
    description "Fpga Empty";
    base svo-al-t:svo-alarm-type;
  }

  identity FPGA-UPGRADE-FAILED {
    description "FPGA Upgrade fail";
    base svo-al-t:svo-alarm-type;
  }

  identity FPGA-VER-MISMATCH {
    description "Fpga Version Mismatch";
    base svo-al-t:svo-alarm-type;
  }

  identity FRCDSWTOINT {
    description "Forced Switch To Internal Clock";
    base svo-al-t:svo-alarm-type;
  }

  identity FRCDSWTOPRI {
    description "Forced Switch To Primary Reference";
    base svo-al-t:svo-alarm-type;
  }

  identity FRCDSWTOSEC {
    description "Forced Switch To Second Reference";
    base svo-al-t:svo-alarm-type;
  }

  identity FRCDSWTOTHIRD {
    description "Forced Switch To Third Reference";
    base svo-al-t:svo-alarm-type;
  }

  identity FRNGSYNC {
    description "Free Running Synchronization Mode";
    base svo-al-t:svo-alarm-type;
  }

  identity FTA-MISMATCH {
    description "FanTray Mismatch";
    base svo-al-t:svo-alarm-type;
  }

  identity GAIN-HDEG {
    description "Optical Amplifier Gain Degrade High";
    base svo-al-t:svo-alarm-type;
  }

  identity GAIN-HFAIL {
    description "Optical Amplifier Gain Failure High";
    base svo-al-t:svo-alarm-type;
  }

  identity GAIN-LDEG {
    description "Optical Amplifier Gain Degrade Low";
    base svo-al-t:svo-alarm-type;
  }

  identity GAIN-LFAIL {
    description "Optical Amplifier Gain Failure Low";
    base svo-al-t:svo-alarm-type;
  }

  identity GAIN-NEAR-LIMIT {
    description "Amplifier Gain is near its limit";
    base svo-al-t:svo-alarm-type;
  }

  identity GCC-EOC {
    description "GCC Termination Failure";
    base svo-al-t:svo-alarm-type;
  }

  identity GE-OOSYNC {
    description "GigaBit Ethernet Out of Sync";
    base svo-al-t:svo-alarm-type;
  }

  identity GFP-CSF {
    description "GFP Client Signal Fail Detected";
    base svo-al-t:svo-alarm-type;
  }

  identity GFP-CSF-SIGLOSS {
    description "GFP Client Signal Fail Detected Due To Sigloss";
    base svo-al-t:svo-alarm-type;
  }

  identity GFP-CSF-SYNCLOSS {
    description "GFP Client Signal Fail Detected Due To Syncloss";
    base svo-al-t:svo-alarm-type;
  }

  identity GFP-DE-MISMATCH {
    description "GFP Fibre Channel Distance Extension Mismatch";
    base svo-al-t:svo-alarm-type;
  }

  identity GFP-EX-MISMATCH {
    description "GFP Extension Header Mismatch";
    base svo-al-t:svo-alarm-type;
  }

  identity GFP-LFD {
    description "GFP Loss of Frame Delineation";
    base svo-al-t:svo-alarm-type;
  }

  identity GFP-NO-BUFFERS {
    description "GFP Fibre Channel Distance Extension Buffer Starvation";
    base svo-al-t:svo-alarm-type;
  }

  identity GFP-UP-MISMATCH {
    description "GFP User Payload Mismatch";
    base svo-al-t:svo-alarm-type;
  }

  identity HELLO {
    description "OSPF Hello Fail";
    base svo-al-t:svo-alarm-type;
  }

  identity HI-BER {
    description "High Bit Error Rate";
    base svo-al-t:svo-alarm-type;
  }

  identity HI-CCVOLT {
    description "Composite Clock High Line Voltage";
    base svo-al-t:svo-alarm-type;
  }

  identity HI-LASERBIAS {
    description "Equipment High Laser Bias";
    base svo-al-t:svo-alarm-type;
  }

  identity HI-LASERTEMP {
    description "Equipment High Laser Temp";
    base svo-al-t:svo-alarm-type;
  }

  identity HI-RXPOWER {
    description "Facility High Rx power";
    base svo-al-t:svo-alarm-type;
  }

  identity HI-TXPOWER {
    description "Equipment High Tx power";
    base svo-al-t:svo-alarm-type;
  }

  identity HIBATVG {
    description "High Volt";
    base svo-al-t:svo-alarm-type;
  }

  identity HITEMP {
    description "High Temperature";
    base svo-al-t:svo-alarm-type;
  }

  identity HLDOVRSYNC {
    description "Holdover Synchronization Mode";
    base svo-al-t:svo-alarm-type;
  }

  identity I-HITEMP {
    description "Industrial High Temperature";
    base svo-al-t:svo-alarm-type;
  }

  identity IDLE {
    description "Idle Signal Condition";
    base svo-al-t:svo-alarm-type;
  }

  identity IMPROPRMVL {
    description "Improper Removal";
    base svo-al-t:svo-alarm-type;
  }

  identity IMPROPRMVL-FS {
    description "Improper removal of Fiber Shuffle";
    base svo-al-t:svo-alarm-type;
  }

  identity INTRUSION-PSWD {
    description "Security Intrusion Attempt Detected - See Audit Log";
    base svo-al-t:svo-alarm-type;
  }

  identity INVALID-SYSDB {
    description "Invalid System DB";
    base svo-al-t:svo-alarm-type;
  }

  identity INVMACADR {
    description "Invalid MAC Address";
    base svo-al-t:svo-alarm-type;
  }

  identity IPC-LASER-FAIL {
    description "Ipc Laser failure";
    base svo-al-t:svo-alarm-type;
  }

  identity IPC-LOOPBACK-MISS {
    description "Patchcords Verification Loopback Missing";
    base svo-al-t:svo-alarm-type;
  }

  identity IPC-VERIFICATION-DEGRADE {
    description "Patchcords Verification Degrade";
    base svo-al-t:svo-alarm-type;
  }

  identity IPC-VERIFICATION-FAIL {
    description "Patchcords Verification Failure";
    base svo-al-t:svo-alarm-type;
  }

  identity IPC-VERIFICATION-RUNNING {
    description "Patchcords Verification Running";
    base svo-al-t:svo-alarm-type;
  }

  identity KEY-EX-FAIL {
    description "Primary Key Exchange Failed";
    base svo-al-t:svo-alarm-type;
  }

  identity KEY-WRITE-FAIL {
    description "Key Program On FPGA Failed";
    base svo-al-t:svo-alarm-type;
  }

  identity LAN-POL-REV {
    description "Lan Connection Polarity Reversed";
    base svo-al-t:svo-alarm-type;
  }

  identity LASER-APR {
    description "Laser Auto Power Reduction";
    base svo-al-t:svo-alarm-type;
  }

  identity LASERBIAS-DEG {
    description "Laser Bias Degrade";
    base svo-al-t:svo-alarm-type;
  }

  identity LASERBIAS-FAIL {
    description "Laser Bias Failure";
    base svo-al-t:svo-alarm-type;
  }

  identity LASEREOL {
    description "Laser Approaching End of Life";
    base svo-al-t:svo-alarm-type;
  }

  identity LASERTEMP-DEG {
    description "Laser Temperature Degrade";
    base svo-al-t:svo-alarm-type;
  }

  identity LIC-EXPIRED {
    description "License Expired";
    base svo-al-t:svo-alarm-type;
  }

  identity LIC-EXPIRING-SHORTLY {
    description "License Will Expire Within 24 Hours";
    base svo-al-t:svo-alarm-type;
  }

  identity LIC-EXPIRING-SOON {
    description "License Will Expire At Any Time After 1 Day But Before 14 Days";
    base svo-al-t:svo-alarm-type;
  }

  identity LIC-MISSING {
    description "License Is Missing";
    base svo-al-t:svo-alarm-type;
  }

  identity LINK-BROKEN {
    description "Ha link Broken";
    base svo-al-t:svo-alarm-type;
  }

  identity LO-LASERBIAS {
    description "Equipment Low Laser Bias";
    base svo-al-t:svo-alarm-type;
  }

  identity LO-LASERTEMP {
    description "Equipment Low Laser Temp";
    base svo-al-t:svo-alarm-type;
  }

  identity LO-RXPOWER {
    description "Facility Low Rx power";
    base svo-al-t:svo-alarm-type;
  }

  identity LO-TXPOWER {
    description "Equipment Low Tx power";
    base svo-al-t:svo-alarm-type;
  }

  identity LOA {
    description "Loss of Alignment";
    base svo-al-t:svo-alarm-type;
  }

  identity LOAM {
    description "DWDM Loss of Alignment Marker  -";
    base svo-al-t:svo-alarm-type;
  }

  identity LOBL {
    description "DWDM Loss of block lock  -";
    base svo-al-t:svo-alarm-type;
  }

  identity LOCAL-CERT-CHAIN-VERIFICATION-FAILED {
    description "Local cert chain verification failed";
    base svo-al-t:svo-alarm-type;
  }

  identity LOCAL-CERT-EXPIRED {
    description "Local certificate expired";
    base svo-al-t:svo-alarm-type;
  }

  identity LOCAL-CERT-EXPIRING-WITHIN-30-DAYS {
    description "Local cert expiring within 30 days";
    base svo-al-t:svo-alarm-type;
  }

  identity LOCAL-CERT-ISSUED-FOR-FUTURE-DATE {
    description "Local cert issued for future date";
    base svo-al-t:svo-alarm-type;
  }

  identity LOCAL-FAULT {
    description "Local Fault";
    base svo-al-t:svo-alarm-type;
  }

  identity LOCAL-SUDI-CERT-VERIFICATION-FAILED {
    description "Local sudi cert verification failed";
    base svo-al-t:svo-alarm-type;
  }

  identity LOCALFECDEGSER {
    description "DWDM Local Degrade of SER status  -";
    base svo-al-t:svo-alarm-type;
  }

  identity LOCKOUT-REQ {
    description "Lockout Switch Request";
    base svo-al-t:svo-alarm-type;
  }

  identity LOF {
    description "Loss Of Frame";
    base svo-al-t:svo-alarm-type;
  }

  identity LOL {
    description "DWDM Loss of Lock of PCS order set  -";
    base svo-al-t:svo-alarm-type;
  }

  identity LOM {
    description "Loss of Multi-Frame";
    base svo-al-t:svo-alarm-type;
  }

  identity LOS {
    description "Loss Of Signal";
    base svo-al-t:svo-alarm-type;
  }

  identity LOS-D {
    description "Loss Of DFB Signal";
    base svo-al-t:svo-alarm-type;
  }

  identity LOS-O {
    description "Incoming Overhead Signal Absent";
    base svo-al-t:svo-alarm-type;
  }

  identity LOS-P {
    description "Incoming Payload Signal Absent";
    base svo-al-t:svo-alarm-type;
  }

  identity LOS-RAMAN {
    description "Loss Of Raman Signal";
    base svo-al-t:svo-alarm-type;
  }

  identity LPBKFACILITY {
    description "Facility Loopback";
    base svo-al-t:svo-alarm-type;
  }

  identity LPBKTERMINAL {
    description "Terminal Loopback";
    base svo-al-t:svo-alarm-type;
  }

  identity LSC-NOT-PRESENT-MIC-IN-USE {
    description "LSC not present using MIC";
    base svo-al-t:svo-alarm-type;
  }

  identity LWBATVG {
    description "Low Volt";
    base svo-al-t:svo-alarm-type;
  }

  identity MAN-LASER-RESTART {
    description "Manual Laser Restart";
    base svo-al-t:svo-alarm-type;
  }

  identity MAN-REQ {
    description "Manual Switch Request";
    base svo-al-t:svo-alarm-type;
  }

  identity MANRESET {
    description "Manual System Reset";
    base svo-al-t:svo-alarm-type;
  }

  identity MANSWTOINT {
    description "Manual Switch To Internal Clock";
    base svo-al-t:svo-alarm-type;
  }

  identity MANSWTOPRI {
    description "Manual Switch To Primary Reference";
    base svo-al-t:svo-alarm-type;
  }

  identity MANSWTOSEC {
    description "Manual Switch To Second Reference";
    base svo-al-t:svo-alarm-type;
  }

  identity MANSWTOTHIRD {
    description "Manual Switch To Third Reference";
    base svo-al-t:svo-alarm-type;
  }

  identity MAX-AUTH-LIST {
    description "Reached Max Authentication List";
    base svo-al-t:svo-alarm-type;
  }

  identity MEA {
    description "Mismatch Of Equipment And Attributes";
    base svo-al-t:svo-alarm-type;
  }

  identity MEM-GONE {
    description "Free Memory On Card Near Zero";
    base svo-al-t:svo-alarm-type;
  }

  identity MEM-LOW {
    description "Free Memory On Card Very Low";
    base svo-al-t:svo-alarm-type;
  }

  identity MFGMEM {
    description "Manufacturing Data Memory (EEPROM) Failure";
    base svo-al-t:svo-alarm-type;
  }

  identity MS-AIS {
    description "AIS - Multiplex Section - Alarm Indication Signal";
    base svo-al-t:svo-alarm-type;
  }

  identity MS-DEG {
    description "Multiplex Section - Signal Degraded";
    base svo-al-t:svo-alarm-type;
  }

  identity MS-EOC {
    description "Multiplex Section DCC Termination Failure";
    base svo-al-t:svo-alarm-type;
  }

  identity MS-EXC {
    description "Multiplex Section - Excessive Errors";
    base svo-al-t:svo-alarm-type;
  }

  identity MS-RDI {
    description "RDI - Multiplex Section - Remote Defect/Alarm Indication";
    base svo-al-t:svo-alarm-type;
  }

  identity NE-DISCONNECTED {
    description "Connection To Managed NE Lost";
    base svo-al-t:svo-alarm-type;
  }

  identity NO-SHARED-CIPHERS {
    description "Different Ciphers Used by Client and Server";
    base svo-al-t:svo-alarm-type;
  }

  identity NODE-FACTORY-MODE {
    description "Node in Factory Mode";
    base svo-al-t:svo-alarm-type;
  }

  identity NON-CISCO-PPM {
    description "Non Cisco PPM Inserted";
    base svo-al-t:svo-alarm-type;
  }

  identity NON-TRAF-AFFECT-SEC-UPG-REQUIRED {
    description "Non Traffic Affecting Security Upgrade Required";
    base svo-al-t:svo-alarm-type;
  }

  identity OCHNC-INC {
    description "Optical Channel Incomplete";
    base svo-al-t:svo-alarm-type;
  }

  identity OCHNC-MT {
    description "OCHNC Maintenance";
    base svo-al-t:svo-alarm-type;
  }

  identity OCHTERM-INC {
    description "Optical Termination Incomplete";
    base svo-al-t:svo-alarm-type;
  }

  identity ODUK-1-AIS-PM {
    description "ODUk1 Alarm Indication Signal";
    base svo-al-t:svo-alarm-type;
  }

  identity ODUK-2-AIS-PM {
    description "ODUk2 Alarm Indication Signal";
    base svo-al-t:svo-alarm-type;
  }

  identity ODUK-3-AIS-PM {
    description "ODUk3 Alarm Indication Signal";
    base svo-al-t:svo-alarm-type;
  }

  identity ODUK-4-AIS-PM {
    description "ODUk4 Alarm Indication Signal";
    base svo-al-t:svo-alarm-type;
  }

  identity ODUK-AIS-PM {
    description "ODUk: PM Alarm Indication Signal";
    base svo-al-t:svo-alarm-type;
  }

  identity ODUK-BDI-PM {
    description "ODUk: PM Backward Defect Indication";
    base svo-al-t:svo-alarm-type;
  }

  identity ODUK-LCK-PM {
    description "ODUk: Locked Defect - PM";
    base svo-al-t:svo-alarm-type;
  }

  identity ODUK-OCI-PM {
    description "ODUk: Open Connection Indication";
    base svo-al-t:svo-alarm-type;
  }

  identity ODUK-SD-PM {
    description "ODUk: Signal Degrade";
    base svo-al-t:svo-alarm-type;
  }

  identity ODUK-SF-PM {
    description "ODUk: Signal Failure";
    base svo-al-t:svo-alarm-type;
  }

  identity ODUK-TIM-PM {
    description "ODUk: Trail Trace Identifier Mismatch";
    base svo-al-t:svo-alarm-type;
  }

  identity OPEN-SLOT {
    description "Open Slot(s)";
    base svo-al-t:svo-alarm-type;
  }

  identity OPU-CSF {
    description "OPU Client Signal Fail";
    base svo-al-t:svo-alarm-type;
  }

  identity OPWR-HDEG {
    description "Optical Power Degrade High";
    base svo-al-t:svo-alarm-type;
  }

  identity OPWR-HFAIL {
    description "Optical Power Failure High";
    base svo-al-t:svo-alarm-type;
  }

  identity OPWR-LDEG {
    description "Optical Power Degrade Low";
    base svo-al-t:svo-alarm-type;
  }

  identity OPWR-LFAIL {
    description "Optical Power Failure Low";
    base svo-al-t:svo-alarm-type;
  }

  identity OSRION {
    description "Optical Safety Remote Interlock On";
    base svo-al-t:svo-alarm-type;
  }

  identity OTDR-ABSOLUTE-A-EXCEEDED-RX {
    description "Attenuation Exceeded Absolute Threshold - RX Direction";
    base svo-al-t:svo-alarm-type;
  }

  identity OTDR-ABSOLUTE-A-EXCEEDED-TX {
    description "Attenuation Exceeded Absolute Threshold - TX Direction";
    base svo-al-t:svo-alarm-type;
  }

  identity OTDR-ABSOLUTE-R-EXCEEDED-RX {
    description "Reflectance Exceeded Absolute Threshold - RX Direction";
    base svo-al-t:svo-alarm-type;
  }

  identity OTDR-ABSOLUTE-R-EXCEEDED-TX {
    description "Reflectance Exceeded Absolute Threshold - TX Direction";
    base svo-al-t:svo-alarm-type;
  }

  identity OTDR-BASELINE-A-EXCEEDED-RX {
    description "Attenuation Exceeded Baseline Threshold - RX Direction";
    base svo-al-t:svo-alarm-type;
  }

  identity OTDR-BASELINE-A-EXCEEDED-TX {
    description "Attenuation Exceeded Baseline Threshold - TX Direction";
    base svo-al-t:svo-alarm-type;
  }

  identity OTDR-BASELINE-R-EXCEEDED-RX {
    description "Reflectance Exceeded Baseline Threshold - RX Direction";
    base svo-al-t:svo-alarm-type;
  }

  identity OTDR-BASELINE-R-EXCEEDED-TX {
    description "Reflectance Exceeded Baseline Threshold - TX Direction";
    base svo-al-t:svo-alarm-type;
  }

  identity OTDR-FAST-FAR-END-IN-PROGRESS {
    description "OTDR Fast Scan Is In Progress On Remote Side";
    base svo-al-t:svo-alarm-type;
  }

  identity OTDR-FAST-SCAN-IN-PROGRESS-RX {
    description "OTDR Fast Scan Is In Progress - RX Direction";
    base svo-al-t:svo-alarm-type;
  }

  identity OTDR-FAST-SCAN-IN-PROGRESS-TX {
    description "OTDR Fast Scan Is In Progress - TX Direction";
    base svo-al-t:svo-alarm-type;
  }

  identity OTDR-FIBER-END-NOT-DETECTED-RX {
    description "Fiber End Not Detected - RX Direction";
    base svo-al-t:svo-alarm-type;
  }

  identity OTDR-FIBER-END-NOT-DETECTED-TX {
    description "Fiber End Not Detected - TX Direction";
    base svo-al-t:svo-alarm-type;
  }

  identity OTDR-HYBRID-FAR-END-IN-PROGRESS {
    description "OTDR Hybrid Scan Is In Progress On Remote Side";
    base svo-al-t:svo-alarm-type;
  }

  identity OTDR-HYBRID-SCAN-IN-PROGRESS-RX {
    description "OTDR Hybrid Scan Is In Progress - RX Direction";
    base svo-al-t:svo-alarm-type;
  }

  identity OTDR-HYBRID-SCAN-IN-PROGRESS-TX {
    description "OTDR Hybrid Scan Is In Progress - TX Direction";
    base svo-al-t:svo-alarm-type;
  }

  identity OTDR-LOSS-THR-EXCEEDED {
    description "OTDR Loss Threshold Exceeded";
    base svo-al-t:svo-alarm-type;
  }

  identity OTDR-ORL-THRESHOLD-EXCEEDED-RX {
    description "ORL Exceeded Threshold - RX Direction";
    base svo-al-t:svo-alarm-type;
  }

  identity OTDR-ORL-THRESHOLD-EXCEEDED-TX {
    description "ORL Exceeded Threshold - TX Direction";
    base svo-al-t:svo-alarm-type;
  }

  identity OTDR-ORL-TRAINING-FAILED-RX {
    description "ORL Training Failed - RX Direction";
    base svo-al-t:svo-alarm-type;
  }

  identity OTDR-ORL-TRAINING-FAILED-TX {
    description "ORL Training Failed - TX Direction";
    base svo-al-t:svo-alarm-type;
  }

  identity OTDR-ORL-TRAINING-IN-PROGRESS-RX {
    description "ORL Training Is In Progress - RX Direction";
    base svo-al-t:svo-alarm-type;
  }

  identity OTDR-ORL-TRAINING-IN-PROGRESS-TX {
    description "ORL Training Is In Progress - TX Direction";
    base svo-al-t:svo-alarm-type;
  }

  identity OTDR-OTDR-TRAINING-FAILED-RX {
    description "OTDR Training Failed - RX Direction";
    base svo-al-t:svo-alarm-type;
  }

  identity OTDR-OTDR-TRAINING-FAILED-TX {
    description "OTDR Training Failed - TX Direction";
    base svo-al-t:svo-alarm-type;
  }

  identity OTDR-SCAN-FAILED {
    description "OTDR Scan Failed";
    base svo-al-t:svo-alarm-type;
  }

  identity OTDR-SCAN-IN-PROGRESS {
    description "OTDR Scan Is In Progress";
    base svo-al-t:svo-alarm-type;
  }

  identity OTDR-SCAN-NOT-COMPLETED {
    description "OTDR Scan Not Completed";
    base svo-al-t:svo-alarm-type;
  }

  identity OTUK-AIS {
    description "OTUk: Alarm Indication Signal";
    base svo-al-t:svo-alarm-type;
  }

  identity OTUK-BDI {
    description "OTUk: SM Backward Defect Indication";
    base svo-al-t:svo-alarm-type;
  }

  identity OTUK-BIAE {
    description "OTUk: SM Backward Incoming Alignment Error";
    base svo-al-t:svo-alarm-type;
  }

  identity OTUK-IAE {
    description "OTUk: Incoming Alignment Error";
    base svo-al-t:svo-alarm-type;
  }

  identity OTUK-LOF {
    description "OTUk: Loss Of Frame";
    base svo-al-t:svo-alarm-type;
  }

  identity OTUK-SD {
    description "OTUk: Signal Degrade";
    base svo-al-t:svo-alarm-type;
  }

  identity OTUK-SF {
    description "OTUk: Signal Failure";
    base svo-al-t:svo-alarm-type;
  }

  identity OTUK-TIM {
    description "OTUk: Trail Trace Identifier Mismatch";
    base svo-al-t:svo-alarm-type;
  }

  identity OVER-TEMP-UNIT-PROT {
    description "Over Temperature Unit Protected";
    base svo-al-t:svo-alarm-type;
  }

  identity PARAM-MISM {
    description "Plug-in Module Range Settings Mismatch";
    base svo-al-t:svo-alarm-type;
  }

  identity PATCH-ACTIVATION-FAILED {
    description "Patch Activation Failed";
    base svo-al-t:svo-alarm-type;
  }

  identity PATCH-DOWNLOAD-FAILED {
    description "Patch Download Failed";
    base svo-al-t:svo-alarm-type;
  }

  identity PEER-CERT-VERIFICATION-FAILED {
    description "Peer card certificate verification failed";
    base svo-al-t:svo-alarm-type;
  }

  identity PEER-CSF {
    description "Peer Port Client Signal Fail Detected";
    base svo-al-t:svo-alarm-type;
  }

  identity PMD-DEG {
    description "PMD Degrade";
    base svo-al-t:svo-alarm-type;
  }

  identity PMI {
    description "Payload Missing Indication";
    base svo-al-t:svo-alarm-type;
  }

  identity PORT-COMM-FAIL {
    description "Module Communication Failure";
    base svo-al-t:svo-alarm-type;
  }

  identity PRBS-ENABLED {
    description "PRBS Generation Enabled";
    base svo-al-t:svo-alarm-type;
  }

  identity PROT-CONFIG-MISMATCH {
    description "Protection Card Configuration Mismatch";
    base svo-al-t:svo-alarm-type;
  }

  identity PROT-SOFT-VERIF-FAIL {
    description "Protect Volume Software Signature Verification Failed";
    base svo-al-t:svo-alarm-type;
  }

  identity PROTNA {
    description "Protection Unit Not Available";
    base svo-al-t:svo-alarm-type;
  }

  identity PROV-MISMATCH {
    description "Provisioning Mismatch";
    base svo-al-t:svo-alarm-type;
  }

  identity PTIM {
    description "Payload Type Identifier Mismatch";
    base svo-al-t:svo-alarm-type;
  }

  identity PWR {
    description "Power Failure at Connector";
    base svo-al-t:svo-alarm-type;
  }

  identity PWR-CON-LMT {
    description "Power Consumption Limit Has Crossed";
    base svo-al-t:svo-alarm-type;
  }

  identity PWR-FAIL-A {
    description "Equipment power failure at connector A";
    base svo-al-t:svo-alarm-type;
  }

  identity PWR-FAIL-B {
    description "Equipment power failure at connector B";
    base svo-al-t:svo-alarm-type;
  }

  identity PWR-FAIL-RET-A {
    description "Equipment power failure at return connector A";
    base svo-al-t:svo-alarm-type;
  }

  identity PWR-FAIL-RET-B {
    description "Equipment power failure at return connector B";
    base svo-al-t:svo-alarm-type;
  }

  identity PWR-PROT-ON {
    description "Raman Power Protection On";
    base svo-al-t:svo-alarm-type;
  }

  identity PWRRESTART {
    description "Powerfail Restart";
    base svo-al-t:svo-alarm-type;
  }

  identity RAI {
    description "Remote Alarm Indication";
    base svo-al-t:svo-alarm-type;
  }

  identity RAMAN-CALIBRATION-FAILED {
    description "Raman Calibration Failed";
    base svo-al-t:svo-alarm-type;
  }

  identity RAMAN-CALIBRATION-PENDING {
    description "Raman Calibration Pending";
    base svo-al-t:svo-alarm-type;
  }

  identity RAMAN-CALIBRATION-RUNNING {
    description "Raman Calibration Running";
    base svo-al-t:svo-alarm-type;
  }

  identity RAMAN-GAIN-NOT-REACHED {
    description "Raman Gain Not Reached";
    base svo-al-t:svo-alarm-type;
  }

  identity REMOTE-CERT-FAIL {
    description "RemoteCard Certificate Validation Failed";
    base svo-al-t:svo-alarm-type;
  }

  identity REMOTE-FAULT {
    description "Remote Fault";
    base svo-al-t:svo-alarm-type;
  }

  identity REROUTE-IN-PROG {
    description "Reroute In Progress";
    base svo-al-t:svo-alarm-type;
  }

  identity RESOURCE-ALLOC-FAIL {
    description "Resource Allocation Failed";
    base svo-al-t:svo-alarm-type;
  }

  identity RESOURCES-GONE {
    description "No More Resources Available";
    base svo-al-t:svo-alarm-type;
  }

  identity RESOURCES-LOW {
    description "Running Low On Resources";
    base svo-al-t:svo-alarm-type;
  }

  identity RESTORE-IN-PROG {
    description "Restoration in Progress";
    base svo-al-t:svo-alarm-type;
  }

  identity REVERT-IN-PROG {
    description "Revert In Progress";
    base svo-al-t:svo-alarm-type;
  }

  identity RFI {
    description "Remote Failure Indication";
    base svo-al-t:svo-alarm-type;
  }

  identity RFI-L {
    description "Remote Failure Indication Line";
    base svo-al-t:svo-alarm-type;
  }

  identity RLS {
    description "Raman Laser Shutdown";
    base svo-al-t:svo-alarm-type;
  }

  identity ROUTE-OVERFLOW {
    description "OSPF Routing Table Overflow";
    base svo-al-t:svo-alarm-type;
  }

  identity RS-EOC {
    description "Regenerator Section - DCC Termination Failure";
    base svo-al-t:svo-alarm-type;
  }

  identity RS-TIM {
    description "Regenerator Section Trace Identifier Mismatch";
    base svo-al-t:svo-alarm-type;
  }

  identity SD {
    description "Signal Degrade";
    base svo-al-t:svo-alarm-type;
  }

  identity SD-L {
    description "BER Threshold Exceeded For Signal Degrade Line";
    base svo-al-t:svo-alarm-type;
  }

  identity SENSOR-HIGH-0-6V-CPU-A {
    description "0.6V-CPU-A sensor high";
    base svo-al-t:svo-alarm-type;
  }

  identity SENSOR-HIGH-0-6V-CPU-B {
    description "0.6V-CPU-B sensor  high";
    base svo-al-t:svo-alarm-type;
  }

  identity SENSOR-HIGH-1-05V-CPU {
    description "1.05V-CPU sensor high";
    base svo-al-t:svo-alarm-type;
  }

  identity SENSOR-HIGH-1-0V {
    description "1.0V sensor high";
    base svo-al-t:svo-alarm-type;
  }

  identity SENSOR-HIGH-1-0V-PHY {
    description "1.0V-PHY sensor high";
    base svo-al-t:svo-alarm-type;
  }

  identity SENSOR-HIGH-1-2V {
    description "1.2V sensor high";
    base svo-al-t:svo-alarm-type;
  }

  identity SENSOR-HIGH-1-2V-CPU {
    description "1.2V-CPU sensor high";
    base svo-al-t:svo-alarm-type;
  }

  identity SENSOR-HIGH-1-3V-CPU {
    description "1.3V-CPU sensor high";
    base svo-al-t:svo-alarm-type;
  }

  identity SENSOR-HIGH-1-5V-CPU {
    description "1.5V-CPU sensor high";
    base svo-al-t:svo-alarm-type;
  }

  identity SENSOR-HIGH-1-7V-CPU {
    description "1.7V-CPU sensor high";
    base svo-al-t:svo-alarm-type;
  }

  identity SENSOR-HIGH-1-82V-CPU {
    description "1.82V-CPU sensor high";
    base svo-al-t:svo-alarm-type;
  }

  identity SENSOR-HIGH-1-8V {
    description "1.8V sensor high";
    base svo-al-t:svo-alarm-type;
  }

  identity SENSOR-HIGH-2-5V {
    description "2.5V sensor high";
    base svo-al-t:svo-alarm-type;
  }

  identity SENSOR-HIGH-3-3V {
    description "3.3V sensor high";
    base svo-al-t:svo-alarm-type;
  }

  identity SENSOR-HIGH-3-3V-CPU {
    description "3.3V-CPU sensor high";
    base svo-al-t:svo-alarm-type;
  }

  identity SENSOR-HIGH-3-3V-STBY {
    description "3.3V-STBY sensor high";
    base svo-al-t:svo-alarm-type;
  }

  identity SENSOR-HIGH-5-0V-STBY {
    description "5.0V-STBY sensor high";
    base svo-al-t:svo-alarm-type;
  }

  identity SENSOR-HIGH-BP-48V {
    description "BP-48V sensor high";
    base svo-al-t:svo-alarm-type;
  }

  identity SENSOR-HIGH-CPU-TEMP {
    description "CPU-TEMP sensor high";
    base svo-al-t:svo-alarm-type;
  }

  identity SENSOR-HIGH-DDR-CH0-TEMP {
    description "DDR-CH0-TEMP sensor high";
    base svo-al-t:svo-alarm-type;
  }

  identity SENSOR-HIGH-DDR-CH1-TEMP {
    description "DDR-CH1-TEMP sensor high";
    base svo-al-t:svo-alarm-type;
  }

  identity SENSOR-HIGH-ETHERNET-SWITCH-TEMP {
    description "ETHERNET-SWITCH-TEMP sensor high";
    base svo-al-t:svo-alarm-type;
  }

  identity SENSOR-HIGH-HOTSPOT1 {
    description "HOTSPOT1 sensor high";
    base svo-al-t:svo-alarm-type;
  }

  identity SENSOR-HIGH-HOTSPOT2 {
    description "HOTSPOT2 sensor high";
    base svo-al-t:svo-alarm-type;
  }

  identity SENSOR-HIGH-INLET-AIR {
    description "INLET-AIR sensor high";
    base svo-al-t:svo-alarm-type;
  }

  identity SENSOR-HIGH-OUTLET-AIR {
    description "OUTLET-AIR sensor high";
    base svo-al-t:svo-alarm-type;
  }

  identity SENSOR-LOW-0-6V-CPU-A {
    description "0.6V-CPU-A sensor low";
    base svo-al-t:svo-alarm-type;
  }

  identity SENSOR-LOW-0-6V-CPU-B {
    description "0.6V-CPU-B sensor  low";
    base svo-al-t:svo-alarm-type;
  }

  identity SENSOR-LOW-1-05V-CPU {
    description "1.05V-CPU sensor low";
    base svo-al-t:svo-alarm-type;
  }

  identity SENSOR-LOW-1-0V {
    description "1.0V sensor low";
    base svo-al-t:svo-alarm-type;
  }

  identity SENSOR-LOW-1-0V-PHY {
    description "1.0V-PHY sensor low";
    base svo-al-t:svo-alarm-type;
  }

  identity SENSOR-LOW-1-2V {
    description "1.2V sensor low";
    base svo-al-t:svo-alarm-type;
  }

  identity SENSOR-LOW-1-2V-CPU {
    description "1.2V-CPU sensor low";
    base svo-al-t:svo-alarm-type;
  }

  identity SENSOR-LOW-1-3V-CPU {
    description "1.3V-CPU sensor low";
    base svo-al-t:svo-alarm-type;
  }

  identity SENSOR-LOW-1-5V-CPU {
    description "1.5V-CPU sensor low";
    base svo-al-t:svo-alarm-type;
  }

  identity SENSOR-LOW-1-7V-CPU {
    description "1.7V-CPU sensor low";
    base svo-al-t:svo-alarm-type;
  }

  identity SENSOR-LOW-1-82V-CPU {
    description "1.82V-CPU sensor low";
    base svo-al-t:svo-alarm-type;
  }

  identity SENSOR-LOW-1-8V {
    description "1.8V sensor low";
    base svo-al-t:svo-alarm-type;
  }

  identity SENSOR-LOW-2-5V {
    description "2.5V sensor low";
    base svo-al-t:svo-alarm-type;
  }

  identity SENSOR-LOW-3-3V {
    description "3.3V sensor low";
    base svo-al-t:svo-alarm-type;
  }

  identity SENSOR-LOW-3-3V-CPU {
    description "3.3V-CPU sensor low";
    base svo-al-t:svo-alarm-type;
  }

  identity SENSOR-LOW-3-3V-STBY {
    description "3.3V-STBY sensor low";
    base svo-al-t:svo-alarm-type;
  }

  identity SENSOR-LOW-5-0V-STBY {
    description "5.0V-STBY sensor low";
    base svo-al-t:svo-alarm-type;
  }

  identity SENSOR-LOW-BP-48V {
    description "BP-48V sensor low";
    base svo-al-t:svo-alarm-type;
  }

  identity SENSOR-LOW-CPU-TEMP {
    description "CPU-TEMP sensor low";
    base svo-al-t:svo-alarm-type;
  }

  identity SENSOR-LOW-DDR-CH0-TEMP {
    description "DDR-CH0-TEMP sensor low";
    base svo-al-t:svo-alarm-type;
  }

  identity SENSOR-LOW-DDR-CH1-TEMP {
    description "DDR-CH1-TEMP sensor low";
    base svo-al-t:svo-alarm-type;
  }

  identity SENSOR-LOW-ETHERNET-SWITCH-TEMP {
    description "ETHERNET-SWITCH-TEMP sensor low";
    base svo-al-t:svo-alarm-type;
  }

  identity SENSOR-LOW-HOTSPOT1 {
    description "HOTSPOT1 sensor low";
    base svo-al-t:svo-alarm-type;
  }

  identity SENSOR-LOW-HOTSPOT2 {
    description "HOTSPOT2 sensor low";
    base svo-al-t:svo-alarm-type;
  }

  identity SENSOR-LOW-INLET-AIR {
    description "INLET-AIR sensor low";
    base svo-al-t:svo-alarm-type;
  }

  identity SENSOR-LOW-OUTLET-AIR {
    description "OUTLET-AIR sensor low";
    base svo-al-t:svo-alarm-type;
  }

  identity SF {
    description "Signal Failure";
    base svo-al-t:svo-alarm-type;
  }

  identity SF-L {
    description "BER Threshold Exceeded For Signal Failure Line";
    base svo-al-t:svo-alarm-type;
  }

  identity SFTWDOWN {
    description "Software Download In Progress";
    base svo-al-t:svo-alarm-type;
  }

  identity SFTWDOWN-FAIL {
    description "Software Download Failed";
    base svo-al-t:svo-alarm-type;
  }

  identity SHELF-COMM-FAIL {
    description "Shelf Communication Failure";
    base svo-al-t:svo-alarm-type;
  }

  identity SIGLOSS {
    description "Signal Loss on Data Interface";
    base svo-al-t:svo-alarm-type;
  }

  identity SIP {
    description "Startup In Progress";
    base svo-al-t:svo-alarm-type;
  }

  identity SNTP-HOST {
    description "NTP/SNTP Host Failure";
    base svo-al-t:svo-alarm-type;
  }

  identity SOFT-VERIF-FAIL {
    description "Software Signature Verification Failed";
    base svo-al-t:svo-alarm-type;
  }

  identity SPAN-NOT-MEASURED {
    description "Span Measurement Cannot Be Performed";
    base svo-al-t:svo-alarm-type;
  }

  identity SPANLEN-OUT-OF-RANGE {
    description "Span Length Out of Range";
    base svo-al-t:svo-alarm-type;
  }

  identity SQUELCHED {
    description "Equipment Squelched";
    base svo-al-t:svo-alarm-type;
  }

  identity SSM-DUS {
    description "Do Not Use For Synchronization";
    base svo-al-t:svo-alarm-type;
  }

  identity SSM-FAIL {
    description "Failed To Receive Synchronization Status Message";
    base svo-al-t:svo-alarm-type;
  }

  identity SSM-LNC {
    description "G812L - Local Node Clock traceable";
    base svo-al-t:svo-alarm-type;
  }

  identity SSM-OFF {
    description "Synchronization Status Messages Are Disabled On This Interface";
    base svo-al-t:svo-alarm-type;
  }

  identity SSM-PRC {
    description "G811 - Primary Reference Clock traceable";
    base svo-al-t:svo-alarm-type;
  }

  identity SSM-PRS {
    description "Stratum 1 Primary Reference Source Traceable";
    base svo-al-t:svo-alarm-type;
  }

  identity SSM-RES {
    description "Reserved For Network Synchronization Use";
    base svo-al-t:svo-alarm-type;
  }

  identity SSM-SDH-TN {
    description "G812T - Transit Node Clock traceable";
    base svo-al-t:svo-alarm-type;
  }

  identity SSM-SETS {
    description "G813 - Synchronous Equipment Timing Source traceable";
    base svo-al-t:svo-alarm-type;
  }

  identity SSM-SMC {
    description "SONET Minimum Clock Traceable";
    base svo-al-t:svo-alarm-type;
  }

  identity SSM-ST2 {
    description "Stratum 2 Traceable";
    base svo-al-t:svo-alarm-type;
  }

  identity SSM-ST3 {
    description "Stratum 3 Traceable";
    base svo-al-t:svo-alarm-type;
  }

  identity SSM-ST3E {
    description "Stratum 3E Traceable";
    base svo-al-t:svo-alarm-type;
  }

  identity SSM-ST4 {
    description "Stratum 4 Traceable";
    base svo-al-t:svo-alarm-type;
  }

  identity SSM-STU {
    description "Synchronized - Traceability Unknown";
    base svo-al-t:svo-alarm-type;
  }

  identity SSM-TNC {
    description "Transit Node Clock Traceable";
    base svo-al-t:svo-alarm-type;
  }

  identity SW-MISMATCH {
    description "Software Mismatch";
    base svo-al-t:svo-alarm-type;
  }

  identity SWTOPRI {
    description "Switch To Primary Reference";
    base svo-al-t:svo-alarm-type;
  }

  identity SWTOSEC {
    description "Switch To Second Reference";
    base svo-al-t:svo-alarm-type;
  }

  identity SWTOTHIRD {
    description "Switch To Third Reference";
    base svo-al-t:svo-alarm-type;
  }

  identity SYNC-FREQ {
    description "Synchronization Reference Frequency Out Of Bounds";
    base svo-al-t:svo-alarm-type;
  }

  identity SYNCCLK {
    description "Synchronization Unit Failure";
    base svo-al-t:svo-alarm-type;
  }

  identity SYNCLOSS {
    description "Synchronization Loss on Data Interface";
    base svo-al-t:svo-alarm-type;
  }

  identity SYNCPRI {
    description "Primary Synchronization Reference Failure";
    base svo-al-t:svo-alarm-type;
  }

  identity SYNCSEC {
    description "Secondary Synchronization Reference Failure";
    base svo-al-t:svo-alarm-type;
  }

  identity SYNCTHIRD {
    description "Third Synchronization Reference Failure";
    base svo-al-t:svo-alarm-type;
  }

  identity SYSBOOT {
    description "System Reboot";
    base svo-al-t:svo-alarm-type;
  }

  identity TEMP-LIC {
    description "Temporary License Is In Use";
    base svo-al-t:svo-alarm-type;
  }

  identity TEMP-MISM {
    description "Temperature Reading Mismatch Between SC Cards";
    base svo-al-t:svo-alarm-type;
  }

  identity TIM {
    description "TIM Section - Trace Identifier Mismatch Failure";
    base svo-al-t:svo-alarm-type;
  }

  identity TIM-S {
    description "Section Trace Identifier Mismatch";
    base svo-al-t:svo-alarm-type;
  }

  identity TRAF-AFFECT-RESET-REQUIRED {
    description "Traffic Affecting Reset Required";
    base svo-al-t:svo-alarm-type;
  }

  identity TRAF-AFFECT-SEC-UPG-REQUIRED {
    description "Traffic Affecting Security Upgrade Required";
    base svo-al-t:svo-alarm-type;
  }

  identity TRAIL-SIGNAL-FAIL {
    description "Trail Signal Fail";
    base svo-al-t:svo-alarm-type;
  }

  identity TRUNK-ODU-AIS {
    description "Trunk ODU Alarm Indication Signal";
    base svo-al-t:svo-alarm-type;
  }

  identity TRUNK-OPU-CSF {
    description "Trunk OPU Client Signal Fail";
    base svo-al-t:svo-alarm-type;
  }

  identity TRUNK-PAYLOAD-MISM {
    description "Trunk Payload Type Mismatch";
    base svo-al-t:svo-alarm-type;
  }

  identity UNC-WORD {
    description "FEC Uncorrected Word";
    base svo-al-t:svo-alarm-type;
  }

  identity UNIT-HIGH-TEMP {
    description "Unit High Temperature";
    base svo-al-t:svo-alarm-type;
  }

  identity UNQUAL-PPM {
    description "Unqualified PPM Inserted";
    base svo-al-t:svo-alarm-type;
  }

  identity USB-MOUNT-FAIL {
    description "USB Mount Failure";
    base svo-al-t:svo-alarm-type;
  }

  identity USB-WRITE-FAIL {
    description "USB Write Failure";
    base svo-al-t:svo-alarm-type;
  }

  identity USBSYNC {
    description "USB Sync in Progress";
    base svo-al-t:svo-alarm-type;
  }

  identity VOA-DISABLED {
    description "VOA Control Loop Disable Due To Excessive Counter-Propagation Light";
    base svo-al-t:svo-alarm-type;
  }

  identity VOA-HDEG {
    description "Variable Optical Attenuator Degrade High";
    base svo-al-t:svo-alarm-type;
  }

  identity VOA-HFAIL {
    description "Variable Optical Attenuator Failure High";
    base svo-al-t:svo-alarm-type;
  }

  identity VOA-LDEG {
    description "Variable Optical Attenuator Degrade Low";
    base svo-al-t:svo-alarm-type;
  }

  identity VOA-LFAIL {
    description "Variable Optical Attenuator Failure Low";
    base svo-al-t:svo-alarm-type;
  }

  identity VOLT-MISM {
    description "Voltage Reading Mismatch Between SC Cards";
    base svo-al-t:svo-alarm-type;
  }

  identity WKSWPR {
    description "Switched To Protection";
    base svo-al-t:svo-alarm-type;
  }

  identity WRK-PATH-RECOVERY-CHECK {
    description "Checking For Work Path Recovery";
    base svo-al-t:svo-alarm-type;
  }

  identity WTR {
    description "Wait To Restore";
    base svo-al-t:svo-alarm-type;
  }

  identity WVL-MISMATCH {
    description "Equipment Wavelength Mismatch";
    base svo-al-t:svo-alarm-type;
  }

  identity WVL-UNLOCKED {
    description "Wavelength Unlocked";
    base svo-al-t:svo-alarm-type;
  }

}
