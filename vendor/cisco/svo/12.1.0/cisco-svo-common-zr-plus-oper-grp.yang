module cisco-svo-common-zr-plus-oper-grp {
  yang-version 1.1;
  namespace "http://cisco.com/yang/svo/common-zr-plus-oper-grp";
  prefix cozrpog;



  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the ZR Plus interface Operational Data.";

    revision 2020-12-04 { 
       description "Model version for SVO Release 12.1.0 "; 
       reference cisco-svo-common-zr-plus-oper-grp.yang; 
    }
 
  
   grouping zr-plus-oper-base-parameter-group {
    
   }
  grouping zr-plus-oper-group {
    uses zr-plus-oper-base-parameter-group;
  }
}
