module cisco-svo-common-pm-oper-grp {

  yang-version 1.1;
  namespace "http://cisco.com/yang/svo/common-pm-oper-grp";
  prefix "ccpmog";

  import ietf-yang-types { prefix yang; revision-date 2013-07-15; }
  import org-openroadm-resource-types { prefix org-openroadm-resource-types; revision-date 2018-09-28; }

  organization
    "Cisco Systems, Inc.";

  contact
    "Cisco Systems, Inc. Customer Service Postal: 170 West Tasman Drive San Jose, CA 95134 Tel: +1 800 553-NETS E-mail: cs-yang@cisco.com";

  description
    "YANG definition for PM Operational Data";

    revision 2020-12-04 { 
       description "Model version for SVO Release 12.1.0 "; 
       reference cisco-svo-common-pm-oper-grp.yang; 
    }
 


  grouping current-pm-group {
    description
        "PM Data with current values - both realtime (granularity=notApplicable) and binned (granularity=15 min, 24h, 1 min, 1 h))";
    leaf pm-resource-instance {
      type instance-identifier;
      config false;
      mandatory true;
      description
            "Retrieves all PM associate with the resource instance";
    }
    leaf pm-resource-type {
      type org-openroadm-resource-types:resource-type-enum;
      config false;
      mandatory true;
      description
            "The supported pm-resource-type associated with the given resource instance.";
    }
    leaf pm-resource-type-extension {
      type string;
      config false;
      description
            "The resource type extension when the type is not defined in the resource-type-enum.";
    }
  }
  
  grouping current-pm-list-cont-grp {
    list current-pm-entry {
      config false;
      key "pm-resource-type pm-resource-type-extension pm-resource-instance";
      uses ccpmog:current-pm-group;
      description
            "List of current PM entries";
    }
  }

  grouping historical-pm-group {
    description
        "PM Data with historical values - binned (granularity=15 min, 24h, 1 min, 1h))";
    leaf pm-resource-instance {
      type instance-identifier;
      config false;
      mandatory true;
      description
            "Retrieves all PM associate with the resource instance";
    }
    leaf pm-resource-type {
      type org-openroadm-resource-types:resource-type-enum;
      config false;
      mandatory true;
    }
    leaf pm-resource-type-extension {
      type string;
      config false;
      description
            "The resource type extension when the type is not defined in the resource-type-enum.";
    }
  }
  
  grouping historical-pm-list-cont-grp {
    list historical-pm-entry {
      config false;
      key "pm-resource-type pm-resource-type-extension pm-resource-instance";
      uses ccpmog:historical-pm-group;
      leaf last-cleared-time {
        type yang:date-and-time;
      }
      description
            "List of historical PM entries";
    }
  }

}
