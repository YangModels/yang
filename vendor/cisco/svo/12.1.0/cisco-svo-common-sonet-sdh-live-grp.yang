module cisco-svo-common-sonet-sdh-live-grp {
  yang-version 1.1;
  namespace "http://cisco.com/yang/svo/common-sonet-sdh-live-grp";
  prefix cossdhlg;

  import cisco-svo-common-sonet-sdh-types { prefix ccssdht; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the SONET/SDH interface Live Data.";

    revision 2020-12-04 { 
       description "Model version for SVO Release 12.1.0 "; 
       reference cisco-svo-common-sonet-sdh-live-grp.yang; 
    }
 

  grouping sonet-sdh-live-data-j0-trace-group {
    leaf rx-j0-trace {
      type ccssdht:j0-trace-t;
      config false;
      description "Current RX J0 TRACE";
    }
  }

  grouping sonet-sdh-live-synchronization-group {
    leaf rx-ssm {
      type ccssdht:sonet-sdh-quality-level-t;
      config false;
      description "Rx Quality of the individual port: clock source quality level for SONET/SDH.";
    }
  }

  grouping sonet-sdh-live-data {
    container live-data {

      container synchronization {
        description "sonet-sdh synchronization live data";
        uses sonet-sdh-live-synchronization-group;
      }

      container j0-trace {
        description "sonet-sdh j0 trace live data";
        uses sonet-sdh-live-data-j0-trace-group;
      }
    }
  }

}
