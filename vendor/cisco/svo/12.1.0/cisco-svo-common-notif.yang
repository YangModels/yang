module cisco-svo-common-notif {
  yang-version 1.1;
  namespace "http://cisco.com/svo/common-notif";
  prefix ccnotif;

  import cisco-svo-common-types { prefix cct; }
  import cisco-svo-common-equipment-oper-grp { prefix cceqptog; }

  organization
      "Cisco Systems, Inc.";

  contact
      "Cisco Systems, Inc. Customer Service Postal: 170 West Tasman
      Drive San Jose, CA 95134 Tel: +1 800 553-NETS E-mail: cs-yang@cisco.com";

  description
      "YANG definition for SVO common netconf notifications";

  revision 2020-12-04 { 
      description "Model version for SVO Release 12.1.0 "; 
      reference cisco-svo-common-notif.yang; 
  }

  notification device-sync {
    leaf device-name {
      type string;
    }
    uses cceqptog:device-sync;
  }

  notification object-change-saved {
    leaf device-name {
      type string;
      mandatory true;
    }
    uses cceqptog:object-change-saved;
  }

  notification gn-data-updated {
    description "notification for update in the OMS link GN data set";

    leaf oms-link-id {
      type cct:degree-uid-t;
      description "Unique Id of OMS-link (id of parent Degree)";
    }
  }

  notification gn-data-missing {
    description "notification of missing/deleted GN data set in the OMS link";

    leaf oms-link-id {
      type cct:degree-uid-t;
      description "Unique Id of OMS-link (id of parent Degree)";
    }
  }
}
