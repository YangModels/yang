module cisco-svo-common-zr-plus-grp {
  yang-version 1.1;
  namespace "http://cisco.com/yang/svo/common-zr-plus-grp";
  prefix cozrp;



  import cisco-svo-common-types { prefix ct; }
  import cisco-svo-common-types { prefix cct; }
  import cisco-svo-common-interface-grp { prefix ccig; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the ZR Plus interface Config group";

  revision 2020-12-04 { 
      description "Model version for SVO Release 12.1.0 "; 
      reference cisco-svo-common-zr-plus-grp.yang; 
  }
   

  grouping zr-plus-config-squelch-group {
    leaf squelch-mode {
      type ct:squelch-ethernet-t;
      config true;
      default "LF";
    }
   
   
    leaf squelch-hold-off-time {
      type ct:squelch-hold-off-time-t;
      config true;
      default "Disable";
    }
    
  }  

  grouping zr-plus-attributes {
		leaf fec {
			type identityref {
				base cct:sd-fec-type;
			}
			description "permitted fec states";
		}
		leaf groupId {
      		type uint32 {
                 range "0..255";
         }
        description
                 "Group identifier Value";
    	}
	}
  grouping zr-plus-config-group {    
    uses zr-plus-config-squelch-group;
    uses zr-plus-attributes;
    uses ccig:maintenance-loopback;
  }

}
