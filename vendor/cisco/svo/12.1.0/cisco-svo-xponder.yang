module cisco-svo-xponder{
    yang-version 1.1;
    namespace "http://cisco.com/yang/svo/xponder";
    prefix svo-xpdr;

    import cisco-svo-common-equipment-types { prefix ccet; }

    organization
        "Cisco Systems, Inc.";

    contact
        "Cisco Systems, Inc. Customer Service Postal: 170 West Tasman
        Drive San Jose, CA 95134 Tel: +1 800 553-NETS E-mail: cs-yang@cisco.com";

    description
        "YANG definition for svo xponder";

    revision 2020-12-04 { 
       description "Model version for SVO Release 12.1.0 "; 
       reference cisco-svo-xponder.yang; 
    }
 

    grouping xponder-grp {
        list xponder {
            description "List of xponder";
            
            key "uid fmg-slot";         
            config false;
 
            leaf uid {
                type ccet:uid-t;
                description " the unique indentifier of chassis in svo across physical devices";  
            }

            leaf fmg-slot {
                type ccet:slot-t;
                description "Functional-module-group primary slot, that could be module slot identifier 1:999 or ppmSlot identifier 1:999-1:99";
            }

            leaf xpdr-type {
                type identityref {
                    base ccet:functional-mode;
                }
            }            

            uses client-connection-grp {
              when "not(derived-from(./xpdr-type, 'ccet:protected-functional-mode')) and not(derived-from(./xpdr-type, 'ccet:regen-functional-mode')) and not(derived-from(./xpdr-type, 'ccet:bundle-functional-mode'))";
            }
            uses bundle-connection-grp {
              when "derived-from(./xpdr-type, 'ccet:bundle-functional-mode')";
            }
            uses regen-connection-grp {
              when "derived-from(./xpdr-type, 'ccet:regen-functional-mode')";
            }
            uses protected-connection-grp {
              when "derived-from(./xpdr-type, 'ccet:protected-functional-mode')";
            }
        }
    }

   grouping client-connection-grp {
     list client-connection {
       key "primary-module-id  primary-port-id";

       leaf primary-module-id {
         type ccet:slot-t;
       }

       leaf primary-port-id {
         type ccet:port-id-t;
       }

       container client-port {
         uses xponder-port-grp;
       }
      
       container trunk-port {
         uses xponder-port-grp;
       }
     }
   }

   grouping bundle-connection-grp {
     list bundle-connection {
       key "primary-module-id  primary-port-id";

       leaf primary-module-id {
         type ccet:slot-t;
       }

       leaf primary-port-id {
         type ccet:port-id-t;
       }
       container client-port {
         uses xponder-port-grp;
       }
       container bundle {
         container trunk-port-1 {
           uses xponder-port-grp;
         }
         container trunk-port-2 {
           uses xponder-port-grp;
         }
       }
     }
   }
 
   grouping regen-connection-grp {
      container regen-connection {
        container trunk-port-1 {
          uses xponder-port-grp;
        }
        container trunk-port-2 {
          uses xponder-port-grp;
        }
      }
    }

    grouping protected-connection-grp {
      container protected-connection {
        container client-port {
          uses xponder-port-grp;
        }
        container trunk-port-1 {
          uses xponder-port-grp;
        }
        container trunk-port-2 {
          uses xponder-port-grp;
        }
      }
    }
  
    grouping xponder-port-grp {
      leaf module-id {
        type ccet:slot-t;
      }
      leaf port-id {
        type ccet:port-id-t;
      }
      leaf port-name {
        type ccet:port-name-t;
      }
    }
}
