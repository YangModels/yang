module cisco-svo-common-mfg-oper-grp {

  yang-version 1.1;
  namespace "http://cisco.com/yang/svo/common-mfg-oper-grp";
  prefix ccmog; 


  organization
    "Cisco Systems, Inc.";

  contact
    "Cisco Systems, Inc.
     Customer Service

     Postal: 170 West Tasman Drive
     San Jose, CA 95134

     Tel: +1 800 553-NETS

     E-mail: cs-yang@cisco.com";

  description "
    This module defines cisco equipment manufacturing data types typically
    used for inventory.
    Content from this model is used for the cisco Product Identification Standard.
    ";

    revision 2020-12-04 { 
       description "Model version for SVO Release 12.1.0 "; 
       reference cisco-svo-common-mfg-oper-grp.yang; 
    }
 

  grouping equipment-manufacturing-data-oper-grp {

    container manufacturing-data {
      description "Cisco Equipment Properties (Manufacturing Data)";
      config false;

      leaf actual-type {
        type string;
        description "Equipment type";
      }
      leaf hardware-part-number {
        type string;
        description "Hardware Part-number";
      }
      leaf hardware-revision {
        type string;
        description "Hardware revision";
      }
      leaf serial {
        type string;
        description "Serial Number";
      }
      leaf clei-code {
        type string;
        description "CLEI Code";
      }
      leaf bootrom-revision {
        type string;
        description "Bootrom Revision";
      }
      leaf product-id {
        type string;
        description "Product ID";
      }
      leaf version-id {
        type string;
        description "Version ID";
      }
    }
  }
}
