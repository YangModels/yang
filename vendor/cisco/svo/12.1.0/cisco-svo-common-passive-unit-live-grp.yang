module cisco-svo-common-passive-unit-live-grp {

  yang-version 1.1;
  namespace "http://cisco.com/yang/svo/common-passive-unit-live-grp";
  prefix ccpulg;

  import cisco-svo-common-types { prefix cct; }
  import cisco-svo-common-equipment-types { prefix ccet; }

  organization
    "Cisco Systems, Inc.";

  contact
        "Cisco Systems, Inc.
     Customer Service

     Postal: 170 West Tasman Drive
     San Jose, CA 95134

     Tel: +1 800 553-NETS

     E-mail: cs-yang@cisco.com";

  description "
    YANG definition for passive units live status data";

    revision 2020-12-04 { 
       description "Model version for SVO Release 12.1.0 "; 
       reference cisco-svo-common-passive-unit-live-grp.yang; 
    }
 

  grouping led-status {

    leaf led-status {
      config false;
      type ccet:passive-led-color;
    }
  }
  
  grouping actual-power {
      leaf actual-power {        
        config false;
        type cct:dbm-oper-t;
      }
  }
}
