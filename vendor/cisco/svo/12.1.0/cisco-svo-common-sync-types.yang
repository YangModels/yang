module cisco-svo-common-sync-types {
  yang-version 1.1;
  namespace "http://cisco.com/yang/svo/sync-common-types";
  prefix synct;

  import cisco-svo-common-types { prefix cct; }

  organization "Cisco Systems, Inc.";

  contact
    "Cisco Systems, Inc.
     Customer Service
     
     Postal: 170 West Tasman Drive
     San Jose, CA 95134
     
     Tel: +1 800 553-NETS
     
     E-mail: cs-yang@cisco.com";

  description "YANG definition for SVO sync common types.";

  revision 2020-12-04 { 
      description "Model version for SVO Release 12.1.0 "; 
      reference cisco-svo-common-sync-types.yang; 
  }
 

  typedef reference-clock-t {
      type enumeration {
        enum ne {
            value 0;
            description "NE";
        }
        enum bits-1-out {
            value 1;
            description "Ext-1: Bits 1 Out";
        }
        enum bits-2-out {
            value 2;
            description "Ext-2: Bits 2 Out";
        }
      }
      description "Identifies which Reference/Clock is being addressed";
  }

  typedef synch-switch-type-t {
      type enumeration {
        enum manual {
            value 0;
            description "Manual";
        }
        enum force {
            value 1;
            description "Force";
        }
        enum no-switch {
            value 2;
            description "No Switch";
        }
      }
      description "Identfies which type of reference switch is in effect";
  }

  typedef timing-mode-t {
      type enumeration {
        enum external {
            value 0;
            description "External - the node derives its clock from the BITS inputs";
        }
        enum line {
            value 1;
            description "Line - the node derives its clock from the SONET line(s)";
        }
        enum mixed {
            value 2;
            description "Mixed - the node derives its clock from the BITS inputs or SONET lines";
        }
      }
      description "Timing Mode Type
      If a node is configured to be Externally timed, then only BITS-1 and
      BITS-2 may be selected as NE references.  It also means that the NE
      clock may not be selected as a source for the External/BITS outputs.
      In such a case, only optical SONET lines may be selected as sources
      for the External/BITS outputs. 
      If a node is configured to be line timed (referred to a loop timed
      in Release 1.0), then only optical SONET lines may be selected as
      NE references.  In such a case, the NE clock as well as the optical
      SONET lines may be selected as sources for the External/BITS outputs.
      If a node is configured to be mixed timed, then optical Sonet lines
      and BITS-1 and BITS-2 may be selected for NE references.  In such a
      case,only optical lines may be selected as sources for the External/Bits
      outputs.";

  }

  typedef timing-state-t {
      type enumeration {
        enum init {
            value 0;
            description "INIT_STATE - NeSynchRef and ExtSynchRef";
        }
        enum holdover {
            value 1;
            description "HOLDOVER_STATE - NeSynchRef Only";
        }
        enum freerun {
            value 2;
            description "FREERUN_STATE - NeSynchRef Only";
        }
        enum no-sync {
            value 3;
            description "NO_SYNC_STATE - ExtSynchRef Only";
        }
        enum ne-sync {
            value 4;
            description "NE_SYNCH_STATE - ExtSynchRef Only";
        }
        enum normal {
            value 5;
            description "NORMAL_STATE - NeSynchRef and ExtSynchRef";
        }
        enum fast-start {
            value 6;
            description "FAST_START_STATE - NeSynchRef Only";
        }
        enum fast-start-failed {
            value 7;
            description "FAST_START_FAILED_STATE - NeSynchRef Only";
        }
      }
      description "Timing State";
  }

  typedef ssm-generation-t {
      type enumeration {
        enum generation-1 {
            value 0;
            description "First generation SSM set";
        }
        enum generation-2 {
            value 1;
            description "Second generation SSM set";
        }
      }
      description "Synchronization Status Message Set Generation";
  }

  typedef res-quality-level-t {
    type enumeration {
      enum above-PRS {
        value 0;
        description "Better than Primary Reference Source, Stratum 1 Tracable (PRS < RES)";
      }
      enum above-STU {
        value 1;
        description "STU < RES < PRS";
      }
      enum above-ST2 {
        value 2;
        description "ST2 < RES < STU";
      }
      enum above-TNC {
        value 3;
        description "TNC < RES < ST2";
      }
      enum above-ST3E {
        value 4;
        description "ST3E < RES < TNC";
      }
      enum above-ST3 {
        value 5;
        description "ST3 < RES < ST3E";
      }
      enum above-SMC {
        value 6;
        description "SMC < RES < ST3";
      }
      enum above-ST4 {
        value 7;
        description "ST4 < RES < SMC";
      }
      enum below-ST4 {
        value 8;
        description "Below ST4 but still usable, RES < ST4";
      }
      enum same-As-DUS {
        value 9;
        description "Disables the RES message by equating it to DUS, RES = DUS";
      }
      enum above-G811 {
        value 10;
        description "Better than G811";
      }
      enum above-STU-SDH {
        value 11;
        description "Between STU_SDH and G812T";
      }
      enum above-G812T {
        value 12;
        description "Between G811 and G812T";
      }
      enum above-G812L {
        value 13;
        description "Between G812T and G812L";
      }
      enum above-SETS {
        value 14;
        description "Between G812L and SETS";
      }
      enum below-SETS {
        value 15;
        description "Below SETS";
      }
      enum same-As-DUS-SDH {
        value 16;
        description " Disables the RES message by equating it to DUS_SDH";
      }
    }
    description "Reserved for Network Synchronization Quality Level";
  }

  typedef reversion-mode-t {
      type enumeration {
        enum use-default-behaviour {
            value 0;
            description "Use default behaviour";
        }
        enum non-revertive-behaviour {
            value 1;
            description "Non revertive behaviour";
        }
        enum revertive-behaviour {
            value 2;
            description "Revertive behaviour";
        }
      }
      description "Revertive Behaviour Type";
  }

  typedef reversion-time-t {
    type union {
      type cct:na-t;
      type uint32 {
        range "0 | 30  | 60  | 90  | 120 | 150 | 180 | 210 | 240 | 270 | 300 |
              330 | 360 | 390 | 420 | 450 | 480 | 510 | 540 | 570 | 600 |
              630 | 660 | 690 | 720";
          }
      }
    description "Time in seconds that the main facility
      must be qualified before switching back to it.  This number may
      only accurate to 30 seconds";
  }

  typedef synch-reference-source-t {
    type enumeration {
        enum none {
            value 0;
            description "None";
        }
        enum internal-clock {
            value 1;
            description "Internal Clock";
        }
        enum ne-reference {
            value 2;
            description "NE Reference";
        }
        enum bits-1-in {
            value 3;
            description "BITS 1";
        }
        enum bits-2-in {
            value 4;
            description "BITS 2";
        }
        enum interface {
            value 5;
            description "Interface";
        }
      }
      description "Synch Reference Source Type";
  }

  typedef reference-condition-t {
      type enumeration {
            enum OK {
                value 0;
                description "REF_OK";
            }
            enum LOS {
                value 1;
                description "LOS";
            }
            enum LOF {
                value 2;
                description "LOF";
            }
            enum AIS {
                value 3;
                description "AIS";
            }
            enum OOB {
                value 4;
                description "OOB";
            }
            enum EQP {
                value 5;
                description "EQP";
            }
            enum BPV {
                value 6;
                description "BPV";
            }
            enum CCHV {
                value 7;
                description "CCHV";
            }
            enum AIS-thresh {
                value 8;
                description "AIS_THRESH";
            }
      }
      description "Reference Condition
        REF_OK - reference is fine
        LOS - reference is LOS
        LOF - reference is LOF
        AIS - refernece is AIS
        OOB - reference is OOB
        EQP - associated eqpt is bad
        BPV - reference is BPV violation
        CCHV -reference is 64K, and high voltage
        AIS_THRESH - reference is bad, because fails AIS threshold test
      ";
  }

  typedef timing-protocol-t {
      type enumeration {
            enum none {
                value 0;
                description "PROTO_NONE";
            }
            enum SONET {
                value 1;
                description "PROTO_SONET";
            }
            enum SDH {
                value 2;
                description "PROTO_SDH";
            }
            enum SyncE {
                value 3;
                description "PROTO_SYNCE";
            }
            enum IEEE-1588 {
                value 4;
                description "PROTO_1588";
            }
            enum OTN {
                value 5;
                description "PROTO_OTN";
            }
      }
    description "Timing Protocol
      PROTO_NONE,
      PROTO_SONET,
      PROTO_SDH,
      PROTO_SYNCE,
      PROTO_1588,
      PROTO_OTN
    ";
  }

  typedef bits-facility-t {
      type enumeration {
        enum BITS-FACILITY-T1 {
            value 0;
            description "BITS T1";
        }
        enum BITS-FACILITY-E1 {
            value 1;
            description "BITS E1";
        }
        enum BITS-FACILITY-64K {
            value 2;
            description "BITS 64K";
        }
        enum BITS-FACILITY-2MHZ {
            value 3;
            description "BITS 2MHZ";
        }
      }
      description "Bits Facility";
  }

  typedef cable-type-t {
      type enumeration {
        enum pause-75-ohm {
            value 0;
            description "75 ohm";
        }
        enum pause-120-ohm {
            value 1;
            description "120 ohm";
        }
        enum pause-100-ohm {
            value 2;
            description "100 ohm";
        }
      }
      description "Cable Type";
  }

  typedef lbo-t {
      type enumeration {
        enum LBO-0-133-feet {
            value 0;
            description "LBO-0-133 FEET";
        }
        enum LBO-134-266-feet {
            value 1;
            description "LBO-134-266 FEET";
        }
        enum LBO-267-399-feet {
            value 2;
            description "LBO-267-399 FEET";
        }
        enum LBO-400-533-feet {
            value 3;
            description "LBO-400-533 FEET";
        }
        enum LBO-534-655-feet {
            value 4;
            description "LBO-534-655 FEET";
        }
      }
      description "line lengths for external Bits out";
  }

  typedef line-type-t {
      type enumeration {
        enum ESF {
            value 0;
            description "ESF - DS1";
        }
        enum D4 {
            value 1;
            description "D4 - DS1";
        }
        enum E1-CRC {
            value 2;
            description "E1 CRC - E1";
        }
        enum E1-MF {
            value 3;
            description "E1 MF - E1";
        }
        enum E1-CRCMF {
            value 4;
            description "E1 CRCMF - E1";
        }
        enum UNFRAMED {
            value 5;
            description "UNFRAMED - DS1/DS3";
        }
        enum DS2-FRAMED {
            value 6;
            description "DS2 FRAMED - DS2";
        }
        enum E2-FRAMED {
            value 7;
            description "E2 FRAMED - E2";
        }
        enum M13 {
            value 8;
            description "M13 - DS3";
        }
        enum SYNTRAN {
            value 9;
            description "SYNTRAN - DS3";
        }
        enum C-BIT-PARITY {
            value 10;
            description "C-BIT-PARITY - DS3";
        }
        enum E3-FRAME {
            value 11;
            description "E3-FRAME - E3";
        }
        enum E3-PLCP {
            value 12;
            description "E3-PLCP - E3";
        }
        enum AUTO-PROVISION-FMT {
            value 13;
            description "AUTO PROVISION FMT";
        }
        enum UNKNOWN-FMT {
            value 14;
            description "UNKNOWN FMT";
        }
        enum LINETYPE-NOT-APPLICABLE {
            value 15;
            description "LINETYPE NOT APPLICABLE";
        }
        enum E1-FRAME {
            value 16;
            description "E1 FRAME - E1";
        }
        enum E1-UNFRAME {
            value 17;
            description "E1 UNFRAME - E1";
        }
        enum BITS-64K {
            value 18;
            description "BITS 64K";
        }
        enum BITS-2MHZ {
            value 19;
            description "BITS 2MHZ";
        }
        enum JESF {
            value 20;
            description "JESF - DS1 (Japan ESF, J1)";
        }
        enum C-BIT {
            value 21;
            description "C BIT";
        }
        enum G-751 {
            value 22;
            description "G 751";
        }
        enum G-832 {
            value 23;
            description "G 832";
        }
        enum M23 {
            value 24;
            description "M23";
        }
      }
      description "Line Type";
  }

  typedef line-coding-t {
      type enumeration {
        enum JBZS {
            value 0;
            description "JBZS";
        }
        enum B8ZS {
            value 1;
            description "B8ZS";
        }
        enum HDB3 {
            value 2;
            description "HDB3";
        }
        enum AMI {
            value 3;
            description "AMI";
        }
        enum ZBTSI {
            value 4;
            description "ZBTSI";
        }
        enum B6ZS {
            value 5;
            description "B6ZS";
        }
        enum B3ZS {
            value 6;
            description "B3ZS";
        }
        enum LINECODING-NOT-APPLICABLE {
            value 7;
            description "LINECODING NOT APPLICABLE";
        }
      }
      description "Line Coding
        Zero suppression mode on line
        JBZS Jammed Bit Zero Suppression (bit 8 stuffed)
        B8ZS, B6ZS, B3ZS - Bipolar 8, 6, or 3 zero suppression.
        HDB3 - E1, E3
        AMI - zero supporession enforced by content, e.g inverted HDLC
        ZBTSI - Zero Byte Time Slot Interchange, clear channel only";
  }

  typedef sa-bit-t {
      type enumeration {
        enum SA4 {
            value 0;
            description "indicates the line set the SA4 bit";
        }
        enum SA5 {
            value 1;
            description "indicates the line set the SA5 bit";
        }
        enum SA6 {
            value 2;
            description "indicates the line set the SA6 bit";
        }
        enum SA7 {
            value 3;
            description "indicates the line set the SA7 bit";
        }
        enum SA8 {
            value 4;
            description "indicates the line set the SA8 bit";
        }
        enum SA-none {
            value 5;
            description "indicates the line does not have SaBit set";
        }
      }
      description "SA Bit for for E1 use only";
  }
}
