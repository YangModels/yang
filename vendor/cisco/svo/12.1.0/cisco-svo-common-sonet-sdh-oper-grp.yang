module cisco-svo-common-sonet-sdh-oper-grp {
  yang-version 1.1;
  namespace "http://cisco.com/yang/svo/common-sonet-sdh-oper-grp";
  prefix cossdhog;

  import cisco-svo-common-sonet-sdh-types { prefix ccssdht; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the SONET/SDH interface Operational Data.";

    revision 2020-12-04 { 
       description "Model version for SVO Release 12.1.0 "; 
       reference cisco-svo-common-sonet-sdh-oper-grp.yang; 
    }
 

  grouping sonet-sdh-oper-base-parameter-group {
    leaf media-type {
      type ccssdht:media-type-t;
      config false;
      description "defines if this is a SONET or SDH interface";
    }

    leaf sonet-sdh-rate {
      type ccssdht:sonet-sdh-rate-t;
      config false;
      description "SONET/SDH Interface Rate";
    }
  }

  
  grouping sonet-sdh-oper-group {
    uses sonet-sdh-oper-base-parameter-group;
  }
}
