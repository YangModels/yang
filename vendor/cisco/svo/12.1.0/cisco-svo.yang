module cisco-svo {
  yang-version 1.1;
  namespace "http://cisco.com/yang/svo";
  prefix svo;

  import tailf-common { prefix tailf; }    
  import cisco-svo-common-interface-grp { prefix ccig;}
  import cisco-svo-equipment-grp { prefix svo-eq-grp; }
  import cisco-svo-interfaces-grp { prefix svo-if-grp; }
  import cisco-svo-common-if-ethernet-csmacd-grp { prefix ncciecg; }
  import cisco-svo-if-optical-transport { prefix cif-ot;}
  import cisco-svo-if-optical-channel { prefix if-och; }
  import cisco-svo-if-otn-otu { prefix svo-otn-otu; }
  import cisco-svo-if-otn-odu { prefix svo-otn-odu; }
  import cisco-svo-if-sonet-sdh { prefix if-sonet-sdh; }
  import cisco-svo-if-zr-plus { prefix if-zr-plus; }
  import cisco-svo-otn-odu-connection { prefix svo-odu-conn; }
  import cisco-svo-als { prefix als; }
  import cisco-svo-amplifier { prefix amp; }
  import cisco-svo-functional-model { prefix funct; }
  import cisco-svo-xponder { prefix xpdr; }

  import cisco-svo-node-grp {prefix svo-node-grp; }
  import org-openroadm-interfaces { prefix or-if; revision-date 2018-09-28; }
  import cisco-svo-common-sonet-sdh-types { prefix ccssdht; }
  import cisco-svo-common-zr-plus-types { prefix cczrpt; }
  import cisco-svo-protection-group {prefix svo-prt-grp;}


  organization
    "Cisco Systems, Inc.";

  contact
    "Cisco Systems, Inc.
     Customer Service

     Postal: 170 West Tasman Drive
     San Jose, CA 95134

     Tel: +1 800 553-NETS

     E-mail: cs-yang@cisco.com";

  description
    "YANG definition for the SVO device model.";

  revision 2020-12-04 { 
      description "Model version for SVO Release 12.1.0 "; 
      reference cisco-svo.yang; 
  }
 

  container svo {
    tailf:info "SVO node container";
    description
       "SVO Node container.";
    uses svo-node-grp:node-ctrl-grp;
    uses svo-node-grp:node-info-grp;
    uses svo-eq-grp:equipment-grp;
    uses svo-eq-grp:external-links-grp;
    uses svo-eq-grp:internal-links-grp;
    uses svo-eq-grp:node-connection-verification-grp;

    uses svo-if-grp:interfaces {
      augment interface {
        when 'derived-from-or-self(type, "or-if:opticalTransport")';
        uses cif-ot:optical-transport-grp;
        description "Optical Transport Interface augment";
      }
      augment interface {
        when 'derived-from-or-self(type, "or-if:ethernetCsmacd")';
        uses ncciecg:ethernet-csmacd-grp;
        description "Ethernet Interface augment";
      }
      augment interface {
        when 'derived-from-or-self(type, "or-if:opticalChannel")';
        uses if-och:optical-channel-grp;
        description "Optical Channel Interface augment";
      }
      augment interface {
        when 'derived-from-or-self(type, "ccssdht:sonetSdh")';
        uses if-sonet-sdh:sonet-sdh-grp;
        description "Sonet/Sdh Interface augment";
      }
       augment interface {
        when 'derived-from-or-self(type, "cczrpt:zrPlus")';
        uses if-zr-plus:zr-plus-grp; 
        description "ZR Plus Interface augment";
      }

      augment interface {
        when 'derived-from-or-self(type, "or-if:otnOtu")';
        uses svo-otn-otu:otn-otu-grp;
        description "OTN OTU Interface augment";
      }
      augment interface {
        when 'derived-from-or-self(type, "or-if:otnOdu")';
        uses svo-otn-odu:otn-odu-grp;
        description "OTN ODU Interface augment";
      }
      augment interface {
        when 'derived-from-or-self(type, "or-if:gcc")';
        uses ccig:gcc-config-grp;
        description "Gcc Interface augment";
      }
    }

    uses amp:amp-grp;
    uses amp:raman-amp-grp;
    uses als:als-grp;
    uses funct:node-degrees;
    uses funct:node-topopology-grp;
    uses funct:OMS-Links;
    uses funct:expected-input-power-grp;
    uses xpdr:xponder-grp;
    uses svo-odu-conn:otn-odu-connection-group;
    uses svo-prt-grp:svo-protection-grps;
  }  
}
