module cisco-svo-common-otn-otu-grp {
	yang-version 1.1;
	namespace "http://cisco.com/yang/svo/common-otn-otu-grp";
	prefix cotu;

	import cisco-svo-common-types { prefix cct; }
	import cisco-svo-common-otn-grp { prefix ccotng; }

	organization 
	"Cisco Systems, Inc.";

	contact 
	"Cisco Systems, Inc.
	Customer Service

	Postal: 170 West Tasman Drive
	San Jose, CA 95134

	Tel: +1 800 553-NETS

	E-mail: cs-yang@cisco.com";

	description "
	This module defines the OpticalChannel interface.";

    revision 2020-12-04 { 
       description "Model version for SVO Release 12.1.0 "; 
       reference cisco-svo-common-otn-otu-grp.yang; 
    }
 

	typedef interop-mode-t {
		type enumeration {
			enum InteropNone;
			enum InteropEnable;
		}
		description "Enable special FEC interoperability features with other vendors";
	}

	grouping proactive-protection-cfg-grp {
		description "Proactive protection configuration";

		leaf trigger-threshold {
			type enumeration {
				enum "9E-2";
				enum "8E-2";  
				enum "7E-2";  
				enum "6E-2";  
				enum "5E-2";  
				enum "4E-2";  
				enum "3E-2";  
				enum "2E-2";  
				enum "1E-2"; 
				enum "9E-3";  
				enum "8E-3";  
				enum "7E-3";  
				enum "6E-3";  
				enum "5E-3";  
				enum "4E-3";  
				enum "3E-3";  
				enum "2E-3";  
				enum "1E-3";
				enum "9E-4";
				enum "8E-4";
				enum "7E-4";
				enum "6E-4";
				enum "5E-4";
				enum "4E-4";
				enum "3E-4";
				enum "2E-4";
				enum "1E-4";
				enum "9E-5";
				enum "8E-5";
				enum "7E-5";
				enum "6E-5";
				enum "5E-5";
				enum "4E-5";
				enum "3E-5";
				enum "2E-5";
				enum "1E-5";
				enum "9E-6";
				enum "8E-6";
				enum "7E-6";
				enum "6E-6";
				enum "5E-6";
				enum "4E-6";
				enum "3E-6";
				enum "2E-6";
				enum "1E-6";
				enum "9E-7";
				enum "8E-7";
				enum "7E-7";
				enum "6E-7";
				enum "5E-7";
				enum "4E-7";
				enum "3E-7";
				enum "2E-7";
				enum "1E-7";
			}
			description "Trigger thresholds";
		}
		leaf trigger-window { // ms
			type uint16 {
				range "1..500";
			}
			description "Trigger time window";
		}
		leaf revert-threshold {
			type enumeration {
				enum "9E-3";
				enum "8E-3";
				enum "7E-3";
				enum "6E-3";
				enum "5E-3";
				enum "4E-3";
				enum "3E-3";
				enum "2E-3";
				enum "1E-3";
				enum "9E-4";
				enum "8E-4";
				enum "7E-4";
				enum "6E-4";					
				enum "5E-4";
				enum "4E-4";
				enum "3E-4";
				enum "2E-4";
				enum "1E-4";
				enum "9E-5";
				enum "8E-5";
				enum "7E-5";
				enum "6E-5";
				enum "5E-5";
				enum "4E-5";
				enum "3E-5";
				enum "2E-5";
				enum "1E-5";
				enum "9E-6";
				enum "8E-6";
				enum "7E-6";
				enum "6E-6";
				enum "5E-6";
				enum "4E-6";
				enum "3E-6";
				enum "2E-6";
				enum "1E-6";
				enum "9E-7";
				enum "8E-7";
				enum "7E-7";
				enum "6E-7";
				enum "5E-7";
				enum "4E-7";
				enum "3E-7";
				enum "2E-7";
				enum "1E-7";
				enum "9E-8";
				enum "8E-8";
				enum "7E-8";
				enum "6E-8";
				enum "5E-8";
			}
			description "Revert Thresholds";
		}
		leaf revert-window { // ms
			type uint16 {
				range "2000..3900";
			}
			description "Revert time window";
		}
		leaf enable-proactive-protection {
			type enumeration {
				enum "Disabled";
				enum "FRR Proactive Protection";
				enum "Pre-FEC PSM Proactive Protection";
				// OP: to be clarified with Tandi / Rizzi 
				// the meaning of this distinction,
				// whether there is a difference impacting functionality

			}
			description "
			Pre-FEC error monitoring to trigger the proactive
			protection based on BER threshodl crossing.";
		}

		leaf forward-proactive-protection {
			type boolean;
			default false;
    	  	description "Valid only on muxponder OTU clients: if 'true', Proactive Protection events from the peer Trunk are forwarded to the client line";
		}
	}     

	grouping hd-fec-grp {
		leaf hd-fec {
			type identityref {
				base cct:fec-type;
			}
			description "permitted fec states";
		}

		leaf interop-mode {
			type cotu:interop-mode-t;
			description "Enable special FEC interoperability features with other vendors";
		}
	}

	grouping otn-otu-config-group {
		uses cotu:hd-fec-grp;

		container proactive-protection {
			uses cotu:proactive-protection-cfg-grp;
		}

		container optical-transport-unit {
			container tti {
				uses ccotng:tti-cfg-grp;
			}

			container synchronization {
				uses ccotng:sync-cfg-grp;
			}
		}
	}

}
