/*
* Generated by python main_svo_generator.py
* Source: alarm_dictionary
*/
submodule cisco-devices-alarm-transient-types {

  belongs-to cisco-svo-alarm-transient-type {
    prefix svo-al-tr-t;
  }

  include cisco-svo-alarm-transient-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the alarm types";

  revision 2020-12-04 { 
       description "Model version for SVO Release 12.1.0 "; 
       reference cisco-devices-alarm-transient-types; 
  }

  identity ADMIN-DISABLE {
    description "Disable Inactive User";
    base svo-al-tr-t:svo-alarm-transient-type;
  }

  identity ADMIN-DISABLE-CLR {
    description "Disable Inactive Clear";
    base svo-al-tr-t:svo-alarm-transient-type;
  }

  identity ADMIN-LOCKOUT {
    description "Admin Lockout of User";
    base svo-al-tr-t:svo-alarm-transient-type;
  }

  identity ADMIN-LOCKOUT-CLR {
    description "Admin Lockout Clear";
    base svo-al-tr-t:svo-alarm-transient-type;
  }

  identity ADMIN-LOGOUT {
    description "Admin Logout of User";
    base svo-al-tr-t:svo-alarm-transient-type;
  }

  identity ADMIN-SUSPEND {
    description "Suspend User";
    base svo-al-tr-t:svo-alarm-transient-type;
  }

  identity ADMIN-SUSPEND-CLR {
    description "Suspend User Clear";
    base svo-al-tr-t:svo-alarm-transient-type;
  }

  identity AUD-ARCHIVE-FAIL {
    description "Archival of Audit Log Failed";
    base svo-al-tr-t:svo-alarm-transient-type;
  }

  identity AUTOWDMANS {
    description "Automatic WDM ANS Finished";
    base svo-al-tr-t:svo-alarm-transient-type;
  }

  identity DBBACKUP-FAIL {
    description "Database Backup Failed";
    base svo-al-tr-t:svo-alarm-transient-type;
  }

  identity DBRESTORE-FAIL {
    description "Database Restore Failed";
    base svo-al-tr-t:svo-alarm-transient-type;
  }

  identity FIRMWARE-DOWNLOAD {
    description "Firmware Download In Progress";
    base svo-al-tr-t:svo-alarm-transient-type;
  }

  identity FIRMWARE-UPG-COMPLETE {
    description "Firmware Upgrade Completed";
    base svo-al-tr-t:svo-alarm-transient-type;
  }

  identity INTRUSION {
    description "Security: Invalid Login Username - See Audit Trail";
    base svo-al-tr-t:svo-alarm-transient-type;
  }

  identity INTRUSION-USERID {
    description "Security Intrusion Attempt Detected - See Audit Log";
    base svo-al-tr-t:svo-alarm-transient-type;
  }

  identity LOGIN-FAIL-LOCKOUT {
    description "Security: Invalid Login - Locked Out - See Audit Log";
    base svo-al-tr-t:svo-alarm-transient-type;
  }

  identity LOGIN-FAIL-ONALRDY {
    description "Security: Invalid Login - Already Logged On - See Audit Log";
    base svo-al-tr-t:svo-alarm-transient-type;
  }

  identity LOGIN-FAILURE-PSWD {
    description "Security: Invalid Login - Password - See Audit Log";
    base svo-al-tr-t:svo-alarm-transient-type;
  }

  identity LOGIN-FAILURE-USER {
    description "Security: Invalid Login - Username - See Audit Log";
    base svo-al-tr-t:svo-alarm-transient-type;
  }

  identity LOGOUT-IDLE-USER {
    description "Automatic Logout of IdleUser";
    base svo-al-tr-t:svo-alarm-transient-type;
  }

  identity MASTERKEY-SUCCESS {
    description "MasterKey Exchange Success";
    base svo-al-tr-t:svo-alarm-transient-type;
  }

  identity PM-TCA {
    description "Performance Monitor Threshold Crossing Alert";
    base svo-al-tr-t:svo-alarm-transient-type;
  }

  identity PSWD-CHG-REQUIRED {
    description "User Password Change Required";
    base svo-al-tr-t:svo-alarm-transient-type;
  }

  identity RMON-ALARM {
    description "RMON Threshold Crossing Alarm";
    base svo-al-tr-t:svo-alarm-transient-type;
  }

  identity RMON-RESET {
    description "RMON Histories And Alarms Reset Reboot";
    base svo-al-tr-t:svo-alarm-transient-type;
  }

  identity ROLE-SWITCH-ACTIVE {
    description "Role is Switched to active";
    base svo-al-tr-t:svo-alarm-transient-type;
  }

  identity SESSION-TIME-LIMIT {
    description "Session Time Limit Expired";
    base svo-al-tr-t:svo-alarm-transient-type;
  }

  identity USB-PORTS-DOWN {
    description "USB Ports in ECU are not functional";
    base svo-al-tr-t:svo-alarm-transient-type;
  }

  identity USER-LOCKOUT {
    description "User Locked Out";
    base svo-al-tr-t:svo-alarm-transient-type;
  }

  identity USER-LOGIN {
    description "Login of User";
    base svo-al-tr-t:svo-alarm-transient-type;
  }

  identity USER-LOGOUT {
    description "Logout of User";
    base svo-al-tr-t:svo-alarm-transient-type;
  }

  identity WRMRESTART {
    description "Warm Restart";
    base svo-al-tr-t:svo-alarm-transient-type;
  }

}
