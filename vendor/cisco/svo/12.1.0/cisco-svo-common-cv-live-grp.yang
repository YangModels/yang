module cisco-svo-common-cv-live-grp {

  yang-version 1.1;
  namespace "http://cisco.com/yang/svo/common-cv-live-grp";
  prefix cccvlg;

  import ietf-yang-types { prefix yang; }
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO CV common Live Data.";

    revision 2020-12-04 { 
       description "Model version for SVO Release 12.1.0 "; 
       reference cisco-svo-common-cv-live-grp.yang; 
    }
 

 grouping internal-link-list-cv-progress {
       leaf internal-link-tested {
         type uint32;
         config false;
         description "Number of tested patch-cords";
       }
       leaf internal-link-total {
         type uint32;
         config false;
         description "Total number of patch-cords to be tested";
       }
       leaf ref-time {
         type yang:date-and-time;
         config false;
         description "Time stamp of when the tests set started";
       }
   }



  grouping cv-live-grp {
         container automatic {
           uses internal-link-list-cv-progress;
         }
         container user-requested {
           uses internal-link-list-cv-progress;
         }
  }
  
}
