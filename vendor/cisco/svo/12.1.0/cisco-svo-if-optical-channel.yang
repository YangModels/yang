module cisco-svo-if-optical-channel {
    yang-version 1.1;
    namespace "http://cisco.com/yang/svo/och";
    prefix svo-och;

    import cisco-svo-common-optical-channel-grp { prefix coch; }
    
    import cisco-svo-common-optical-channel-oper-grp { prefix cochog; }
    import cisco-svo-common-optical-channel-live-grp { prefix cochlg; }

    organization
        "Cisco Systems, Inc.";

    contact
        "Cisco Systems, Inc. Customer Service Postal: 170 West Tasman
        Drive San Jose, CA 95134 Tel: +1 800 553-NETS E-mail: cs-yang@cisco.com";

    description
        "YANG definition for device interfaces";

    revision 2020-12-04 { 
       description "Model version for SVO Release 12.1.0 "; 
       reference cisco-svo-if-optical-channel.yang; 
    }
 

    grouping optical-channel-grp {
    	description "Optical Chanel grouping";
        container optical-channel {
            description "Specific optical-channel Data";

            uses coch:optch-config-group;
            uses cochog:optch-oper-group;
            uses cochlg:optch-live-data;
        }
    }
}
