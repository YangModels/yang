module cisco-svo-common-pm-types {
  namespace "http://cisco.com/yang/svo/common-pm-types";
  prefix ccpmt;

  import org-openroadm-pm-types { prefix org-openroadm-pm-types; revision-date 2017-12-15; }

  organization
    "Cisco Systems, Inc.";

  contact
    "Cisco Systems, Inc. Customer Service Postal: 170 West Tasman Drive San Jose, CA 95134 Tel: +1 800 553-NETS E-mail: cs-yang@cisco.com";

  description
    "YANG definition for NSC2K platform Automatic Laser Shutdown (ALS) feature.";

  revision 2020-12-04 { 
      description "Model version for SVO Release 12.1.0 "; 
      reference cisco-svo-common-pm-types.yang; 
  }
 

  typedef pm-granularity {
    type enumeration {
      enum "notApplicable" {
        value 1;
        description "This is for total statistic counters on devices that support them.";
      }
      enum "15min" {
        value 2;
      }
      enum "24Hour" {
        value 3;
      }
      enum "1min" {
        value 4;
      }
      enum "1Hour" {
        value 5;
      }
    }
    description "Granularity of PM bin";
  }

  typedef pm-clear-time-frame {
    type enumeration {
      enum "current" {
         value 1;
      }
      enum "all" {
         value 2;
      }
    }
  }

  typedef pm-resource-type {
    type enumeration {
      enum "ethernetCsmacd";
      enum "opticalChannel";
      enum "opticalTransport";
      enum "otnOdu";
      enum "otnOtu";
      enum "opticalXConnection";
    }
  }
  
  typedef pm-data-type {
    type union {
      type uint64;
      type int64;
      type decimal64 {
        fraction-digits 2;
      }
      type decimal64 {
        fraction-digits 7;
      }
      type decimal64 {
        fraction-digits 17;
      }
    }
  }
  
  grouping pm-measurement {
    description
      "Set of parameters related to a PM Measurement";
    leaf pmParameterValue {
      type pm-data-type;
      config false;
      mandatory true;
    }
    leaf pmParameterUnit {
      type string;
      mandatory false;
      description
        "Unit PM parameter has been measured - frames, packets, u, etc";
    }
    leaf validity {
      type org-openroadm-pm-types:validity;
      mandatory false;
    }
  }
}
