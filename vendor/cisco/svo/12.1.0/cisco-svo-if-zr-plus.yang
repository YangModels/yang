module cisco-svo-if-zr-plus {
    yang-version 1.1;
    namespace "http://cisco.com/yang/svo/zr-plus";
    prefix if-zrp;

    import cisco-svo-common-zr-plus-grp { prefix cozrp; }   
    import cisco-svo-common-zr-plus-oper-grp { prefix cozrpog; }

    organization
        "Cisco Systems, Inc.";

    contact
        "Cisco Systems, Inc. Customer Service Postal: 170 West Tasman
        Drive San Jose, CA 95134 Tel: +1 800 553-NETS E-mail: cs-yang@cisco.com";

    description
        "YANG definition for ZR Plus device interfaces";

    revision 2020-12-04 { 
       description "Model version for SVO Release 12.1.0 "; 
       reference cisco-svo-if-zr-plus.yang; 
    }
 

    grouping zr-plus-grp {
    	description "ZR Plus grouping";
        container zrPlus {
            description "Specific ZR Plus Data";

            uses cozrp:zr-plus-config-group;
            uses cozrpog:zr-plus-oper-group;
        }
    }
}
