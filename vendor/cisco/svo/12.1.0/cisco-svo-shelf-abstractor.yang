module cisco-svo-shelf-abstractor {
  namespace "http://cisco.com/yang/svo/shelf-abstractor";
  prefix svo-shelf-abs;

  import tailf-common { prefix tailf; }
  import cisco-svo-common-equipment-types { prefix ccet; }

  tailf:export cli;

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "Grouping YANG definition internal links.";

    revision 2020-12-04 { 
       description "Model version for SVO Release 12.1.0 "; 
       reference cisco-svo-shelf-abstractor.yang; 
    }

  grouping virtual-shelf-chassis-entry-grp {
    leaf uid {
      type ccet:chassis-uid-t;
      mandatory true;
      description "chassis global unique indentifier";
    }

    leaf device {
      type string;
      mandatory true;
      description "physical device identifier";
    }

    leaf lid {
      type ccet:chassis-id-t;
      description "chassis local (device) unique identifier";
    }        
  }

  grouping virtual-shelf-passive-unit-entry-grp {
    leaf uid {
      type ccet:passive-unit-uid-t;
      mandatory true;
      description "passive unit global unique indentifier";
    }

    leaf device {
      type string;
      mandatory true;
      description "physical device identifier";
    }

    leaf lid {
      type ccet:passive-unit-id-t;
      mandatory true;
      description "passive unit local (device) unique identifier";
    }        
  }

  container virtual-shelf {
    list chassis-from-uid {
      key uid;
      unique "device lid";
      uses virtual-shelf-chassis-entry-grp;
      leaf display-name {
        type string;
        description "user-defined custom non-unique mnemonic path";
      }
    }

    list uid-from-chassis {
      key "device lid";
      unique "uid";
      uses virtual-shelf-chassis-entry-grp;
    }

    list passive-from-uid {
      key uid;
      unique "device lid";
      uses virtual-shelf-passive-unit-entry-grp;
      leaf display-name {
        type string;
        description "user-defined custom non-unique mnemonic path";
      }
    }

    list uid-from-passive {
      key "device lid";
      unique "uid";
      uses virtual-shelf-passive-unit-entry-grp;
    }
  }
}
