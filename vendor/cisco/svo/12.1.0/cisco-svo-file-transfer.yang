module cisco-svo-file-transfer {
  yang-version 1.1;
  namespace "http://cisco.com/yang/cisco-svo-file-transfer";
  prefix svo-ft;

  import ietf-inet-types { prefix inet; }
  import tailf-common { prefix tailf; }
  
  organization
    "Cisco Systems, Inc.";

  contact
    "Cisco Systems, Inc.
     Customer Service

     Postal: 170 West Tasman Drive
     San Jose, CA 95134

     Tel: +1 800 553-NETS

     E-mail: cs-yang@cisco.com";

  description
    "YANG definition for file transfer. 
     The model is enough generic in order to allow transferring any kind
     of file including SW packages, DB images or diagnostics files";

  revision 2020-12-04 { 
     description "Model version for SVO Release 12.1.0 "; 
     reference cisco-svo-file-transfer; 
  }

  typedef transfer-type {
    type enumeration {
      enum "download" {
        description "Specify transfer is download. 
                     The SVO gets the file from the server
                     (storing it in local folder)";
      }
      enum "upload" {
        description "Specify transfer is upload. 
                     The SVO puts the file to the server 
                     (reading it from the local folder)";
      }
    }
  }
  
  typedef rpc-status {
    type enumeration {
      enum "Successful" {
        value 1;
      }
      enum "Failed" {
        value 2;
      }
      enum "In-progress" {
        value 3;
      }
    }
    description
      "result of RPC execution";
  }

  grouping rpc-response-status {
    leaf status {
      type rpc-status;
      mandatory true;
      description
        "Successful, Failed or In-progress";
    }
    leaf message {
      type string;
      description
        "Gives a more detailed status.";
    }
  }

  container file-transfer {
    tailf:action transfer {
      description "File transfer using SFTP";
      tailf:actionpoint transfer;
      input {
        leaf action {
          type transfer-type;
          mandatory true;
          description "Type of action - download/upload";
        }
        leaf local-file-path {
          type string;
          mandatory true;
          description "Local file path. Ex: /tmp/local-file.txt";
        }
        leaf remote-file-path {
          type inet:uri;
          mandatory true;
          description
            "Remote file path. A URI for the remote file path.
             Format:sftp://user[:password]@host[:port]/path. 
             Ex: sftp://test:verify@[2001:db8:0:1::10]:22/home/user/sample";
        }
      }
      output {
        uses rpc-response-status;
      }
    }
  }

  notification transfer-notification {
    description
      "notification for transfer operation events.";
    leaf remote-file-name {
      type string;
      description
        "Remote file name used in transfer RPC.
    	 It is the file name only without any path.";
    }

    uses rpc-response-status;

    container progress {
      when "current()/../status = 'In-progress'";
      description
        "progress status when response is in-progress";
      leaf bytes-transferred {
        type uint64;
        description
          "bytes transferred";
      }
      leaf speed {
        type uint64;
        description
          "transfer speed expressed in bytes per seconds";
      }
      leaf percentage-complete {
        type uint8;
        description
          "percentage completed";
      }
      leaf remaining-time {
        type uint32;
      description 
          "estimated remaining time in milliseconds";
      }
    }
  }  
}
