module cisco-ncs2k-equipment-oper-grp {

  yang-version 1.1;
  namespace "http://cisco.com/yang/ncs2k/equipment-oper";
  prefix ncs2k-eq-op;

  import tailf-common { prefix tailf; }
  import ietf-yang-types { prefix ietf; revision-date 2013-07-15; }
  import cisco-svo-common-types { prefix cct; }
  import cisco-svo-common-equipment-types { prefix ccet; }
  import cisco-ncs2k-common-eei-types { prefix ncs2k-ceeit; }
  import cisco-svo-common-equipment-oper-grp { prefix cceqptog; }
  import cisco-ncs2k-ncs2k-equipment-types { prefix ncs2k-2k-cet; }
  import cisco-ncs2k-ancillary-oper-grp { prefix ncs2k-anc-op; }
  import cisco-ncs2k-equipment-types { prefix cet; }
  
  organization
    "Cisco Systems, Inc.";

  contact
    "Cisco Systems, Inc. Customer Service Postal: 170 West Tasman Drive San Jose, CA 95134 Tel: +1 800 553-NETS E-mail: cs-yang@cisco.com";

  description
    "YANG definition for NSC2K platform: node, equipments, interfaces, internal links, xconn.";

    revision 2020-12-04 { 
       description "Model version for SVO Release 12.1.0 "; 
       reference cisco-ncs2k-equipment-oper-grp.yang; 
    }
 

  grouping usb-port-association-info-grp-oper {

    leaf usb-port-equipment-entity-index {
      config false;
      type ncs2k-ceeit:equipment-entity-index-t;
      tailf:cli-show-template '$(.|hex)';
    }
  }

  grouping lane-list-oper {
    list lane {
      key lane-id;
      description "List of lanes";
      leaf lane-id {
        type ccet:lane-id-t;
        description "Port Lane identifier";
      }

      uses ncs2k-2k-cet:equipment-entity-index-grp;
      uses cceqptog:lane-content-oper;
    }
  }

  grouping port-content-oper {

    leaf port-name {
      type ccet:port-name-t;
      config false;
      description "Portname with syntax UId/[Slot-Id/]Port-Id.";
    }

    leaf port-number {
      type uint16;
      config false;
      description "Port number";
    }

    leaf direction {
      type cct:direction;
      config false;
      description "Port direction: RX, TX, BIDI";
    }

    leaf port-role {
      type ccet:port-role-t;
      config false;
      description "Port role: Trunk or Client";
    }
    uses cceqptog:mpo-addressing;
  }


  typedef obfl-status-t {
    type enumeration {
      enum "OBFL_UNSUPPORTED" {
        description "OBFL Not Supported";
      }
      enum "OBFL_CARD_NOT_READY" {
        description "Card Not ready for OBFL operation";
      }
      enum "OBFL_IDLE" {
        description "Ready for OBFL operation";
      }
      enum "OBFL_WRITING" {
        description "OBFL Procedure already start";
      }
    }
    description "all possible OBFL card status";
  }
  
  grouping obfl-info-oper {
    leaf obfl-status {
      type ncs2k-eq-op:obfl-status-t;
    }

    leaf last-operation-time {
      type ietf:date-and-time;
      description "UTC Time and Date of the last completed obfl operation";
    }
  }

  grouping port-list-oper {
    list port {
      key port-id;
      description "
        List of configured (provisioned or pre-provisioned)
        ports";

      leaf port-id {
        type ccet:port-id-t;
        description "Port identifier";
      }

      // Duplicated from Config
      leaf port-type {
        type identityref {
          base ccet:port-type;
        }
        mandatory true;
        description "Port Type";
      }

      uses ncs2k-2k-cet:equipment-entity-index-grp;
      uses port-content-oper;
      uses lane-list-oper;
    }
  }

  grouping passive-unit-id-grp {
    leaf passive-unit-id {
      type ccet:passive-unit-id-t;
      mandatory true;
      description " passive-unit-id is the unique index that identifies the passive-unit in the node. The passive-unit-id is unique in the node,
            so, multi-rack nodes do not have passive-unit-id duplicated";
    }
  }

  grouping parent-equipment-entity-index-grp {
    description "
      Parent Equipment entity index reusable grouping";

    leaf parent-equipment-entity-index {
      type ncs2k-ceeit:equipment-entity-index-t;
      config false;
      tailf:cli-show-template '$(.|hex)';
    }
  }

  grouping child-equipment-entity-indices-grp {
    description "
      Child Equipment entity indices reusable grouping";

    list children {
      key equipment-entity-index;
      description "Children equipment entity indices operdata references for fast navigation/deletion";
      uses ncs2k-2k-cet:equipment-entity-index-grp;
    }
  }

  grouping module-content-oper {
    uses cceqptog:equipment-properties-oper;

    leaf degree-of-support {
      type ccet:degree-of-support-type-t;
      config false;
      description "Degree of card type supporting. The partial supporting means that the ports and interfaces information is hidden";
    }

    container obfl-report {
      config false;
      uses obfl-info-oper;
    }
  }

  grouping module-content-oper-usb-association {
    uses usb-port-association-info-grp-oper {
      when "../../chassis-type = 'cet:NCS2K-MF10-6RU' or ../../chassis-type = 'cet:NCS2K-MF-6RU'";
    }
  }

  grouping equipments-oper {
    description "Definition for equipments, chassis, modules, ports";

    list equipment-entity-references {
      key equipment-entity-index;
      description "Equipment entity index operdata references for fast navigation";

      uses ncs2k-2k-cet:equipment-entity-index-grp;
      uses parent-equipment-entity-index-grp;
      uses child-equipment-entity-indices-grp;

      leaf equipment-path {
        type instance-identifier;
        config false;
        description "Equipment path reference";
      }
    }

    list passive-unit {
      key passive-unit-id;
      unique equipment-entity-index;
      description "List of standalone passive units";

      uses passive-unit-id-grp;
      uses ncs2k-2k-cet:equipment-entity-index-grp;

      // copy of configurable parameter needed here for 'when/must' constraints
      leaf passive-unit-type {
        type identityref {
          base ccet:ru-passive-type;
        }
        config false;
        description "Module type";
      }
      leaf actual-ru-occupation {
        type ccet:ru-occupation-t;
        config false;
        description "Actual number of used Rack Units";
      }

      uses cceqptog:equipment-properties-oper;
      
      container usb-port-association-info-oper {
        uses usb-port-association-info-grp-oper;
      }
      
      uses port-list-oper;
    }

    list chassis {
      key chassis-id;
      unique equipment-entity-index;
      description "List of the chassis constituting the node";
      leaf chassis-id {
        type ccet:chassis-id-t;

        description "chassis-id is the unique index that identifies the chassis in the node. The chassis-id is unique in the node, so, multi-rack
                nodes do not have chassis-id duplicated";
      }

      uses ncs2k-2k-cet:equipment-entity-index-grp;

      // copy of configurable parameter needed here for 'when/must' constraints
      leaf chassis-type {
        type ccet:chassis-type-t;
        config false;
        description "Chassis Type";
      }

      leaf actual-ru-occupation {
        type ccet:ru-occupation-t;
        config false;
        description "Number of used Rack Units";
      }

      uses cceqptog:equipment-properties-oper;
      
      container usb-port-association-info-oper {
        when "../chassis-type = 'cet:NCS2K-MF10-6RU' or ../chassis-type = 'cet:NCS2K-MF-6RU'";
        uses usb-port-association-info-grp-oper;
      }
      
      uses ncs2k-anc-op:ancillary-grp {
        when "chassis-type = 'cet:NCS2006-ANSI' or chassis-type = 'cet:NCS2006-ETSI' or chassis-type = 'cet:NCS2015-ANSI' or chassis-type
                = 'cet:NCS2015-ETSI'";
        augment "ancillary/ecu-slot/ecu/usb-uts-module/usb-port/associated-passive" {
          leaf chassis-id {
            type ccet:chassis-id-t;
            description " chassis-id is the unique index that identifies the chassis in the node. The chassis-id is unique in the node, so, multi-rack
                        nodes do not have chassis-id duplicated";
          }
        }
      }

      uses ncs2k-anc-op:ancillary-passive-grp {
        when "chassis-type = 'cet:NCS2K-MF10-6RU' or chassis-type = 'cet:NCS2K-MF-6RU'";
        augment "ancillary-passive/usb-uts-passive-module/usb-passive-port/associated-passive" {
          leaf chassis-id {
            type ccet:chassis-id-t;
            description " chassis-id is the unique index that identifies the chassis in the node. The chassis-id is unique in the node, so, multi-rack
                        nodes do not have chassis-id duplicated";
          }
        }
      }

      container monitor {
        container voltage {
          list psu-voltage {
            key psu-id;
            description "List of the PSU Voltage";
            leaf psu-id {
              type cct:psu-id-t;
              description "PSU identifier";
            }
          }
        }
      }

      list module {
        key slot;
        unique equipment-entity-index;
        description "List of the modules, cards and ppm";

        leaf slot {
          type ccet:slot-t;

          description "Slot identifier 1:999 or ppmSlot identifier 1:999-1:99";
        }

        // duplicated in config
        uses passive-unit-id-grp {
          when "../chassis-type = 'cet:NCS2K-MF10-6RU' or ../chassis-type = 'cet:NCS2K-MF-6RU'";
        }

        // copy of configurable parameter needed here for 'when/must' constraints
        leaf module-type {
          type identityref {
            base ccet:module-type;
          }
          config false;
          description "Module type";
        }

        uses ncs2k-2k-cet:equipment-entity-index-grp;

        uses parent-equipment-entity-index-grp {
          when "re-match(./slot, '[0-9]+[-]{1}[0-9]+')";
        }

        uses module-content-oper;
        
        container usb-port-association-info-oper {
          config false;
          uses module-content-oper-usb-association;
        }
        
        uses port-list-oper;
      }
    }
  }

  grouping internal-links-oper {
    list internal-link {
      key "src-port-name dst-port-name";
      description "Internal patchcord";

      leaf src-port-name {
        description "Identifier of the source portname in the format uid/[slot-id/]port-id.";
        type string;
      }

      leaf dst-port-name {
        description "Identifier of the destination portname in the format uid/[slot-id/]port-id.";
        type string;
      }

      leaf ipc-index {
        type ncs2k-ceeit:equipment-entity-index-t;
        config false;
      }

      leaf source-index {
        type ncs2k-ceeit:equipment-entity-index-t;
        config false;
      }

      leaf destination-index {
        type ncs2k-ceeit:equipment-entity-index-t;
        config false;
      }

      uses cceqptog:internal-links-oper-grp;
    }
  }

  grouping node-connection-verification-oper-grp {
    container connection-verification {
      uses cceqptog:node-connection-verification-oper-grp;
    }
  }

}
