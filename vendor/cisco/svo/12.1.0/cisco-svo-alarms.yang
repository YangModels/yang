module cisco-svo-alarms {
    namespace "http://cisco.com/yang/svo/alarms";
    prefix svo-al;
    
    import tailf-common {
        prefix tailf;
    }

    import tailf-ncs-alarms {
        prefix al;
    }

    import cisco-svo-common-equipment-types { prefix ccet; }

		organization
			"Cisco Systems, Inc.";

		contact
			"Cisco Systems, Inc.
			Customer Service

			Postal: 170 West Tasman Drive
			San Jose, CA 95134

			Tel: +1 800 553-NETS

			E-mail: cs-yang@cisco.com";

    description
    "Yang definition for alarms";

    revision 2020-12-04 { 
       description "Model version for SVO Release 12.1.0 "; 
       reference cisco-svo-alarms.yang; 
    }
 

    typedef service-affecting-type-t {
      type enumeration {
        enum not-specified {
          description "Not Available";
        }
        enum SA {
          description "Service Affecting";
        }
        enum NSA {
          description "Not Service Affecting";
        }
      }
      description "Indicates is the Alarm is Service Affecting";
    }

    typedef direction-t {
      type enumeration {
		    enum Transmit;
		    enum Receive;
		    enum NA;
      }
      description "Indicates is the Alarm direction (Transmit/Receive/NA)";
    }

    typedef location-t {
      type enumeration {
			  enum FAR;
		    enum NEAR;
		    enum NA;
      }
      description "Indicates is the Alarm location (Far/Near/NA)";
    }

    typedef equipment-type-t {
      type string;
      description "Equipment type of the associated object";
    }

    typedef low-device-name-t {
      type string;
      description "Name of the low level device";
    }

    typedef alarm-obj-name-t {
      type string;
      description "Managed Object Path as String";
    }

  	grouping common-ext-alarm-parameters {
      description
        "Common parameters for an alarm.

         This grouping is used both in the active alarm list and in the
         notification representing an alarm state change.";

    	leaf equipment-type {
    	  type equipment-type-t;
		    default "";      
        description
          "Equipment type of the associated object";
        tailf:info "Equipment type of the associated object";
   	  } 
 
    	leaf low-device-name {
    	  type low-device-name-t;
		    default "";      
        description
             "Name of the low level device";
        tailf:info "Name of the low level device";
   	  }  

    	leaf alarm-obj-name {
    	  type alarm-obj-name-t;
		    default "";      
        description
             "AlarmObjectName: the managed-object as short string";
         tailf:info "Alarm Object Name: the managed-object as short string";
   	  }  

		  leaf service-affecting-type {
		    type service-affecting-type-t;
        description
          "Indicates is the Alarm is Service Affecting";
        tailf:info "Indicates is the Alarm is Service Affecting";
		    default not-specified;
		  }

		  leaf not-alarmed {
	      type boolean;
		    default false;
		    description
		      "Indicates if the alarm has a 2k severity: not-alarmed.";
		    tailf:info "Indicates if the alarm has a 2k severity: not-alarmed.";
		  }

		  leaf transient {
	      type boolean;
		    default false;
		    description
		      "Indicates if the alarm is transient.";
		    tailf:info "Indicates if the alarm is transient.";
		  }

		  leaf direction {
        type direction-t;
        description
          "Indicates is the Alarm direction (Transmit/Receive/NA)";
        tailf:info "Indicates is the Alarm direction (Transmit/Receive/NA)";
		    default NA;
		  }

		  leaf location {
        type location-t;
        description
          "Indicates is the Alarm location (Far/Near/NA)";
        tailf:info "Indicates is the Alarm location (Far/Near/NA)";
		    default NEAR;
		  }

      leaf rack-id {
        type ccet:rack-id-t;
        description "Rack ID";
      }

      leaf ru-position {
        type ccet:ru-position-t;
        description "Rack Unit (RU) Position";
      }
	  }

    /*
     * The Augment of /alarms data tree
    */
    augment /al:alarms/al:alarm-list/al:alarm { 
		uses common-ext-alarm-parameters;     
    } 	 

 	  augment /al:alarm-notification {
		  uses common-ext-alarm-parameters; 
	  }
}
