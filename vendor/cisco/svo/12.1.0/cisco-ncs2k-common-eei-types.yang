module cisco-ncs2k-common-eei-types {

  yang-version 1.1;
  namespace "http://cisco.com/yang/ncs2k/common-eei-types";
  prefix ncs2k-ceeit;

  organization
    "Cisco Systems, Inc.";

  contact
    "Cisco Systems, Inc.
       Customer Service
       
       Postal: 170 West Tasman Drive
       San Jose, CA 95134
       
       Tel: +1 800 553-NETS
       
       E-mail: cs-yang@cisco.com";

  description "
  YANG model definition for NCS2K common types";

    revision 2020-12-04 { 
       description "Model version for SVO Release 12.1.0 "; 
       reference cisco-ncs2k-common-eei-types.yang; 
    }
 

  typedef equipment-entity-index-t {
    type uint32 {
      range 0..2147483647 {
        error-message "equipment-entity-index must be >= 0";
      }
    }
    description "TNC entity index";
  }
}
