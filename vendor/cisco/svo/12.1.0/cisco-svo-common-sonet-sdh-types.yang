module cisco-svo-common-sonet-sdh-types {
  yang-version 1.1;
  namespace "http://cisco.com/yang/svo/common-sonet-sdh-types";
  prefix ccssdht;

  import org-openroadm-interfaces { prefix or-if; revision-date 2018-09-28; }
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO SONET/SDH common types.";

  revision 2020-12-04 { 
      description "Model version for SVO Release 12.1.0 "; 
      reference cisco-svo-common-sonet-sdh-types.yang; 
  }
 

  typedef media-type-t {
    type enumeration {
      enum sonet {
        description "SONET media type";
      }
      enum sdh {
        description "SDH media type";
      }
    }
  }

  typedef sonet-sdh-rate-t {
    type enumeration {
      enum OC3 {
        description "OC3 SONET Rate";
      }
      enum OC12 {
        description "OC12 SONET Rate";
      }
      enum OC48 {
        description "OC48 SONET Rate";
      }
      enum OC192 {
        description "OC192 SONET Rate";
      }
      enum STM1 {
        description "STM1 SDH Rate";
      }
      enum STM4 {
        description "STM4 SDH Rate";
      }
      enum STM16 {
        description "STM16 SDH Rate";
      }
      enum STM64 {
        description "STM64 SDH Rate";
      }
    }
  }

  typedef sonet-sdh-quality-level-t {
    type enumeration {
      enum DUS {
        value 0;
        description "Don't Use for Synchronization";
      }
      enum PRS {
        value 1;
        description "Primary Reference Source, Stratum 1 Traceable";
      }
      enum RES {
        value 2;
        description "Reserved for network synchronization use";
      }
      enum SMC {
        value 3;
        description "Sonet Minimum Clock Traceable";
      }
      enum ST2 {
        value 4;
        description "Stratum 2 Traceable";
      }
      enum ST3 {
        value 5;
        description "Stratum 3 Traceable";
      }
      enum ST3E {
        value 6;
        description "Stratum 3E Traceable (2nd generation only)";
      }
      enum ST4 {
        value 7;
        description "Stratum 4 Traceable";
      }
      enum STU {
        value 8;
        description "Synchronized, Traceability Unknown";
      }
      enum TNC {
        value 9;
        description "Transit Node Clock (2nd generation only)";
      }
    }
    description "Clock Source Quality Level
      PRS  - Primary Reference Source, Stratum 1 Tracable
      STU  - Synchronized, Tracability Unknown
      ST2  - Stratum 2 Tracable
      TNC  - Transit Node Clock (2nd generation only)
      ST3E - Stratum 3E Tracable (2nd generation only)
      ST3  - Stratum 3 Tracable
      SMC  - Sonet Minimum Clock Tracable
      ST4  - Stratum 4 Tracable
      DUS  - Don't Use for Synchronization
      RES  - Reserved for network synchronization use.";
   }

   typedef j0-trace-t {
     type string {
       length "0..16";
     }
     description "J0 TRACE String";
   }

  identity sonetSdh {
    base or-if:interface-type;
    description "Sonet or Sdh type";
  }

}
