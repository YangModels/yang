module cisco-svo-common-functional-grp {
    yang-version 1.1;
    namespace "http://cisco.com/yang/svo/common-functional-grp";
    prefix "ccfunctg";

    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description "Cisco Common Functional Config group";

    revision 2020-12-04 { 
       description "Model version for SVO Release 12.1.0 "; 
       reference cisco-svo-common-functional-grp.yang; 
    }
 

    grouping node-degrees-config-data {
    	description "Degree configuration paramters grouping";

        leaf degree-label {
            type string;
            description "Mnemonic label for the degree";
        }
    }

    grouping optical-span-config-data {
    	description "Optical span fibre properties configuration paramters grouping";

        list tx-span-fibers-data {
            key "fiber-id";
			description "List of the fibre data traversed by the optical signal sent into the TX span";

            leaf fiber-id {
                type uint32;
                description "Ordinal id of the fiber; fibers must be ordered as traversed by the optical signal sent into the span";
            }

            leaf fiber-type {
                type cct:fiber-type-t;
                mandatory true;
                description "Fiber type (e.g. G652-SMF, ELEAF, ...";
            }

            leaf fiber-length {
                type cct:length-km-t;
                mandatory true;
                description "Fiber length in km";
            }

            leaf PMD-coefficient {
                type cct:pmd-coeff-t;
                default 0.00;
                description "Polarization Mode Dispersion (PMD) coefficient expressed in ps/sqrt(km)";
            }

            leaf input-attenuator {
                type cct:attenuation-t;
                default 0.0;
                description "Concentrated attenuation (or loss) and the input of the fiber";
            }

            leaf output-attenuator {
                type cct:attenuation-t;
                default 0.0;
                description "Concentrated attenuation (or loss) and the output of the fiber";
            }
        }

        leaf tx-span-optical-validation {
            type boolean;
			default true;
            description "Fiber span support Optical Validation for services routing:
        		true: services will be routed on this span if Optical Validation is passed
        		false: services will be routed on this span only if no Optical Validation is required";
        }


    }

    grouping OMS-link-GN-performance-config-data {
    	description "GN model configuration parameters grouping";

        choice planned-wavelength-spacing {
        	case fixed-grid {
                leaf spacing {
                    type cct:fixed-grid-spacing-t;
                    description "Select the services spectral spacing using a fixed ITU grid";
                }
            }

            case flexible-grid {
                leaf spectrum-occupancy {
                    type cct:flexible-grid-spectrum-occupancy-t;
                    description "Select the services spectral occupancy (percentage) using a flexible allocation";
                }
            }
            description "Select the GN Model wavelength spacing; selecting either of the option will enable the GN Model
            	on the OMS link; deleting both leaf (unselecting the choice) will disable the GN Model validation";
        }
    }

    grouping OMS-link-power-control-conf {
    	description "OMS link power control configuration paramters grouping";
        leaf admin-status {
            type cct:Pwr-Ctrl-Admin-status-t;
            description "Admin Status of Link Power Control";
        }
    }

    grouping span-loss-config-data {
        description "Span loss configuration data grouping";

        leaf min-expected-span-loss {
            type cct:attenuation-t {
            }
            description "Min expected span loss";
        }

        leaf max-expected-span-loss {
            type cct:attenuation-t {
            }
            description "Max expected span loss";
        }
    }

}
