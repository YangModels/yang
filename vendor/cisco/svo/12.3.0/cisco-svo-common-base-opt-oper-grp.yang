module cisco-svo-common-base-opt-oper-grp {

    yang-version 1.1;
    namespace "http://cisco.com/yang/svo/common-base-opt-oper-grp";
    prefix ccboog;

    import tailf-common { prefix tailf; }
    import ietf-yang-types { prefix yang; }
    import cisco-svo-common-types { prefix cct; }
    import org-openroadm-common-optical-channel-types { prefix roadm-oct; revision-date 2018-05-30; }

    organization
        "Cisco Systems, Inc.";

    contact
        "Cisco Systems, Inc.
     Customer Service

     Postal: 170 West Tasman Drive
     San Jose, CA 95134

     Tel: +1 800 553-NETS

     E-mail: cs-yang@cisco.com";

    description "
    Cisco Common Types, used inside both,
    the equipment and the network modules and them
    submodules.";

  revision 2021-12-25 {
  	description "Model version for SVO Release 12.3.0";
  	reference cisco-svo-common-base-opt-oper-grp.yang;
  }
  
    revision 2020-12-04 { 
       description "Model version for SVO Release 12.1.0 "; 
       reference cisco-svo-common-base-opt-oper-grp.yang; 
    }
 

    grouping oper-state-grp {
        description
          "Operational State reusable grouping";

        leaf oper-primary-state {
            type enumeration {
                enum IS;
                enum OOS;
            }
            config false;
            description
              "Primary Oper State";
        }

        leaf oper-secondary-state {
            type enumeration {
                enum NR;
                enum AU-AINS;
                enum MA-DSBLD;
                enum MA-MT;
                enum MA-LPBK-MT;
                enum AU-AINS-MEA;
                enum AU-AINS-SWDL;
                enum AU-AINS-UEQ;
                enum AU-MEA;
                enum AU-SWDL;
                enum AU-UEQ;
                enum AUMA-MEA-MT;
                enum AUMA-MEA-UAS;
                enum AUMA-MT-UEQ;
                enum AUMA-MT-SWDL;
                enum AUMA-UAS;
                enum AUMA-UAS-UEQ;
                enum MA-DSBLD-OOG;
                enum MA-MT-OOG;
                enum MA-LPBK-MT-OOG;
                enum MA-FLT-MT;
                enum MA-FLT-LPBK-MT;
                enum AU-FLT;
                enum AU-AINS-FLT;
                enum AU-FLT-OOG;
                enum AUMA-FLT-MT;
                enum AUMA-FLT-LPBK-MT;
                enum AUMA-FLT-MT-OOG;
                enum AUMA-FLT-LPBK-MT-OOG;
                enum AU-AINS-FLT-OOG;
                enum MA-FLT-MT-OOG;
                enum AU;
            }
            config false;
            description
              "Secondary Oper State";
        }
    }

    grouping gain-degrade-thresholds-grp {
        description
          "Thresholds to detect Optical Gain degrade alarms";
        leaf gain-degrade-high {
            type cct:db-oper-t;
            config false;
            description
              "High Gain Degrade Value";
        }

        leaf gain-degrade-low {
            type cct:db-oper-t;
            config false;
            description
              "Low Gain Degrade Value";
        }
    }

    grouping power-degrade-thresholds-grp {
        description
          "Thresholds to detect Optical Power degrade alarms";
        leaf power-degrade-high {
            type cct:pwr-oper-t;
            config false;
            description
              "Low Power Degrade Value";
        }
        leaf power-degrade-low {
            type cct:pwr-oper-t;
            config false;
            description
              "High Power Degrade Value";
        }
    }

    grouping power-failure-low-threshold-oper-grp {
        description
          "Threshold to detect Optical Power fail alarm";
        leaf power-failure-low {
            type cct:pwr-oper-t;
            config false;
            description
              "Power Failure Low Value";
        }
    }

    grouping power-thresholds-grp {
        description
          "Optical power Thresholds for deg/fail alrams";
        uses power-degrade-thresholds-grp;
        uses power-failure-low-threshold-oper-grp;
    }

    grouping noise {
        description
          "Equivalent Cross-Talk (XT) - average grouping";
        leaf noise {
            type decimal64 {
                fraction-digits 3;
            }
            units "dB";
            config false;
            description
              "Equivalent Cross-Talk (XT) for GN model validation - average value";
        }
    }

    grouping noise-sigma {
        description
          "Equivalent Cross-Talk (XT) - standard deviation grouping";
        leaf noise-sigma {
            type decimal64 {
                fraction-digits 3;
            }
            units "dB";
            config false;

            description
              "Equivalent Cross-Talk (XT) for GN model validation - standard deviation";
        }
    }

    grouping chromatic-dispersion {
        description
          "Cumulated Chromatic Dispersion (CD) grouping";
        leaf chromatic-dispersion {
            type decimal64 {
                fraction-digits 3;
            }
            units "ps/nm";
            config false;

            description
              "Cumulated Chromatic Dispersion (CD) for GN model validation";
        }
    }

    grouping chromatic-dispersion-slope {
        description
          "Cumulated Chromatic Dispersion (CD) slope grouping";
        leaf chromatic-dispersion-slope {
            type decimal64 {
                fraction-digits 3;
            }
            units "ps/nm^2";
            config false;

            description
              "Cumulated Chromatic Dispersion (CD) Slope for GN model validation";
        }
    }

    grouping pmd {
        description
          "Cumulated Polarization Mode Dispersion (PMD) grouping";
        leaf pmd {
            type decimal64 {
                fraction-digits 3;
            }
            units "ps";
            config false;

            description
              "Cumulated Polarization Mode Dispersion (PMD) for GN model validation";
        }
    }

    grouping pdl {
        description
          "Cumulated Polarization Dependent Loss (PDL) grouping";
        leaf pdl {
            type decimal64 {
                fraction-digits 3;
            }
            units "dB";
            config false;

            description
              "Cumulated Polarization Dependent Loss (PDL) for GN model validation";
        }
    }
	
	grouping q-factor {
        description
          "Quality Factor";
        leaf q-factor {
            type decimal64 {
                fraction-digits 3;
            }
            units "dB";
            config false;

            description
              "Quality Factor";
        }
    }
    
     grouping temp {
        description
          "Temperature";
        leaf  temp{
            type decimal64 {
                fraction-digits 3;
            }
            units "Celsius";
            config false;

            description
              "Temperature";
        }
    }
    
     grouping cfo {
        description
          "Central Frequency Offset";
         leaf cfo{
            type decimal64 {
                fraction-digits 3;
            }
            units "MHz";
            config false;

            description
              "Central Frequency Offset";
        }
    }
	
    grouping drop-power {
        description
          "Circuit Drop Power - average grouping";
        // Valid for DROP
        leaf drop-power {
            type decimal64 {
                fraction-digits 3;
            }
            units "dBm";
            config false;

            description
              "Circuit Drop Power for GN model validation - average value";
        }
    }

    grouping drop-power-sigma {
        description
          "Circuit Drop Power - standard deviation grouping";
        // Valid for DROP
        leaf drop-power-sigma {
            type decimal64 {
                fraction-digits 3;
            }
            units "dB";
            config false;

            description
              "Circuit Drop Power for GN model validation - standard deviation";
        }
    }

    grouping sf-filter {
        description
          "Self-Filtering (SF) grouping";
        list sf-filter {
            key "filter-type";
            leaf filter-type {
                type enumeration {
                    enum "32MuxDeMuxO";
                    enum "4MD";
                    enum "32DeMux";
                    enum "32WSS";
                    enum "40WSS";
                    enum "40MuxDeMux";
                    enum "WXC";
                    enum "Intl";
                    enum "SMR";
                    enum "WXC80";
                    enum "nullSfFilter";
                    enum "16WXC";
                }
                description
                  "GN model Self-Filtering Optical Filter Type";
            }
            leaf filters-count {
                type uint32;
                description
                  "Number of traversed filters";
            }
            config false;
            description
              "Self-Filtering (SF) list of equivalent traversed filters for GN model validation";
        }
    }

    grouping fgdr-filter {
        description
          "Filtering-Group-Delay-Ripple (FGDR) grouping";
        list fgdr-filter {
            key "filter-type";
            leaf filter-type {
                type enumeration {
                    enum "40wssExp";
                    enum "40wssAdd";
                    enum "40muxdmx";
                    enum "32wssExp";
                    enum "interleaver";
                    enum "deinterleaver";
                    enum "nullFgdrFilter";
                    enum "smroadm";
                    enum "chiantiMuxDmx";
                    enum "16WXCMuxDmx";
                }
                description
                  "GN model FGDR Optical Filter Type";
            }
            leaf filters-count {
                type uint32;
                description
                  "Number of traversed filters";
            }
            config false;
            description
              "Filtering-Group-Delay-Ripple (FGDR) list of equivalent traversed filters for GN model validation";
        }
    }

    grouping GN-Performance-Data {
        description
          "Optical data required by GN model grouping";
        container gn-data {
            presence
              "Optional - GN Model data";
            config false;
            description
              "Optical data required by GN model for validation and feasibility studies";

            leaf last-change {
                type yang:date-and-time;
                description "Time stamp of last change";
                config false;
            }

            // Valid for APC Domain, ADD, DROP
            uses noise;
            uses noise-sigma;

            // Valid for APC Domain
            uses chromatic-dispersion;
            uses chromatic-dispersion-slope;

            // Valid for ADD, DROP
            uses drop-power;
            uses drop-power-sigma;

            // Valid for APC Domain, ADD, DROP
            uses pmd;
            uses pdl;
            uses sf-filter;
            uses fgdr-filter;
        }
    }

	grouping common-automatic-raman-calibration-report-grp {
	
	    description "Automatic Raman calibration operational data grouping (common data)"; 
	
        leaf time-stamp {
            type yang:date-and-time;
            config false;
            description
              "Time stamp of calibration";
        }

        leaf status {
            type cct:raman-automatic-calib-status-t;
            config false;
            description
              "Status of automatic Raman Calibration";
        }

        leaf target-gain {
            type cct:db-oper-t;
            config false;
            description
              "Target raman gain";
        }

        leaf obtained-gain {
            type cct:db-oper-t;
            config false;
            description
              "Obtained gain";
        }

        leaf target-tilt {
            type cct:db-oper-t;
            config false;
            description
              "Target spectrum tilt";
        }

        leaf obtained-tilt {
            type cct:db-oper-t;
            config false;
            description
              "Obtained spectrum tilt";
        }

        leaf result {
            type cct:raman-calib-result-t;
            config false;
            description
              "Calibration result versus target gain and tilt";
        }	
	}

    grouping device-automatic-raman-calibration-report-grp {
    
        description "Automatic Raman calibration operational data grouping (calibration directed by the device)"; 

        leaf raman-noise-floor {
            type cct:dbm-oper-t;
            config false;
            description
              "Power level of noise floor generated by Raman Amplification";
        }

        leaf incoming-power-with-pumps-off {
            type cct:dbm-oper-t;
            config false;
            description
              "Power level of probe signal with raman pumps off";
        }

        leaf incoming-power-with-pumps-on {
            type cct:dbm-oper-t;
            config false;
            description
              "Power level of probe signal with raman pumps on (combined with raman noise floor)";
        }

        leaf power-source {
            type cct:raman-automatic-calib-pwr-src-t;
            config false;
            description
              "Type of power source used for calibration";
        }

        leaf calibration-gain {
            type cct:db-oper-t;
            config false;
            description
              "Raman gain obtained with calibration total pumps power";
        }

        leaf calibration-total-pumps-power {
            type cct:mw-oper-t;
            config false;
            description
              "Reference total pump power used through-out the calibration procedure";
        }
    }

    grouping orchestrator-automatic-raman-calibration-report-grp {
    
        description "Automatic Raman calibration operational data grouping (calibration directed by the orchestrator)"; 
        
        leaf progress {
        	type string;
        	config false;
        	description "indication of clibration progress state";
        }
        
		leaf max-gain {
		    type cct:db-oper-t;
            config false;
            description
              "Maximum obtainable Raman Gain";
		}

		container persistence {
		    tailf:hidden full;
			config false;
			description "Hidden and persisted Data for Raman Calibration managed by Orchestrator";
		
			leaf last_error {
				type string;
			}
		
			//---------------------------------
			// Probing Data section
			
		 	leaf span_length_km {
		 		type cct:length-km-t;
		 	}
		 	
         	leaf con_in_for_db {
         		type cct:db-oper-t;
         	}
         	
         	leaf con_out_back_db {
         		type cct:db-oper-t;
         	}
         	
           	leaf dfb_tx_pumps_off_dbm {
         		type cct:dbm-oper-t;
         	}
         	
         	leaf dfb_rx_pumps_off_dbm {
         		type cct:dbm-oper-t;
         	}       	
         	
         	leaf dfb_rx_pumps_max_dbm {
         		type cct:dbm-oper-t;
         	}       	
         	
            leaf pumps_max_residual_dbm  {
         		type cct:dbm-oper-t;
         	}       	
         	
         	list concentrated_losses_location_km {
         		key id;
         		leaf id {
         			type cct:id-t;
         		}
         		leaf value {
         			type cct:length-km-t;
         		}
		 	}
		 	
         	list concentrated_losses_value_dbm {
         		key id;
         		leaf id {
         			type cct:id-t;
         		}
         		leaf value {
         			type cct:dbm-oper-t;
         		}
         	}
         	         
         	list pumps_launch_alpha_dbm {
         		key id;
         		leaf id {
         			type cct:id-t;
         		}
         		leaf value {
         			type cct:dbm-oper-t;
         		}
         	}
         	
        	list pumps_residual_alpha_dbm {
        		key id;
         		leaf id {
         			type cct:id-t;
         		}
         		leaf value {
         			type cct:dbm-oper-t;
         		}
         	}
         	
         	list pump_launch_kr_dbm {
         		key id;
         		leaf id {
         			type cct:id-t;
         		}
         		leaf value {
         			type cct:dbm-oper-t;
         		}
         	}
         	
         	list rx_pumps_on_dbm {
         		key id;
         		leaf id {
         			type cct:id-t;
         		}
         		leaf value {
         			type cct:dbm-oper-t;
         		}
         	}
         	
         	list pumps_launch_max_gain_dbm {
         		key id;
         		leaf id {
         			type cct:id-t;
         		}
         		leaf value {
         			type cct:dbm-oper-t;
         		}
         	}

         	//---------------------------------
			//   design config Section:
			
        	leaf f_max_nm {
		 		type cct:wavelength-nm-t;
		 	}
		 	
        	leaf f_min_nm {
		 		type cct:wavelength-nm-t;
		 	}
		 	
		 	leaf f_max_lband_nm {
		 		type cct:wavelength-nm-t;
		 	}
		 	
        	leaf f_min_lband_nm {
		 		type cct:wavelength-nm-t;
		 	}
		 	
        	leaf channel_bandwidth_ghz {
		 		type roadm-oct:frequency-GHz;
		 	}
		 	  
        	leaf dfb_wavelength_nm {
		 		type cct:wavelength-nm-t;
		 	}
		 	
        	list pumps_wavelength_nm {
        		key id;
         		leaf id {
         			type cct:id-t;
         		}
         		leaf value {
		 			type cct:wavelength-nm-t;
		 		}
		 	}
		 	
        	list min_pump_value_mw {
        		key id;
         		leaf id {
         			type cct:id-t;
         		}
         		leaf value {
		 			type cct:mw-t;
		 		}
		 	}
		 	
        	list max_pump_value_mw {
        		key id;
         		leaf id {
         			type cct:id-t;
         		}
         		leaf value {
		 			type cct:mw-t;
		 		}
		 	}
		 	
        	//---------------------------------
			//   design target Section:

        	leaf goo_correction_db {
         		type cct:db-oper-t;
         	}
         	
        	leaf tilt_correction_db {
         		type cct:db-oper-t;
         	}
         	
         	//---------------------------------
			//   control Section:
         	
         	leaf goo_av_db {
         		type cct:db-oper-t;
         	}
         	
        	leaf tilt_db {
         		type cct:db-oper-t;
         	}
         	
            leaf measured_dfb_rx_pumps_on_dbm {
         		type cct:dbm-oper-t;
         	}
         	
         	leaf measured_ase_rx_pumps_on_dbm {
         		type cct:dbm-oper-t;
         	}         	
         	
         	list power_pump_mw {
        		key id;
         		leaf id {
         			type cct:id-t;
         		}
         		leaf value {
		 			type cct:mw-t;
		 		}
		 	}
         	
        	//---------------------------------
			//   sensitivity Section:
			
        	list sensitivity_higher_gain {
        		key id;
         		leaf id {
         			type cct:id-t;
         		}
         		leaf value {
		 			type cct:small-number-t;
		 		}
		 	}
		 	
        	list sensitivity_lower_gain {
        		key id;
         		leaf id {
         			type cct:id-t;
         		}
         		leaf value {
		 			type cct:small-number-t;
		 		}
		 	}
		 	
		    //---------------------------------
			//   fibre_params:
			
			list attenuation_graph_alpha {
				key id;
         		leaf id {
         			type cct:id-t;
         		}
         		leaf value {
		 			type cct:small-number-t;
		 		}
		 	}
		 	
        	list attenuation_graph_freq_ghz {
        		key id;
         		leaf id {
         			type cct:id-t;
         		}
         		leaf value {
		 			type roadm-oct:frequency-GHz;
		 		}
		 	}
		 	  
        	list efficiency_graph_kr {
        		key id;
         		leaf id {
         			type cct:id-t;
         		}
         		leaf value {
		 			type cct:small-number-t;
		 		}
		 	}
		 	
        	list efficiency_graph_freq_ghz {
        		key id;
         		leaf id {
         			type cct:id-t;
         		}
         		leaf value {
		 			type roadm-oct:frequency-GHz;
		 		}
		 	}
		 	
		 	leaf attenuation_coeff_a {
         		type cct:small-number-t;
         	}       	
  
            leaf attenuation_coeff_b {
         		type cct:small-number-t;
         	} 
  
            leaf attenuation_coeff_kir {
         		type cct:db-oper-t;
         	} 
  
            leaf attenuation_coeff_a1 {
         		type cct:small-number-t;
         	} 
		}
    }
     
    grouping manual-raman-calibration-report-grp {

        description "Manual Raman calibration operational data grouping";

        leaf time-stamp {
            type yang:date-and-time;
            config false;
            description
              "Time stamp of calibration";
        }

        leaf status {
            type cct:raman-manual-calib-status-t;
            config false;
            description 
              "Status of automatic Raman Calibration";
        }
 
        leaf pump-1-low-power {
            type cct:dbm-oper-t;
            config false;
            description 
              "measured incoming power with only Pump 1 on at low power level";
        }

        leaf pump-1-high-power {
            type cct:dbm-oper-t;
            config false;
            description 
              "measured incoming power with only Pump 1 on at high power level";
        }

        leaf pump-2-low-power {
            type cct:dbm-oper-t;
            config false;
            description 
              "measured incoming power with only Pump 2 on at low power level";
        }

        leaf pump-2-high-power {
            type cct:dbm-oper-t;
            config false;
            description 
              "measured incoming power with only Pump 2 on at high power level";
        }	
        
        leaf target-gain {
            type cct:db-oper-t;
            config false;
            description
              "Target raman gain";
        }

        leaf obtained-gain {
            type cct:db-oper-t;
            config false;
            description
              "Obtained gain";
        }

        leaf target-tilt {
            type cct:db-oper-t;
            config false;
            description
              "Target spectrum tilt";
        }

        leaf obtained-tilt {
            type cct:db-oper-t;
            config false;
            description
              "Obtained spectrum tilt";
        }
        
        leaf result {
            type cct:raman-calib-result-t;
            config false;
            description
              "Calibration result versus target gain";
        }
    }
}
