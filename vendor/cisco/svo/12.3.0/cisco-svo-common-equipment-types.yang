module cisco-svo-common-equipment-types {
  yang-version 1.1;
  namespace "http://cisco.com/yang/svo/common-equipment-types";
  prefix ccet;

  import cisco-svo-common-types { prefix cct; }

  organization
    "Cisco Systems, Inc.";

  contact
    "Cisco Systems, Inc.
     Customer Service

     Postal: 170 West Tasman Drive
     San Jose, CA 95134

     Tel: +1 800 553-NETS

     E-mail: cs-yang@cisco.com";

  description "
    This module defines the basic equipment types ";

  revision 2021-12-25 {
  	description "Model version for SVO Release 12.3.0";
  	reference cisco-svo-common-equipment-types.yang;
  }
  
   revision 2021-04-16 { 
      description "Model version for SVO Release 12.2.0 "; 
      reference cisco-svo-common-equipment-types.yang; 
   }
 

    revision 2020-12-04 { 
       description "Model version for SVO Release 12.1.0 "; 
       reference cisco-svo-common-equipment-types.yang; 
    }
 

  /* Supported system types */

  identity tdm-terminology-type {
    description "Base Type for region specific system, i.e. ANSI, ETSI";
  }

  identity ansi {
    base ccet:tdm-terminology-type;
    description "ANSI system type";
  }

  identity etsi {
    base ccet:tdm-terminology-type;
    description "ETSI system type";
  }

  /* Supported optical types */

  identity optical-type {
    description
    "Base type for optical node type, i.e. ROADM, AMPLIFIER";
  }

  identity roadm {
    base optical-type;
    description "ROADM Node";
  }

  identity txp {
    base optical-type;
    description "Standalone TXP Node.
                 Node with this optical type is a special node used to connect 2 different ROADM ring.
                 normally it has only TXP cards on it. ";
  }

  identity ola {
    base optical-type;
    description "Amplifier Node";
  }

  identity dge {
    base optical-type;
    description "DGE Node";
  }

  /* Supported device flavour types */

  identity device-flavour-type {
    description
    "Base type for device flavour, i.e. any-config, txp-only";
  }

  identity any-config {
    base device-flavour-type;
    description "any card type shall be equipped.";
  }

  identity txp-only {
    base device-flavour-type;
    description "only TXP/MXP cards shall be equipped.";
  }

  typedef degree-of-support-type-t {
    type enumeration {
      enum unsupported;
      enum partially-supported;
      enum fully-supported;
    }
    description "The level of support: full, partial or none";
  }


  typedef usb-port-type-t {
    type enumeration {
      enum usb2;
      enum usb3;
    }
    description "Usb Port Type";
  }

  typedef ems-craft-port-t {
    type enumeration {
      enum ems;
      enum craft;
      enum ems-craft;
    }
    description "EMS/CRAFT Port Type";
  }

  typedef ethernet-port-t {
    type enumeration {
      enum ems;
      enum craft;
      enum ems-craft;
      enum udc-voip;
      enum isc;
    }
    description "Ethernet Port Type";
  }

  typedef rack-id-t {
    type uint16 {
      range 1..65535 {
        error-message "Rack Id must be within 1 to 65535";
      }
    }
    description "Rack ID is a numeric identifier of the rack; it is a unique number in the node";
  }

  typedef ru-position-t {
    type uint8 {
      range 1..44 {
        error-message "ru-position must be 1 to 44";
      }
    }
    description "
      ru-position indicate where the chassis is physically
      placed in the rack.The ru-position is a unique attribute
      per rack.";
  }

  typedef ru-occupation-t {
    type uint8 {
      range 1..44 {
        error-message "ru-occupation must be 1 to 44";
      }
    }
    description "Number of used Rack Units";
  }

  typedef passive-unit-id-t {
    type uint8 {
      range 1..126 {
        error-message "Passive unit unique id must be between 1 and 126";
      }
    }
    description "Passive unit unique id";
  }

  typedef passive-unit-slot-t {
    type uint8 {
      range 1..8;
    }
    description "Passive unit slot when insert on the mechanical unit and not
        in the passive chassis. Max value is 8 for mech unit FL2";
  }

  typedef max-oper-passive-unit-slot-t {
    type uint8 {
      range 1..14;
    }
    description "Max number of Passive unit slot,
                 it depends on the bigger passive shelf has the system";
  }

  typedef chassis-id-t {
    type uint16 {
      range "0..50 | 1001..1126";
    }
    description "
      chassis-id is the unique index that identifies
      the chassis in the node.
      The chassis-id is unique in the node, so,
      multi-rack nodes do not have chassis-id duplicated.
      1..50 is a range for non-passive chassis,
      1001..1126 is a range for passive chassis";
  }

  typedef uid-t {
    type uint16;
    description "global unique identifier of chassis or passive-unit";
  }

  typedef chassis-uid-t {
    type uid-t;
    description "chassis global unique identifier";
  }

  typedef passive-unit-uid-t {
    type uid-t;
    description "passive unit global unique identifier";
  }

  typedef slot-t {
    type string {
      // pattern '[1-9]{1}([0-9]{1,2})?|[1-9]{1}([0-9]{1,2})?(-[1-9]{1}([0-9]{1})?)';
      pattern '[1-9]{1}([0-9]{1,2})?|[1-9]{1}([0-9]{1,2})?(-[1-9]{1}([0-9]{1})?)|0/[0-9]-Optics0/[0-9]/[0-9]/[0-9]{1,2}';
    }
    description "Slot identifier 1:999 or ppmSlot identifier 1:999-1:99; NA if not supported";
  }

  typedef multi-shelf-t {
    description "The node is installed in one of two modes (operdata): node-conroller or standalone";
    type enumeration {
      enum node-controller;
      enum standalone;
    }
  }

  typedef lcd-setting-t {
    description "The possible setting of the LCD display";
    type enumeration {
      enum allow-configuration; // some system settings are possible through the display;
      enum display-only;         // just show some system settings
      enum suppress-display;    // do not show/config from display
    }
  }

  typedef eqp-state-t {
    type enumeration {
      // 2K device session
      enum not-present;
      enum mismatch;
      enum loading;
      enum failed;
      enum standby;
      enum active;
      enum deleted;
      // 1K device section
      enum unknown;
      enum ok;
      enum disabled;
      enum okButDiagFailed;
      enum boot;
      enum selfTest;
      enum failed_1k;
      enum missing;
      enum mismatchWithParent;
      enum mismatchConfig;
      enum diagFailed;
      enum dormant;
      enum outOfServiceAdmin;
      enum outOfServiceEnvTemp;
      enum poweredDown;
      enum poweredUp;
      enum powerDenied;
      enum powerCycled;
      enum okButPowerOverWarning;
      enum okButPowerOverCritical;
      enum syncInProgress;
      enum upgrading;
      enum okButAuthFailed;
      enum mdr;
      enum fwMismatchFound;
      enum fwDownloadSuccess;
    }
    description "Eqp State Type";
  }

  typedef port-id-t {
    type string;
    description "description Port identifier";
  }

  typedef lane-id-t {
    type string;
    description "description Port Lane identifier";
  }

  typedef usb-uts-id-t {
    type uint8 {
      range 1..2;
    }
    description "Usb uts identifier";
  }

  typedef usb-port-id-t {
    type uint8 {
      range 1..14;
    }
    description "
      usb port unique id";
  }

  typedef power-unit-id-t {
    type uint8 {
      range 1..4;
    }
    description "
      power unit unique id";
  }

  typedef env-control-id-t {
    type uint8 {
      range 1..4;
    }
    description "
      env control unique id";
  }

  typedef env-alarm-id-t {
    type uint8 {
      range 1..14;
    }
    description "
      env alarm unique id";
  }

  typedef ms-isc-id-t {
    type uint8 {
      range 1..2;
    }
    description "
      ECU MSC Group identifier unique id";
  }

  typedef ms-isc-port-t {
    type uint8 {
      range 1..3;
    }
    description "
      ECU MSC Port identifier unique id";
  }

  typedef port-name-t {
    type string {
      pattern '\d{1,8}/(\d{1,2}/.*|.*)';
    }
    description "Portname with syntax UId/[Slot-Id/]Port-Id.";
  }
    
  typedef port-role-t {
    type enumeration {
      enum trunk;
      enum client;
      enum none;
    }
    description "Trunk or Client port";
  }

  typedef passive-led-color {
    type enumeration {
      enum gray;
      enum blinking-green;
      enum solid-green;
      enum blinking-blue;
      enum solid-blue;
      enum unknown-color;
    }
    description "Color of the passive unit LED";
  }

  typedef wson-sson-status-t {
    type enumeration {
      enum cpstate-active;
      enum cpstate-inactive;
      enum cpstate-force-inactive;
      enum cpstate-activating;
      enum cpstate-deactivating;
    }
    description "WSON/SSON control plane status";
  }

  typedef device-sync-t {
    type enumeration {
      enum "sync-not-started" {
        description "Device waiting for the start of the sync";
      }
      enum "sync-operational" {
        description "Device is synching the operational parameters";
      }
      enum "sync-configuration" {
        description "Device is synching the configuration parameters";
      }
      enum "sync-completed" {
        description "Device is fully synched";
      }
      enum "sync-mea" {
        description "device could not be synched because is different from the SVO tdt-terminology-type.
          refer to cet:tdm-terminology-type to known all the possibilities of terminology of SVO";
      }
      enum "full-sync-requested" {
        description "Device full data synchronization requested by user or to recover an error";
      }
    }
    description "All possible sync status of a device";
  }

  typedef alarm-sync-t {
    type enumeration {
      enum "out-of-sync" {
        description "Device Alarms are out of sync. This could be due to not started sync, sync in progess.
          In case of Device that depends on the synch of another device, the sync status is conditioned to
          the sync status of the other device";
      }
      enum "alarm-synchronised" {
        description "Device Alarms are fully synched";
      }
    }
    description "All possible sync status of a device alarm status";
  }

  typedef internal-link-type-t {
    type enumeration {
      enum "Unknown-type" {
        description "Unknown link type";
      }
      enum "Transport" {
        description "Optical Transport link type";
      }
      enum "Add-Drop" {
        description "Add-Drop link type";
      }
    }
    description "Type of internal link connection";
  }

  typedef internal-link-connection-result-t {
    type enumeration {
      enum "Connection-Not-Verified" {
        description "Cable not verified";
      }
      enum "Connection-Not-Measurable" {
        description "Cable connectivity cannot be established";
      }
      enum "Connected" {
        description "Cable is connected";
      }
      enum "Disconnected" {
        description "Cable is disconnected";
      }
      enum "Connection-Check-Disabled" {
        description "Connectivity check disabled by user";
      }
    }
    description "Connection check status and result";
  }

  typedef internal-link-insertion-loss-result-t {
    type enumeration {
      enum "Insertion-Loss-Not-Verified" {
        description "Cable not verified";
      }
      enum "Insertion-Loss-Not-Measurable" {
        description "Cable insertion loss cannot be established";
      }
      enum "Insertion-Loss-OK" {
        description "Cable insertion loss is within allowed limit";
      }
      enum "Insertion-Loss-Degrade" {
        description "Cable insertion loss is slightly above allowed limit but below critical level";
      }
      enum "Insertion-Loss-Fail" {
        description "Cable insertion loss is above critical level";
      }
      enum "Insertion-Loss-Check-Disabled" {
        description "Cable insertion loss check is disabled by user";
      }
    }
    description "Insertion loss check status and result";
  }

  typedef cv-running-status-t {
    type enumeration {
      enum "Connection-Verification-Not-Running" {
        description "Connection Verification not running";
      }
      enum "Connection-Verification-Running" {
        description "Connection Verification running";
      }
      enum "Insertion-Loss-Verification-Running" {
        description "Insertion Loss Verification running";
      }
    }
    description "Connection Verification status";
  }

  /* Net Element types */

  identity cisco-ne-type {
    description "Base Type for CISCO Net Elements, i.e. ncs2000";
  }

  identity equipment-type {
    base  cct:common-hw-identity;
    description "
      Base for all-type of equipment (Chassis, card, ppm (plubbagle
      port module), port)";
  }

  /* chassis types */

  identity chassis-type {
    base ccet:equipment-type;
    description "Generic Chassis Type";
  }

  typedef chassis-type-t {
    type identityref {
      base ccet:chassis-type;
    }
  }

  identity unknown-chassis-type {
    base ccet:chassis-type;
    description "Unknown Chassis Type";
  }


  identity passive-chassis {
    base ccet:chassis-type;
    description "
      Passive Chassis with 8 slot - this is for passive unit like
      fiber shuffle and patch panel";
  }

  identity ncs1k-chassis {
    base ccet:chassis-type;
    description "
      NCS1K chassis type";
  }

  identity NCS1004 {
    base ncs1k-chassis;
    description "
      Base rack 1K.";
  }

  /* ecu type */

  typedef ecu-type-t {
    type identityref {
      base ccet:ecu-type;
    }
  }

  identity ecu-type {
    base ccet:equipment-type;
    description "Generic ecu Type";
  }

  identity UNKNOWN_ECU {
    base ccet:ecu-type;
    description "Unknown ECU Type";
  }

  /* card mode */

  identity card-mode {
    base  cct:common-hw-identity;
    description "Card mode identity for TXP/MXP cards";
  }

  /* card with card mode */

  identity card-with-card-mode {
    description "Card type identity for cards with card-mode";
  }

  /* card types */

  identity module-type {
    base ccet:equipment-type;
    description "Basic Module Type";
  }

  identity card-type {
    base ccet:module-type;
    description "Basic Card Type";
  }

  identity UNKNOWN-CARD {
    base ccet:card-type;
    description "Unknown Card";
  }

  identity NCS1K4-1.2T-K9 {
    base ccet:card-type;
    description "
      Module type 1K.";
  }

  identity NCS1K4-OTN-XP {
    base ccet:card-type;
    description "
      Module Type 1K.";
  }

  identity NCS1K4-LC-FILLER {
    base ccet:card-type;
    description "
      Module Type 1K.";
  }

  identity NCS1K4-CNTLR-K9 {
    base ccet:card-type;
    description "
      Module Type 1K.";
  }  

  identity NCS1K4-FAN {
    base ccet:card-type;
    description "
      Module Type 1K.";
  }

  identity NCS1K4-AC-PSU {
    base ccet:card-type;
    description "
      Module Type 1K.";
  }

  identity NCS1004-CARD {
    base ccet:card-type;
    description "
      Module Type 1K.";
  }
  /* oper card types */

  identity oper-card-type {
    base ccet:module-type;
    description "Basic Oper Card Type";
  }

  /* ancillary card types */

  identity ancillary-type {
    base ccet:module-type;
    description "Basic Type for ancillary modules";
  }

  typedef ancillary-type-t {
    type identityref {
      base ccet:ancillary-type;
    }
  }

  identity UNKNOWN-ANCILLARY {
    base ccet:ancillary-type;
    description "Unknown Ancillary";
  }

  /* ppm types */

  identity ppm-type {
    base module-type;
    description "Basic PPM Type";
  }

  /*
    Supported ppm types.
  */
  identity PPM-1K-PORT {
    base ccet:ppm-type;
    description "PPM 1 Port";
  }


  /* port types */

  identity port-type {
    base ccet:equipment-type;
    description "Basic Port Type";
  }

  identity DWDM-TRUNK-PORT-1K {
    base ccet:port-type;
    description "DWDM-TRUNK-PORT";
  }

  identity DWDM-CLIENT-PORT-1K {
    base ccet:port-type;
    description "DWDM-CLIENT-PORT";
  }

  identity UNKNOWN-PORT-1K {
    base ccet:port-type;
    description "UNKNOWN-PORT-1K";
  }
  /* passive-types */

  identity passive-type {
    base ccet:module-type;
    description "Base Passive Type";
  }

  identity unknown-passive-type {
    base ccet:passive-type;
    description "Unknown Passive Type used when there's a
        passive unit physically installed in a rack
        or in a passive chassis but
        unsupported by the current SVO release";
  }

  /* ru-passive subtypes */

  identity ru-passive-type {
    base ccet:passive-type;
    description "Passive Type physically installed in the rack";
  }

  /* mech-unit subtypes */

  identity module-subtype {
    base ccet:equipment-type;
    description "Passive Module Subtype";
  }

  identity mech-unit-subtype {
    base ccet:module-subtype;
    description "MECH UNIT subtype";
  }

  /* dcu subtypes */

  identity dcu-subtype {
    base ccet:module-subtype;
    description "Dcu subtype";
  }

  /* Transponder/Muxponder functional mode */

  identity functional-mode {
    base  cct:common-hw-identity;
    description "Functional module mode identity for TXP/MXP card groups";
  }

  identity regen-functional-mode {
    description "Regen functional groups";
  }

  identity protected-functional-mode {
    description "Functional module mode identity for protected op/mode";
  }

  identity bundle-functional-mode {
    description "Functional module mode identity for T5 2x150 op/mode";
  }

  /* Supported Slice submode for 400G line card */

  identity slice-mode {
    description "Slice submode for 400G line card";
  }
  
  /* Protection Type */
  
  identity protection-type {
      description "base protection identity from which specific protection types
              are derived.";
  }

  typedef protection-type-t {
        type identityref {
            base ccet:protection-type;
        }
    }
  

  identity functional-mode-1k {
    base ccet:functional-mode;
    description "MXP 1K";
  }

  identity MXP-1K {
    base ccet:functional-mode-1k;
    description "MXP 1K";
  }

  identity MXP-SLICES-1K {
    base ccet:functional-mode-1k;
    description "MXP SLICES 1K";
  }

  identity RGN-1K {
    base ccet:functional-mode-1k;
    description "REGEN 1K";
  }

  identity UNKNOWN-MODE {
    base ccet:functional-mode-1k;
    description "UNKNOWN MODE 1K";
  }
}
