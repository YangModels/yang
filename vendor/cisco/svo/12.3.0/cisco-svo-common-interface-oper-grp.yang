module cisco-svo-common-interface-oper-grp {

    yang-version 1.1;
    namespace "http://cisco.com/yang/svo/common-interface-oper-grp";
    prefix "cciog";

    import org-openroadm-common-optical-channel-types { prefix org-openroadm-common-optical-channel-types; revision-date 2018-05-30; }
    import cisco-svo-common-types { prefix cct; }
    import cisco-svo-common-base-opt-oper-grp { prefix ccboog; }

    organization
        "Cisco Systems, Inc.";

    contact
        "Cisco Systems, Inc. Customer Service Postal: 170 West Tasman
        Drive San Jose, CA 95134 Tel: +1 800 553-NETS E-mail: cs-yang@cisco.com";

    description "Cisco Common Interface Operational data";

	revision 2021-12-25 {
		description "Model version for SVO Release 12.3.0 
			obsoleted : oxc-role
		";
		reference cisco-svo-common-interface-oper-grp.yang;
	}

    revision 2020-12-04 { 
       description "Model version for SVO Release 12.1.0 "; 
       reference cisco-svo-common-interface-oper-grp.yang; 
    }
 

    grouping optical-transport-oper-params-grp {
    	description "OTS Interface operational data grouping";
    	
        leaf direction {
            type cct:direction;
            default "Bidirectional";
            config false;
            description "Interface transmit direction";
        }
        
        leaf degree {
        	type cct:degree-uid-t;
        	config false;
            description "Unique Id of Degree to which the interface logically belongs";  
        }
        
        leaf oxc-role {
        	status obsolete;
        	type cct:oxc-role-t;
        	config false;
        	description "Role of the interface for the creation of a Service of type Optical X-Connection";
        }
        
        leaf frequency {
            type org-openroadm-common-optical-channel-types:frequency-THz;
            config false;
            description "Interface central frequency [THz] - value is provided only on coloured ports, i.e. ports which allow 
            	transmission of only a single circuits on the standard ITU 50 GHz grid";
        }

		leaf power-unit {
			type cct:unit-of-measure-t;
			config false;
			description "Unit of measure used for all power levels, logarithmic (dBm) or linear (mW)";
		}

       	leaf current-optical-psd-setpoint {
       		type cct:psd-oper-t;
       		config false;
       		description "Current optical power setpoint expressed as Power Spectral Density (used only for logarithmic units)"; 
       	}
         
        leaf current-optical-power-setpoint {
       		type cct:mw-oper-t;
       		config false;
       		description "Current optical power setpoint expressed as mW (used only for linear units)"; 
       	} 
               
       	container current-optical-power-thresholds {
   			uses ccboog:power-thresholds-grp;
   			config false;
   			description "Current optical power thresholds";
   		}

    }

	grouping variable-optical-attenuator-oper-param-grp {
		leaf current-attenuation {
			type cct:db-oper-t;
			config false;
            description "Current attenuation value of the Variable Optical Attenuator (VOA)";
		}
	}

    grouping optical-transport-oper-loss-info-grp
    {
       container loss-info {
           leaf il-path {
        	   type string;
        	   config false;
        	   description "path of topoloy arc to which the insertion loss is associated";
           }

           leaf insertion-loss {
        	   type cct:db-oper-t;
        	   config false;
        	   description "Insertion loss related to the downstream interface";
           }
        }
    }
    

    grouping interface-common-oper-grp {
    	description "Interface common operational data grouping";
    	
        uses ccboog:oper-state-grp;

        leaf tl1-aid {
            type string;
            config false;
            description "Access Identifier used by TL1";
        }
    }

}
