module cisco-svo-common-optical-channel-live-grp {

  yang-version 1.1;
  namespace "http://cisco.com/yang/svo/common-optical-channel-live-grp";
  prefix cochlg;

  import org-openroadm-common-link-types { prefix org-openroadm-common-link-types; revision-date 2018-03-30; }
  import cisco-svo-common-types { prefix cct; }
  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the OpticalChannel interface Live Data.";

  revision 2021-12-25 {
  	description "Model version for SVO Release 12.3.0";
  	reference cisco-svo-common-optical-channel-live-grp.yang;
  }
  
    revision 2020-12-04 { 
       description "Model version for SVO Release 12.1.0 "; 
       reference cisco-svo-common-optical-channel-live-grp.yang; 
    }
 

  
  
  grouping optch-live-data {
    container live-data {
      leaf laser-bias {
        type cct:laser-bias-t;
        config false;
        description "Current laser bias";
      }

      leaf rx-optical-pwr {
        type org-openroadm-common-link-types:power-dBm;
        config false;
        description "Current RX-Optical-PWR";
      }

      leaf tx-optical-pwr {
        type org-openroadm-common-link-types:power-dBm;
        config false;
        description "Current TX Optical PWR";
      }

      leaf dgd {
        type cct:dgd-t;
        config false;
        description "Current DGD";
      }

      leaf osnr {
        type cct:osnr-t;
        config false;
        description "Current OSNR";
      }

      leaf cd {
        type cct:cd-t;
        config false;
        description "Current CD";
      }

      leaf sopmd {
        type cct:sopmd-t;
        config false;
        description "Current SOPMD";
      }

      leaf pcr {
        type cct:pcr-t;
        config false;
        description "Current PCR";
      }

      leaf pdl {
        type cct:pdl-t;
        config false;
        description "Current PDL";
      }
      leaf q-factor {
        type cct:q-factor-t;
        config false;
        description "Current Q factor";
      }
      leaf temp {
        type cct:temp-t;
        config false;
        description "Temperature";
      }
       leaf cfo {
        type cct:cfo-t;
        config false;
        description "Central Frequency Offset";
      }
      
    }
  }

}
