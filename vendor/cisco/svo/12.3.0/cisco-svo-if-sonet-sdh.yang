module cisco-svo-if-sonet-sdh {
    yang-version 1.1;
    namespace "http://cisco.com/yang/svo/sonet-sdh";
    prefix if-sonet-sdh;
        
    import cisco-svo-common-interface-grp { prefix ccig;}
    import cisco-svo-common-sonet-sdh-grp { prefix cossdh; }   
    import cisco-svo-common-sonet-sdh-oper-grp { prefix cossdhog; }
    import cisco-svo-common-sonet-sdh-live-grp { prefix cossdhlg; }

    organization
        "Cisco Systems, Inc.";

    contact
        "Cisco Systems, Inc. Customer Service Postal: 170 West Tasman
        Drive San Jose, CA 95134 Tel: +1 800 553-NETS E-mail: cs-yang@cisco.com";

    description
        "YANG definition for SONET/SDH device interfaces";

   revision 2021-04-16 { 
      description "Model version for SVO Release 12.2.0 "; 
      reference cisco-svo-if-sonet-sdh.yang; 
   }
 

    revision 2020-12-04 { 
       description "Model version for SVO Release 12.1.0 "; 
       reference cisco-svo-if-sonet-sdh.yang; 
    }
 

    grouping sonet-grp {
    	description "Sonet grouping";
        container sonet {
            description "Specific Sonet Data";

            uses cossdh:sonet-config-group;
            uses cossdhog:sonet-oper-group;
            uses cossdhlg:sonet-sdh-live-data;
            uses ccig:maintenance-loopback;
        }
    }

    grouping sdh-grp {
        description "Sdh grouping";
        container sdh {
            description "Specific Sdh Data";

            uses cossdh:sdh-config-group;
            uses cossdhog:sdh-oper-group;
            uses cossdhlg:sonet-sdh-live-data;
            uses ccig:maintenance-loopback;
        }
    }
}
