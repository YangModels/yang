submodule cisco-svo-alarm-transient-type-def {

  belongs-to cisco-svo-alarm-transient-type {
    prefix svo-al-tr-t;
  }

  import tailf-ncs-alarms {
    prefix al;
  }


  organization
    "Cisco Systems, Inc.";

  contact
    "Cisco Systems, Inc.
    Customer Service

    Postal: 170 West Tasman Drive
    San Jose, CA 95134

    Tel: +1 800 553-NETS

    E-mail: cs-yang@cisco.com";

  description
    "This module defines the root of svo alarms under the 
      alarm-type under the module tailf-ncs-alarms";

    revision 2020-12-04 { 
       description "Model version for SVO Release 12.1.0 "; 
       reference cisco-svo-alarm-transient-type-def.yang; 
    }
 

  identity svo-alarm-transient-type {
    description "Root of svo alarm transient type";
    base al:alarm-type;
  }

  typedef svo-alarm-transient-type-t {
    type identityref {
      base svo-alarm-transient-type;
    }
  }
}
