module cisco-svo-common-license-types {
  yang-version 1.1;
  namespace "http://cisco.com/yang/svo/common-license-types";
  prefix cclict;


  organization
    "Cisco Systems, Inc.";

  contact
    "Cisco Systems, Inc.
     Customer Service

     Postal: 170 West Tasman Drive
     San Jose, CA 95134

     Tel: +1 800 553-NETS

     E-mail: cs-yang@cisco.com";

  description "
    This module defines the basic license types ";

  revision 2021-12-25 {
  	description "Model version for SVO Release 12.3.0";
      reference cisco-svo-common-license-types.yang;
   }

   typedef license-feature-name-t {
    type enumeration {
      enum "Unknown-License" {
                description "Unknown License";
      }
      enum "DWDM-Wavelength" {
                description "LIC_COUNT_CH_10-Licensing feature name on DWDM cards";
      }
      enum "GIGE-PORT" {
                description "LIC_COUNT_SA_PT_11-Licensing feature name on NGXP-PB";
      }
      enum "Low-Rate" {
                description "LIC_FEATURE_LR-Licensing feature name on AR_XP_LINE_CARD";
      }
      enum "HR-TXP" {
        description "LIC_FEATURE_HR_TXP-Licensing feature name on AR_XP_LINE_CARD";
      }
      enum "10DME-MXP" {
                description "LIC_FEATURE_DME_MXP-Licensing feature name on AR_XP_LINE_CARD";
      }
      enum "MR-MXP" {
                description "LIC_FEATURE_AR_MXP-Licensing feature name on AR_XP_LINE_CARD";
      }
      enum "4x2.5G-MXP" {
                description "LIC_FEATURE_25G_MXP-Licensing feature name on AR_XP_LINE_CARD";
      }
      enum "VD-MXP" {
                description "LIC_FEATURE_VD_MXP-Licensing feature name on AR_XP_LINE_CARD";
      }
      enum "REGEN" {
                description "LIC_FEATURE_REG-Licensing feature name on AR_XP_LINE_CARD";
      }
      enum "SFP-PORT" {
                description "LIC_COUNT_CARP_SFP-Licensing feature name on TENxTENGIG_LINE_CARD WSE_LINE_CARD";
      }
      enum "MXP-10x10G" {
                description "LIC_FEATURE_MXP_10x10G-Licensing feature name on HUNDREDGIG_LINE_CARD";
      }
      enum "TXP-100G" {
                description "LIC_FEATURE_TXP_10x10G-Licensing feature name on HUNDREDGIG_LINE_CARD";
      }
      enum "RGN-100G" {
                description "LIC_FEATURE_RGN_100G-Licensing feature name on HUNDREDGIG_LINE_CARD";
      }
      enum "NON-CPAK" {
                description "LIC_FEATURE_NON_CPAK-Licensing feature name on NCS2K_200G_CK_C_LC";
      }
      enum "CPAK" {
                description "LIC_FEATURE_CPAK-Licensing feature name on NCS2K_200G_CK_C_LC";
      }
      enum "METRO-EDGE" {
                description "LIC_FEATURE_METRO_EDGE-Licensing feature name on NCS2K_200G_CK_C_LC";
      }
      enum "100G-HG-FEC-OR-CD-RANGE" {
                description "LIC_FEATURE_LONG_HAUL-Licensing feature name on NCS2K_200G_CK_C_LC";
      }
      enum "STD-FEC" {
                description "LIC_FEATURE_STD_FEC-Licensing feature name on NCS2K_200G_CK_C_LC";
      }
      enum "100G-SD-FEC-OR-CD-RANGE" {
                description "LIC_FEATURE_SD_FEC-Licensing feature name on NCS2K_200G_CK_C_LC";
      }
      enum "ITU-GRID" {
                description "LIC_FEATURE_ITU_GRID-Licensing feature name on NCS2K_200G_CK_C_LC";
      }
      enum "FLEX-GRID" {
                description "LIC_FEATURE_FLEX_GRID-Licensing feature name on NCS2K_200G_CK_C_LC";
      }
      enum "200G" {
                description "LIC_FEATURE_200G-Licensing feature name on NCS2K_200G_CK_C_LC";
      }
      enum "50G" {
                description "LIC_FEATURE_50G-Licensing feature name on NCS2K_200G_CK_C_LC";
      }
      enum "FLEX" {
               description  "LIC_FEATURE_FLEX-Licensing feature name on SMR_CARD";
      }
      enum "SMR9-EXP-Ports" {
               description  "LLIC_COUNT_PORT_SMR9-icensing feature name on SMR_CARD";
      }
      enum "SMR20-EXP-Ports" {
               description  "LIC_COUNT_PORT_SMR20-Licensing feature name on SMR_CARD";
      }
      enum "LS-CRYPT" {
                description "LIC_FEATURE_LS_CRYPT-Licensing feature name on MR_MXP";
      }
      enum "HS-CRYPT" {
                description "LIC_FEATURE_HS_CRYPT-Licensing feature name on MR_MXP";
     }
    }
  }


   typedef license-type-t {
    type enumeration {
       enum "Unknow-Type" {
                description "License type unknown";
       }
       enum "Permanent" {
                description "Non time based license. Will not expire and can be rehosted";
       }
       enum "Evaluation" {
                description "Time based license. Will expire after stipulated date";
       }
       enum "Temporary" {
                description "Time based license. Will expire after stipulated date";
       }
       enum "Paid-Subscription" {
                  description "Paid License";
       }
       enum "Extension-Subscription" {
                description "Extension License";
       }
       enum "Evaluation-Subscription" {
                description "Evalution License";
       }
    }
   }
   typedef license-state-t {
       type enumeration {
         enum "Inactive" {
                   description "LIC_INACTIVE-License not deployed";
         }
         enum "Active-In-Use" {
                  description "License deployed and in use";
         }
         enum "Active-Not-In-Use" {
           description "License deployed and not in use";
         }
         enum "Active-Not-In-Use-EULA-Needed" {
                   description "License deployed and not in use and EULA needed";
         }
         enum "Active-In-Use-EULA-Accepted" {
                   description "License deployed and in use and EULA accepted";
                }
         enum "Active-Not-In-Use-EULA-Accepted" {
                   description "License active and not in use and EULA accepted";
                }
                enum "Unknown-State" {
                   description "License state unknown";
         }
      }
   }
   typedef precedence-t {
       type enumeration {
         enum "High" {
                   description "High pri";
         }
         enum "None" {
           description "LIC_PRI_NONE-none";
         }
         enum "Medium" {
                   description "medium";
         }
         enum "Low" {
           description "low";
         }
     }
   }
   typedef is-expired-t {
       type enumeration {
       enum "Expiry-Not-Applicable" {
                description "LIC_EXPIRY_NA-expiried na";
       }
       enum "Expired" {
                description "LIC_EXPIRED-expired";
       }
       enum "Not-Expired" {
                description "LIC_NOT_EXPIRED-not expired";
       }
     }
   }
   typedef license-om-state-t {
      type enumeration {
        enum "Not-Provisioned" {
                 description "LIC_UN_PROV-unprov";
        }
        enum "Pre-Provisioned" {
                  description "LIC_PRE_PROV-pre-prov";
        }
        enum "Licensed" {
                  description "LIC_LICENSED-licensed";
        }
        enum "Unlicensed" {
          description "LIC_UN_LICENSED-un licensed";
        }
     }
   } 
}
