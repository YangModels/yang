/*
 * BEWARE BEWARE BEWARE BEWARE BEWARE BEWARE BEWARE BEWARE BEWARE
 * This file has been auto-generated by the python alarm dictionary parser: DO NOT EDIT
 * See: python main_svo_generator.py
 * Source: alarm_dictionary
 * BEWARE BEWARE BEWARE BEWARE BEWARE BEWARE BEWARE BEWARE BEWARE
*/
submodule cisco-svo-pm-tca-alarm-types {

  belongs-to cisco-svo-alarm-tca-type {
    prefix svo-al-tca-t;
  }

  include cisco-svo-alarm-tca-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the pm tca alarm types";

  revision 2020-12-04 {
    description "Model version for SVO Release 12.1.0";
    reference cisco-svo-pm-tca-alarm-types.yang;
  }

  identity pm-tca-alarm-type {
    description "Root of pm tca alarm type";
    base svo-al-tca-t:svo-alarm-tca-type;
  }

  identity T-BBE-PM {
    description "Performance Monitor Threshold Crossing Alert: BBE-PM";
    base pm-tca-alarm-type;
  }

  identity T-BBE-SM {
    description "Performance Monitor Threshold Crossing Alert: BBE-SM";
    base pm-tca-alarm-type;
  }

  identity T-BBE-TCM1 {
    description "Performance Monitor Threshold Crossing Alert: BBE-TCM1";
    base pm-tca-alarm-type;
  }

  identity T-BBE-TCM2 {
    description "Performance Monitor Threshold Crossing Alert: BBE-TCM2";
    base pm-tca-alarm-type;
  }

  identity T-BBEL {
    description "Performance Monitor Threshold Crossing Alert: BBEL";
    base pm-tca-alarm-type;
  }

  identity T-BBER-PM {
    description "Performance Monitor Threshold Crossing Alert: BBER-PM";
    base pm-tca-alarm-type;
  }

  identity T-BBER-SM {
    description "Performance Monitor Threshold Crossing Alert: BBER-SM";
    base pm-tca-alarm-type;
  }

  identity T-BBER-TCM1 {
    description "Performance Monitor Threshold Crossing Alert: BBER-TCM1";
    base pm-tca-alarm-type;
  }

  identity T-BBER-TCM2 {
    description "Performance Monitor Threshold Crossing Alert: BBER-TCM2";
    base pm-tca-alarm-type;
  }

  identity T-BBES {
    description "Performance Monitor Threshold Crossing Alert: BBES";
    base pm-tca-alarm-type;
  }

  identity T-BIEC {
    description "Performance Monitor Threshold Crossing Alert: BIEC";
    base pm-tca-alarm-type;
  }

  identity T-BIT-EC {
    description "Performance Monitor Threshold Crossing Alert: BIT-EC";
    base pm-tca-alarm-type;
  }

  identity T-BYTE-EC {
    description "Performance Monitor Threshold Crossing Alert: BYTE-EC";
    base pm-tca-alarm-type;
  }

  identity T-CDPM-AVG {
    description "Performance Monitor Threshold Crossing Alert: CDPM-AVG";
    base pm-tca-alarm-type;
  }

  identity T-CDPM-MAX {
    description "Performance Monitor Threshold Crossing Alert: CDPM-MAX";
    base pm-tca-alarm-type;
  }

  identity T-CDPM-MIN {
    description "Performance Monitor Threshold Crossing Alert: CDPM-MIN";
    base pm-tca-alarm-type;
  }

  identity T-CHROM-DISP {
    description "Performance Monitor Threshold Crossing Alert: CHROM-DISP";
    base pm-tca-alarm-type;
  }

  identity T-CVL {
    description "Performance Monitor Threshold Crossing Alert: CVL";
    base pm-tca-alarm-type;
  }

  identity T-CVS {
    description "Performance Monitor Threshold Crossing Alert: CVS";
    base pm-tca-alarm-type;
  }

  identity T-DGD-MAX {
    description "Performance Monitor Threshold Crossing Alert: DGD-MAX";
    base pm-tca-alarm-type;
  }

  identity T-ES-PM {
    description "Performance Monitor Threshold Crossing Alert: ES-PM";
    base pm-tca-alarm-type;
  }

  identity T-ES-SM {
    description "Performance Monitor Threshold Crossing Alert: ES-SM";
    base pm-tca-alarm-type;
  }

  identity T-ES-TCM1 {
    description "Performance Monitor Threshold Crossing Alert: ES-TCM1";
    base pm-tca-alarm-type;
  }

  identity T-ES-TCM2 {
    description "Performance Monitor Threshold Crossing Alert: ES-TCM2";
    base pm-tca-alarm-type;
  }

  identity T-ESL {
    description "Performance Monitor Threshold Crossing Alert: ESL";
    base pm-tca-alarm-type;
  }

  identity T-ESR-PM {
    description "Performance Monitor Threshold Crossing Alert: ESR-PM";
    base pm-tca-alarm-type;
  }

  identity T-ESR-SM {
    description "Performance Monitor Threshold Crossing Alert: ESR-SM";
    base pm-tca-alarm-type;
  }

  identity T-ESR-TCM1 {
    description "Performance Monitor Threshold Crossing Alert: ESR-TCM1";
    base pm-tca-alarm-type;
  }

  identity T-ESR-TCM2 {
    description "Performance Monitor Threshold Crossing Alert: ESR-TCM2";
    base pm-tca-alarm-type;
  }

  identity T-ESS {
    description "Performance Monitor Threshold Crossing Alert: ESS";
    base pm-tca-alarm-type;
  }

  identity T-FC-PM {
    description "Performance Monitor Threshold Crossing Alert: FC-PM";
    base pm-tca-alarm-type;
  }

  identity T-FC-SM {
    description "Performance Monitor Threshold Crossing Alert: FC-SM";
    base pm-tca-alarm-type;
  }

  identity T-FC-TCM1 {
    description "Performance Monitor Threshold Crossing Alert: FC-TCM1";
    base pm-tca-alarm-type;
  }

  identity T-FC-TCM2 {
    description "Performance Monitor Threshold Crossing Alert: FC-TCM2";
    base pm-tca-alarm-type;
  }

  identity T-GAIN-AVG {
    description "Performance Monitor Threshold Crossing Alert: GAIN-AVG";
    base pm-tca-alarm-type;
  }

  identity T-GAIN-MAX {
    description "Performance Monitor Threshold Crossing Alert: GAIN-MAX";
    base pm-tca-alarm-type;
  }

  identity T-GAIN-MIN {
    description "Performance Monitor Threshold Crossing Alert: GAIN-MIN";
    base pm-tca-alarm-type;
  }

  identity T-LASER-BIAS-MAX {
    description "Performance Monitor Threshold Crossing Alert: LASER-BIAS-MAX";
    base pm-tca-alarm-type;
  }

  identity T-LASER-BIAS-MIN {
    description "Performance Monitor Threshold Crossing Alert: LASER-BIAS-MIN";
    base pm-tca-alarm-type;
  }

  identity T-LASER-TEMP-MAX {
    description "Performance Monitor Threshold Crossing Alert: LASER-TEMP-MAX";
    base pm-tca-alarm-type;
  }

  identity T-LASER-TEMP-MIN {
    description "Performance Monitor Threshold Crossing Alert: LASER-TEMP-MIN";
    base pm-tca-alarm-type;
  }

  identity T-MS-BBE {
    description "Performance Monitor Threshold Crossing Alert: MS-BBE";
    base pm-tca-alarm-type;
  }

  identity T-MS-BBER {
    description "Performance Monitor Threshold Crossing Alert: MS-BBER";
    base pm-tca-alarm-type;
  }

  identity T-MS-ES {
    description "Performance Monitor Threshold Crossing Alert: MS-ES";
    base pm-tca-alarm-type;
  }

  identity T-MS-ESR {
    description "Performance Monitor Threshold Crossing Alert: MS-ESR";
    base pm-tca-alarm-type;
  }

  identity T-MS-FC {
    description "Performance Monitor Threshold Crossing Alert: MS-FC";
    base pm-tca-alarm-type;
  }

  identity T-MS-LOSS {
    description "Performance Monitor Threshold Crossing Alert: MS-LOSS";
    base pm-tca-alarm-type;
  }

  identity T-MS-SES {
    description "Performance Monitor Threshold Crossing Alert: MS-SES";
    base pm-tca-alarm-type;
  }

  identity T-MS-SESR {
    description "Performance Monitor Threshold Crossing Alert: MS-SESR";
    base pm-tca-alarm-type;
  }

  identity T-MS-UAS {
    description "Performance Monitor Threshold Crossing Alert: MS-UAS";
    base pm-tca-alarm-type;
  }

  identity T-OPR-AVG {
    description "Performance Monitor Threshold Crossing Alert: OPR-AVG";
    base pm-tca-alarm-type;
  }

  identity T-OPR-MAX {
    description "Performance Monitor Threshold Crossing Alert: OPR-MAX";
    base pm-tca-alarm-type;
  }

  identity T-OPR-MIN {
    description "Performance Monitor Threshold Crossing Alert: OPR-MIN";
    base pm-tca-alarm-type;
  }

  identity T-OPT-AVG {
    description "Performance Monitor Threshold Crossing Alert: OPT-AVG";
    base pm-tca-alarm-type;
  }

  identity T-OPT-MAX {
    description "Performance Monitor Threshold Crossing Alert: OPT-MAX";
    base pm-tca-alarm-type;
  }

  identity T-OPT-MIN {
    description "Performance Monitor Threshold Crossing Alert: OPT-MIN";
    base pm-tca-alarm-type;
  }

  identity T-OPWR-AVG {
    description "Performance Monitor Threshold Crossing Alert: OPWR-AVG";
    base pm-tca-alarm-type;
  }

  identity T-OPWR-MAX {
    description "Performance Monitor Threshold Crossing Alert: OPWR-MAX";
    base pm-tca-alarm-type;
  }

  identity T-OPWR-MIN {
    description "Performance Monitor Threshold Crossing Alert: OPWR-MIN";
    base pm-tca-alarm-type;
  }

  identity T-OSC-PWR-AVG {
    description "Performance Monitor Threshold Crossing Alert: OSC-PWR-AVG";
    base pm-tca-alarm-type;
  }

  identity T-OSC-PWR-MAX {
    description "Performance Monitor Threshold Crossing Alert: OSC-PWR-MAX";
    base pm-tca-alarm-type;
  }

  identity T-OSC-PWR-MIN {
    description "Performance Monitor Threshold Crossing Alert: OSC-PWR-MIN";
    base pm-tca-alarm-type;
  }

  identity T-OSNR-AVG {
    description "Performance Monitor Threshold Crossing Alert: OSNR-AVG";
    base pm-tca-alarm-type;
  }

  identity T-OSNR-MAX {
    description "Performance Monitor Threshold Crossing Alert: OSNR-MAX";
    base pm-tca-alarm-type;
  }

  identity T-OSNR-MIN {
    description "Performance Monitor Threshold Crossing Alert: OSNR-MIN";
    base pm-tca-alarm-type;
  }

  identity T-PCR-AVG {
    description "Performance Monitor Threshold Crossing Alert: PCR-AVG";
    base pm-tca-alarm-type;
  }

  identity T-PCR-MAX {
    description "Performance Monitor Threshold Crossing Alert: PCR-MAX";
    base pm-tca-alarm-type;
  }

  identity T-PCR-MIN {
    description "Performance Monitor Threshold Crossing Alert: PCR-MIN";
    base pm-tca-alarm-type;
  }

  identity T-PDL-AVG {
    description "Performance Monitor Threshold Crossing Alert: PDL-AVG";
    base pm-tca-alarm-type;
  }

  identity T-PDL-MAX {
    description "Performance Monitor Threshold Crossing Alert: PDL-MAX";
    base pm-tca-alarm-type;
  }

  identity T-PDL-MIN {
    description "Performance Monitor Threshold Crossing Alert: PDL-MIN";
    base pm-tca-alarm-type;
  }

  identity T-PMD-AVG {
    description "Performance Monitor Threshold Crossing Alert: PMD-AVG";
    base pm-tca-alarm-type;
  }

  identity T-PMD-MIN {
    description "Performance Monitor Threshold Crossing Alert: PMD-MIN";
    base pm-tca-alarm-type;
  }

  identity T-PWR-AVG {
    description "Performance Monitor Threshold Crossing Alert: PWR-AVG";
    base pm-tca-alarm-type;
  }

  identity T-PWR-MAX {
    description "Performance Monitor Threshold Crossing Alert: PWR-MAX";
    base pm-tca-alarm-type;
  }

  identity T-PWR-MIN {
    description "Performance Monitor Threshold Crossing Alert: PWR-MIN";
    base pm-tca-alarm-type;
  }

  identity T-RS-BBE {
    description "Performance Monitor Threshold Crossing Alert: RS-BBE";
    base pm-tca-alarm-type;
  }

  identity T-RS-BBER {
    description "Performance Monitor Threshold Crossing Alert: RS-BBER";
    base pm-tca-alarm-type;
  }

  identity T-RS-ES {
    description "Performance Monitor Threshold Crossing Alert: RS-ES";
    base pm-tca-alarm-type;
  }

  identity T-RS-ESR {
    description "Performance Monitor Threshold Crossing Alert: RS-ESR";
    base pm-tca-alarm-type;
  }

  identity T-RS-OFS {
    description "Performance Monitor Threshold Crossing Alert: RS-OFS";
    base pm-tca-alarm-type;
  }

  identity T-RS-SES {
    description "Performance Monitor Threshold Crossing Alert: RS-SES";
    base pm-tca-alarm-type;
  }

  identity T-RS-SESR {
    description "Performance Monitor Threshold Crossing Alert: RS-SESR";
    base pm-tca-alarm-type;
  }

  identity T-RS-UAS {
    description "Performance Monitor Threshold Crossing Alert: RS-UAS";
    base pm-tca-alarm-type;
  }

  identity T-RX-PWR-MAX {
    description "Performance Monitor Threshold Crossing Alert: RX-PWR-MAX";
    base pm-tca-alarm-type;
  }

  identity T-RX-PWR-MIN {
    description "Performance Monitor Threshold Crossing Alert: RX-PWR-MIN";
    base pm-tca-alarm-type;
  }

  identity T-RX-TEMP-MAX {
    description "Performance Monitor Threshold Crossing Alert: RX-TEMP-MAX";
    base pm-tca-alarm-type;
  }

  identity T-RX-TEMP-MIN {
    description "Performance Monitor Threshold Crossing Alert: RX-TEMP-MIN";
    base pm-tca-alarm-type;
  }

  identity T-SEFS {
    description "Performance Monitor Threshold Crossing Alert: SEFS";
    base pm-tca-alarm-type;
  }

  identity T-SES-PM {
    description "Performance Monitor Threshold Crossing Alert: SES-PM";
    base pm-tca-alarm-type;
  }

  identity T-SES-SM {
    description "Performance Monitor Threshold Crossing Alert: SES-SM";
    base pm-tca-alarm-type;
  }

  identity T-SES-TCM1 {
    description "Performance Monitor Threshold Crossing Alert: SES-TCM1";
    base pm-tca-alarm-type;
  }

  identity T-SES-TCM2 {
    description "Performance Monitor Threshold Crossing Alert: SES-TCM2";
    base pm-tca-alarm-type;
  }

  identity T-SESL {
    description "Performance Monitor Threshold Crossing Alert: SESL";
    base pm-tca-alarm-type;
  }

  identity T-SESR-PM {
    description "Performance Monitor Threshold Crossing Alert: SESR-PM";
    base pm-tca-alarm-type;
  }

  identity T-SESR-SM {
    description "Performance Monitor Threshold Crossing Alert: SESR-SM";
    base pm-tca-alarm-type;
  }

  identity T-SESR-TCM1 {
    description "Performance Monitor Threshold Crossing Alert: SESR-TCM1";
    base pm-tca-alarm-type;
  }

  identity T-SESR-TCM2 {
    description "Performance Monitor Threshold Crossing Alert: SESR-TCM2";
    base pm-tca-alarm-type;
  }

  identity T-SESS {
    description "Performance Monitor Threshold Crossing Alert: SESS";
    base pm-tca-alarm-type;
  }

  identity T-SOPMD-AVG {
    description "Performance Monitor Threshold Crossing Alert: SOPMD-AVG";
    base pm-tca-alarm-type;
  }

  identity T-SOPMD-MAX {
    description "Performance Monitor Threshold Crossing Alert: SOPMD-MAX";
    base pm-tca-alarm-type;
  }

  identity T-SOPMD-MIN {
    description "Performance Monitor Threshold Crossing Alert: SOPMD-MIN";
    base pm-tca-alarm-type;
  }

  identity T-TX-PWR-MAX {
    description "Performance Monitor Threshold Crossing Alert: TX-PWR-MAX";
    base pm-tca-alarm-type;
  }

  identity T-TX-PWR-MIN {
    description "Performance Monitor Threshold Crossing Alert: TX-PWR-MIN";
    base pm-tca-alarm-type;
  }

  identity T-UAS-PM {
    description "Performance Monitor Threshold Crossing Alert: UAS-PM";
    base pm-tca-alarm-type;
  }

  identity T-UAS-SM {
    description "Performance Monitor Threshold Crossing Alert: UAS-SM";
    base pm-tca-alarm-type;
  }

  identity T-UAS-TCM1 {
    description "Performance Monitor Threshold Crossing Alert: UAS-TCM1";
    base pm-tca-alarm-type;
  }

  identity T-UAS-TCM2 {
    description "Performance Monitor Threshold Crossing Alert: UAS-TCM2";
    base pm-tca-alarm-type;
  }

  identity T-UASL {
    description "Performance Monitor Threshold Crossing Alert: UASL";
    base pm-tca-alarm-type;
  }

  identity T-UASS {
    description "Performance Monitor Threshold Crossing Alert: UASS";
    base pm-tca-alarm-type;
  }

  identity T-UNC-WORDS {
    description "Performance Monitor Threshold Crossing Alert: UNC-WORDS";
    base pm-tca-alarm-type;
  }

  identity T-VOA-AVG {
    description "Performance Monitor Threshold Crossing Alert: VOA-AVG";
    base pm-tca-alarm-type;
  }

  identity T-VOA-MAX {
    description "Performance Monitor Threshold Crossing Alert: VOA-MAX";
    base pm-tca-alarm-type;
  }

  identity T-VOA-MIN {
    description "Performance Monitor Threshold Crossing Alert: VOA-MIN";
    base pm-tca-alarm-type;
  }

  identity T-gfpStatsRoundTripLatencyUSec {
    description "Performance Monitor Threshold Crossing Alert: gfpStatsRoundTripLatencyUSec";
    base pm-tca-alarm-type;
  }

  identity T-rxControlFrames {
    description "Performance Monitor Threshold Crossing Alert: rxControlFrames";
    base pm-tca-alarm-type;
  }

  identity T-rxPauseFrames {
    description "Performance Monitor Threshold Crossing Alert: rxPauseFrames";
    base pm-tca-alarm-type;
  }

  identity T-rxPktsDroppedInternalCongestion {
    description "Performance Monitor Threshold Crossing Alert: rxPktsDroppedInternalCongestion";
    base pm-tca-alarm-type;
  }

  identity T-rxUnknownOpcodeFrames {
    description "Performance Monitor Threshold Crossing Alert: rxUnknownOpcodeFrames";
    base pm-tca-alarm-type;
  }

  identity T-txPauseFrames {
    description "Performance Monitor Threshold Crossing Alert: txPauseFrames";
    base pm-tca-alarm-type;
  }

  identity T-txPktsDroppedInternalCongestion {
    description "Performance Monitor Threshold Crossing Alert: txPktsDroppedInternalCongestion";
    base pm-tca-alarm-type;
  }

}
