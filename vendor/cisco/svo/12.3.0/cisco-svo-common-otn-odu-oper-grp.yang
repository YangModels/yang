module cisco-svo-common-otn-odu-oper-grp {

	yang-version 1.1;
	namespace "http://cisco.com/yang/svo/common-otn-odu-oper-grp";
	prefix coduog;

  import cisco-svo-common-otn-oper-grp { prefix ccotnog; }

	organization 
	"Cisco Systems, Inc.";

	contact 
	"Cisco Systems, Inc.
	Customer Service

	Postal: 170 West Tasman Drive
	San Jose, CA 95134

	Tel: +1 800 553-NETS

	E-mail: cs-yang@cisco.com";

	description "
	This module defines the OpticalChannel interface Operational.";

    revision 2020-12-04 { 
       description "Model version for SVO Release 12.1.0 "; 
       reference cisco-svo-common-otn-odu-oper-grp.yang; 
    }
 


    grouping otn-odu-prbs-oper-group {
      leaf supports-prbs {
        type boolean;
        config false;
        description "True if a PRBS generator can be enabled on the interface";
      }
    }
    
    grouping otn-odu-oper-group {
      uses ccotnog:odu-attributes;
      container tti {
       uses ccotnog:tti-oper-grp;
      }
      container prbs {
        uses otn-odu-prbs-oper-group;
      }
   }
}
