module cisco-svo-alarm-tca-type {
  namespace "http://cisco.com/yang/svo/alarm-tca-type";
  prefix svo-al-tca-t;

  include cisco-svo-alarm-tca-type-def;
  include cisco-svo-pm-tca-alarm-types;
  include cisco-svo-pm-rmon-alarm-types;

  
  organization
    "Cisco Systems, Inc.";

  contact
    "Cisco Systems, Inc.
    Customer Service

    Postal: 170 West Tasman Drive
    San Jose, CA 95134

    Tel: +1 800 553-NETS

    E-mail: cs-yang@cisco.com";

  description
    "This module defines the root of svo alarms under the 
      alarm-type under the module tailf-ncs-alarms";

    revision 2020-12-04 { 
       description "Model version for SVO Release 12.1.0 "; 
       reference cisco-svo-alarm-tca-type.yang; 
    }
 
  typedef svo-pm-rmon-alarm-type-t {
    type identityref {
      base pm-rmon-alarm-type;
    }
  }
 
  typedef svo-pm-tca-alarm-type-t {
    type identityref {
      base pm-tca-alarm-type;
    }
  }

}
