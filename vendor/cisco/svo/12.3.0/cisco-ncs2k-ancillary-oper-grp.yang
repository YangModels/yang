module cisco-ncs2k-ancillary-oper-grp {

  yang-version 1.1;
  namespace "http://cisco.com/yang/ncs2k/ancillary-oper";
  prefix ncs2k-anc-op;

  import cisco-svo-common-equipment-types { prefix ccet; }
  import cisco-svo-common-base-opt-oper-grp { prefix ccboog; }
  import cisco-svo-common-equipment-oper-grp {prefix cceqptog; }
  import cisco-ncs2k-ncs2k-equipment-types { prefix ncs2k-2k-cet; }
  import cisco-ncs2k-equipment-types { prefix cet; }

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "YANG definition for NSC2K platform: ancillary.";

    revision 2020-12-04 { 
       description "Model version for SVO Release 12.1.0 "; 
       reference cisco-ncs2k-ancillary-oper-grp.yang; 
    }
   

  grouping ancillary-type-grp  {
    leaf ancillary-type {
      type ccet:ancillary-type-t;        
      mandatory true;
      config false;
      description "Ancillary Type";
    }
  }

  grouping ethernet-port-grp  {

    leaf ethernet-port-type {
      type ccet:ethernet-port-t;
      mandatory true;
      
      description "Ethernet Port Type";
    }
  }

  grouping ethernet-isc-port-grp  {

    leaf port-id {
      type ccet:ms-isc-port-t;
      
      description "Port identifier";
    }

    uses ncs2k-2k-cet:equipment-entity-index-grp;

    uses ethernet-port-grp {
      refine "ethernet-port-type" {
        must "current()='isc'";
      }     
    }
  }

  grouping ethernet-fixed-port-grp  {
    container port {
      leaf port-id {
        type uint8 {
          range "1";
        }
        
        description "Port identifier";
      }

      uses ncs2k-2k-cet:equipment-entity-index-grp;

      uses ethernet-port-grp;
    }    
  }

  grouping ethernet-udc-voip-port-grp  {
    uses ethernet-fixed-port-grp {
      refine "port/ethernet-port-type" {
        must "current()='udc-voip'";
      }
    }    
  }

  grouping ethernet-single-isc-port-grp  {
    uses ethernet-fixed-port-grp {
      refine "port/ethernet-port-type" {
        must "current()='isc'";
      }
    }    
  }

  grouping ethernet-ems-craft-grp  {
    uses ethernet-fixed-port-grp {
      refine "port/ethernet-port-type" {
        must "current()='ems' or current()='craft' or current()='ems-craft'";
      }
    }    
  }

  grouping ecu-pluggable-port-grp  {
    container port {
      leaf port-id {
        type uint8 {
          range "1";
        }
        
        description "Port identifier";
      }

       
      uses ncs2k-2k-cet:equipment-entity-index-grp;
      
      leaf port-type {
        type identityref {
          base ccet:port-type;
        }
        mandatory true;
        config false;
        description "Port Type";
      }

      uses ccboog:oper-state-grp;
    } 
  }

  grouping usb-associated-passive-grp {

    container associated-passive {
//      leaf chassis-id {
//        type cet:chassis-id-t;
//        description "
//          chassis-id is the unique index that identifies
//          the chassis in the node.
//          The chassis-id is unique in the node, so,
//          multi-rack nodes do not have chassis-id duplicated";
//      }

      leaf passive-unit-id {
        type ccet:passive-unit-id-t;
        description "
          passive-unit-id is the unique index that identifies
          the passive-unit in the node.
          The passive-unit-id is unique in the node, so,
          multi-rack nodes do not have passive-unit-id duplicated";
      }

      leaf rack-id {
        type ccet:rack-id-t;
        config false;
        description "Chassis of the associated passive";
      }

      leaf slot {
        type ccet:max-oper-passive-unit-slot-t;
        config false;
        description "Slot of the associated passive";
      }

      leaf ru-position {
        type ccet:ru-position-t;
        config false;
        description "Ru-position of the associated passive";
      }

      leaf associated-passive-type {
        type identityref {
          base ccet:passive-type;
        }
        config false;
        description "actual passive-type read from the usb association. This is the
                type of the module that has been associated to this usb port";
      }

      leaf associated-chassis-type {
        type ccet:chassis-type-t;
        config false;
        description "actual chassis-type read from the usb association. This is the
                type of the chassis that has been associated to this usb port";
      }
    }
  }

  grouping usb-port-grp  {

    leaf port-id {
      type ccet:usb-port-id-t;
      
      description "Port identifier";
    }
        
    uses ncs2k-2k-cet:equipment-entity-index-grp;

    leaf usb-port-type {
      type ccet:usb-port-type-t;
      mandatory true;
      config false;
      description "Usb Port Type";
      must "(((../port-id < 11 and current()='usb2') or (../port-id > 10 and current()='usb3')) and (../../../../ecu/ecu-type='cet:NCS2015-ECU')) or " +
            "(((current()='usb2') or (../port-id > 10 and current()='usb3')) and (../../../../ecu/ecu-type!='cet:NCS2015-ECU' "+
                                         "and ../../../../ecu/ecu-type!='cet:NCS2006-ECU-S' and ../../../../ecu/ecu-type!='cet:NCS2006-ECU-60-S')) or " +
            "(((../port-id != 5 and current()='usb2') or (../port-id =5 and current()='usb3')) " + 
                                         "and (../../../../ecu/ecu-type='cet:NCS2006-ECU-S' or ../../../../ecu/ecu-type='cet:NCS2006-ECU-60-S'))";
    }

    uses usb-associated-passive-grp;
    uses cceqptog:equipment-properties-oper;
  }

  grouping usb-port-list-grp  {
    list usb-port {
      key port-id;
      unique equipment-entity-index;
      description "List of usb ports";
      uses usb-port-grp;
    }
  }

  grouping usb-passive-port-grp  {

    leaf port-id {
      type uint8 {
        range "1..max";
      }
      
      description "Port identifier";
    }

    uses ncs2k-2k-cet:equipment-entity-index-grp;

    leaf usb-port-type {
      type ccet:usb-port-type-t;
      mandatory true;
      config false;
      description "Usb Port Type";
    }

    uses usb-associated-passive-grp;
    uses cceqptog:equipment-properties-oper;
  }

  grouping usb-passive-port-list-grp  {
    list usb-passive-port {
      key port-id;
      unique equipment-entity-index;
      description "List of usb ports";
      uses usb-passive-port-grp;
    }
  }

  grouping udc-voip-modules-grp  {
    list udc-voip-module {
      key udc-voip-id;
      unique equipment-entity-index;
      description "List of udc-voip ports";
      min-elements 0;
      max-elements 2;

      leaf udc-voip-id {
        type uint8 {
          range "1..2";
        }
        
        description "Udc/voip id";
      }

      uses ncs2k-2k-cet:equipment-entity-index-grp;

      uses ancillary-type-grp;
      uses cceqptog:equipment-state-oper-grp;
      uses ethernet-udc-voip-port-grp;
    }
  }

  grouping ms-isc-port-list-grp  {
    list port {
      key port-id;
      unique equipment-entity-index;
      description "List of ms-isc ports";
      min-elements 0;
      max-elements 3;
      uses ethernet-isc-port-grp;
    }
  }

  grouping ms-isc-single-port-grp  {
    uses ethernet-single-isc-port-grp;
  }

  grouping usb-uts-modules-grp {
    list usb-uts-module {
      key usb-uts-id;
      unique equipment-entity-index;
      description "List of usb uts";
      min-elements 0;
      max-elements 2;

      leaf usb-uts-id {
        type ccet:usb-uts-id-t;
        description "Usb uts identifier";
      }
      uses ncs2k-2k-cet:equipment-entity-index-grp;
      must "(usb-uts-id = 1) or " +
           "(usb-uts-id = 2 and (../../../../chassis-type = 'cet:NCS2006-ANSI' or ../../../../chassis-type = 'cet:NCS2006-ETSI'))";

      uses ancillary-type-grp;
      uses cceqptog:equipment-state-oper-grp;
      uses usb-port-list-grp;
      must "(count(usb-port) = 12 and (../../ecu/ecu-type != 'cet:NCS2015-ECU')) or " +
           "(count(usb-port) =  5 and (../../ecu/ecu-type  = 'cet:NCS2006-ECU-S' or ../../ecu/ecu-type ='cet:NCS2006-ECU-60-S')) or " +
           "(count(usb-port) =  6 and (../../ecu/ecu-type  = 'cet:_15454-M6-ECU'  or ../../ecu/ecu-type ='cet:NCS2006-ECU'
                                                                                 or ../../ecu/ecu-type = 'cet:_15454-M6-ECU'
                                                                                 or ../../ecu/ecu-type = 'cet:_15454-M6-ECU-60'))";
    }
  }

  grouping ms-isc-modules-grp {
    list ms-isc-module {
      key ms-isc-id;
      unique equipment-entity-index;
      description "List of ms isc groups";
      min-elements 0;
      max-elements 2;

      leaf ms-isc-id {
        type ccet:ms-isc-id-t;
        
        description "Ms isc group identifier";
      }

      uses ncs2k-2k-cet:equipment-entity-index-grp;
      uses ancillary-type-grp;
      uses cceqptog:equipment-state-oper-grp;
      uses ms-isc-port-list-grp;
      must "(count(port) = 1 and (../../../../chassis-type ='cet:NCS2015-ANSI' or ../../../../chassis-type = 'cet:NCS2015-ETSI')) or" +
           "(count(port) = 3 and (../../../../chassis-type ='cet:NCS2006-ANSI'  or ../../../../chassis-type = 'cet:NCS2006-ETSI'))";
    }
  }

  grouping ems-craft-modules-grp  {
    list ems-craft-module {
      key ems-id;
      unique equipment-entity-index;
      description "List of ems-craft ports";
      min-elements 0;
      max-elements 2;

      leaf ems-id {
        type uint8 {
          range "1..2";
        }
        
        description "Ems module id";
      }
      uses ncs2k-2k-cet:equipment-entity-index-grp;
      uses ancillary-type-grp;
      uses cceqptog:equipment-state-oper-grp;
      uses ethernet-ems-craft-grp;
      must "(current()/port/ethernet-port-type = 'ems'       and current()/ems-id = 1 and (../../../../chassis-type = 'cet:NCS2006-ANSI'  or ../../../../chassis-type = 'cet:NCS2006-ETSI')) or " +
           "(current()/port/ethernet-port-type = 'craft'     and current()/ems-id = 2 and (../../../../chassis-type = 'cet:NCS2006-ANSI'  or ../../../../chassis-type = 'cet:NCS2006-ETSI')) or " +
           "(current()/port/ethernet-port-type = 'ems-craft' and current()/ems-id = 1 and (../../../../chassis-type = 'cet:NCS2015-ANSI' or ../../../../chassis-type = 'cet:NCS2015-ETSI')) ";
    }
  }

  grouping bits-uts-module-grp {
    container bits-uts-module {
       uses ncs2k-2k-cet:equipment-entity-index-grp;
       uses ancillary-type-grp;
       uses cceqptog:equipment-state-oper-grp;

       list bits-uts {
        key bits-uts-id;
        description "List of bits uts";
        min-elements 0;
        max-elements 2;

        leaf bits-uts-id {
          type uint8 {
            range "1..2";
          }
          
          description "Bits uts identifier";
        }
      }
    }
  }

  grouping sync-bits-uts-module-grp {
    container sync-bits-uts-module {

      list sync-bits-uts {
        key sync-bits-uts-id;
        description "List of sync bits uts";
        min-elements 0;
        max-elements 2;

        leaf sync-bits-uts-id {
          type uint8 {
            range "1..2";
          }
          
          description "Sync Bits uts identifier";
        }
      }
    }
  }

  grouping alarm-contacts-grp {
    container alarm-contacts {
      container alarm-dry-contact-module {
        uses ncs2k-2k-cet:equipment-entity-index-grp;
        uses ancillary-type-grp;
        uses cceqptog:equipment-state-oper-grp;

        list env-alarm {
          key env-alarm-id;
          unique equipment-entity-index;
          description "List of env alarms";
          min-elements 0;
          max-elements 14;

          leaf env-alarm-id {
            type ccet:env-alarm-id-t;
            
            description "Env alarm identifier";
          }
          uses ncs2k-2k-cet:equipment-entity-index-grp;
        }
        list env-control {
          key env-control-id;
          unique equipment-entity-index;
          description "List of env controls";
          min-elements 0;
          max-elements 4;

          leaf env-control-id {
            type ccet:env-control-id-t;
            
            description "Env control identifier";
          }
          uses ncs2k-2k-cet:equipment-entity-index-grp;
        }
      }

      container io-uts-module {
        uses ncs2k-2k-cet:equipment-entity-index-grp;
        uses ancillary-type-grp;
        uses cceqptog:equipment-state-oper-grp;
      }
    }
  }

  grouping pluggable-ports-module-grp {
    container pluggable-ports-module {
      list ppm-module {
        key ppm-id;
        unique equipment-entity-index;
        min-elements 0;
        max-elements 5;
        description "List of the ppm modules";
        
        leaf ppm-id {
          type uint8 {
            range "1..5";
          }
          
          description "Ppm identifier";
        }

        uses ncs2k-2k-cet:equipment-entity-index-grp;

        uses cceqptog:equipment-properties-oper;    
        uses ecu-pluggable-port-grp;
      }
    }
  }
  
  grouping fan-tray-module-grp {
    container fan-tray-module {
      leaf fan-id {
        type uint8 {
          range "1";
        }
        config false;
        description "Fan identifier";
      }
 
      uses ncs2k-2k-cet:equipment-entity-index-grp;

      uses ancillary-type-grp;
      uses cceqptog:equipment-properties-oper;
    }
  }

  grouping lcd-flash-module-grp {
    container lcd-flash-module {
      leaf lcd-flash-id {
        type uint8 {
          range "1";
        }
        config false;
        description "LCD Flash identifier";
      }

      uses ncs2k-2k-cet:equipment-entity-index-grp;

      uses ancillary-type-grp;
      uses cceqptog:equipment-properties-oper;
      uses usb-flash-module-grp {
        when "../../chassis-type = 'cet:NCS2006-ANSI' or ../../chassis-type = 'cet:NCS2006-ETSI'";
      }
    }
  }

  grouping usb-flash-module-grp {
    container usb-flash-module {
      leaf usb-flash-id {
        type uint8 {
          range "1";
        }
        config false;
        description "USB Flash identifier";
      }
    }
  }

  grouping backplane-module-grp {
    container backplane-module {
      leaf bp-id {
        type uint8 {
          range "1";
        }
        config false;
        description "Backplane identifier";
      }
      uses ncs2k-2k-cet:equipment-entity-index-grp;
      uses cceqptog:equipment-properties-oper;
    }
  }

  grouping power-monitor-grp {
    container power-monitor {
      list power-unit-module {
        key power-unit-id;
        unique equipment-entity-index;
        description "List of the power units";
        min-elements 0;
        max-elements 4;

        leaf power-unit-id {
          type ccet:power-unit-id-t;
          
          description "Power Unit identifier";
        }

        uses ncs2k-2k-cet:equipment-entity-index-grp;
        uses ancillary-type-grp;
        uses cceqptog:equipment-properties-oper;
      }
      must "(count(power-unit-module) = 4 and (../../chassis-type='cet:NCS2015-ANSI' or ../../chassis-type='cet:NCS2015-ETSI')) or " +
           "(count(power-unit-module) = 2 and (../../chassis-type='cet:NCS2006-ANSI'  or ../../chassis-type='cet:NCS2006-ETSI'))";
    }
  }

  grouping ancillary-grp {
    container ancillary {
      config false;

      uses backplane-module-grp;
      uses fan-tray-module-grp;
      uses sync-bits-uts-module-grp;
      uses lcd-flash-module-grp;
      uses usb-flash-module-grp {
        when "../chassis-type = 'cet:NCS2015-ANSI' or ../chassis-type = 'cet:NCS2015-ETSI'";
      }
      uses power-monitor-grp;

      uses bits-uts-module-grp {
        when "../chassis-type = 'cet:NCS2015-ANSI' or ../chassis-type='cet:NCS2015-ETSI'";
      }
      uses alarm-contacts-grp {
        when "../chassis-type = 'cet:NCS2015-ANSI' or ../chassis-type='cet:NCS2015-ETSI'";
      }

      container ecu-slot {
        uses ncs2k-2k-cet:equipment-entity-index-grp;

        container ecu {

          uses ncs2k-2k-cet:equipment-entity-index-grp;

          leaf ecu-type {
            type ccet:ecu-type-t;        
            // mandatory true;
            config false;
            description "ECU Type";
          }
          must "derived-from(ecu-type, 'cet:ncs2k-ecu-type')" {
            error-message "Abstract ecu types are not allowed";
          }

          uses cceqptog:equipment-properties-oper;

          // ECU submodules
          uses usb-uts-modules-grp;
          uses udc-voip-modules-grp;
          uses ms-isc-modules-grp;
          uses ems-craft-modules-grp;

          uses bits-uts-module-grp {
            when "../../../chassis-type = 'cet:NCS2006-ANSI'  or ../../../chassis-type = 'cet:NCS2006-ETSI'";
          }
          uses alarm-contacts-grp {
            when "../../../chassis-type = 'cet:NCS2006-ANSI'  or ../../../chassis-type = 'cet:NCS2006-ETSI'";
          }
          uses pluggable-ports-module-grp {
            when "../../../chassis-type = 'cet:NCS2015-ANSI' or ../../../chassis-type = 'cet:NCS2015-ETSI'";
          }
        }
      }
    }
  }
    
  grouping usb-uts-passive-modules-grp {
    list usb-uts-passive-module {
      key usb-uts-id;
      unique equipment-entity-index;
      description "List of usb uts within passive shelf";
      min-elements 0;
      max-elements 2;

      leaf usb-uts-id {
        type ccet:usb-uts-id-t;
        description "Usb uts identifier";
      }

      uses ncs2k-2k-cet:equipment-entity-index-grp;

      uses ancillary-type-grp;
      uses cceqptog:equipment-state-oper-grp;
      uses usb-passive-port-list-grp;
    }
  }

  grouping ancillary-passive-grp {
    container ancillary-passive {
      presence "Container of all ancillary elements of passive shelf";
      config false;
      uses usb-uts-passive-modules-grp;
    }
  }
}
