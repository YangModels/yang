module cisco-svo-common-zr-plus-types {
  yang-version 1.1;
  namespace "http://cisco.com/yang/svo/common-zr-plus-types";
  prefix cczrpt;

  import org-openroadm-interfaces { prefix or-if; revision-date 2018-09-28; }
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO OIF ZR Plus common types.";

   revision 2021-04-16 { 
      description "Model version for SVO Release 12.2.0 "; 
      reference cisco-svo-common-zr-plus-types.yang; 
   }
 

  revision 2020-12-04 { 
      description "Model version for SVO Release 12.1.0 "; 
      reference cisco-svo-common-zr-plus-types.yang; 
  }
  
  
  identity zrPlus {
    base or-if:interface-type;
    description
      "OIF-ZR/ZR-Plus Interface";
  }
  
  identity zr-plus-rate-identity {
    description
      "A unique rate identification of the OIF-ZR/ZR-Plus.";
  }

  identity ZR-400G {
    base zr-plus-rate-identity;
    description
      "Identity for OIF 400ZR";
  }
  
  identity ZR-300G {
    base zr-plus-rate-identity;
    description
      "Identity for OIF 300ZR";
  }
 
  identity ZR-200G {
    base zr-plus-rate-identity;
    description
      "Identity for OIF 200ZR";
  }

}
