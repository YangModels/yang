module cisco-svo-pm {
  yang-version 1.1;
  namespace "http://cisco.com/yang/svo/svo-pm";
  prefix svo-pm;

  import tailf-common { prefix tailfs; }
  import cisco-svo-common-pm-grp { prefix cpmg; }
  import cisco-svo-tca { prefix tca;}
  import cisco-svo-rmons-thresholds { prefix rthresholds;}

  import cisco-svo-common-pm-types { prefix ccpmt; }

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "YANG definition for the SVO-PM device model.";

    revision 2020-12-04 { 
       description "Model version for SVO Release 12.1.0 "; 
       reference cisco-svo-pm.yang; 
    }
 
  
  container svo-pm {
    tailfs:info "Performance Node container";
    description 
       "Performance Node container.";

    list pm-active-resource {
      key "resource-type granularity";
      leaf resource-type {
        type ccpmt:pm-resource-type;
      }
      leaf granularity {
        type ccpmt:pm-granularity;
      }
    }

    uses cpmg:pm-commands-grp;
    uses tca:tca-group;
    uses rthresholds:rmon-threshold-group;
    uses tca:tca-commands-grp;
  }

  notification pm-data-file-available {
    description
    "Notification for availability of a PM data file";

    uses cpmg:pm-data-file-grp;
  } 
}
