module cisco-svo-common-license-oper-grp {

  yang-version 1.1;
  namespace "http://cisco.com/yang/svo/common-license-oper-grp";
  prefix cclicog;

 
  import tailf-common { prefix tailf; }
  import ietf-yang-types { prefix yang; }
  import cisco-svo-common-license-types { prefix cclict; }


  organization
    "Cisco Systems, Inc.";

  contact
    "Cisco Systems, Inc.
     Customer Service

     Postal: 170 West Tasman Drive
     San Jose, CA 95134

     Tel: +1 800 553-NETS

     E-mail: cs-yang@cisco.com";

  description
    "Cisco Common License Operational Data Group";

  revision 2021-12-25 {
  	description "Model version for SVO Release 12.3.0";
      reference cisco-svo-common-license-oper-grp.yang;
   }

   grouping license-unit {
       leaf license-store-index {
          type uint64;
          description "index of the store in which this license exist";
          tailf:hidden full;
       }
       leaf license-unit-index {
          type uint64;
          description "index license ";
          tailf:hidden full;
       }
       leaf license-type {
          type cclict:license-type-t;
          description "Type of license LICENSE_TYPE_PERMANENT, LICENSE_TYPE_TRIAL,LICENSE_TYPE_UNKNOWN";
       }
       leaf feature-version {
          type string;
          description "license feature version";
          tailf:hidden full;
       }
       leaf validity-period {
          type string;
          description "total life time of the license";
          tailf:hidden full;
       }
       leaf validity-period-remaining {
          type string;
          description "life time of the license remaining";
       }
       leaf license-line {
          type string;
          description "actual license line (not the whole file) that gets installed into the flash";
       }
       leaf license-state {
          type cclict:license-state-t;
          description "state of the feature";
       }
       leaf license-eula-status {
          type uint64;
          description "if @ref LICENSE_EULA_ACCEPTED then EULA has been accepted else 0";
          tailf:hidden full;
       }
       leaf is-node-locked {
          type boolean;
          description "TRUE if license is node locked";
          tailf:hidden full;
       }
       leaf priority {
          type cclict:precedence-t;
       }
       leaf comments {
          type string;
          description "comments added to the license using annotate operation";
          tailf:hidden full;
       }
       leaf count {
          type uint64;
          description "count ";
       }
       leaf usage {
          type uint64;
          description "0 if non-counted license else contains count being used";
          tailf:hidden full;
       }
       leaf license-hash {
          type string;
          description "hash of the license line, also called id of the license";
          tailf:hidden full;
       }
       leaf license-version {
          type uint64;
          description "license Version";
          tailf:hidden full;
       }
       leaf is-counted-license {
          type boolean;
          description "TRUE if max count supported";
          tailf:hidden full;
       }
       leaf is-expired {
          type cclict:is-expired-t;
          description "license expired";
       }
       leaf expiry-date {
          type string;
          description "expiry Date";
       }
       leaf start-date {
          type string;
          description "start Date";
          tailf:hidden full;
       }

    }
    grouping countedlic-entity-data {
        leaf ent-index {
	     type uint64;
	     description "port index";
        }
        leaf port-number {
	     type uint64;
	     description "port index";
        }
        leaf wave-length {
	     type string;
	     description "wave length";
        }
        leaf is-base-license {
                  type boolean;
                  description "is base license";
        }
        leaf entity-license-state {
                  type cclict:license-om-state-t;
          description "license state";
        }
    }
  grouping countedlic-feature-data {
       leaf total-base-count {
          type uint32;
          description "total base count";
       }
       leaf total-license-count {
                  type uint32;
                  description "total license count";
       }
       leaf available-base-count {
          type uint32;
          description "available base count";
       }
       leaf available-license-count {
          type uint32;
          description "available base count";
       }
       leaf count-violation-count {
                  type uint32;
          description "violation count";
       }
       list countedlic-entity-data-list {
         key index;
         leaf index {
                   type uint64;
                   description "index";
         }
         uses countedlic-entity-data;
       }
       list manage-license-lines {
                key license-index;
         leaf license-index {
                   type string;
                   description "String of license-type+-count";
         }
         uses license-unit;
      }
    }

    grouping noncountedlic-feature-data {
                leaf lic-state {
                  type cclict:license-om-state-t;
        }
        leaf is-base-functionality {
           type boolean;
        }
       list manage-license-lines {
                key license-index;
         leaf license-index {
                   type string;
                   description "String of license-type+-count";
         }
         uses license-unit;
      }
   }

}
