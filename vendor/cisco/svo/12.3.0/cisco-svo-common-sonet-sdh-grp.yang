module cisco-svo-common-sonet-sdh-grp {
  yang-version 1.1;
  namespace "http://cisco.com/yang/svo/common-sonet-sdh-grp";
  prefix cossdh;

  import cisco-svo-common-base-opt-grp { prefix ccbog; }
  import cisco-svo-common-sonet-sdh-types { prefix ccssdht; }
  import cisco-svo-common-types { prefix ct; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the SONET/SDH interface Config group";

   revision 2021-04-16 { 
      description "Model version for SVO Release 12.2.0 "; 
      reference cisco-svo-common-sonet-sdh-grp.yang; 
   }
 

  revision 2020-12-04 { 
      description "Model version for SVO Release 12.1.0 "; 
      reference cisco-svo-common-sonet-sdh-grp.yang; 
  }
 

  grouping sonet-sdh-config-synchronization-group {
    leaf send-DUS {
      type boolean;
      config true;
      description "The facility will send the DUS (Do not use for Synchronization) value in 0x0f bits pattern as the synchronization status message for that facility";
    }

    leaf rx-ssm {
      type ccssdht:sonet-sdh-quality-level-t;
      description "Rx Quality of the individual port: clock source quality level for SONET/SDH.";
    }

    leaf admin-ssm {
      type ccssdht:sonet-sdh-quality-level-t;
      config true;
      description "Quality of the individual port: clock source quality level for SONET/SDH.";
    }
    leaf sync-MessageIn {
        type boolean;
        description "syncMessageIn - are valid SSM's coming in on the S1 byte?";
    }
  }

  grouping sonet-sdh-config-squelch-group {
    leaf squelch-mode {
      type ct:squelch-sonet-sdh-t;
      config true;
      default "Ais";
    }

    leaf squelch-hold-off-time {
      type ct:squelch-hold-off-time-t;
      config true;
      default "Disable";
    }
  }

  grouping sonet-sdh-config-j0-trace-group {
    leaf enable-j0-trace {
      type boolean;
      config true;
      description "Enable J0 Trace";
    }

    leaf format-j0-trace {
      type ccssdht:trace-format-t;
      config true;
      description "Trace format";
    }

    leaf tx-j0-trace {
      type ccssdht:j0-trace-t;
      config true;
      description "TX J0 TRACE";
    }

    leaf expected-j0-trace {
      type ccssdht:j0-trace-t;
      config true;
      description "Expected J0 TRACE";
    }
  }

  grouping sonet-config-group {
    container synchronization {
      description "Configures the sonet-sdh synchronization data";
      uses sonet-sdh-config-synchronization-group;
    }

    uses ccbog:ber-grp;
    uses sonet-sdh-config-squelch-group;

    container j0-trace {
      uses sonet-sdh-config-j0-trace-group;
    }  

    leaf termination-mode {
        type ccssdht:sonet-termination-mode-t;
    }
  }

  grouping sdh-config-group {
    container synchronization {
      description "Configures the sonet-sdh synchronization data";
      uses sonet-sdh-config-synchronization-group;
    }

    uses ccbog:ber-grp;
    uses sonet-sdh-config-squelch-group;

    container j0-trace {
      uses sonet-sdh-config-j0-trace-group;
    }

    leaf termination-mode {
        type ccssdht:sdh-termination-mode-t;
    }
  }
}
