module cisco-ncs2k-equipment-types {
  yang-version 1.1;
  namespace "http://cisco.com/yang/ncs2k/equipment-types";
  prefix cet;

  import cisco-svo-common-equipment-types { prefix ccet; }
  
  organization
    "Cisco Systems, Inc.";

  contact
    "Cisco Systems, Inc.
     Customer Service

     Postal: 170 West Tasman Drive
     San Jose, CA 95134

     Tel: +1 800 553-NETS

     E-mail: cs-yang@cisco.com";

  description "
    This module defines the basic cisco equipment types for NCS2K platform.";

   revision 2021-04-16 { 
      description "Model version for SVO Release 12.2.0 "; 
      reference cisco-ncs2k-equipment-types.yang; 
   }
 

    revision 2020-12-04 { 
       description "Model version for SVO Release 12.1.0 "; 
       reference cisco-ncs2k-equipment-types.yang; 
    }
 


  /*
    Supported Net Element types.
  */
  identity NCS2000 {
    base ccet:cisco-ne-type;
    description "NCS2000 Net Element Type";
  }


  /*
    Supported Slice submode for 400G line card.
  */
  identity OPM-100G  {
    base ccet:slice-mode;
  }

  identity OPM-10x10G {
    base ccet:slice-mode;
  }

  identity OPM-2x100G  {
    base ccet:slice-mode;
  }
  
  identity OPM-4x100G  {
   base ccet:slice-mode;
  }
  
  identity OPM-400G  {
    base ccet:slice-mode;
  }
  
  identity OPM-4x100G-DD  {
   base ccet:slice-mode;
  }
  
  identity OPM-3x100G-DD  {
   base ccet:slice-mode;
  }
  
  identity OPM-3x100G  {
   base ccet:slice-mode;
  }
  
  identity OPM_B_300G  {
   base ccet:slice-mode;
  }

  identity OPM-6x16G-FC {
    base ccet:slice-mode;
  }

  identity OPM-2x40G-2x10G {
    base ccet:slice-mode;
  }

  identity OPM-PEER-ODU2 {
    base ccet:slice-mode;
  }

  identity OPM-PEER-ODU2E {
    base ccet:slice-mode;
  }
  
  /*
  Supported card mode.
  */
  identity GEXP-MXP {
    base ccet:card-mode;
    description "Card Mode 10 GE MXP for card GE-XP";
  }

  identity GEXP-2MXP {
    base ccet:card-mode;
    description "Card Mode 20 GE MXP for card GE-XP";
  }

  identity GEXP-MXP-L2-SWITCH {
    base ccet:card-mode;
    description "Card Mode L2 over DWDM for card GE-XP";
  }

  identity XP10GE-TXP {
    base ccet:card-mode;
    description "Card Mode 10 GE TXP for card 10GE-XP";
  }

  identity XP10GE-TXP-L2-SWITCH {
    base ccet:card-mode;
    description "Card Mode L2 over DWDM for card 10GE-XP";
  }

  identity OTU2XP-2XP {
    base ccet:card-mode;
    description "Card Mode Transponder for card OTU2-XP";
  }

  identity OTU2XP-2REG {
    base ccet:card-mode;
    description "Card Mode Two Regen Mode for card OTU2-XP";
  }

  identity OTU2XP-XP-REG {
    base ccet:card-mode;
    description "Card Mode Txp-Regen Mode for card OTU2-XP";
  }

  identity OTU2XP-REG-XP {
    base ccet:card-mode;
    description "Card Mode Regen-Txp Mode for card OTU2-XP";
  }

  identity OTU2XP-EFEC-REG {
    base ccet:card-mode;
    description "Card Mode Standard Regen for card OTU2-XP";
  }

  identity OTU2XP-SPLITTER {
    base ccet:card-mode;
    description "Card Mode Enhanced FEC for card OTU2-XP";
  }

  identity OTU2XP-LANWAN {
    base ccet:card-mode;
    description "Card Mode Mixed for card OTU2-XP";
  }

  identity OTU2XP-LANWAN-SPLITTER {
    base ccet:card-mode;
    description "Card Mode 10GE LAN to WAN for card OTU2-XP";
  }

  identity PSM-NORMAL {
    base ccet:card-mode;
    description "Card Mode Normal for card PSM";
  }

  identity PSM-STANDALONE {
    base ccet:card-mode;
    description "Card Mode Standalone for card PSM";
  }

  identity XM-40G-OTU3 {
    base ccet:card-mode;
    description "Card Mode Muxponder for cards 40E-MXP-C and 40G-MXP-C";
  }

  identity XM-40G-OTU3E2 {
    base ccet:card-mode;
    description "Card Mode Muxponder for cards 40E-MXP-C and 40G-MXP-C with Overclocked trunk";
  }

  identity XM-40G-UNIDIR-REGEN  {
    base ccet:card-mode;
    description "Card Mode unidirectional Regen for cards 40E-MXP-C and 40G-MXP-C";
  }

  identity TNC-MODE  {
    base ccet:card-mode;
    description "Card Mode TNC for card TNC";
  }

  identity TNCO-MODE  {
    base ccet:card-mode;
    description "Card Mode TNCO for card TNC";
  }

  identity WXC-BIDI  {
    base ccet:card-mode;
    description "Card Mode Bidirectional for card 80-WXC";
  }

  identity WXC-MUX  {
    base ccet:card-mode;
    description "Card Mode Bidirectional for card 80-WXC";
  }
  
  identity WXC-DEMUX  {
    base ccet:card-mode;
    description "Card Mode Bidirectional for card 80-WXC";
  }
 
  /*
  Supported Transponder/Muxponder functional mode.
  */
  
  identity TXP-MR {
    base ccet:functional-mode;
    description "TXP mode for cards AR-XP, AR-XPE and AR-MXP";
  }

  identity TXPP-MR {
    base ccet:functional-mode;
    description "Protected TXP mode for cards AR-XP, AR-XPE and AR-MXP";
  }

  identity MXP-DME {
    base ccet:functional-mode;
    description "MXP DME mode for cards AR-XP and AR-XPE";
  }

  identity MXPP-DME {
    base ccet:functional-mode;
    description "Protected MXP DME mode for cards AR-XP and AR-XPE";
  }

  identity MXP-4x25-10G {
    base ccet:functional-mode;
    description "MXP 4x25 10G mode for cards AR-XP and AR-XPE";
  }

  identity MXPP-4x25-10G {
    base ccet:functional-mode;
    description "Protected MXP 4x25 10G mode for cards AR-XP and AR-XPE";
  }

  identity MXP-MR {
    base ccet:functional-mode;
    description "MXP mode for cards AR-XP, AR-XPE and AR-MXP";
  }

  identity MXPP-MR {
    base ccet:functional-mode;
    description "Protected MXP mode for cards AR-XP, AR-XPE and AR-MXP";
  }

  identity TXPMXP {
    base ccet:functional-mode;
    description "TXPMXP Mode for Cards T6";
  }
  
  identity BUNDLE-3x300-2DD {
    base ccet:functional-mode;
    description "BUNDLE-3x300-2DD Mode for Cards T6";
  }
  

  identity MXP-VD-10G {
    base ccet:functional-mode;
    description "MXP Video 10G mode for cards AR-XP and AR-XPE";
  }

  identity RGN {
    base ccet:functional-mode;
    description "Regenerator mode for cards AR-XP, AR-XPE and AR-MXP";
  }

  identity MXP-DME-UNISTAGE-MUX {
    base ccet:functional-mode;
    description "Regenerator mode for card AR-XPE";
  }

  identity TXP-100G {
    base ccet:functional-mode;
    description "TXP 100G mode for cards 100G-CK-C, 100G-LC-C, 100GS-CK-LC, 200G-CK-LC and MR-MXP";
  }

  identity RGN-100G {
    base ccet:functional-mode;
    base ccet:regen-functional-mode;
    description "Regenerator 100G for cards 100G-CK-C, 100G-LC-C, 100GS-CK-LC and 200G-CK-LC";
  }

  identity MXP-10x10G {
    base ccet:functional-mode;
    description "MXP 10X10G for card 10x10G-LC";
  }

  identity FANOUT-10x10G {
    base ccet:functional-mode;
    description "FANOUT 10X10G for card 10x10G-LC";
  }

  identity TXP-10G {
    base ccet:functional-mode;
    description "TXP 10G for card 10x10G-LC and WSE";
  }

  identity RGN-10G {
    base ccet:functional-mode;
    base ccet:regen-functional-mode;
    description "Regenerator 10G for card 10x10G-LC and WSE";
  }

  identity CFP-TXP {
    base ccet:functional-mode;
    description "TXP mode for CFP-LINE";
  }

  identity CFP-MXP {
    base ccet:functional-mode;
    description "MXP mode for CFP-LINE";
  }

  identity LOW-LATENCY {
    base ccet:functional-mode;
    base ccet:regen-functional-mode;
    description "TXP 10G for card 10x10G-LC";
  }

  identity MXP-2x40G {
    base ccet:functional-mode;
    description "MXP 2x40G mode for card 100G-CK-C";
  }

  identity MXP-MR-S {
    base ccet:functional-mode;
    description "MXP Static mode for cards AR-XP, AR-XPE and AR-MXP";
  }

  identity MXPP-MR-S {
    base ccet:functional-mode;
    description "Protected MXP Static mode for cards AR-XP, AR-XPE and AR-MXP";
  }

  identity MXP-200G {
    base ccet:functional-mode;
    description "MXP 200G mode for card 100GS-CK-LC and 200G-CK-LC";
  }

  identity MXP-10x10G-100G {
    base ccet:functional-mode;
    description "MXP 10X10G 100G for card 100GS-CK-LC and 200G-CK-LC";
  }

  identity MXP-CK-100G-CPAK {
    base ccet:functional-mode;
    description "MXP CK 100G for card 100GS-CK-LC and 200G-CK-LC, uses CPAK of MR-MXP";
  }

  identity MXP-CK-100G-SFP-QSFP {
    base ccet:functional-mode;
    description "MXP CK 100G for card 100GS-CK-LC and 200G-CK-LC uses SFP and QSFP ports of MR-MXP";
  }

  identity MXP-100G {
    base ccet:functional-mode;
    description "MXP 100G mode for card MR-MXP with with 10x10G submode";
  }

  identity MXP-2x40G-2x10G {
    base ccet:functional-mode;
    description "MXP 100G mode for card MR-MXP with 2x40G-2x10G submode";
  }

  identity TXPP-10G {
    base ccet:functional-mode;
    base ccet:protected-functional-mode;
    description "Protected TXP 10G for card 10x10G-LC";
  }

  identity B2B-100G-CPAK {
    base ccet:functional-mode;
    description "B2B 100G mode for card MR-MXP, uses CPAK";
  }

  identity B2B-100G-SFP-QSFP {
    base ccet:functional-mode;
    description "B2B 100G mode for card MR-MXP, uses SFP and QSFP ports";
  }

  identity MXP {
    base ccet:functional-mode;
    description "MXP mode for card 400G-XP-LC";
  }

  identity MXP-2x150G {
    base ccet:functional-mode;
    base ccet:bundle-functional-mode;

    description "MXP 2x150G 8QAM mode for card 400G-XP-LC";
  }

  identity OTNXC {
    base ccet:functional-mode;
    description "OTN XC mode for card 400G-XP-LC";
  }

  identity REGEN-100G {
    base ccet:functional-mode;
    base ccet:regen-functional-mode;
    description "Regenerator mode with 100G submode for card 400G-XP-LC";
  }

  identity REGEN-200G {
    base ccet:functional-mode;
    base ccet:regen-functional-mode;
    description "Regenerator mode with 200G submode for card 400G-XP-LC";
  }

  /*
    Supported NCS2k chassis types.
  */
  identity ncs2k-chassis {
    base ccet:chassis-type;
    description
      "NCS2k Chassis Type";
  }
  
  identity NCS2006-ANSI {
    base ncs2k-chassis;
    description "
      15454 M6 ANSI - 6 line card horizontal slots + 2 Controllers.";
  }

  identity NCS2006-ETSI {
    base ncs2k-chassis;
    description "
      15454 M6 ETSI - 6 line card horizontal slots + 2 Controllers.";
  }

  identity NCS2015-ANSI {
    base ncs2k-chassis;
    description "
      15454 M15 ANSI - 15 line card vertical slots + 2 Controllers.";
  }

  identity NCS2015-ETSI {
    base ncs2k-chassis;
    description "
      15454 M15 ETSI - 15 line card vertical slots + 2 Controllers.";
  }


  identity NCS2K-MF10-6RU {
    base ccet:passive-chassis;
    description "
      Passive Chassis with 10 slot is 6RU high";
  }

  identity NCS2K-MF-6RU {
    base ccet:passive-chassis;
    description "
      Passive Chassis is 6RU high";
  }

  /*
    Supported ECU types.
  */
  identity ncs2k-ecu-type {
    base ccet:ecu-type;
    description "NCS2k ECU Type";
  }

  identity NCS2006-ECU-S {
    base ncs2k-ecu-type;
    description "NCS 2006 External Connections Unit -w/2x USB 3.0 Ports";
  }

  identity NCS2006-ECU-60-S {
    base ncs2k-ecu-type;
    description "NCS 2006 External Connections Unit -w/2x USB 3.0 Ports -60V";
  }

  identity _15454-M6-ECU2 {
    base ncs2k-ecu-type;
    description "6 service slot MSTP external connection unit with TOD/PPS";
  }

  identity NCS2006-ECU {
    base ncs2k-ecu-type;
    description "NCS 2006 External Connections Unit";
  }

  identity _15454-M6-ECU {
    base ncs2k-ecu-type;
    description "6 slot MSTP external connection unit with TOD/PPS";
  }

  identity _15454-M6-ECU-60 {
    base ncs2k-ecu-type;
    description "6 slot MSTP external connection unit with TOD/PPS (60V)";
  }

  identity NCS2015-ECU {
    base ncs2k-ecu-type;
    description "NCS 2015 External Connections Unit";
  }

  
  /*
    Supported ppm types.
  */
  identity PPM-1-PORT {
    base ccet:ppm-type;
    description "PPM 1 Port";
  }

  
  /*
    Supported card types.
  */

  identity FILLER {
    base ccet:card-type;
    base ccet:oper-card-type;
    description "FILLER Card Type";
  }

  identity TNC {
    base ccet:card-type;
    base ccet:card-with-card-mode;
    description "
      Transport Network Controller - NCS2K controller working for M2,
      M6";
  }

  identity TNCS-2O {
    base ccet:card-type;
    description "
      Transport Network Controller Type 2 with Otdr - NCS2K controller working for M2,
      M6";
  }

  identity TSC {
    base ccet:card-type;
    description "
      TSC
    ";
  }

  identity _15454-OPT-BST {
    base ccet:card-type;
    description "Optical Booster card";
  }

  identity _15454-OPT-PRE {
    base ccet:card-type;
    description "Optical Preamplifier card";
  }

  identity _15454-OPT-BST-E {
    base ccet:card-type;
    description "Optical Booster Enhanced card";
  }

  identity _15454-OPT-AMP-17C {
    base ccet:card-type;
    description "Optical Booster Gain Block card";
  }
  
  identity _15454-OPT-AMP-C {
    base ccet:card-type;
    description "Optical Amplifier with mid access loss support";
  }

  identity _15454-OPT-RAMP-C {
    base ccet:card-type;
    description "Raman Amplifier card";
  }
  
  identity _15454-OPT-RAMP-CE {
    base ccet:card-type;
    description "Raman Amplifier Extended card";
  }
  
  identity _15454-OPT-EDFA-24 {
    base ccet:card-type;
    description "OPT_EDFA_24_LINE Card";
  }

  identity _15454-OPT-EDFA-17 {
    base ccet:card-type;
    description "OPT_EDFA_17_LINE Card";
  }

  identity NCS2K-OPT-EDFA-35 {
    base ccet:card-type;
    description "OPT_EDFA2_35_LINE Card";
  }

  identity _15454-M-RAMAN-COP {
    base ccet:card-type;
    description "OPT_RAMP_COP Card";
  }

  identity _15454-M-RAMAN-CTP {
    base ccet:card-type;
    description "OPT_RAMP_CTP Card";
  }

  identity NCS2K-EDRA1-26C {
    base ccet:card-type;
    description "
      EDRA-1-26 C Erbium Doped amplifier + Raman amplifier - up to 26 dB span";
  }

  identity NCS2K-EDRA2-26C {
    base ccet:card-type;
    description "
      EDRA-2-26 C Erbium Doped amplifier + Raman amplifier - up to 26 dB span";
  }

  identity NCS2K-EDRA2-35C {
    base ccet:card-type;
    description "
      EDRA-2-35 Erbium Doped amplifier + Raman amplifier - up to 35 dB span";
  }

  identity NCS2K-EDRA1-35C {
    base ccet:card-type;
    description "
      EDRA-1-35 Erbium Doped amplifier + Raman amplifier - up to 35 dB span";
  }

  identity NCS2K-RMN-CTP-CL {
    base ccet:card-type;
    description "NCS2K RMN-CTP card for C and L band (Rel 12.3)";
  }

  identity _15454-32-WSS {
    base ccet:card-type;
    description "Wavelength Selector switch 32 chs card";
  }

  identity _15454-32-DMX {
    base ccet:card-type;
    description "Active Demux 32 chs card";
  }

  identity _15454-40-WSS-C {
    base ccet:card-type;
    description "Wavelength Selector switch 40 chs odd grid card";
  }

  identity _15454-40-DMX-C {
    base ccet:card-type;
    description "Active Demux 40 chs card";
  }

  identity _15454-40-MUX-C {
    base ccet:card-type;
    description "Active Mux 40 chs card";
  }

  identity _15454-40-WXC-C {
    base ccet:card-type;
    description "Wavelength Cross Connect 40 chs odd grid card";
  }
    
  identity _15454-40-SMR1-C {
    base ccet:card-type;
    description "Single Module ROADM 1 card";
  }

  identity _15454-40-SMR2-C {
    base ccet:card-type;
    description "Single Module ROADM 2 card";
  }
  
  identity _15454-80-WXC-C {
    base ccet:card-type;
    base ccet:card-with-card-mode;
    description "80 WXC roadm card";
  }

  identity NCS2K-16-WXC-FS {
    base ccet:card-type;
    description "16 WXC FS roadm card";
  }

  identity NCS2K-9-SMR24FS {
    base ccet:card-type;
    description "
      SMR9_24_FS_LINE_CARD
    ";
  }

  identity NCS2K-9-SMR17FS {
    base ccet:card-type;
    description "
      SMR9_17_FS_LINE_CARD
    ";
  }

  identity NCS2K-9-SMR34FS {
    base ccet:card-type;
    description "
      SMR9_34_FS_LINE_CARD
    ";
  }

  identity NCS2K-20-SMRFS-CV {
    base ccet:card-type;
    description "
      SMR20
    ";
  }

  identity NCS2K-20-SMRFS {
    base ccet:card-type;
    description "
      SMR20
    ";
  }

  identity NCS2K-16-AD-CCOFS {
    base ccet:card-type;
    description "
      AD_16_FS_LINE_CARD
    ";
  }

  identity NCS2K-12-AD-CCOFS {
    base ccet:card-type;
    description "
      AD_12_FS_LINE_CARD
    ";
  }

  identity NCS2K-6AD-DD-CFS {
    base ccet:card-type;
    description "NCS2K 6 AD Colourless add/drop (Rel 12.3)";
  }

  identity _15454-40G-TXP-C {
    base ccet:card-type;
    description "40G Transponder line card";
  }

  identity _15454-40G-MXP-C {
    base ccet:card-type;
    base ccet:card-with-card-mode;
    description "40G Muxponder line card";
  }

  identity _15454-40E-TXP-C {
    base ccet:card-type;
    description "40G PM-QPSK Transponder line card";
  }

  identity _15454-40E-MXP-C {
    base ccet:card-type;
    base ccet:card-with-card-mode;
    description "40G PM-QPSK Muxponder line card";
  }

  identity _15454-10GE-XP {
    base ccet:card-type;
    base ccet:card-with-card-mode;
    description "XP_10GE_LINE Card";
  }

  identity _15454-OTU2-XP {
    base ccet:card-type;
    base ccet:card-with-card-mode;
    description "XP_4_10G_LINE Card";
  }

  identity NCS2K-100G-CK-C {
    base ccet:card-type;
    description "
      100G-CK-C Transponder";
  }

  identity _15454-M-100G-LC-C {
    base ccet:card-type;
    description "100G-LC-C Transponder";
  }

  identity _15454-M-CFP-LC {
    base ccet:card-type;
    description "CFP-LC card";
  }

  identity _15454-AR-MXP {
    base ccet:card-type;
    description "AR_MXP_LINE Card";
  }

  identity _15454-AR-XP {
    base ccet:card-type;
    description "AR_XP_LINE Card";
  }

  identity _15454-AR-XPE {
    base ccet:card-type;
    description "AR_XPE_LINE Card";
  }

  identity _15454-M-10X10G-LC {
    base ccet:card-type;
    description "Carpegna Card";
  }

  identity NCS2K-100GS-CK-C {
    base ccet:card-type;
    description "NCS2K_100GS_CK_C_LC Card";
  }

  identity NCS2K-200G-CK-C {
    base ccet:card-type;
    description "Titano 3 card";
  }

  identity NCS2K-1.2T-MXP {
    base ccet:card-type;
    description "Titano 6 card";
  }
  
  identity NCS2K-400G-XP {
    base ccet:card-type;
    description "Titano 5 card";
  }

  identity NCS2K-MR-MXP {
    base ccet:card-type;
    description "Falco Card";
  }

  identity _15454-GE-XP {
    base ccet:card-type;
    base ccet:card-with-card-mode;
    description "XP_GE_LINE Card";
  }

  identity _15454-M-WSE-K9 {
    base ccet:card-type;
    description "WSE_LINE Card";
  }

  identity _15454-PSM {
    base ccet:card-type;
    base ccet:card-with-card-mode;
    description "
      PSM_LINE CARD
    ";
  }
  
  identity _15454-OSC-CSM {
    base ccet:card-type;
    description "Optical Service Channel - Combiner Separator Module";
  }

  identity NCS2K-SVO-K9 {
    base ccet:card-type;
    description "
      SVO Card
    ";
  }

  /*
    Supported ancillary card types.
  */
  identity FAN-TRAY-UTS {
    base ccet:ancillary-type;
    description "
      Fan Tray ancillary unit (this is for M2, M6 and M15";
  }

  identity ALARM-DRYCONTACT-UTS {
    base ccet:ancillary-type;
    description "
      Dry Contacts and Alarms interface unit,
      this is a External Connections Unit (ECU) submodule";
  }

  identity USB-UTS {
    base ccet:ancillary-type;
    description "
      USB for passive unit interconnation 'interface unit',
      this is a External Connections Unit (ECU) submodule";
  }

  identity UDC-VOIP-UTS {
    base ccet:ancillary-type;
    description "
      User Data Channel and Voice-over-IP interface,
      this is a External Connections Unit (ECU) submodule";
  }

  identity ISC-EQPT-UTS {
    base ccet:ancillary-type;
    description "
      EMS, CT and Multishelf interfaces,
      this is a External Connections Unit (ECU) submodule";
  }

  identity BITS-UTS {
    base ccet:ancillary-type;
    description "
      Input-Output Synchronization connectors,
      this is a External Connections Unit (ECU) submodule";
  }

  identity IO-UTS {
    base ccet:ancillary-type;
    description "
      External parallel I/O interface,
      this is a External Connections Unit (ECU) submodule";
  }

  identity POWERSUPPLY-UTS {
    base ccet:ancillary-type;
    description "Power Supplay UTS Unit";
  }

  identity LCD-FLASH-UTS {
    base ccet:ancillary-type;
    description "LCD Display Unit + Chassis Data Base Flash";
  }

  identity ENVIRONMENT-CONTROL {
    base ccet:ancillary-type;
    description "Environment Comtrol";
  }

  identity ENVIRONMENT-ALARM {
    base ccet:ancillary-type;
    description "Environment Alarm";
  }

  identity MS-ISC-UTS-PORT {
    base ccet:ancillary-type;
    description "MS_ISC_UTS_PORT";
  }

  identity EMS-PORT-UTS  {
    base ccet:ancillary-type;
    description "EMS_PORT_UTS";
  }


  /*
    Supported port types.
  */
  identity DWDM-TRUNK-PORT {
    base ccet:port-type;
    description "DWDM-TRUNK-PORT";
  }

  identity DWDM-CLIENT-PORT {
    base ccet:port-type;
    description "DWDM-CLIENT-PORT";
  }

  identity OTU4-PORT {
    base ccet:port-type;
    description "OTU 4 Port";
  }

  identity OTU3-PORT {
    base ccet:port-type;
    description "OTU 3 Port";
  }

  identity OTU2-PORT {
    base ccet:port-type;
    description "OTU 2 Port";
  }

  identity OTU2E-PORT {
    base ccet:port-type;
    description "OTU 2e Port";
  }

  identity OTU1-PORT {
    base ccet:port-type;
    description "OTU 1 Port";
  }

  identity OTU4C2-PORT {
    base ccet:port-type;
    description "OTU4C2 Port";
  }

  identity ZR-400G-PORT {
  	status deprecated;
    base ccet:port-type;
    description "OIF 400ZR Port";
  }

  identity ZR-200G-PORT {
  	  status deprecated;
      base ccet:port-type;
      description "OIF 200ZR Port";
    }
  
  identity ZR-300G-PORT {
  	status deprecated;
    base ccet:port-type;
    description "OIF 300ZR Port";
  }

  identity ZRPLUS-400G-PORT {
    base ccet:port-type;
    description "OIF 400ZR Port";
  }

  identity ZRPLUS-200G-PORT {
      base ccet:port-type;
      description "OIF 200ZR Port";
    }
  
  identity ZRPLUS-300G-PORT {
    base ccet:port-type;
    description "OIF 300ZR Port";
  }
  
  identity OTU4C3-150G-PORT {
    base ccet:port-type;
    description "OTU4C3-150G Port";
  }

  identity OTL-PORT {
    base ccet:port-type;
    description "OTL Port";
  }

  identity FE-PORT {
    base ccet:port-type;
    description "Fast Ethernet";
  }

  identity ONE-GE-PORT {
    base ccet:port-type;
    description "1Gbit Ethernet";
  }

  identity OC3-PORT {
    base ccet:port-type;
    description "Port OC3 (ANSI only)";
  }

  identity STM1-PORT {
    base ccet:port-type;
    description "Port STM1 (ETSI only)";
  }

  identity OC12-PORT {
    base ccet:port-type;
    description "Port OC12 (ANSI only)";
  }

  identity STM4-PORT {
    base ccet:port-type;
    description "Port STM4 (ETSI only)";
  }

  identity OCH-PORT {
    base ccet:port-type;
    description "Optical Channel";
  }

  identity ONEHUNDRED-GE-PORT {
    base ccet:port-type;
    description "100G Ethernet Port";
  }
  
  identity FOURHUNDRED-GE-PORT {
    base ccet:port-type;
    description "400G Ethernet Port";
  }

  identity TEN-GE-PORT {
    base ccet:port-type;
    description "10G Ethernet Port";
  }

  identity FORTY-GE-PORT {
    base ccet:port-type;
    description "40G Ethernet Port";
  }

  identity OC48-PORT {
    base ccet:port-type;
    description "OC48 Port (ANSI only)";
  }

  identity STM16-PORT {
    base ccet:port-type;
    description "STM16 Port (ETSI only)";
  }

  identity OC192-PORT {
    base ccet:port-type;
    description "OC192 Port (ANSI only)";
  }

  identity STM64-PORT {
    base ccet:port-type;
    description "STM64 Port (ETSI only)";
  }

  identity FC1G-PORT {
    base ccet:port-type;
    description "FC1G Port";
  }

  identity FC2G-PORT {
    base ccet:port-type;
    description "FC2G Port";
  }

  identity FC10G-PORT {
    base ccet:port-type;
    description "FC10G Port";
  }

  identity FC8G-PORT {
    base ccet:port-type;
    description "FC8G Port";
  }

  identity FC16G-PORT {
    base ccet:port-type;
    description "FC16G Port";
  }

  identity IB-5G-PORT {
    base ccet:port-type;
    description "IB 5G  Port";
  }
    
  identity OTS-PORT {
    base ccet:port-type;
    description "Optical Transport";
  }

  identity AOTS-PORT {
    base ccet:port-type;
    description "Amplified Optical Transport";
  }
  
  
  /* Supported Passive-types */
  identity mf-6ru-passive-type {
    base ccet:passive-type;
    description "Passive Type installed in the MF 6ru Passive Shelf";
  }

  identity mf10-6ru-passive-type {
    base ccet:passive-type;
    description "Passive Type installed in the MF 6ru Passive Shelf";
  }
  
  
  /*
  Supported ru-passive subtypes.
  */
  identity _15216-MD-40-ODD {
    base ccet:ru-passive-type;
    description "Passive MD 40 Odd";
  }

  identity _15216-MD-40-EVEN {
    base ccet:ru-passive-type;
    description "Passive MD 40 Even";
  }

  identity _15216-MD-ID-50 {
    base ccet:ru-passive-type;
    description "Passive MD ID 50";
  }

  identity _15216-PP-MESH-8 {
    base ccet:ru-passive-type;
    description "Passive Mesh Patch-Panel 8 Degrees";
  }

  identity _15216-PP-MESH-4 {
    base ccet:ru-passive-type;
    description "Passive Mesh Patch-Panel 4 Degrees";
  }

  identity _15216-PP-4-SMR {
    base ccet:ru-passive-type;
    description "Passive SMR-2 Patch-Panel 4 Degrees";
  }

  identity PASSIVE_DCU {
    base ccet:ru-passive-type;
    description "Passive DCU";
  }

  identity _15216-FLD-OSC {
    base ccet:ru-passive-type;
    description "Passive FLD OSC";
  }

  identity PASSIVE_FBGDCU_165 {
    base ccet:ru-passive-type;
    description "Passive FBGDCU 165";
  }

  identity PASSIVE_FBGDCU_331 {
    base ccet:ru-passive-type;
    description "Passive FBGDCU_331";
  }

  identity PASSIVE_FBGDCU_496 {
    base ccet:ru-passive-type;
    description "Passive FBGDCU_496";
  }

  identity PASSIVE_FBGDCU_661 {
    base ccet:ru-passive-type;
    description "Passive FBGDCU_661";
  }

  identity PASSIVE_FBGDCU_826 {
    base ccet:ru-passive-type;
    description "Passive FBGDCU_826";
  }

  identity PASSIVE_FBGDCU_992 {
    base ccet:ru-passive-type;
    description "Passive FBGDCU_992";
  }

  identity PASSIVE_FBGDCU_1157 {
    base ccet:ru-passive-type;
    description "Passive FBGDCU_1157";
  }

  identity PASSIVE_FBGDCU_1322 {
    base ccet:ru-passive-type;
    description "Passive FBGDCU_1322";
  }

  identity PASSIVE_FBGDCU_1653 {
    base ccet:ru-passive-type;
    description "Passive FBGDCU_1653";
  }

  identity PASSIVE_FBGDCU_1983 {
    base ccet:ru-passive-type;
    description "Passive FBGDCU_1983";
  }

  identity _15216-MD-48-ODD {
    base ccet:ru-passive-type;
    description "Passive MD_48_ODD";
  }

  identity _15216-MD-48-EVEN {
    base ccet:ru-passive-type;
    description "Passive MD_48_EVEN";
  }

  identity _15216-MD-48-ODDE {
    base ccet:ru-passive-type;
    description "Passive MD_48_ODD_E";
  }

  identity _15216-MD-48-EVENE {
    base ccet:ru-passive-type;
    description "Passive MD_48_EVEN_E";
  }

  identity _15216-MD-48-CM {
    base ccet:ru-passive-type;
    description "Passive MD_48_CM";
  }

  identity _15216-MD-48-CME {
    base ccet:ru-passive-type;
    description "Passive MD_48_CM_E";
  }

  identity NCS1K-MD-64-C {
    base ccet:ru-passive-type;
    description "Passive MD_64_C";
  }

  identity NCS2K-PPMESH8-5AD {
    base ccet:ru-passive-type;
    description "Passive PPMESH8_5AD";
  }

  identity MECH_UNIT {
    base ccet:ru-passive-type;
    description "MECH_UNIT";
  }

  identity NCS2K-MF-4X4-COFS {
    base ccet:ru-passive-type;
    base mf-6ru-passive-type;
    description "Passive 4X4_COFS_C";
  }

  identity NCS2K-MF-DEG-5 {
    base ccet:ru-passive-type;
    base mf-6ru-passive-type;
    description "Passive MOD_DEG_5";
  }

  identity NCS2K-MF-UPG-4 {
    base ccet:ru-passive-type;
    base mf-6ru-passive-type;
    description "Passive MOD_UPG_4";
  }

  identity NCS2K-MF-MPO-8LC {
    base ccet:ru-passive-type;
    base mf-6ru-passive-type;
    description "Passive MPO_8LC_ADPT";
  }

  identity NCS2K-MF-16AD-CFS {
    base ccet:ru-passive-type;
    base mf10-6ru-passive-type;
    description "Passive 1X16_COFS_C";
  }

  identity NCS2K-MF-2MPO-ADP {
    base ccet:ru-passive-type;
    base mf-6ru-passive-type;
    description "Passive 2MPO_ADP";
  }

  identity NCS2K-MF-6AD-CFS {
    base ccet:ru-passive-type;
    base mf-6ru-passive-type;
    description "PASSIVE_6AD_CFS";
  }
  
  identity NCS2K-MF-CL-SC {
    base ccet:ru-passive-type;
    base mf-6ru-passive-type;
    description "Passive MF_CL_SC";
  }

  identity NCS2K-MF-MPO-16LC {
    base ccet:ru-passive-type;
    base mf10-6ru-passive-type;
    description "Passive MPO_16LC";
  }

  identity NCS2K-MF-MPO-20LC {
    base ccet:ru-passive-type;
    base mf10-6ru-passive-type;
    description "Passive MPO_20LC";
  }

  identity NCS2K-MF-16AE-CFS {
    base ccet:ru-passive-type;
    base mf10-6ru-passive-type;
    description "Passive 16AE_CFS";
  }

  identity NCS2K-MF-10AD-CFS {
    base ccet:ru-passive-type;
    base mf10-6ru-passive-type;
    description "Passive 10AD_CFS";
  }

  identity NCS2K-MF-8X10G-FO {
    base ccet:ru-passive-type;
    base mf10-6ru-passive-type;
    description "PASSIVE_8X10G_FO";
  }

  
  /*
  Supported mech-unit subtypes.
  */
  identity AIR_RAMP {
    base ccet:mech-unit-subtype;
    description "MECH UNIT AIR RAMP";
  }

  identity ALIEN_SHELF {
    base ccet:mech-unit-subtype;
    description "MECH UNIT ALIEN SHELF";
  }

  identity EAP {
    base ccet:mech-unit-subtype;
    description "MECH UNIT EAP";
  }

  identity ETH_SWITCH {
    base ccet:mech-unit-subtype;
    description "MECH UNIT ETH SWITCH";
  }

  identity FIBER_STORAGE {
    base ccet:mech-unit-subtype;
    description "MECH UNIT FIBER STORAGE";
  }

  identity FL_1 {
    base ccet:mech-unit-subtype;
    description "MECH UNIT FL 1";
  }

  identity FL_2 {
    base ccet:mech-unit-subtype;
    description "MECH UNIT FL 2";
  }

  identity FLD_2_ISO {
    base ccet:mech-unit-subtype;
    description "MECH UNIT FLD-2-ISO";
  }

  identity FLD_9_ISO {
    base ccet:mech-unit-subtype;
    description "MECH UNIT FLD-9-ISO";
  }

  identity FLD_CDWDM_8 {
    base ccet:mech-unit-subtype;
    description "MECH UNIT FLD-CDWDM-8";
  }

  identity PDP {
    base ccet:mech-unit-subtype;
    description "MECH UNIT PDP";
  }

  identity PP_64_LC {
    base ccet:mech-unit-subtype;
    description "MECH UNIT PP-64-LC";
  }

  identity PP_80_LC {
    base ccet:mech-unit-subtype;
    description "MECH UNIT PP-80-LC";
  }

  identity PP2_64_LC {
    base ccet:mech-unit-subtype;
    description "MECH UNIT PP2-64-LC";
  }

  identity MECH_UNIT_UNK {
    base ccet:mech-unit-subtype;
    description "MECH UNIT UNKNOWN";
  }
  
  /*
  Supported dcu subtypes.
  */
  identity DCU_DS_100 {
    base ccet:dcu-subtype;
    description "DcuDS-100.0";
  }

  identity DCU_DS_200 {
    base ccet:dcu-subtype;
    description "DcuDS-200.0";
  }

  identity DCU_DS_300 {
    base ccet:dcu-subtype;
    description "DcuDS-300.0";
  }

  identity DCU_ELEAF_200 {
    base ccet:dcu-subtype;
    description "DcuELEAF-200.0";
  }

  identity DCU_ELEAF_350 {
    base ccet:dcu-subtype;
    description "DcuELEAF-350.0";
  }

  identity DCU_SMF_1000 {
    base ccet:dcu-subtype;
    description "DcuSMF-1000.0";
  }

  identity DCU_SMF_1100 {
    base ccet:dcu-subtype;
    description "DcuSMF-1100.0";
  }

  identity DCU_SMF_300 {
    base ccet:dcu-subtype;
    description "DcuSMF-300.0";
  }

  identity DCU_SMF_600 {
    base ccet:dcu-subtype;
    description "DcuSMF-600.0";
  }

  identity DCU_SMF_700 {
    base ccet:dcu-subtype;
    description "DcuSMF-700.0";
  }

  identity DCU_SMF_800 {
    base ccet:dcu-subtype;
    description "DcuSMF-800.0";
  }

  identity DCU_SMR_100 {
    base ccet:dcu-subtype;
    description "DcuSMR-100.0";
  }

  identity DCU_SMR_1150 {
    base ccet:dcu-subtype;
    description "DcuSMR-1150.0";
  }

  identity DCU_SMR_1350 {
    base ccet:dcu-subtype;
    description "DcuSMR-1350.0";
  }

  identity DCU_SMR_1550 {
    base ccet:dcu-subtype;
    description "DcuSMR-1550.0";
  }

  identity DCU_SMR_1950 {
    base ccet:dcu-subtype;
    description "DcuSMR-1950.0";
  }

  identity DCU_SMR_350 {
    base ccet:dcu-subtype;
    description "DcuSMR-350.0";
  }

  identity DCU_SMR_450 {
    base ccet:dcu-subtype;
    description "DcuSMR-450.0";
  }

  identity DCU_SMR_550 {
    base ccet:dcu-subtype;
    description "DcuSMR-550.0";
  }

  identity DCU_SMR_750 {
    base ccet:dcu-subtype;
    description "DcuSMR-750.0";
  }

  identity DCU_SMR_950 {
    base ccet:dcu-subtype;
    description "DcuSMR-950.0";
  }

  /* Protection Type */
  
  identity odu-one-plus-one {
      base ccet:protection-type;
      description "ODU Linear Protection 1+1 permanent bridge";
  }

  identity y-cable {
      base ccet:protection-type;
      description "Y-cable protection";
  }
  
  identity splitter {
      base ccet:protection-type;
      description "Splitter protection";
  }
  
}
