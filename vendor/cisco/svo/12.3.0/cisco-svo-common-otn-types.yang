module cisco-svo-common-otn-types {
  yang-version 1.1;
  namespace "http://cisco.com/yang/svo/common-otn-types";
  prefix ccotnt;
  

  import org-openroadm-otn-common-types { prefix org-openroadm-otn-common-types; revision-date 2018-09-28; }

  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO OTN common types.";

   revision 2021-04-16 { 
      description "Model version for SVO Release 12.2.0 "; 
      reference cisco-svo-common-otn-types.yang; 
   }
 

  revision 2020-12-04 { 
      description "Model version for SVO Release 12.1.0 "; 
      reference cisco-svo-common-otn-types.yang; 
  }

  identity OTU4C2 {
    base org-openroadm-otn-common-types:otu-rate-identity;
    description
      "Identity for an OTU4C2";
  }

  identity ODU4C2 {
    base org-openroadm-otn-common-types:odu-rate-identity;
    description
      "Identity for an ODU4C2";
  }

  identity OTU4C3 {
    base org-openroadm-otn-common-types:otu-rate-identity;
    description
      "Identity for an OTU4C3 (used for 3xOTU4 -> 2x150G configurations)";
  }

  identity ODU4C3 {
    base org-openroadm-otn-common-types:odu-rate-identity;
    description
      "Identity for an ODU4C3 (used for 3xOTU4 -> 2x150G configurations)";
  }

  identity OTU3e2 {
    base org-openroadm-otn-common-types:otu-rate-identity;
    description
      "Identity for an OTU3e2";
  }

  identity ODU3e2 {
    base org-openroadm-otn-common-types:odu-rate-identity;
    description
      "Identity for an ODU3e2";
  }

  typedef prbs-pattern {
        type enumeration {
            enum "PRBS_NONE" {
                value 0;
                description "Do not set prbs patter";
            }
            enum "PRBS_PN11" {
                value 1;
                description "PRBS pattern type PN11";
            }
            enum "PRBS_PN23" {
                value 2;
                description "PRBS pattern type PN23";
            }
            enum "PRBS_PN31" {
                value 3;
                description "PRBS pattern type PN31";
            }
            enum "INVERTEDPRBS_11" {
                value 4;
                description "PRBS pattern type PN11 inverted";
            }
            enum "INVERTEDPRBS_31" {
                value 5;
                description "PRBS pattern type PN31 inverted";
            }
        }
    }

  typedef prbs-pattern-status {
       type enumeration {
          enum "PRBS_PATTERN_NONE" {
             value 0;
             description "No pattern detected";
          }
          enum "PRBS_PATTERN_OK" {
             value 1;
             description "Detected pattern match ok";
          }
          enum "PRBS_PATTERN_ERROR" {
             value 2;
             description "Detected pattern match not ok";
          }
       }
  }
  
  typedef signal-type-type {
      type enumeration {
          enum "ETHERNET" {
              value 0;
              description "Ethernet signal Type";
          }
          enum "FC" {
              value 1;
              description "Fiber Channel signal type";
          }
          enum "SONET" {
              value 2;
              description "Sonet signal type";
          }
          enum "SDH" {
              value 3;
              description "Sdh signal type";
          }
      }
  }
}
