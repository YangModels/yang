/*
 * BEWARE BEWARE BEWARE BEWARE BEWARE BEWARE BEWARE BEWARE BEWARE
 * This file has been auto-generated by the python alarm dictionary parser: DO NOT EDIT
 * See: python main_svo_generator.py
 * Source: alarm_dictionary
 * BEWARE BEWARE BEWARE BEWARE BEWARE BEWARE BEWARE BEWARE BEWARE
*/
submodule cisco-devices-alarm-transient-types {

  belongs-to cisco-svo-alarm-transient-type {
    prefix svo-al-tr-t;
  }

  include cisco-svo-alarm-transient-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the alarm types";

  revision 2022-03-15 {
    description 
      "Released as part of SVO Release 12.4.0.
        added alarm: DEG-SER
        added alarm: HI-SER
        added alarm: LOCAL-DEG-SER
        added alarm: ODUK-AIS-TCM1
        added alarm: ODUK-AIS-TCM2
        added alarm: ODUK-AIS-TCM3
        added alarm: ODUK-AIS-TCM4
        added alarm: ODUK-AIS-TCM5
        added alarm: ODUK-AIS-TCM6
        added alarm: ODUK-BDI-TCM1
        added alarm: ODUK-BDI-TCM2
        added alarm: ODUK-BDI-TCM3
        added alarm: ODUK-BDI-TCM4
        added alarm: ODUK-BDI-TCM5
        added alarm: ODUK-BDI-TCM6
        added alarm: ODUK-BIAE
        added alarm: ODUK-BIAE-TCM1
        added alarm: ODUK-BIAE-TCM2
        added alarm: ODUK-BIAE-TCM3
        added alarm: ODUK-BIAE-TCM4
        added alarm: ODUK-BIAE-TCM5
        added alarm: ODUK-BIAE-TCM6
        added alarm: ODUK-IAE
        added alarm: ODUK-IAE-TCM1
        added alarm: ODUK-IAE-TCM2
        added alarm: ODUK-IAE-TCM3
        added alarm: ODUK-IAE-TCM4
        added alarm: ODUK-IAE-TCM5
        added alarm: ODUK-IAE-TCM6
        added alarm: ODUK-LCK-TCM1
        added alarm: ODUK-LCK-TCM2
        added alarm: ODUK-LCK-TCM3
        added alarm: ODUK-LCK-TCM4
        added alarm: ODUK-LCK-TCM5
        added alarm: ODUK-LCK-TCM6
        added alarm: ODUK-LTC-TCM1
        added alarm: ODUK-LTC-TCM2
        added alarm: ODUK-LTC-TCM3
        added alarm: ODUK-LTC-TCM4
        added alarm: ODUK-LTC-TCM5
        added alarm: ODUK-LTC-TCM6
        added alarm: ODUK-OCI-TCM1
        added alarm: ODUK-OCI-TCM2
        added alarm: ODUK-OCI-TCM3
        added alarm: ODUK-OCI-TCM4
        added alarm: ODUK-OCI-TCM5
        added alarm: ODUK-OCI-TCM6
        added alarm: ODUK-SD-TCM1
        added alarm: ODUK-SD-TCM2
        added alarm: ODUK-SD-TCM3
        added alarm: ODUK-SD-TCM4
        added alarm: ODUK-SD-TCM5
        added alarm: ODUK-SD-TCM6
        added alarm: ODUK-SF-TCM1
        added alarm: ODUK-SF-TCM2
        added alarm: ODUK-SF-TCM3
        added alarm: ODUK-SF-TCM4
        added alarm: ODUK-SF-TCM5
        added alarm: ODUK-SF-TCM6
        added alarm: ODUK-TIM-TCM1
        added alarm: ODUK-TIM-TCM2
        added alarm: ODUK-TIM-TCM3
        added alarm: ODUK-TIM-TCM4
        added alarm: ODUK-TIM-TCM5
        added alarm: ODUK-TIM-TCM6
        added alarm: OTUK-LOM
        added alarm: PROV-IN-PROG
        added alarm: REMOTE-DEG-SER
        added alarm: TX-POWER-PROV-MISMATCH
      ";
  }

  revision 2021-12-15 {
    description 
      "Released as part of SVO Release 12.3.0.
        added alarm: WKSWBK
      ";
  }

  revision 2020-12-04 {
    description "Model version for SVO Release 12.1.0";
    reference cisco-devices-alarm-transient-types.yang;
  }

  identity ADMIN-DISABLE {
    description "Disable Inactive User";
    base svo-al-tr-t:svo-alarm-transient-type;
  }

  identity ADMIN-DISABLE-CLR {
    description "Disable Inactive Clear";
    base svo-al-tr-t:svo-alarm-transient-type;
  }

  identity ADMIN-LOCKOUT {
    description "Admin Lockout of User";
    base svo-al-tr-t:svo-alarm-transient-type;
  }

  identity ADMIN-LOCKOUT-CLR {
    description "Admin Lockout Clear";
    base svo-al-tr-t:svo-alarm-transient-type;
  }

  identity ADMIN-LOGOUT {
    description "Admin Logout of User";
    base svo-al-tr-t:svo-alarm-transient-type;
  }

  identity ADMIN-SUSPEND {
    description "Suspend User";
    base svo-al-tr-t:svo-alarm-transient-type;
  }

  identity ADMIN-SUSPEND-CLR {
    description "Suspend User Clear";
    base svo-al-tr-t:svo-alarm-transient-type;
  }

  identity AUD-ARCHIVE-FAIL {
    description "Archival of Audit Log Failed";
    base svo-al-tr-t:svo-alarm-transient-type;
  }

  identity AUTOWDMANS {
    description "Automatic WDM ANS Finished";
    base svo-al-tr-t:svo-alarm-transient-type;
  }

  identity DBBACKUP-FAIL {
    description "Database Backup Failed";
    base svo-al-tr-t:svo-alarm-transient-type;
  }

  identity DBRESTORE-FAIL {
    description "Database Restore Failed";
    base svo-al-tr-t:svo-alarm-transient-type;
  }

  identity DEG-SER {
    description "FEC Degraded Symbol Error Rate";
    base svo-al-tr-t:svo-alarm-transient-type;
  }

  identity FIRMWARE-DOWNLOAD {
    description "Firmware Download In Progress";
    base svo-al-tr-t:svo-alarm-transient-type;
  }

  identity FIRMWARE-UPG-COMPLETE {
    description "Firmware Upgrade Completed";
    base svo-al-tr-t:svo-alarm-transient-type;
  }

  identity HI-SER {
    description "High Symbol Error Rate";
    base svo-al-tr-t:svo-alarm-transient-type;
  }

  identity INTRUSION {
    description "Security: Invalid Login Username - See Audit Trail";
    base svo-al-tr-t:svo-alarm-transient-type;
  }

  identity INTRUSION-USERID {
    description "Security Intrusion Attempt Detected - See Audit Log";
    base svo-al-tr-t:svo-alarm-transient-type;
  }

  identity LOCAL-DEG-SER {
    description "Local FEC Degraded Symbol Error Rate";
    base svo-al-tr-t:svo-alarm-transient-type;
  }

  identity LOGIN-FAIL-LOCKOUT {
    description "Security: Invalid Login - Locked Out - See Audit Log";
    base svo-al-tr-t:svo-alarm-transient-type;
  }

  identity LOGIN-FAIL-ONALRDY {
    description "Security: Invalid Login - Already Logged On - See Audit Log";
    base svo-al-tr-t:svo-alarm-transient-type;
  }

  identity LOGIN-FAILURE-PSWD {
    description "Security: Invalid Login - Password - See Audit Log";
    base svo-al-tr-t:svo-alarm-transient-type;
  }

  identity LOGIN-FAILURE-USER {
    description "Security: Invalid Login - Username - See Audit Log";
    base svo-al-tr-t:svo-alarm-transient-type;
  }

  identity LOGOUT-IDLE-USER {
    description "Automatic Logout of IdleUser";
    base svo-al-tr-t:svo-alarm-transient-type;
  }

  identity MASTERKEY-SUCCESS {
    description "MasterKey Exchange Success";
    base svo-al-tr-t:svo-alarm-transient-type;
  }

  identity ODUK-AIS-TCM1 {
    description "TCM1 Alarm Indication Signal";
    base svo-al-tr-t:svo-alarm-transient-type;
  }

  identity ODUK-AIS-TCM2 {
    description "TCM2 Alarm Indication Signal";
    base svo-al-tr-t:svo-alarm-transient-type;
  }

  identity ODUK-AIS-TCM3 {
    description "TCM3 Alarm Indication Signal";
    base svo-al-tr-t:svo-alarm-transient-type;
  }

  identity ODUK-AIS-TCM4 {
    description "TCM4 Alarm Indication Signal";
    base svo-al-tr-t:svo-alarm-transient-type;
  }

  identity ODUK-AIS-TCM5 {
    description "TCM5 Alarm Indication Signal";
    base svo-al-tr-t:svo-alarm-transient-type;
  }

  identity ODUK-AIS-TCM6 {
    description "TCM6 Alarm Indication Signal";
    base svo-al-tr-t:svo-alarm-transient-type;
  }

  identity ODUK-BDI-TCM1 {
    description "TCM1 Backward Defect Monitoring";
    base svo-al-tr-t:svo-alarm-transient-type;
  }

  identity ODUK-BDI-TCM2 {
    description "TCM2 Backward Defect Monitoring";
    base svo-al-tr-t:svo-alarm-transient-type;
  }

  identity ODUK-BDI-TCM3 {
    description "TCM3 Backward Defect Monitoring";
    base svo-al-tr-t:svo-alarm-transient-type;
  }

  identity ODUK-BDI-TCM4 {
    description "TCM4 Backward Defect Monitoring";
    base svo-al-tr-t:svo-alarm-transient-type;
  }

  identity ODUK-BDI-TCM5 {
    description "TCM5 Backward Defect Monitoring";
    base svo-al-tr-t:svo-alarm-transient-type;
  }

  identity ODUK-BDI-TCM6 {
    description "TCM6 Backward Defect Monitoring";
    base svo-al-tr-t:svo-alarm-transient-type;
  }

  identity ODUK-BIAE {
    description "Path Monitoring Backward Incoming Alignment Error";
    base svo-al-tr-t:svo-alarm-transient-type;
  }

  identity ODUK-BIAE-TCM1 {
    description "TCM1 Backward Incoming Alignment Error";
    base svo-al-tr-t:svo-alarm-transient-type;
  }

  identity ODUK-BIAE-TCM2 {
    description "TCM2 Backward Incoming Alignment Error";
    base svo-al-tr-t:svo-alarm-transient-type;
  }

  identity ODUK-BIAE-TCM3 {
    description "TCM3 Backward Incoming Alignment Error";
    base svo-al-tr-t:svo-alarm-transient-type;
  }

  identity ODUK-BIAE-TCM4 {
    description "TCM4 Backward Incoming Alignment Error";
    base svo-al-tr-t:svo-alarm-transient-type;
  }

  identity ODUK-BIAE-TCM5 {
    description "TCM5 Backward Incoming Alignment Error";
    base svo-al-tr-t:svo-alarm-transient-type;
  }

  identity ODUK-BIAE-TCM6 {
    description "TCM6 Backward Incoming Alignment Error";
    base svo-al-tr-t:svo-alarm-transient-type;
  }

  identity ODUK-IAE {
    description "Path Monitoring Incoming Alignment Error";
    base svo-al-tr-t:svo-alarm-transient-type;
  }

  identity ODUK-IAE-TCM1 {
    description "TCM1 Incoming Alignment Error";
    base svo-al-tr-t:svo-alarm-transient-type;
  }

  identity ODUK-IAE-TCM2 {
    description "TCM2 Incoming Alignment Error";
    base svo-al-tr-t:svo-alarm-transient-type;
  }

  identity ODUK-IAE-TCM3 {
    description "TCM3 Incoming Alignment Error";
    base svo-al-tr-t:svo-alarm-transient-type;
  }

  identity ODUK-IAE-TCM4 {
    description "TCM4 Incoming Alignment Error";
    base svo-al-tr-t:svo-alarm-transient-type;
  }

  identity ODUK-IAE-TCM5 {
    description "TCM5 Incoming Alignment Error";
    base svo-al-tr-t:svo-alarm-transient-type;
  }

  identity ODUK-IAE-TCM6 {
    description "TCM6 Incoming Alignment Error";
    base svo-al-tr-t:svo-alarm-transient-type;
  }

  identity ODUK-LCK-TCM1 {
    description "TCM1 Locked";
    base svo-al-tr-t:svo-alarm-transient-type;
  }

  identity ODUK-LCK-TCM2 {
    description "TCM2 Locked";
    base svo-al-tr-t:svo-alarm-transient-type;
  }

  identity ODUK-LCK-TCM3 {
    description "TCM3 Locked";
    base svo-al-tr-t:svo-alarm-transient-type;
  }

  identity ODUK-LCK-TCM4 {
    description "TCM4 Locked";
    base svo-al-tr-t:svo-alarm-transient-type;
  }

  identity ODUK-LCK-TCM5 {
    description "TCM5 Locked";
    base svo-al-tr-t:svo-alarm-transient-type;
  }

  identity ODUK-LCK-TCM6 {
    description "TCM6 Locked";
    base svo-al-tr-t:svo-alarm-transient-type;
  }

  identity ODUK-LTC-TCM1 {
    description "TCM1 Loss of Tandem Connection";
    base svo-al-tr-t:svo-alarm-transient-type;
  }

  identity ODUK-LTC-TCM2 {
    description "TCM2 Loss of Tandem Connection";
    base svo-al-tr-t:svo-alarm-transient-type;
  }

  identity ODUK-LTC-TCM3 {
    description "TCM3 Loss of Tandem Connection";
    base svo-al-tr-t:svo-alarm-transient-type;
  }

  identity ODUK-LTC-TCM4 {
    description "TCM4 Loss of Tandem Connection";
    base svo-al-tr-t:svo-alarm-transient-type;
  }

  identity ODUK-LTC-TCM5 {
    description "TCM5 Loss of Tandem Connection";
    base svo-al-tr-t:svo-alarm-transient-type;
  }

  identity ODUK-LTC-TCM6 {
    description "TCM6 Loss of Tandem Connection";
    base svo-al-tr-t:svo-alarm-transient-type;
  }

  identity ODUK-OCI-TCM1 {
    description "TCM1 Open Connection Indication";
    base svo-al-tr-t:svo-alarm-transient-type;
  }

  identity ODUK-OCI-TCM2 {
    description "TCM2 Open Connection Indication";
    base svo-al-tr-t:svo-alarm-transient-type;
  }

  identity ODUK-OCI-TCM3 {
    description "TCM3 Open Connection Indication";
    base svo-al-tr-t:svo-alarm-transient-type;
  }

  identity ODUK-OCI-TCM4 {
    description "TCM4 Open Connection Indication";
    base svo-al-tr-t:svo-alarm-transient-type;
  }

  identity ODUK-OCI-TCM5 {
    description "TCM5 Open Connection Indication";
    base svo-al-tr-t:svo-alarm-transient-type;
  }

  identity ODUK-OCI-TCM6 {
    description "TCM6 Open Connection Indication";
    base svo-al-tr-t:svo-alarm-transient-type;
  }

  identity ODUK-SD-TCM1 {
    description "TCM1 Signal Degrade";
    base svo-al-tr-t:svo-alarm-transient-type;
  }

  identity ODUK-SD-TCM2 {
    description "TCM2 Signal Degrade";
    base svo-al-tr-t:svo-alarm-transient-type;
  }

  identity ODUK-SD-TCM3 {
    description "TCM3 Signal Degrade";
    base svo-al-tr-t:svo-alarm-transient-type;
  }

  identity ODUK-SD-TCM4 {
    description "TCM4 Signal Degrade";
    base svo-al-tr-t:svo-alarm-transient-type;
  }

  identity ODUK-SD-TCM5 {
    description "TCM5 Signal Degrade";
    base svo-al-tr-t:svo-alarm-transient-type;
  }

  identity ODUK-SD-TCM6 {
    description "TCM6 Signal Degrade";
    base svo-al-tr-t:svo-alarm-transient-type;
  }

  identity ODUK-SF-TCM1 {
    description "TCM1 Signal Failure";
    base svo-al-tr-t:svo-alarm-transient-type;
  }

  identity ODUK-SF-TCM2 {
    description "TCM2 Signal Failure";
    base svo-al-tr-t:svo-alarm-transient-type;
  }

  identity ODUK-SF-TCM3 {
    description "TCM3 Signal Failure";
    base svo-al-tr-t:svo-alarm-transient-type;
  }

  identity ODUK-SF-TCM4 {
    description "TCM4 Signal Failure";
    base svo-al-tr-t:svo-alarm-transient-type;
  }

  identity ODUK-SF-TCM5 {
    description "TCM5 Signal Failure";
    base svo-al-tr-t:svo-alarm-transient-type;
  }

  identity ODUK-SF-TCM6 {
    description "TCM6 Signal Failure";
    base svo-al-tr-t:svo-alarm-transient-type;
  }

  identity ODUK-TIM-TCM1 {
    description "TCM1 Trail Trace Identifier Mismatch";
    base svo-al-tr-t:svo-alarm-transient-type;
  }

  identity ODUK-TIM-TCM2 {
    description "TCM2 Trail Trace Identifier Mismatch";
    base svo-al-tr-t:svo-alarm-transient-type;
  }

  identity ODUK-TIM-TCM3 {
    description "TCM3 Trail Trace Identifier Mismatch";
    base svo-al-tr-t:svo-alarm-transient-type;
  }

  identity ODUK-TIM-TCM4 {
    description "TCM4 Trail Trace Identifier Mismatch";
    base svo-al-tr-t:svo-alarm-transient-type;
  }

  identity ODUK-TIM-TCM5 {
    description "TCM5 Trail Trace Identifier Mismatch";
    base svo-al-tr-t:svo-alarm-transient-type;
  }

  identity ODUK-TIM-TCM6 {
    description "TCM6 Trail Trace Identifier Mismatch";
    base svo-al-tr-t:svo-alarm-transient-type;
  }

  identity OTUK-LOM {
    description "OTUK Loss Of MultiFrame";
    base svo-al-tr-t:svo-alarm-transient-type;
  }

  identity PM-TCA {
    description "Performance Monitor Threshold Crossing Alert";
    base svo-al-tr-t:svo-alarm-transient-type;
  }

  identity PROV-IN-PROG {
    description "Provisioning In Progress";
    base svo-al-tr-t:svo-alarm-transient-type;
  }

  identity PSWD-CHG-REQUIRED {
    description "User Password Change Required";
    base svo-al-tr-t:svo-alarm-transient-type;
  }

  identity REMOTE-DEG-SER {
    description "Remote FEC Degraded Symbol Error Rate";
    base svo-al-tr-t:svo-alarm-transient-type;
  }

  identity RMON-ALARM {
    description "RMON Threshold Crossing Alarm";
    base svo-al-tr-t:svo-alarm-transient-type;
  }

  identity RMON-RESET {
    description "RMON Histories And Alarms Reset Reboot";
    base svo-al-tr-t:svo-alarm-transient-type;
  }

  identity ROLE-SWITCH-ACTIVE {
    description "Role is Switched to active";
    base svo-al-tr-t:svo-alarm-transient-type;
  }

  identity SESSION-TIME-LIMIT {
    description "Session Time Limit Expired";
    base svo-al-tr-t:svo-alarm-transient-type;
  }

  identity TX-POWER-PROV-MISMATCH {
    description "Provisioned Optics Transmit Power Not Supported";
    base svo-al-tr-t:svo-alarm-transient-type;
  }

  identity USB-PORTS-DOWN {
    description "USB Ports in ECU are not functional";
    base svo-al-tr-t:svo-alarm-transient-type;
  }

  identity USER-LOCKOUT {
    description "User Locked Out";
    base svo-al-tr-t:svo-alarm-transient-type;
  }

  identity USER-LOGIN {
    description "Login of User";
    base svo-al-tr-t:svo-alarm-transient-type;
  }

  identity USER-LOGOUT {
    description "Logout of User";
    base svo-al-tr-t:svo-alarm-transient-type;
  }

  identity WKSWBK {
    description "Switched Back To Working";
    base svo-al-tr-t:svo-alarm-transient-type;
  }

  identity WRMRESTART {
    description "Warm Restart";
    base svo-al-tr-t:svo-alarm-transient-type;
  }

}
