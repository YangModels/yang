module cisco-svo-node-functionalities-internal {
    yang-version 1.1;
    namespace "http://cisco.com/yang/svo/node-funct-int";
    prefix svo-node-funct-int;

    import tailf-common { prefix tailf; }
    import ietf-inet-types { prefix inet; }    
    import cisco-svo-common-base-opt-grp { prefix ccbog; }

    organization
        "Cisco Systems, Inc.";

    contact
        "Cisco Systems, Inc. Customer Service Postal: 170 West Tasman
        Drive San Jose, CA 95134 Tel: +1 800 553-NETS E-mail: cs-yang@cisco.com";

     
    description 
       "Yang definition of types and action for manage internal non public operations";
  
  revision 2021-12-25 {
  	description "Model version for SVO Release 12.3.0";
  	reference cisco-svo-node-functionalities-internal.yang;
  }
  
    revision 2021-04-16 { 
       description "Model version for SVO Release 12.2.0 
					
					moved:
       	 				otdr machine learning debug function in the more appropiated cisco-svo-debug model";        	  
       reference cisco-svo-node-functionalities-internal.yang; 
    }
    
    revision 2020-12-04 { 
       description "Model version for SVO Release 12.1.0 "; 
       reference cisco-svo-node-functionalities-internal.yang; 
    }
    
    tailf:export cli; //none cli netconf  
          
    container svo-node-function {
        
        container commands {

            tailf:action move-uploaded-file {
                tailf:info "Move file from source to destination directory based on operation
                                type";
                description "Move file from source to destination directory based on operation
                                type";
                tailf:actionpoint move-uploaded-file;
                input {
                    leaf-list file-path {
                        description "The backup filename to move on the system";
                        type string;
                    }

                    leaf operation-type {
                        type move-op-type;
                        description "Give information for destination operation";
                    }
                }

                output {
                    uses ccbog:rpc-status;
                }
            }
        }
    }

    typedef move-op-type {
        type enumeration {

            enum "backup-restore" {
                description "Move operation for Backup&Restore.";
            }

            enum "capabilities" {
                description "Move operation for Backup&Restore.";
            }
        }
        description "The destination of move operation";
    }
}
