/*
 * BEWARE BEWARE BEWARE BEWARE BEWARE BEWARE BEWARE BEWARE BEWARE
 * This file has been auto-generated by the python alarm dictionary parser: DO NOT EDIT
 * See: python main_svo_generator.py
 * Source: alarm_dictionary
 * BEWARE BEWARE BEWARE BEWARE BEWARE BEWARE BEWARE BEWARE BEWARE
*/
submodule cisco-svo-pm-rmon-alarm-types {

  belongs-to cisco-svo-alarm-tca-type {
    prefix svo-al-tca-t;
  }

  include cisco-svo-alarm-tca-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the pm rmon alarm types";

  revision 2020-12-04 {
    description "Model version for SVO Release 12.1.0";
    reference cisco-svo-pm-rmon-alarm-types.yang;
  }

  identity pm-rmon-alarm-type {
    description "Root of pm rmon alarm type";
    base svo-al-tca-t:svo-alarm-tca-type;
  }

  identity T-8b10bDataOrderedSets {
    description "RMON Performance Monitor Threshold Crossing Alert: 8b10bDataOrderedSets";
    base pm-rmon-alarm-type;
  }

  identity T-8b10bIdleOrderedSets {
    description "RMON Performance Monitor Threshold Crossing Alert: 8b10bIdleOrderedSets";
    base pm-rmon-alarm-type;
  }

  identity T-8b10bInvalidOrderedSets {
    description "RMON Performance Monitor Threshold Crossing Alert: 8b10bInvalidOrderedSets";
    base pm-rmon-alarm-type;
  }

  identity T-8b10bInvalidOrderedSetsDispErrorsSum {
    description "RMON Performance Monitor Threshold Crossing Alert: 8b10bInvalidOrderedSetsDispErrorsSum";
    base pm-rmon-alarm-type;
  }

  identity T-8b10bLossOfSync {
    description "RMON Performance Monitor Threshold Crossing Alert: 8b10bLossOfSync";
    base pm-rmon-alarm-type;
  }

  identity T-8b10bNonIdleOrderedSets {
    description "RMON Performance Monitor Threshold Crossing Alert: 8b10bNonIdleOrderedSets";
    base pm-rmon-alarm-type;
  }

  identity T-8b10bStatsEncodingDispErrors {
    description "RMON Performance Monitor Threshold Crossing Alert: 8b10bStatsEncodingDispErrors";
    base pm-rmon-alarm-type;
  }

  identity T-cisRxGeneralQueries {
    description "RMON Performance Monitor Threshold Crossing Alert: cisRxGeneralQueries";
    base pm-rmon-alarm-type;
  }

  identity T-cisRxGroupSpecificQueries {
    description "RMON Performance Monitor Threshold Crossing Alert: cisRxGroupSpecificQueries";
    base pm-rmon-alarm-type;
  }

  identity T-cisRxInvalidPackets {
    description "RMON Performance Monitor Threshold Crossing Alert: cisRxInvalidPackets";
    base pm-rmon-alarm-type;
  }

  identity T-cisRxLeaves {
    description "RMON Performance Monitor Threshold Crossing Alert: cisRxLeaves";
    base pm-rmon-alarm-type;
  }

  identity T-cisRxReports {
    description "RMON Performance Monitor Threshold Crossing Alert: cisRxReports";
    base pm-rmon-alarm-type;
  }

  identity T-cisRxValidPackets {
    description "RMON Performance Monitor Threshold Crossing Alert: cisRxValidPackets";
    base pm-rmon-alarm-type;
  }

  identity T-cisTxGeneralQueries {
    description "RMON Performance Monitor Threshold Crossing Alert: cisTxGeneralQueries";
    base pm-rmon-alarm-type;
  }

  identity T-cisTxGroupSpecificQueries {
    description "RMON Performance Monitor Threshold Crossing Alert: cisTxGroupSpecificQueries";
    base pm-rmon-alarm-type;
  }

  identity T-cisTxLeaves {
    description "RMON Performance Monitor Threshold Crossing Alert: cisTxLeaves";
    base pm-rmon-alarm-type;
  }

  identity T-cisTxReports {
    description "RMON Performance Monitor Threshold Crossing Alert: cisTxReports";
    base pm-rmon-alarm-type;
  }

  identity T-crepHflRxPdus {
    description "RMON Performance Monitor Threshold Crossing Alert: crepHflRxPdus";
    base pm-rmon-alarm-type;
  }

  identity T-crepHflTxPdus {
    description "RMON Performance Monitor Threshold Crossing Alert: crepHflTxPdus";
    base pm-rmon-alarm-type;
  }

  identity T-crepLslRxPdus {
    description "RMON Performance Monitor Threshold Crossing Alert: crepLslRxPdus";
    base pm-rmon-alarm-type;
  }

  identity T-crepLslTxPdus {
    description "RMON Performance Monitor Threshold Crossing Alert: crepLslTxPdus";
    base pm-rmon-alarm-type;
  }

  identity T-dot3StatsAlignmentErrors {
    description "RMON Performance Monitor Threshold Crossing Alert: dot3StatsAlignmentErrors";
    base pm-rmon-alarm-type;
  }

  identity T-dot3StatsCarrierSenseErrors {
    description "RMON Performance Monitor Threshold Crossing Alert: dot3StatsCarrierSenseErrors";
    base pm-rmon-alarm-type;
  }

  identity T-dot3StatsControlInUnknownOpCodes {
    description "RMON Performance Monitor Threshold Crossing Alert: dot3StatsControlInUnknownOpCodes";
    base pm-rmon-alarm-type;
  }

  identity T-dot3StatsDeferredTransmissions {
    description "RMON Performance Monitor Threshold Crossing Alert: dot3StatsDeferredTransmissions";
    base pm-rmon-alarm-type;
  }

  identity T-dot3StatsExcessiveCollisions {
    description "RMON Performance Monitor Threshold Crossing Alert: dot3StatsExcessiveCollisions";
    base pm-rmon-alarm-type;
  }

  identity T-dot3StatsFCSErrors {
    description "RMON Performance Monitor Threshold Crossing Alert: dot3StatsFCSErrors";
    base pm-rmon-alarm-type;
  }

  identity T-dot3StatsFrameTooLong {
    description "RMON Performance Monitor Threshold Crossing Alert: dot3StatsFrameTooLong";
    base pm-rmon-alarm-type;
  }

  identity T-dot3StatsInPauseFrames {
    description "RMON Performance Monitor Threshold Crossing Alert: dot3StatsInPauseFrames";
    base pm-rmon-alarm-type;
  }

  identity T-dot3StatsInternalMacRxErrors {
    description "RMON Performance Monitor Threshold Crossing Alert: dot3StatsInternalMacRxErrors";
    base pm-rmon-alarm-type;
  }

  identity T-dot3StatsInternalMacTxErrors {
    description "RMON Performance Monitor Threshold Crossing Alert: dot3StatsInternalMacTxErrors";
    base pm-rmon-alarm-type;
  }

  identity T-dot3StatsLateCollisions {
    description "RMON Performance Monitor Threshold Crossing Alert: dot3StatsLateCollisions";
    base pm-rmon-alarm-type;
  }

  identity T-dot3StatsLayer1Errors {
    description "RMON Performance Monitor Threshold Crossing Alert: dot3StatsLayer1Errors";
    base pm-rmon-alarm-type;
  }

  identity T-dot3StatsLcvErrors {
    description "RMON Performance Monitor Threshold Crossing Alert: dot3StatsLcvErrors";
    base pm-rmon-alarm-type;
  }

  identity T-dot3StatsMultipleCollisionFrames {
    description "RMON Performance Monitor Threshold Crossing Alert: dot3StatsMultipleCollisionFrames";
    base pm-rmon-alarm-type;
  }

  identity T-dot3StatsOutPauseFrames {
    description "RMON Performance Monitor Threshold Crossing Alert: dot3StatsOutPauseFrames";
    base pm-rmon-alarm-type;
  }

  identity T-dot3StatsSQETestErrors {
    description "RMON Performance Monitor Threshold Crossing Alert: dot3StatsSQETestErrors";
    base pm-rmon-alarm-type;
  }

  identity T-dot3StatsSingleCollisionFrames {
    description "RMON Performance Monitor Threshold Crossing Alert: dot3StatsSingleCollisionFrames";
    base pm-rmon-alarm-type;
  }

  identity T-dot3StatsSymbolErrors {
    description "RMON Performance Monitor Threshold Crossing Alert: dot3StatsSymbolErrors";
    base pm-rmon-alarm-type;
  }

  identity T-dot3adAggPortStatsLACPDUsRx {
    description "RMON Performance Monitor Threshold Crossing Alert: dot3adAggPortStatsLACPDUsRx";
    base pm-rmon-alarm-type;
  }

  identity T-dot3adAggPortStatsLACPDUsTx {
    description "RMON Performance Monitor Threshold Crossing Alert: dot3adAggPortStatsLACPDUsTx";
    base pm-rmon-alarm-type;
  }

  identity T-etherStatsBroadcastPkts {
    description "RMON Performance Monitor Threshold Crossing Alert: etherStatsBroadcastPkts";
    base pm-rmon-alarm-type;
  }

  identity T-etherStatsCRCAlignErrors {
    description "RMON Performance Monitor Threshold Crossing Alert: etherStatsCRCAlignErrors";
    base pm-rmon-alarm-type;
  }

  identity T-etherStatsCollisionFrames {
    description "RMON Performance Monitor Threshold Crossing Alert: etherStatsCollisionFrames";
    base pm-rmon-alarm-type;
  }

  identity T-etherStatsCollisions {
    description "RMON Performance Monitor Threshold Crossing Alert: etherStatsCollisions";
    base pm-rmon-alarm-type;
  }

  identity T-etherStatsDropEvents {
    description "RMON Performance Monitor Threshold Crossing Alert: etherStatsDropEvents";
    base pm-rmon-alarm-type;
  }

  identity T-etherStatsFragments {
    description "RMON Performance Monitor Threshold Crossing Alert: etherStatsFragments";
    base pm-rmon-alarm-type;
  }

  identity T-etherStatsHighCapacityOctets {
    description "RMON Performance Monitor Threshold Crossing Alert: etherStatsHighCapacityOctets";
    base pm-rmon-alarm-type;
  }

  identity T-etherStatsHighCapacityPkts {
    description "RMON Performance Monitor Threshold Crossing Alert: etherStatsHighCapacityPkts";
    base pm-rmon-alarm-type;
  }

  identity T-etherStatsHighCapacityPkts1024to1518Octets {
    description "RMON Performance Monitor Threshold Crossing Alert: etherStatsHighCapacityPkts1024to1518Octets";
    base pm-rmon-alarm-type;
  }

  identity T-etherStatsHighCapacityPkts128to255Octets {
    description "RMON Performance Monitor Threshold Crossing Alert: etherStatsHighCapacityPkts128to255Octets";
    base pm-rmon-alarm-type;
  }

  identity T-etherStatsHighCapacityPkts256to511Octets {
    description "RMON Performance Monitor Threshold Crossing Alert: etherStatsHighCapacityPkts256to511Octets";
    base pm-rmon-alarm-type;
  }

  identity T-etherStatsHighCapacityPkts512to1023Octets {
    description "RMON Performance Monitor Threshold Crossing Alert: etherStatsHighCapacityPkts512to1023Octets";
    base pm-rmon-alarm-type;
  }

  identity T-etherStatsHighCapacityPkts64Octets {
    description "RMON Performance Monitor Threshold Crossing Alert: etherStatsHighCapacityPkts64Octets";
    base pm-rmon-alarm-type;
  }

  identity T-etherStatsHighCapacityPkts65to127Octets {
    description "RMON Performance Monitor Threshold Crossing Alert: etherStatsHighCapacityPkts65to127Octets";
    base pm-rmon-alarm-type;
  }

  identity T-etherStatsJabbers {
    description "RMON Performance Monitor Threshold Crossing Alert: etherStatsJabbers";
    base pm-rmon-alarm-type;
  }

  identity T-etherStatsMulticastPkts {
    description "RMON Performance Monitor Threshold Crossing Alert: etherStatsMulticastPkts";
    base pm-rmon-alarm-type;
  }

  identity T-etherStatsOctets {
    description "RMON Performance Monitor Threshold Crossing Alert: etherStatsOctets";
    base pm-rmon-alarm-type;
  }

  identity T-etherStatsOversizePkts {
    description "RMON Performance Monitor Threshold Crossing Alert: etherStatsOversizePkts";
    base pm-rmon-alarm-type;
  }

  identity T-etherStatsPkts {
    description "RMON Performance Monitor Threshold Crossing Alert: etherStatsPkts";
    base pm-rmon-alarm-type;
  }

  identity T-etherStatsPkts1024to1518Octets {
    description "RMON Performance Monitor Threshold Crossing Alert: etherStatsPkts1024to1518Octets";
    base pm-rmon-alarm-type;
  }

  identity T-etherStatsPkts128to255Octets {
    description "RMON Performance Monitor Threshold Crossing Alert: etherStatsPkts128to255Octets";
    base pm-rmon-alarm-type;
  }

  identity T-etherStatsPkts1519to1522Octets {
    description "RMON Performance Monitor Threshold Crossing Alert: etherStatsPkts1519to1522Octets";
    base pm-rmon-alarm-type;
  }

  identity T-etherStatsPkts1519toMaxOctets {
    description "RMON Performance Monitor Threshold Crossing Alert: etherStatsPkts1519toMaxOctets";
    base pm-rmon-alarm-type;
  }

  identity T-etherStatsPkts256to511Octets {
    description "RMON Performance Monitor Threshold Crossing Alert: etherStatsPkts256to511Octets";
    base pm-rmon-alarm-type;
  }

  identity T-etherStatsPkts512to1023Octets {
    description "RMON Performance Monitor Threshold Crossing Alert: etherStatsPkts512to1023Octets";
    base pm-rmon-alarm-type;
  }

  identity T-etherStatsPkts64Octets {
    description "RMON Performance Monitor Threshold Crossing Alert: etherStatsPkts64Octets";
    base pm-rmon-alarm-type;
  }

  identity T-etherStatsPkts65to127Octets {
    description "RMON Performance Monitor Threshold Crossing Alert: etherStatsPkts65to127Octets";
    base pm-rmon-alarm-type;
  }

  identity T-etherStatsTxFifoOverflowEvents {
    description "RMON Performance Monitor Threshold Crossing Alert: etherStatsTxFifoOverflowEvents";
    base pm-rmon-alarm-type;
  }

  identity T-etherStatsUndersizePkts {
    description "RMON Performance Monitor Threshold Crossing Alert: etherStatsUndersizePkts";
    base pm-rmon-alarm-type;
  }

  identity T-fibreStatsLinkRecoveries {
    description "RMON Performance Monitor Threshold Crossing Alert: fibreStatsLinkRecoveries";
    base pm-rmon-alarm-type;
  }

  identity T-fibreStatsRXCredits {
    description "RMON Performance Monitor Threshold Crossing Alert: fibreStatsRXCredits";
    base pm-rmon-alarm-type;
  }

  identity T-fibreStatsRxRecvrReady {
    description "RMON Performance Monitor Threshold Crossing Alert: fibreStatsRxRecvrReady";
    base pm-rmon-alarm-type;
  }

  identity T-fibreStatsTXCredits {
    description "RMON Performance Monitor Threshold Crossing Alert: fibreStatsTXCredits";
    base pm-rmon-alarm-type;
  }

  identity T-fibreStatsTxRecvrReady {
    description "RMON Performance Monitor Threshold Crossing Alert: fibreStatsTxRecvrReady";
    base pm-rmon-alarm-type;
  }

  identity T-fibreStatsZeroTxCredits {
    description "RMON Performance Monitor Threshold Crossing Alert: fibreStatsZeroTxCredits";
    base pm-rmon-alarm-type;
  }

  identity T-gfpRxCmfFrame {
    description "RMON Performance Monitor Threshold Crossing Alert: gfpRxCmfFrame";
    base pm-rmon-alarm-type;
  }

  identity T-gfpStatsCHecRxMBitErrors {
    description "RMON Performance Monitor Threshold Crossing Alert: gfpStatsCHecRxMBitErrors";
    base pm-rmon-alarm-type;
  }

  identity T-gfpStatsCSFRaised {
    description "RMON Performance Monitor Threshold Crossing Alert: gfpStatsCSFRaised";
    base pm-rmon-alarm-type;
  }

  identity T-gfpStatsLFDRaised {
    description "RMON Performance Monitor Threshold Crossing Alert: gfpStatsLFDRaised";
    base pm-rmon-alarm-type;
  }

  identity T-gfpStatsRoundTripLatency {
    description "RMON Performance Monitor Threshold Crossing Alert: gfpStatsRoundTripLatency";
    base pm-rmon-alarm-type;
  }

  identity T-gfpStatsRxCIDInvalid {
    description "RMON Performance Monitor Threshold Crossing Alert: gfpStatsRxCIDInvalid";
    base pm-rmon-alarm-type;
  }

  identity T-gfpStatsRxCRCErrors {
    description "RMON Performance Monitor Threshold Crossing Alert: gfpStatsRxCRCErrors";
    base pm-rmon-alarm-type;
  }

  identity T-gfpStatsRxDistanceExtBuffers {
    description "RMON Performance Monitor Threshold Crossing Alert: gfpStatsRxDistanceExtBuffers";
    base pm-rmon-alarm-type;
  }

  identity T-gfpStatsRxFrame {
    description "RMON Performance Monitor Threshold Crossing Alert: gfpStatsRxFrame";
    base pm-rmon-alarm-type;
  }

  identity T-gfpStatsRxMBitErrors {
    description "RMON Performance Monitor Threshold Crossing Alert: gfpStatsRxMBitErrors";
    base pm-rmon-alarm-type;
  }

  identity T-gfpStatsRxOctets {
    description "RMON Performance Monitor Threshold Crossing Alert: gfpStatsRxOctets";
    base pm-rmon-alarm-type;
  }

  identity T-gfpStatsRxSBitErrors {
    description "RMON Performance Monitor Threshold Crossing Alert: gfpStatsRxSBitErrors";
    base pm-rmon-alarm-type;
  }

  identity T-gfpStatsRxSblkCRCErrors {
    description "RMON Performance Monitor Threshold Crossing Alert: gfpStatsRxSblkCRCErrors";
    base pm-rmon-alarm-type;
  }

  identity T-gfpStatsRxTypeInvalid {
    description "RMON Performance Monitor Threshold Crossing Alert: gfpStatsRxTypeInvalid";
    base pm-rmon-alarm-type;
  }

  identity T-gfpStatsTHecRxMBitErrors {
    description "RMON Performance Monitor Threshold Crossing Alert: gfpStatsTHecRxMBitErrors";
    base pm-rmon-alarm-type;
  }

  identity T-gfpStatsTxDistanceExtBuffers {
    description "RMON Performance Monitor Threshold Crossing Alert: gfpStatsTxDistanceExtBuffers";
    base pm-rmon-alarm-type;
  }

  identity T-gfpStatsTxFrame {
    description "RMON Performance Monitor Threshold Crossing Alert: gfpStatsTxFrame";
    base pm-rmon-alarm-type;
  }

  identity T-gfpStatsTxOctets {
    description "RMON Performance Monitor Threshold Crossing Alert: gfpStatsTxOctets";
    base pm-rmon-alarm-type;
  }

  identity T-gfpTxCmfFrame {
    description "RMON Performance Monitor Threshold Crossing Alert: gfpTxCmfFrame";
    base pm-rmon-alarm-type;
  }

  identity T-hdlcInOctets {
    description "RMON Performance Monitor Threshold Crossing Alert: hdlcInOctets";
    base pm-rmon-alarm-type;
  }

  identity T-hdlcOutOctets {
    description "RMON Performance Monitor Threshold Crossing Alert: hdlcOutOctets";
    base pm-rmon-alarm-type;
  }

  identity T-hdlcPktDrops {
    description "RMON Performance Monitor Threshold Crossing Alert: hdlcPktDrops";
    base pm-rmon-alarm-type;
  }

  identity T-hdlcRxAborts {
    description "RMON Performance Monitor Threshold Crossing Alert: hdlcRxAborts";
    base pm-rmon-alarm-type;
  }

  identity T-ifHCInBroadcastPkts {
    description "RMON Performance Monitor Threshold Crossing Alert: ifHCInBroadcastPkts";
    base pm-rmon-alarm-type;
  }

  identity T-ifHCInMulticastPkts {
    description "RMON Performance Monitor Threshold Crossing Alert: ifHCInMulticastPkts";
    base pm-rmon-alarm-type;
  }

  identity T-ifHCInOctets {
    description "RMON Performance Monitor Threshold Crossing Alert: ifHCInOctets";
    base pm-rmon-alarm-type;
  }

  identity T-ifHCInUcastPkts {
    description "RMON Performance Monitor Threshold Crossing Alert: ifHCInUcastPkts";
    base pm-rmon-alarm-type;
  }

  identity T-ifHCOutBroadcastPkts {
    description "RMON Performance Monitor Threshold Crossing Alert: ifHCOutBroadcastPkts";
    base pm-rmon-alarm-type;
  }

  identity T-ifHCOutMulticastPkts {
    description "RMON Performance Monitor Threshold Crossing Alert: ifHCOutMulticastPkts";
    base pm-rmon-alarm-type;
  }

  identity T-ifHCOutOctets {
    description "RMON Performance Monitor Threshold Crossing Alert: ifHCOutOctets";
    base pm-rmon-alarm-type;
  }

  identity T-ifInBroadcastPkts {
    description "RMON Performance Monitor Threshold Crossing Alert: ifInBroadcastPkts";
    base pm-rmon-alarm-type;
  }

  identity T-ifInDiscards {
    description "RMON Performance Monitor Threshold Crossing Alert: ifInDiscards";
    base pm-rmon-alarm-type;
  }

  identity T-ifInErrorBytePkts {
    description "RMON Performance Monitor Threshold Crossing Alert: ifInErrorBytePkts";
    base pm-rmon-alarm-type;
  }

  identity T-ifInErrors {
    description "RMON Performance Monitor Threshold Crossing Alert: ifInErrors";
    base pm-rmon-alarm-type;
  }

  identity T-ifInFramingErrorPkts {
    description "RMON Performance Monitor Threshold Crossing Alert: ifInFramingErrorPkts";
    base pm-rmon-alarm-type;
  }

  identity T-ifInJunkInterPkts {
    description "RMON Performance Monitor Threshold Crossing Alert: ifInJunkInterPkts";
    base pm-rmon-alarm-type;
  }

  identity T-ifInMulticastPkts {
    description "RMON Performance Monitor Threshold Crossing Alert: ifInMulticastPkts";
    base pm-rmon-alarm-type;
  }

  identity T-ifInOctets {
    description "RMON Performance Monitor Threshold Crossing Alert: ifInOctets";
    base pm-rmon-alarm-type;
  }

  identity T-ifInPayloadCrcErrors {
    description "RMON Performance Monitor Threshold Crossing Alert: ifInPayloadCrcErrors";
    base pm-rmon-alarm-type;
  }

  identity T-ifInUcastPkts {
    description "RMON Performance Monitor Threshold Crossing Alert: ifInUcastPkts";
    base pm-rmon-alarm-type;
  }

  identity T-ifOutBroadcastPkts {
    description "RMON Performance Monitor Threshold Crossing Alert: ifOutBroadcastPkts";
    base pm-rmon-alarm-type;
  }

  identity T-ifOutDiscards {
    description "RMON Performance Monitor Threshold Crossing Alert: ifOutDiscards";
    base pm-rmon-alarm-type;
  }

  identity T-ifOutErrors {
    description "RMON Performance Monitor Threshold Crossing Alert: ifOutErrors";
    base pm-rmon-alarm-type;
  }

  identity T-ifOutMulticastPkts {
    description "RMON Performance Monitor Threshold Crossing Alert: ifOutMulticastPkts";
    base pm-rmon-alarm-type;
  }

  identity T-ifOutOctets {
    description "RMON Performance Monitor Threshold Crossing Alert: ifOutOctets";
    base pm-rmon-alarm-type;
  }

  identity T-ifOutOversizePkts {
    description "RMON Performance Monitor Threshold Crossing Alert: ifOutOversizePkts";
    base pm-rmon-alarm-type;
  }

  identity T-ifOutPayloadCrcErrors {
    description "RMON Performance Monitor Threshold Crossing Alert: ifOutPayloadCrcErrors";
    base pm-rmon-alarm-type;
  }

  identity T-ifOutUcastPkts {
    description "RMON Performance Monitor Threshold Crossing Alert: ifOutUcastPkts";
    base pm-rmon-alarm-type;
  }

  identity T-mediaIndStatsOversizeDropped {
    description "RMON Performance Monitor Threshold Crossing Alert: mediaIndStatsOversizeDropped";
    base pm-rmon-alarm-type;
  }

  identity T-mediaIndStatsRxFramesBadCRC {
    description "RMON Performance Monitor Threshold Crossing Alert: mediaIndStatsRxFramesBadCRC";
    base pm-rmon-alarm-type;
  }

  identity T-mediaIndStatsRxFramesTooLong {
    description "RMON Performance Monitor Threshold Crossing Alert: mediaIndStatsRxFramesTooLong";
    base pm-rmon-alarm-type;
  }

  identity T-mediaIndStatsRxFramesTruncated {
    description "RMON Performance Monitor Threshold Crossing Alert: mediaIndStatsRxFramesTruncated";
    base pm-rmon-alarm-type;
  }

  identity T-mediaIndStatsRxLcvErrors {
    description "RMON Performance Monitor Threshold Crossing Alert: mediaIndStatsRxLcvErrors";
    base pm-rmon-alarm-type;
  }

  identity T-mediaIndStatsRxShortPkts {
    description "RMON Performance Monitor Threshold Crossing Alert: mediaIndStatsRxShortPkts";
    base pm-rmon-alarm-type;
  }

  identity T-mediaIndStatsTxFramesBadCRC {
    description "RMON Performance Monitor Threshold Crossing Alert: mediaIndStatsTxFramesBadCRC";
    base pm-rmon-alarm-type;
  }

  identity T-mediaIndStatsTxFramesTooLong {
    description "RMON Performance Monitor Threshold Crossing Alert: mediaIndStatsTxFramesTooLong";
    base pm-rmon-alarm-type;
  }

  identity T-mediaIndStatsTxFramesTruncated {
    description "RMON Performance Monitor Threshold Crossing Alert: mediaIndStatsTxFramesTruncated";
    base pm-rmon-alarm-type;
  }

  identity T-mediaIndStatsTxLcvErrors {
    description "RMON Performance Monitor Threshold Crossing Alert: mediaIndStatsTxLcvErrors";
    base pm-rmon-alarm-type;
  }

  identity T-mediaIndStatsTxShortPkts {
    description "RMON Performance Monitor Threshold Crossing Alert: mediaIndStatsTxShortPkts";
    base pm-rmon-alarm-type;
  }

  identity T-pcs49RxErrBer {
    description "RMON Performance Monitor Threshold Crossing Alert: pcs49RxErrBer";
    base pm-rmon-alarm-type;
  }

  identity T-pcs49RxErrDec {
    description "RMON Performance Monitor Threshold Crossing Alert: pcs49RxErrDec";
    base pm-rmon-alarm-type;
  }

  identity T-pcsEgRxErrFrames {
    description "RMON Performance Monitor Threshold Crossing Alert: pcsEgRxErrFrames";
    base pm-rmon-alarm-type;
  }

  identity T-pcsErrCount {
    description "RMON Performance Monitor Threshold Crossing Alert: pcsErrCount";
    base pm-rmon-alarm-type;
  }

  identity T-pcsErrCount2 {
    description "RMON Performance Monitor Threshold Crossing Alert: pcsErrCount2";
    base pm-rmon-alarm-type;
  }

  identity T-receiveControlFrames {
    description "RMON Performance Monitor Threshold Crossing Alert: receiveControlFrames";
    base pm-rmon-alarm-type;
  }

  identity T-receivePauseFrames {
    description "RMON Performance Monitor Threshold Crossing Alert: receivePauseFrames";
    base pm-rmon-alarm-type;
  }

  identity T-receivePktsDroppedInternalCongestion {
    description "RMON Performance Monitor Threshold Crossing Alert: receivePktsDroppedInternalCongestion";
    base pm-rmon-alarm-type;
  }

  identity T-receiveUnknownOpcodeFrames {
    description "RMON Performance Monitor Threshold Crossing Alert: receiveUnknownOpcodeFrames";
    base pm-rmon-alarm-type;
  }

  identity T-rprClientStatsInBcastFrames {
    description "RMON Performance Monitor Threshold Crossing Alert: rprClientStatsInBcastFrames";
    base pm-rmon-alarm-type;
  }

  identity T-rprClientStatsInMcastClassAFrames {
    description "RMON Performance Monitor Threshold Crossing Alert: rprClientStatsInMcastClassAFrames";
    base pm-rmon-alarm-type;
  }

  identity T-rprClientStatsInMcastClassAOctets {
    description "RMON Performance Monitor Threshold Crossing Alert: rprClientStatsInMcastClassAOctets";
    base pm-rmon-alarm-type;
  }

  identity T-rprClientStatsInMcastClassBCirFrames {
    description "RMON Performance Monitor Threshold Crossing Alert: rprClientStatsInMcastClassBCirFrames";
    base pm-rmon-alarm-type;
  }

  identity T-rprClientStatsInMcastClassBCirOctets {
    description "RMON Performance Monitor Threshold Crossing Alert: rprClientStatsInMcastClassBCirOctets";
    base pm-rmon-alarm-type;
  }

  identity T-rprClientStatsInMcastClassBEirFrames {
    description "RMON Performance Monitor Threshold Crossing Alert: rprClientStatsInMcastClassBEirFrames";
    base pm-rmon-alarm-type;
  }

  identity T-rprClientStatsInMcastClassBEirOctets {
    description "RMON Performance Monitor Threshold Crossing Alert: rprClientStatsInMcastClassBEirOctets";
    base pm-rmon-alarm-type;
  }

  identity T-rprClientStatsInMcastClassCFrames {
    description "RMON Performance Monitor Threshold Crossing Alert: rprClientStatsInMcastClassCFrames";
    base pm-rmon-alarm-type;
  }

  identity T-rprClientStatsInMcastClassCOctets {
    description "RMON Performance Monitor Threshold Crossing Alert: rprClientStatsInMcastClassCOctets";
    base pm-rmon-alarm-type;
  }

  identity T-rprClientStatsInUcastClassAFrames {
    description "RMON Performance Monitor Threshold Crossing Alert: rprClientStatsInUcastClassAFrames";
    base pm-rmon-alarm-type;
  }

  identity T-rprClientStatsInUcastClassAOctets {
    description "RMON Performance Monitor Threshold Crossing Alert: rprClientStatsInUcastClassAOctets";
    base pm-rmon-alarm-type;
  }

  identity T-rprClientStatsInUcastClassBCirFrames {
    description "RMON Performance Monitor Threshold Crossing Alert: rprClientStatsInUcastClassBCirFrames";
    base pm-rmon-alarm-type;
  }

  identity T-rprClientStatsInUcastClassBCirOctets {
    description "RMON Performance Monitor Threshold Crossing Alert: rprClientStatsInUcastClassBCirOctets";
    base pm-rmon-alarm-type;
  }

  identity T-rprClientStatsInUcastClassBEirFrames {
    description "RMON Performance Monitor Threshold Crossing Alert: rprClientStatsInUcastClassBEirFrames";
    base pm-rmon-alarm-type;
  }

  identity T-rprClientStatsInUcastClassBEirOctets {
    description "RMON Performance Monitor Threshold Crossing Alert: rprClientStatsInUcastClassBEirOctets";
    base pm-rmon-alarm-type;
  }

  identity T-rprClientStatsInUcastClassCFrames {
    description "RMON Performance Monitor Threshold Crossing Alert: rprClientStatsInUcastClassCFrames";
    base pm-rmon-alarm-type;
  }

  identity T-rprClientStatsInUcastClassCOctets {
    description "RMON Performance Monitor Threshold Crossing Alert: rprClientStatsInUcastClassCOctets";
    base pm-rmon-alarm-type;
  }

  identity T-rprClientStatsOutBcastFrames {
    description "RMON Performance Monitor Threshold Crossing Alert: rprClientStatsOutBcastFrames";
    base pm-rmon-alarm-type;
  }

  identity T-rprClientStatsOutMcastClassAFrames {
    description "RMON Performance Monitor Threshold Crossing Alert: rprClientStatsOutMcastClassAFrames";
    base pm-rmon-alarm-type;
  }

  identity T-rprClientStatsOutMcastClassAOctets {
    description "RMON Performance Monitor Threshold Crossing Alert: rprClientStatsOutMcastClassAOctets";
    base pm-rmon-alarm-type;
  }

  identity T-rprClientStatsOutMcastClassBCirFrames {
    description "RMON Performance Monitor Threshold Crossing Alert: rprClientStatsOutMcastClassBCirFrames";
    base pm-rmon-alarm-type;
  }

  identity T-rprClientStatsOutMcastClassBCirOctets {
    description "RMON Performance Monitor Threshold Crossing Alert: rprClientStatsOutMcastClassBCirOctets";
    base pm-rmon-alarm-type;
  }

  identity T-rprClientStatsOutMcastClassBEirFrames {
    description "RMON Performance Monitor Threshold Crossing Alert: rprClientStatsOutMcastClassBEirFrames";
    base pm-rmon-alarm-type;
  }

  identity T-rprClientStatsOutMcastClassBEirOctets {
    description "RMON Performance Monitor Threshold Crossing Alert: rprClientStatsOutMcastClassBEirOctets";
    base pm-rmon-alarm-type;
  }

  identity T-rprClientStatsOutMcastClassCFrames {
    description "RMON Performance Monitor Threshold Crossing Alert: rprClientStatsOutMcastClassCFrames";
    base pm-rmon-alarm-type;
  }

  identity T-rprClientStatsOutMcastClassCOctets {
    description "RMON Performance Monitor Threshold Crossing Alert: rprClientStatsOutMcastClassCOctets";
    base pm-rmon-alarm-type;
  }

  identity T-rprClientStatsOutUcastClassAFrames {
    description "RMON Performance Monitor Threshold Crossing Alert: rprClientStatsOutUcastClassAFrames";
    base pm-rmon-alarm-type;
  }

  identity T-rprClientStatsOutUcastClassAOctets {
    description "RMON Performance Monitor Threshold Crossing Alert: rprClientStatsOutUcastClassAOctets";
    base pm-rmon-alarm-type;
  }

  identity T-rprClientStatsOutUcastClassBCirFrames {
    description "RMON Performance Monitor Threshold Crossing Alert: rprClientStatsOutUcastClassBCirFrames";
    base pm-rmon-alarm-type;
  }

  identity T-rprClientStatsOutUcastClassBCirOctets {
    description "RMON Performance Monitor Threshold Crossing Alert: rprClientStatsOutUcastClassBCirOctets";
    base pm-rmon-alarm-type;
  }

  identity T-rprClientStatsOutUcastClassBEirFrames {
    description "RMON Performance Monitor Threshold Crossing Alert: rprClientStatsOutUcastClassBEirFrames";
    base pm-rmon-alarm-type;
  }

  identity T-rprClientStatsOutUcastClassBEirOctets {
    description "RMON Performance Monitor Threshold Crossing Alert: rprClientStatsOutUcastClassBEirOctets";
    base pm-rmon-alarm-type;
  }

  identity T-rprClientStatsOutUcastClassCFrames {
    description "RMON Performance Monitor Threshold Crossing Alert: rprClientStatsOutUcastClassCFrames";
    base pm-rmon-alarm-type;
  }

  identity T-rprClientStatsOutUcastClassCOctets {
    description "RMON Performance Monitor Threshold Crossing Alert: rprClientStatsOutUcastClassCOctets";
    base pm-rmon-alarm-type;
  }

  identity T-rprErrorOversizeFrames {
    description "RMON Performance Monitor Threshold Crossing Alert: rprErrorOversizeFrames";
    base pm-rmon-alarm-type;
  }

  identity T-rprErrorStatsBadAddrFrames {
    description "RMON Performance Monitor Threshold Crossing Alert: rprErrorStatsBadAddrFrames";
    base pm-rmon-alarm-type;
  }

  identity T-rprErrorStatsBadFcsFrames {
    description "RMON Performance Monitor Threshold Crossing Alert: rprErrorStatsBadFcsFrames";
    base pm-rmon-alarm-type;
  }

  identity T-rprErrorStatsBadHecFrames {
    description "RMON Performance Monitor Threshold Crossing Alert: rprErrorStatsBadHecFrames";
    base pm-rmon-alarm-type;
  }

  identity T-rprErrorStatsBadParityFrames {
    description "RMON Performance Monitor Threshold Crossing Alert: rprErrorStatsBadParityFrames";
    base pm-rmon-alarm-type;
  }

  identity T-rprErrorStatsContainedFrames {
    description "RMON Performance Monitor Threshold Crossing Alert: rprErrorStatsContainedFrames";
    base pm-rmon-alarm-type;
  }

  identity T-rprErrorStatsPmdAbortFrames {
    description "RMON Performance Monitor Threshold Crossing Alert: rprErrorStatsPmdAbortFrames";
    base pm-rmon-alarm-type;
  }

  identity T-rprErrorStatsScffErrors {
    description "RMON Performance Monitor Threshold Crossing Alert: rprErrorStatsScffErrors";
    base pm-rmon-alarm-type;
  }

  identity T-rprErrorStatsSelfSrcUcastFrames {
    description "RMON Performance Monitor Threshold Crossing Alert: rprErrorStatsSelfSrcUcastFrames";
    base pm-rmon-alarm-type;
  }

  identity T-rprErrorStatsTooLongFrames {
    description "RMON Performance Monitor Threshold Crossing Alert: rprErrorStatsTooLongFrames";
    base pm-rmon-alarm-type;
  }

  identity T-rprErrorStatsTooShortFrames {
    description "RMON Performance Monitor Threshold Crossing Alert: rprErrorStatsTooShortFrames";
    base pm-rmon-alarm-type;
  }

  identity T-rprErrorStatsTtlExpFrames {
    description "RMON Performance Monitor Threshold Crossing Alert: rprErrorStatsTtlExpFrames";
    base pm-rmon-alarm-type;
  }

  identity T-rprIfStatsInFrames {
    description "RMON Performance Monitor Threshold Crossing Alert: rprIfStatsInFrames";
    base pm-rmon-alarm-type;
  }

  identity T-rprIfStatsInOctets {
    description "RMON Performance Monitor Threshold Crossing Alert: rprIfStatsInOctets";
    base pm-rmon-alarm-type;
  }

  identity T-rprIfStatsOutFrames {
    description "RMON Performance Monitor Threshold Crossing Alert: rprIfStatsOutFrames";
    base pm-rmon-alarm-type;
  }

  identity T-rprIfStatsOutOctets {
    description "RMON Performance Monitor Threshold Crossing Alert: rprIfStatsOutOctets";
    base pm-rmon-alarm-type;
  }

  identity T-rprPortCounterError {
    description "RMON Performance Monitor Threshold Crossing Alert: rprPortCounterError";
    base pm-rmon-alarm-type;
  }

  identity T-rprSpanStatsInCtrlFrames {
    description "RMON Performance Monitor Threshold Crossing Alert: rprSpanStatsInCtrlFrames";
    base pm-rmon-alarm-type;
  }

  identity T-rprSpanStatsInMcastClassAFrames {
    description "RMON Performance Monitor Threshold Crossing Alert: rprSpanStatsInMcastClassAFrames";
    base pm-rmon-alarm-type;
  }

  identity T-rprSpanStatsInMcastClassAOctets {
    description "RMON Performance Monitor Threshold Crossing Alert: rprSpanStatsInMcastClassAOctets";
    base pm-rmon-alarm-type;
  }

  identity T-rprSpanStatsInMcastClassBCirFrames {
    description "RMON Performance Monitor Threshold Crossing Alert: rprSpanStatsInMcastClassBCirFrames";
    base pm-rmon-alarm-type;
  }

  identity T-rprSpanStatsInMcastClassBCirOctets {
    description "RMON Performance Monitor Threshold Crossing Alert: rprSpanStatsInMcastClassBCirOctets";
    base pm-rmon-alarm-type;
  }

  identity T-rprSpanStatsInMcastClassBEirFrames {
    description "RMON Performance Monitor Threshold Crossing Alert: rprSpanStatsInMcastClassBEirFrames";
    base pm-rmon-alarm-type;
  }

  identity T-rprSpanStatsInMcastClassBEirOctets {
    description "RMON Performance Monitor Threshold Crossing Alert: rprSpanStatsInMcastClassBEirOctets";
    base pm-rmon-alarm-type;
  }

  identity T-rprSpanStatsInMcastClassCFrames {
    description "RMON Performance Monitor Threshold Crossing Alert: rprSpanStatsInMcastClassCFrames";
    base pm-rmon-alarm-type;
  }

  identity T-rprSpanStatsInMcastClassCOctets {
    description "RMON Performance Monitor Threshold Crossing Alert: rprSpanStatsInMcastClassCOctets";
    base pm-rmon-alarm-type;
  }

  identity T-rprSpanStatsInOamEchoFrames {
    description "RMON Performance Monitor Threshold Crossing Alert: rprSpanStatsInOamEchoFrames";
    base pm-rmon-alarm-type;
  }

  identity T-rprSpanStatsInOamFlushFrames {
    description "RMON Performance Monitor Threshold Crossing Alert: rprSpanStatsInOamFlushFrames";
    base pm-rmon-alarm-type;
  }

  identity T-rprSpanStatsInOamOrgFrames {
    description "RMON Performance Monitor Threshold Crossing Alert: rprSpanStatsInOamOrgFrames";
    base pm-rmon-alarm-type;
  }

  identity T-rprSpanStatsInTopoAtdFrames {
    description "RMON Performance Monitor Threshold Crossing Alert: rprSpanStatsInTopoAtdFrames";
    base pm-rmon-alarm-type;
  }

  identity T-rprSpanStatsInTopoChkSumFrames {
    description "RMON Performance Monitor Threshold Crossing Alert: rprSpanStatsInTopoChkSumFrames";
    base pm-rmon-alarm-type;
  }

  identity T-rprSpanStatsInTopoTpFrames {
    description "RMON Performance Monitor Threshold Crossing Alert: rprSpanStatsInTopoTpFrames";
    base pm-rmon-alarm-type;
  }

  identity T-rprSpanStatsInUcastClassAFrames {
    description "RMON Performance Monitor Threshold Crossing Alert: rprSpanStatsInUcastClassAFrames";
    base pm-rmon-alarm-type;
  }

  identity T-rprSpanStatsInUcastClassAOctets {
    description "RMON Performance Monitor Threshold Crossing Alert: rprSpanStatsInUcastClassAOctets";
    base pm-rmon-alarm-type;
  }

  identity T-rprSpanStatsInUcastClassBCirFrames {
    description "RMON Performance Monitor Threshold Crossing Alert: rprSpanStatsInUcastClassBCirFrames";
    base pm-rmon-alarm-type;
  }

  identity T-rprSpanStatsInUcastClassBCirOctets {
    description "RMON Performance Monitor Threshold Crossing Alert: rprSpanStatsInUcastClassBCirOctets";
    base pm-rmon-alarm-type;
  }

  identity T-rprSpanStatsInUcastClassBEirFrames {
    description "RMON Performance Monitor Threshold Crossing Alert: rprSpanStatsInUcastClassBEirFrames";
    base pm-rmon-alarm-type;
  }

  identity T-rprSpanStatsInUcastClassBEirOctets {
    description "RMON Performance Monitor Threshold Crossing Alert: rprSpanStatsInUcastClassBEirOctets";
    base pm-rmon-alarm-type;
  }

  identity T-rprSpanStatsInUcastClassCFrames {
    description "RMON Performance Monitor Threshold Crossing Alert: rprSpanStatsInUcastClassCFrames";
    base pm-rmon-alarm-type;
  }

  identity T-rprSpanStatsInUcastClassCOctets {
    description "RMON Performance Monitor Threshold Crossing Alert: rprSpanStatsInUcastClassCOctets";
    base pm-rmon-alarm-type;
  }

  identity T-rprSpanStatsOutCtrlFrames {
    description "RMON Performance Monitor Threshold Crossing Alert: rprSpanStatsOutCtrlFrames";
    base pm-rmon-alarm-type;
  }

  identity T-rprSpanStatsOutMcastClassAFrames {
    description "RMON Performance Monitor Threshold Crossing Alert: rprSpanStatsOutMcastClassAFrames";
    base pm-rmon-alarm-type;
  }

  identity T-rprSpanStatsOutMcastClassAOctets {
    description "RMON Performance Monitor Threshold Crossing Alert: rprSpanStatsOutMcastClassAOctets";
    base pm-rmon-alarm-type;
  }

  identity T-rprSpanStatsOutMcastClassBCirFrames {
    description "RMON Performance Monitor Threshold Crossing Alert: rprSpanStatsOutMcastClassBCirFrames";
    base pm-rmon-alarm-type;
  }

  identity T-rprSpanStatsOutMcastClassBCirOctets {
    description "RMON Performance Monitor Threshold Crossing Alert: rprSpanStatsOutMcastClassBCirOctets";
    base pm-rmon-alarm-type;
  }

  identity T-rprSpanStatsOutMcastClassBEirFrames {
    description "RMON Performance Monitor Threshold Crossing Alert: rprSpanStatsOutMcastClassBEirFrames";
    base pm-rmon-alarm-type;
  }

  identity T-rprSpanStatsOutMcastClassBEirOctets {
    description "RMON Performance Monitor Threshold Crossing Alert: rprSpanStatsOutMcastClassBEirOctets";
    base pm-rmon-alarm-type;
  }

  identity T-rprSpanStatsOutMcastClassCFrames {
    description "RMON Performance Monitor Threshold Crossing Alert: rprSpanStatsOutMcastClassCFrames";
    base pm-rmon-alarm-type;
  }

  identity T-rprSpanStatsOutMcastClassCOctets {
    description "RMON Performance Monitor Threshold Crossing Alert: rprSpanStatsOutMcastClassCOctets";
    base pm-rmon-alarm-type;
  }

  identity T-rprSpanStatsOutOamEchoFrames {
    description "RMON Performance Monitor Threshold Crossing Alert: rprSpanStatsOutOamEchoFrames";
    base pm-rmon-alarm-type;
  }

  identity T-rprSpanStatsOutOamFlushFrames {
    description "RMON Performance Monitor Threshold Crossing Alert: rprSpanStatsOutOamFlushFrames";
    base pm-rmon-alarm-type;
  }

  identity T-rprSpanStatsOutOamOrgFrames {
    description "RMON Performance Monitor Threshold Crossing Alert: rprSpanStatsOutOamOrgFrames";
    base pm-rmon-alarm-type;
  }

  identity T-rprSpanStatsOutTopoAtdFrames {
    description "RMON Performance Monitor Threshold Crossing Alert: rprSpanStatsOutTopoAtdFrames";
    base pm-rmon-alarm-type;
  }

  identity T-rprSpanStatsOutTopoChkSumFrames {
    description "RMON Performance Monitor Threshold Crossing Alert: rprSpanStatsOutTopoChkSumFrames";
    base pm-rmon-alarm-type;
  }

  identity T-rprSpanStatsOutTopoTpFrames {
    description "RMON Performance Monitor Threshold Crossing Alert: rprSpanStatsOutTopoTpFrames";
    base pm-rmon-alarm-type;
  }

  identity T-rprSpanStatsOutUcastClassAFrames {
    description "RMON Performance Monitor Threshold Crossing Alert: rprSpanStatsOutUcastClassAFrames";
    base pm-rmon-alarm-type;
  }

  identity T-rprSpanStatsOutUcastClassAOctets {
    description "RMON Performance Monitor Threshold Crossing Alert: rprSpanStatsOutUcastClassAOctets";
    base pm-rmon-alarm-type;
  }

  identity T-rprSpanStatsOutUcastClassBCirFrames {
    description "RMON Performance Monitor Threshold Crossing Alert: rprSpanStatsOutUcastClassBCirFrames";
    base pm-rmon-alarm-type;
  }

  identity T-rprSpanStatsOutUcastClassBCirOctets {
    description "RMON Performance Monitor Threshold Crossing Alert: rprSpanStatsOutUcastClassBCirOctets";
    base pm-rmon-alarm-type;
  }

  identity T-rprSpanStatsOutUcastClassBEirFrames {
    description "RMON Performance Monitor Threshold Crossing Alert: rprSpanStatsOutUcastClassBEirFrames";
    base pm-rmon-alarm-type;
  }

  identity T-rprSpanStatsOutUcastClassBEirOctets {
    description "RMON Performance Monitor Threshold Crossing Alert: rprSpanStatsOutUcastClassBEirOctets";
    base pm-rmon-alarm-type;
  }

  identity T-rprSpanStatsOutUcastClassCFrames {
    description "RMON Performance Monitor Threshold Crossing Alert: rprSpanStatsOutUcastClassCFrames";
    base pm-rmon-alarm-type;
  }

  identity T-rprSpanStatsOutUcastClassCOctets {
    description "RMON Performance Monitor Threshold Crossing Alert: rprSpanStatsOutUcastClassCOctets";
    base pm-rmon-alarm-type;
  }

  identity T-rx8b10bWords {
    description "RMON Performance Monitor Threshold Crossing Alert: rx8b10bWords";
    base pm-rmon-alarm-type;
  }

  identity T-rxTotalPkts {
    description "RMON Performance Monitor Threshold Crossing Alert: rxTotalPkts";
    base pm-rmon-alarm-type;
  }

  identity T-transmitPauseFrames {
    description "RMON Performance Monitor Threshold Crossing Alert: transmitPauseFrames";
    base pm-rmon-alarm-type;
  }

  identity T-transmitPktsDroppedInternalCongestion {
    description "RMON Performance Monitor Threshold Crossing Alert: transmitPktsDroppedInternalCongestion";
    base pm-rmon-alarm-type;
  }

  identity T-tx8b10bWords {
    description "RMON Performance Monitor Threshold Crossing Alert: tx8b10bWords";
    base pm-rmon-alarm-type;
  }

  identity T-txTotalPkts {
    description "RMON Performance Monitor Threshold Crossing Alert: txTotalPkts";
    base pm-rmon-alarm-type;
  }

}
