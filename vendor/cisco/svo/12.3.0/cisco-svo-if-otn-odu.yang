module cisco-svo-if-otn-odu {
    yang-version 1.1;
    namespace "http://cisco.com/yang/svo/otn-odu";
    prefix svo-otn-odu;

    import cisco-svo-common-base-opt-grp { prefix ccbog; }  
    import cisco-svo-common-otn-grp { prefix ccotng; }
    import cisco-svo-common-otn-oper-grp { prefix ccotnog; }
    import cisco-svo-common-otn-odu-oper-grp { prefix coduog; }
    import cisco-svo-common-otn-live-grp { prefix ccotnlg; }

    organization
        "Cisco Systems, Inc.";

    contact
        "Cisco Systems, Inc. Customer Service Postal: 170 West Tasman
        Drive San Jose, CA 95134 Tel: +1 800 553-NETS E-mail: cs-yang@cisco.com";

    description
        "YANG definition for device interfaces";

  revision 2021-12-25 {
  	description "Model version for SVO Release 12.3.0 ";
  	reference cisco-svo-if-otn-odu.yang;
  }
  
    revision 2020-12-04 { 
       description "Model version for SVO Release 12.1.0 "; 
       reference cisco-svo-if-otn-odu.yang; 
    }
 

    grouping otn-odu-group {
      description "OTN ODU operational and configuration data";
        uses ccotnog:odu-attributes;
        uses ccotng:parent-odu-allocation;
        uses ccbog:ber-grp;
        
        container tti {
          uses ccotng:tti-cfg-grp;
          uses ccotnog:tti-oper-grp;
        }
        container legacy-tti {
          uses ccotng:legacy-tti-cfg-grp;
          uses ccotnog:tti-oper-grp;
        }
        
        uses ccotnlg:tti-live-grp;
        uses ccotnlg:legacy-tti-live-grp;
        
        uses ccotng:squelch-odu;
        container prbs {
            uses coduog:otn-odu-prbs-oper-group;
            uses ccotng:prbs-cfg;
        }
        uses ccotnlg:prbs-live-grp;
    }
      
    grouping otn-odu-grp {
    	description "OTN-ODU grouping";
        container otn-odu {
            description "Specific otn-odu Data";
            uses otn-odu-group;
        }
    }    
    
}
