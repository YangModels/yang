module cisco-svo-equipment-oper-grp {
  yang-version 1.1;
  namespace "http://cisco.com/yang/svo/equipment-oper";
  prefix ceqog;

  import ietf-yang-types { prefix ietf; revision-date 2013-07-15; }
  import cisco-svo-common-equipment-types { prefix ccet; }
  import cisco-svo-common-equipment-oper-grp { prefix cceqptog; }
  import cisco-ncs2k-equipment-types { prefix cet; }
  import tailf-common { prefix tailf; }
  import cisco-svo-common-license-types { prefix cclict; }
  import cisco-svo-common-license-oper-grp { prefix cclicog; }

  organization
    "Cisco Systems, Inc.";

  contact
    "Cisco Systems, Inc. Customer Service Postal: 170 West Tasman Drive San Jose, CA 95134 Tel: +1 800 553-NETS E-mail: cs-yang@cisco.com";

  description
    "YANG definition for: node, equipments, interfaces, internal links, xconn Operational Data";

  revision 2021-12-25 {
  	description "Model version for SVO Release 12.3.0 ";
  	reference cisco-svo-equipment-oper-grp.yang;
  }
  
   revision 2021-04-16 { 
      description "Model version for SVO Release 12.2.0 "; 
      reference cisco-svo-equipment-oper-grp.yang; 
   }
 

    revision 2020-12-04 { 
       description "Model version for SVO Release 12.1.0 "; 
       reference cisco-svo-equipment-oper-grp.yang; 
    }
 

  grouping usb-port-association-info-grp-oper {

  }
	typedef obfl-status-t {
	 type enumeration {
	   enum "OBFL_UNSUPPORTED" {
	     description "OBFL Not Supported";
	   }
	   enum "OBFL_CARD_NOT_READY" {
	     description "Card Not ready for OBFL operation";
	   }
	   enum "OBFL_IDLE" {
	     description "Ready for OBFL operation";
	   }
	   enum "OBFL_WRITING" {
	     description "OBFL Procedure already start";
	   }
	 }
	 description "all possible OBFL card status";
	}
	

  grouping obfl-info-oper {

    leaf obfl-status {
      type ceqog:obfl-status-t;
    }

    leaf last-operation-time {
      type ietf:date-and-time;
      description "UTC Time and Date of the last completed obfl operation";
    }
  }

  grouping module-content-oper {
    uses cceqptog:equipment-properties-oper;

    leaf degree-of-support {
      type ccet:degree-of-support-type-t;
      config false;
      description "Degree of card type supporting. The partial supporting means that the ports and interfaces information is hidden";
    }

    container obfl-report {
      config false;
      uses ceqog:obfl-info-oper;
    }
    container license-data {
       config false;
       list counted-license-features {
         key feature-name;
         leaf feature-name {
           type cclict:license-feature-name-t;
         }
         leaf license-type-in-use {
             type cclict:license-type-t;
         }
        uses cclicog:countedlic-feature-data;
       }
       list feature-license {
         key feature-name;
         leaf feature-name {
           type cclict:license-feature-name-t;
         }
         leaf license-type-in-use {
             type cclict:license-type-t;
         }
         uses cclicog:noncountedlic-feature-data;
       }
       leaf sync-status {
           type string;
           description "License-data sync status";
       }
    }
  }

grouping fpd-version-grp{
		list fpd-version{	
      key fpd-name;
      config false;
      description "List of the firmware versions";

        leaf fpd-name {
        type string;
        description "Port number";
        }
        
        leaf curr-version {
        type string;
        description "Current FPD version";
        }

        leaf pkg-version {
        type string;
        description "Package FPD version";
        }
    }
  }
  grouping module-content-oper-usb-association {
    uses usb-port-association-info-grp-oper {
      when "../../chassis-type = 'cet:NCS2K-MF10-6RU' or ../../chassis-type = 'cet:NCS2K-MF-6RU'";
    }
  }

 
}
