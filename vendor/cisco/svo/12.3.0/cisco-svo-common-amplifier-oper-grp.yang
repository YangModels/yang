module cisco-svo-common-amplifier-oper-grp {

    yang-version 1.1;
    namespace "http://cisco.com/yang/svo/common-amplifier-oper-grp";
    prefix "ccaog";

    import cisco-svo-common-types { prefix cct; }
    import cisco-svo-common-base-opt-oper-grp { prefix ccboog; }

    organization
        "Cisco Systems, Inc.";

    contact
        "Cisco Systems, Inc. Customer Service Postal: 170 West Tasman
        Drive San Jose, CA 95134 Tel: +1 800 553-NETS E-mail: cs-yang@cisco.com";

    description " CISCO Common Amplifier Operational grouping";

  revision 2021-12-25 {
  	description "Model version for SVO Release 12.3.0";
  	reference cisco-svo-common-amplifier-oper-grp.yang;
  }
  
    revision 2020-12-04 { 
       description "Model version for SVO Release 12.1.0 "; 
       reference cisco-svo-common-amplifier-oper-grp.yang; 
    }
 
 
    grouping amp-optics-oper-grp {
    	description "Amplifier operational data grouping";
        
    	container gain-degrade-thresholds {
            uses ccboog:gain-degrade-thresholds-grp;
            config false;
            description "Gain threshold values";
        }

        container power-degrade-thresholds {
            uses ccboog:power-degrade-thresholds-grp;
            config false;
            description "Output power threshold values";
        }
    }
    
    grouping rmn-amp-optics-oper-grp {
    	description "Raman amplifier operational data grouping";
        
         leaf actual-gain {
             type cct:db-oper-t;
             config false;
             description "Actual Raman gain value";
         }
         
         leaf actual-tilt {
             type cct:db-oper-t;
             config false;
             description "Actual Raman tilt value";
         }   
         
         leaf pumping-scheme {
        	 type cct:raman-pumping-scheme-t;
        	 config false;
        	 description "Type of pumping scheme for Raman amplification";
         }
         
        list pumps-power-target {
        	key "pump-id";       	
        	description "List of single Raman pump power current target value";
        	config false;

			leaf pump-id {
                type cct:pump-id-t;
                config false;
                description "Ordinal id of the Raman pump";
            }

            leaf pump-power {
                type cct:mw-oper-t;
                config false;
                description "Single pump power target";
            }
        }      
    }
}
