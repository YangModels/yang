module cisco-svo-interfaces-grp {
    yang-version 1.1;
    namespace "http://cisco.com/yang/svo/interfaces";
    prefix cif;
   
    import org-openroadm-interfaces { prefix or-if; revision-date 2018-09-28; }
    import cisco-svo-common-interface-grp { prefix ccig; }
    import cisco-svo-common-equipment-types { prefix ccet; }
    import cisco-svo-common-base-opt-grp { prefix ccbog; }
    import cisco-svo-common-interface-oper-grp { prefix cciog; }
    
    organization
        "Cisco Systems, Inc.";

    contact
        "Cisco Systems, Inc.
     Customer Service
     
     Postal: 170 West Tasman Drive
     San Jose, CA 95134
     
     Tel: +1 800 553-NETS
     
     E-mail: cs-yang@cisco.com";

    description
        "YANG definition for SVO device interfaces";

  revision 2021-12-25 {
  	description "Model version for SVO Release 12.3.0 ";
  	reference cisco-svo-interfaces-grp.yang;
  }
  
    revision 2020-12-04 { 
       description "Model version for SVO Release 12.1.0 "; 
       reference cisco-svo-interfaces-grp.yang; 
    }
 

    grouping interface-ref {
    	description "Reference to an Interface grouping";

        leaf type {
            type identityref {
                base or-if:interface-type;
            }
            description "Type of the interface.";
        }

        leaf name {
            type leafref {
                path "../../../interface[type=current()/../type]/name";
            }
            description "Higher level interface";
        }
    }

    grouping interfaces {
        description "Common Interface parameters.";
        
        list interface {
            key "type name";
            description "The list of configured interfaces on the device.";

            // oper data
            leaf uid {
                type ccet:uid-t;
                config false;
                description "Identifier of the linked chassis, same device the interface is based on";
            }

            leaf type {
                type identityref {
                    base or-if:interface-type;
                }
                description "Type of the interface.";
            }

            leaf name {
                type ccet:port-name-t;
                description "The name of the interface.";
            }

            leaf active-or-preconfigured {
                type string {
                    pattern '(act)|(pre)';
                }
                default "act";
                
                description
                "Effective only for NCS1004: it indicates whether the interface is active or
                preconfigured";
            }

            uses ccig:interface-common-config-grp;
            uses cciog:interface-common-oper-grp;

            container supporting-port {
            	description "Reference to equipment supporting port";
                leaf module-id {
                    type ccet:slot-t;
                    config false;
                    description "Identifier of the linked module.";
                }

                leaf port-id {
                    type ccet:port-id-t;
                    config false;
                    description "Identifier of the linked port.";
                }
            
                leaf port-name {
                  type ccet:port-name-t;
                  config false;
                  description "The name of the interface.";
                }
            }

            list higher-interface-list {
                key "type name";
                uses interface-ref;
                config false;
                description "Higher level interface";
            }

            list lower-interface-list {
                key "type name";
                uses interface-ref;
                config false;
                description "lower level interface";
            }
        }

        action automatic-in-service {
        description
        "Execute ains soak configuration operations";
        input {
            leaf interface-name {
                type string;
                description
                "Controller name in R/S/I/P format";
            }
            leaf interface-type {
                type identityref {
                    base or-if:interface-type;
                }
                description "Type of the interface.";
            }
            leaf hours {
                type uint32 {
                range "0..48";
                }
                description
                "Hours in range of 0-48";
            }
            leaf minutes {
                type uint32 {
                range "0..59";
                }
                description
                "Minutes in range of 0-59";
            }
        }
        output {
            uses ccbog:rpc-status;
        }
      }        
    }
}
