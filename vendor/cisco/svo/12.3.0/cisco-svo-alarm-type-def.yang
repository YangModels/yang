submodule cisco-svo-alarm-type-def {

  belongs-to cisco-svo-alarm-type {
    prefix svo-al-t;
  }

  import tailf-ncs-alarms {
    prefix al;
  }


  organization
    "Cisco Systems, Inc.";

  contact
    "Cisco Systems, Inc.
    Customer Service

    Postal: 170 West Tasman Drive
    San Jose, CA 95134

    Tel: +1 800 553-NETS

    E-mail: cs-yang@cisco.com";

  description
    "This module defines the root of svo alarms under the 
      alarm-type under the module tailf-ncs-alarms";

    revision 2020-12-04 { 
       description "Model version for SVO Release 12.1.0 "; 
       reference cisco-svo-alarm-type-def.yang; 
    }
 

  identity svo-alarm-type {
    description "Root of svo alarm type";
    base al:alarm-type;
  }

  typedef svo-alarm-type-t {
    type identityref {
      base svo-alarm-type;
    }
  }

  identity svo-tca-type {
    description "Root of svo tca event type";
    base al:alarm-type;
  }
}
