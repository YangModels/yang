module cisco-svo-device-flavour {
  namespace "http://cisco.com/yang/svo/device-flavour";
  prefix svo-device-flavour;

  import tailf-common { prefix tailf; }
  import cisco-svo-common-equipment-types { prefix ccet; }

  tailf:export none;

  organization "Cisco Systems";

  description "This module defines the svo device flavours";

  revision 2021-12-25 {
  	description "Model version for SVO Release 12.3.0 ";
  	reference cisco-svo-device-flavour.yang;
  }
  
  revision 2021-04-16 { 
    description "Model version for SVO Release 12.2.0 "; 
    reference cisco-svo-device-flavour.yang; 
  }
 
  container svo-device-flavour {
    description "device flavours container";

    list device-flavour {
      key "device";

      leaf device {
        tailf:info "A string uniquely identifying the managed device";
        description "A string uniquely identifying the managed device";
        type string;
      }
      leaf flavour {
        type identityref {
          base ccet:device-flavour-type;
        }
        default ccet:any-config; // shall be ccet:txp-only in case of node optical-type is ccet:txp
        description "TXP-only node or ROADM node accepting TXP/MXP cards only.";
      }
    }
  }
}
