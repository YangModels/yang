module cisco-svo-tca {
    yang-version 1.1;
    namespace "http://cisco.com/yang/svo/tca";
    prefix hltca;

    import tailf-common { prefix tailf; }
    import org-openroadm-tca { prefix ortca; }
    import cisco-svo-common-equipment-types { prefix ccet; }
    import org-openroadm-common-types { prefix org-openroadm-common-types; }
    import cisco-svo { prefix svo; }

    
    organization
        "Cisco Systems, Inc.";

    contact
        "Cisco Systems, Inc.
     Customer Service
     
     Postal: 170 West Tasman Drive
     San Jose, CA 95134
     
     Tel: +1 800 553-NETS
     
     E-mail: cs-yang@cisco.com";

    description
        "YANG definition for SVO TCA";

   revision 2021-04-16 { 
      description "Model version for SVO Release 12.2.0 "; 
      reference cisco-svo-tca.yang; 
   }
 

    revision 2020-12-04 { 
       description "Model version for SVO Release 12.1.0 "; 
       reference cisco-svo-tca.yang; 
    }
 
    
    typedef tca-type-enum {
        type enumeration {
          enum "INTERFACETCA" {
            value 1;
            description
              "Interface related TCA";
          }
          enum "DWDMTCA" {
            value 2;
            description
              "DWDM interface related TCA";
          }
          
          enum "OPTICSTCA" {
              value 3;
              description
                "Optics related TCA";
            }
          
          enum "FECTCA" {
              value 4;
              description
                "FEC related TCA";
            }
          
          enum "OTNTCA" {
              value 5;
              description
                "OTN related TCA";
            }
          
          enum "ODUTCA" {
              value 6;
              description
                "ODU payload related TCA";
            }
          enum "OCNTCA" {
              value 7;
              description
                "OCN payload related TCA";
            }
        }
    }
    
    typedef monitor-type-enum {
        type enumeration {
          enum "MON_SECTION" {
            value 1;
            description
              "Section Monitoring";
          }
          enum "MON_PATH" {
            value 2;
            description
              "Path Monitoring";
          }
          enum "NA" {
              value 3;
              description
                "Not Applicable";
          }
          enum "MON_LINE" {
            value 4;
            description
              "Line Monitoring";
          }
          enum "MON_MS" {
            value 5;
            description
              "Line/Multiplex Monitoring";
          }
          enum "MON_RS" {
            value 6;
            description
              "Section/Regeneration Monitoring";
          }
        }
    }
    
    grouping tca {
    	leaf interface-name {
  	      type string;
  	      mandatory true;
  		}
    	    	
    	uses ortca:potential-tca;     	
    	
    	leaf uid {
    	      type ccet:uid-t;
    	      mandatory true;
    	}
    	
    	leaf slot-id{
    	      type string;
    	      mandatory true;
    	}
    	
    	leaf index{
    		type uint32;
            tailf:hidden full;
    	}
    	
    	leaf tca-type{
    		type tca-type-enum;
    	}
    	
    	leaf monitor-type{
    		type monitor-type-enum;
    	}
    	
    	leaf ochOnOtlEditable {
    		type string;
    	}
    }
    
    grouping tca-group {
    	list tca-list{
        	key "id";
        	uses tca;	
        }	
    }

    grouping tca-commands-grp {
    	action fetch-tca-on-slot {
    		description
    			"Command to fetch TCA information on required slot";
    		
    		input {
    			leaf deviceId {
    				type string;
    			}
    			
    			leaf chassisId {
    				type string;
    			}
    			
    			leaf slotId {
    				type string;
    			}
    		}
    		
    		output {
    			uses org-openroadm-common-types:rpc-response-status;
    		}
    	}
        action get-tca-on-slot {
            description
                "Command to fetch TCA information on required slot";

            input {

                leaf uid {
                   type leafref {
                       path '/svo:svo/svo:chassis/svo:uid';
                   }

                }

                leaf slotId {
                    type string;
                }
            }

            output {
                uses tca-group;
            }
        }

    }
}
