module cisco-ext-switch-ned {

  namespace "http://cisco.com/yang/ext/switch-ned";
  prefix cisco-ext-switch-ned;

  import tailf-ncs-ned {
    prefix ned;
  }

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "YANG definition for Cisco External Switch: ned identification class.";

  revision 2020-12-04 { 
      description "Model version for SVO Release 12.1.0 "; 
      reference cisco-ext-switch-ned; 
  }

  identity cisco-ext-switch-ned-id {
    base ned:netconf-ned-id;
  }
}
