module cisco-svo-common-otdr-grp {
    yang-version 1.1;
    namespace "http://cisco.com/yang/svo/common-otdr-grp";
    prefix "ccog";

    import cisco-svo-common-otdr-live-grp { prefix colg; }
    
    organization
        "Cisco Systems, Inc.";

    contact
        "Cisco Systems, Inc. Customer Service Postal: 170 West Tasman
        Drive San Jose, CA 95134 Tel: +1 800 553-NETS E-mail: cs-yang@cisco.com";

    description " CISCO Common Otdr Config
        yang models.";

    revision 2021-04-16 {
        description "
          Model version for SVO Release 12.2.0
          added:
                 new automatic-scan container and leaf for the OTDR automatism on scan. 
        ";
        reference cisco-svo-otdr.yang;
    }
    
    revision 2020-12-04 { 
       description "Model version for SVO Release 12.1.0 "; 
       reference cisco-svo-common-otdr-grp.yang; 
    }
 
     typedef Direction {
        type enumeration {
            enum "direction-tx" {
                description "Tx";
            }
            enum "direction-rx" {
                description "Rx";
            }
        }
        description "Direction";
    }

   grouping otdrs-conf {
     container otdr-node-configuration {
     
        leaf absolute-loss-threshold {
           type decimal64 {
             fraction-digits 1;
             range "0.1..30.0";
           }
            default 2.0;
            description "Otdr loss absolute threshold:valid for all otdrs of the device";
         } 
         leaf absolute-reflection-threshold {
            type decimal64 {
            fraction-digits 1;
            range "-50.0..0.0";
          }
            default -30.0;
            description "Otdr reflection absolute threshold:valid for all otdr of the device";
         }
         
         container automatic-scan {
         
           leaf on-osc-loss {
             type boolean;
             default false;
             description "Scan is triggered by rise and clear of OSC_LOSS alarm";
           }
           
           leaf delay-scan {
             type int8 {             
             	range "5..30";
             }
             default 5;
             description "Minute of delay from the alarm detection to the start of scan.";
           }
           
           leaf span-loss-increase {
             type boolean;
             default false;
             description "Scan is triggered on an increased value of the span loss";
           }
           
           leaf span-loss-increase-threshold {
             type decimal64 {
               fraction-digits 1;
               range "0.1..30.0";
             }
             default 2.0;
             description "Threshold that trigger the span-loss-increase automatic scan";
           }
           
           leaf excessive-orl {
             type boolean;
             default false;
             description "Scan is triggered on an excessive ORL alarm rise";
           }
           
         }
     }
  }



    grouping otdr-conf {
      description "Grouping for OTDR configs";

        container direction-tx { 
          container orl {
            
            uses colg:orl-live;
            
            leaf absolute-threshold {
                type decimal64 {
                  fraction-digits 2;
                  range "0..40.00";                  
                }
                default 28.00;
            }
          }
          
          leaf backscatter {
            type decimal64 {
              fraction-digits 1;
              range "-100.0..0";                  
            }
            default -82.0;
            units "dB";
          }
        
          leaf refractive-index {
            type decimal64 {
              fraction-digits 6;
              range "1.000000..2.000000";
            }
            default 1.498960;
          }
        
        }
        container direction-rx {
          container orl {
          
            uses colg:orl-live; 
            
            leaf absolute-threshold {
                type decimal64 {
                  fraction-digits 2;
                  range "0..40.00";                  
                }
                default 28.00;
            }
          }
          leaf backscatter {
            type decimal64 {
              fraction-digits 1;
              range "-100.0..0";                  
            }
            default -82.0;
            units "dB";
          }
        
          leaf refractive-index {
            type decimal64 {
              fraction-digits 6;
              range "1.000000..2.000000";
            }
            default 1.498960;
          }
        
        }
              
        container sector-autosector {
            description "Mode Auto";
            leaf loss-sensitivity {
                 type decimal64 {
                    fraction-digits 2;
                    range "0.40..5.00";
                 }

              default 1.50;
              description
                                "Otdr Loss Sensitivity, supported values [40 ,500] in db * 100";
            }
            leaf reflection-sensitivity {
                 type decimal64 {
                   fraction-digits 2;
                   range "-40.00..-14.00";
                 }

                default -30.00;
                description
                                "Otdr Reflection Sensitivity, supported values [-4000,-1400] in
                                units of db * 100";
            }
        }

    }
}
