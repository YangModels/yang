module cisco-svo-common-wson-sson-live-grp {
  yang-version 1.1;
  namespace "http://cisco.com/yang/svo/common-wson-sson-live-grp";
  prefix ccwsonlg;

  import cisco-svo-common-equipment-types { prefix ccet; }

  organization
    "Cisco Systems, Inc.";

  contact
        "Cisco Systems, Inc.
     Customer Service

     Postal: 170 West Tasman Drive
     San Jose, CA 95134

     Tel: +1 800 553-NETS

     E-mail: cs-yang@cisco.com";

  description "
    YANG definition for wson sson live status data";

    revision 2020-12-04 { 
       description "Model version for SVO Release 12.1.0 "; 
       reference cisco-svo-common-wson-sson-live-grp.yang; 
    }
 

  grouping wson-sson-live-grp {
    leaf wson-sson-status {
      config false;
      type ccet:wson-sson-status-t;
    }
  }
}
