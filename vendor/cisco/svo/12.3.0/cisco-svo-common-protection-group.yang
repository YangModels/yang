module cisco-svo-common-protection-group {
    yang-version 1.1;
    namespace "http://cisco.com/yang/svo/common-protection-group";
    prefix cprt-grp;

    import cisco-svo-common-types { prefix cct; }
    import cisco-svo-common-equipment-types { prefix ccet; }
    import cisco-svo-common-base-opt-grp { prefix ccbog; }

    organization
        "Cisco Systems, Inc.";

    contact
        "Cisco Systems, Inc. Customer Service Postal: 170 West Tasman
        Drive San Jose, CA 95134 Tel: +1 800 553-NETS E-mail: cs-yang@cisco.com";

    description "
    YANG model definition for SVO Protection Groups";

  revision 2021-12-25 {
  	description "Model version for SVO Release 12.3.0";
  	reference cisco-svo-common-protection-group.yang;
  }
  
    revision 2020-12-04 { 
       description "Model version for SVO Release 12.1.0 "; 
       reference cisco-svo-common-protection-group.yang; 
    }
 
    
    grouping protection-group-config-grp {
        
        leaf name {
            type string;
            mandatory true;
            description "The protection-group name";
        }
        
        leaf prot-type {
            type ccet:protection-type-t;
            mandatory true;
            description "The type of the protection group.";
        }

        leaf level {
            type cct:protection-level-t;
            mandatory true;
            description "Designates protection group as Line or Path";
        }

        leaf switching-direction {
            type cct:switching-direction-t;
            default "bidirectional-switching";
            description "Bidirectional refers to APS signaling enabled (G.873.1 Table
                        7-1 Table 8-1).";
        }

        leaf revertive {
            type boolean;
            default "false";
            description "Sets reversion behavior.";
        }

        leaf mode {
            type cct:protection-mode-t;
            description "Sets the protection mode";
        }
        
        leaf wait-to-restore {
            type cct:wait-restore-timer-t;
            description "Wait to restore time in minutes";
        }       
        
        leaf reversion-pulse-width {
            type cct:reversion-pulse-width-t;
            description "Reversion pulse width in seconds (PSM protection specific)";
        }       

        leaf protection-trigger-level {
            type cct:protection-level-trigger-t;
            description "Indicates switch trigger.";
        }

        container holdoff-timer {
            leaf holdoff {
                type cct:holdoff-timer-t;
                description "switch hold-off time in milliseconds";
            }

            leaf holdoff-multiplier {
                when "../holdoff= 100";
                type cct:holdoff-multiplier-t;
                description "switch holdoff time multiplier x100 milliseconds";
            }
        }

        leaf-list working-interfaces {
            type ccet:port-name-t;
            min-elements 1;
            description "List of designated working interfaces";
        }

        leaf-list protection-interfaces {
            type ccet:port-name-t;
            min-elements 1;
            description "List of availbale protection interfaces";
        }
    }
    
    grouping protection-group-action-grp {
        action protection-switch {
            description "Protection Switch Action with synchronous implementation";
            
            input {
                leaf target-interface {
                    type ccet:port-name-t;
                    description "Target interface for command";
                }

                leaf switch-command {
                    type cct:switch-action-t;
                }
            }
            
            output {
                uses ccbog:rpc-status;
            }
        }
    }

}
