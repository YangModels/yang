module cisco-svo-if-optical-transport {
    yang-version 1.1;
    namespace "http://cisco.com/yang/svo/if-optical-transport";
    prefix cif-ot;

    import cisco-svo-common-base-opt-grp { prefix ccbog; }
    import cisco-svo-common-interface-grp { prefix ccig;}
    import cisco-svo-common-action-param-grp { prefix ccapg; }
    
    import cisco-svo-common-interface-oper-grp { prefix cciog;}
    import cisco-svo-common-interface-live-grp { prefix ccilg;}

    
    organization
        "Cisco Systems, Inc.";

    contact
        "Cisco Systems, Inc.
     Customer Service
     
     Postal: 170 West Tasman Drive
     San Jose, CA 95134
     
     Tel: +1 800 553-NETS
     
     E-mail: cs-yang@cisco.com";

    description "
    YANG model definition for SVO Optical Transport interfaces";

    revision 2020-12-04 { 
       description "Model version for SVO Release 12.1.0 "; 
       reference cisco-svo-if-optical-transport.yang; 
    }
 
    
    grouping optical-transport-grp {
        description "Specific optical-transport Interface Data";

        container optical-transport {
            description "Specific optical-transport Data";

            action get-raw-power-data {
                description "get the raw power data from the device";
                output {
                  uses ccapg:raw-power-data-grp;
                  uses ccbog:rpc-status;
                }
            }
            
            // Oper Data
            list upstream-interface {
                key "interface-name";
                leaf interface-name {
                  type leafref {
                    path "../../../../interface[type=current()/../../../type]/name";
                  }
                }

                uses cciog:optical-transport-oper-loss-info-grp;
                config false;
                description "List of upstream interface(s) within the same module";
            }

            // Oper Data
            list downstream-interface {
                key "interface-name";
                leaf interface-name {
                type leafref {
                    path "../../../../interface[type=current()/../../../type]/name";
                   }
                }

                uses cciog:optical-transport-oper-loss-info-grp;
                config false;
                description "List of downstream interface(s) within the same module";
            }
            uses ccig:optical-transport-config-params-grp;
            container variable-optical-attenuator {
            	uses ccig:variable-optical-attenuator-config-param-grp;
            	uses cciog:variable-optical-attenuator-oper-param-grp;
            }
            uses cciog:optical-transport-oper-params-grp;
            uses ccilg:optical-transport-live-data;
        }
    }
}
