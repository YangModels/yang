module cisco-svo-alarm-debug {
    namespace "http://cisco.com/yang/svo/alarm/debug";
    prefix svo-alarm-dbg;

    import tailf-common { prefix tailf; }

    import tailf-ncs-alarms { prefix al; }

    tailf:export none;

    organization "Cisco Systems";

    description
        "This module defines the debug utility commands for svo alarm manager";

    revision 2020-12-04 { 
       description "Model version for SVO Release 12.1.0 "; 
       reference cisco-svo-alarm-debug.yang; 
    }
 


    augment /al:alarms {

        tailf:action debug-cmd {
            description "Send debug command to the Alarm Manager";
            tailf:info "Send debug command to the Alarm Manager";

            tailf:actionpoint debug-cmd-point;

            input {
                leaf cmd {
                    type string;
                    default "help";
                }
                leaf param {
                    type string;
                    default "";
                }
            }
            output {
                leaf result {
                    type string;
                    default "";
                }
            }
        }
    }
}
