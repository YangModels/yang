module cisco-svo-common-sync-grp {
    yang-version 1.1;
    namespace "http://cisco.com/yang/svo/common-sync-grp";
    prefix "ccsync";

    import ietf-yang-types { prefix yang; }
    import org-openroadm-interfaces { prefix or-if; revision-date 2018-09-28; }
    import cisco-svo-common-types { prefix cct; }
    import cisco-svo-common-equipment-types { prefix ccet; }
    import cisco-svo-common-sync-types { prefix synct; }
    import cisco-svo-common-base-opt-grp { prefix ccbog; }
    import cisco-ncs2k-equipment-types { prefix cet; }
    
    organization
        "Cisco Systems, Inc.";

    contact
        "Cisco Systems, Inc. Customer Service Postal: 170 West Tasman
        Drive San Jose, CA 95134 Tel: +1 800 553-NETS E-mail: cs-yang@cisco.com";

    description " Cisco Common Sync Interface, used inside both, SVO and NCS2K yang models.";

  revision 2021-12-25 {
  	description "Model version for SVO Release 12.3.0";
  	reference cisco-svo-common-sync-grp.yang;
  }
  
    revision 2020-12-04 { 
       description "Model version for SVO Release 12.1.0 "; 
       reference cisco-svo-common-sync-grp.yang; 
    }
 

    grouping timing-standard-grp {
        description "Timing - Standard grouping";
      leaf  current-timing-standard {
        type identityref {
          base ccet:tdm-terminology-type;
        }
        default 'ccet:ansi';
        config true;
        description "Timing Standard, ANSI or ETSI. In case of ETSI NE this elemnt is not present";
      }
    }

    grouping res-quality-level-ansi-grp {
      description "Res Quality Levell (ANSI) grouping";
      leaf  res-quality-level {
        type synct:res-quality-level-t;
        default same-As-DUS;
        config true;
        description "Reserved for Network Synchronization Quality Level.
          In case of Etsi this element is not present and the associated fixed value within the NE is above G811";
      }
    }

    grouping sync-config-grp {
        description "Timing - Sync Config grouping";
      
      container sync-config {
        description "Timing - sync-config container";

        leaf  timing-mode {
          type synct:timing-mode-t;
          default external;
          config true;
          description "Timing Mode (seconds)";
        }

        leaf  ssm-message-set {
          type synct:ssm-generation-t;
          default generation-1;
          config true;
          description "Synchronization Status Message Set Generation";
        }

        uses res-quality-level-ansi-grp  {
          when "(../../../chassis-type = 'cet:NCS2006-ANSI' or ../../../chassis-type = 'cet:NCS2015-ANSI') and 
                (../current-timing-standard = 'ccet:ansi' or not(../current-timing-standard))";
        }

        leaf  reversion-mode {
          type synct:reversion-mode-t;
          default non-revertive-behaviour;
          config true;
          description "Revertive Behaviour";
        }

        leaf  reversion-time {
          type synct:reversion-time-t;
          units "second";
          default NA;
          config true;
          description "Revertive time";
        }
      }
    }

    grouping synch-reference-interface-grp {
      description "Timing - Sync Reference Interface grouping";
      container interface {
        description "Timing - Sync Reference Interface container";
        
        leaf name {
          type string;
          config true;
          description "The name of the interface.";
        }
        leaf type {
          type identityref {
            base or-if:interface-type;
          }
          config true;
          description "The type of the interface.";
        }
      }
    }

    grouping synch-reference-source-bits-grp {
      description "Timing - Sync Reference source Bits grouping";
      leaf source-type {
        type synct:synch-reference-source-t;
        default none;
        config true;
        description "Source Reference Type";
      }
      uses synch-reference-interface-grp  {
        when "source-type = 'interface'";
      }
    }

    grouping primary-bits-grp {
      description "Timing - Primary source grouping";
      container primary-source {
        description "Timing - Primary source container";
        uses synch-reference-source-bits-grp;
      }
    }

    grouping secondary-bits-grp {
      description "Timing - secondary source grouping";
      container secondary-source {
        description "Timing - secondary source container";
        uses synch-reference-source-bits-grp;
        // Check that primary and secondary if interface must be different
      }
    }

    grouping tertiary-bits-grp {
      description "Timing - tertiary source grouping";
      container tertiary-source {
        description "Timing - tertiary source container";
        uses synch-reference-source-bits-grp;
      }
    }

    grouping sync-refs-bits-grp {
      description "Timing - sources (primary/secondary/tertiary) grouping";
      uses primary-bits-grp;
      uses secondary-bits-grp;
      uses tertiary-bits-grp;
    }

    grouping synch-reference-source-ne-grp {
      description "Timing - source reference grouping for ne section";
      leaf source-type {
        type synct:synch-reference-source-t;
        default internal-clock;
        config true;
        description "Timing - source reference type";
      }
      uses synch-reference-interface-grp  {
        when "source-type = 'interface'";
      }
    }

    grouping primary-ne-grp {
      description "Timing - source primary grouping for ne section";
      container primary-source {
        description "Timing - source primary container for ne section";
        uses synch-reference-source-ne-grp;
      }
    }

    grouping secondary-ne-grp {
      description "Timing - source secondary grouping for ne section";
      container secondary-source {
        description "Timing - source secondary container for ne section";
        uses synch-reference-source-ne-grp;
      }
    }

    grouping tertiary-ne-grp {
      description "Timing - source tertiary grouping for ne section";
      container tertiary-source {
        description "Timing - source tertiary container for ne section";
        uses synch-reference-source-ne-grp;
      }
    }

    grouping sync-refs-ne-grp {
      description "Timing - sources grouping for ne section";
      uses primary-ne-grp;
      uses secondary-ne-grp;
      uses tertiary-ne-grp;
    }

    grouping ne-reference-grp {
      description "Timing - Sync Ne Reference grouping";
      
      container ne-reference {
        description "Timing - Sync Ne Reference conatiner";
        uses sync-refs-ne-grp;
      }
    }

    grouping bits-1-out-grp {
        description "Timing - Sync Bits 1 Out grouping";
      
      container bits-1-out {
        description "Timing - Sync Bits 1 Out container";
        uses sync-refs-bits-grp;
      }
    }

    grouping bits-2-out-grp {
      description "Timing - Sync Bits 2 Out grouping";
      
      container bits-2-out {
        description "Timing - Sync Bits 2 Out container";
        uses sync-refs-bits-grp;
      }
    }

    grouping refs-grp {
      description "Timing - refs grouping";
      container timing-references {
        description "Timing - refs container";
        uses ne-reference-grp;
        uses bits-1-out-grp;
        uses bits-2-out-grp;
      }
    }

    grouping timing-general-grp {      
      description "Timing General grouping";
      container general {
        description "Timing General";
        uses timing-standard-grp  {
          when "../../chassis-type = 'cet:NCS2015-ANSI' or ../../chassis-type = 'cet:NCS2006-ANSI'";
        }
        uses sync-config-grp;
        uses refs-grp;
      }
    }

    grouping synch-reference-source-grp {
      description "Synch Reference source grouping";
      leaf source-type {
        type synct:synch-reference-source-t;
        mandatory true;
        description "Synch Reference source Type";
      }
      uses synch-reference-interface-grp  {
        when "source-type = 'interface'";
      }
    }

    grouping timing-actions-grp {
      description "Timing Action group";
      container commands {
        description "Timing Action commands container";

        action switch-reference-source {
          description "Action to set switch source mode of Clock reference";

          input {
            leaf reference-clock {
              type synct:reference-clock-t;
              mandatory true;
              description "Refence Clock Type (NE, Bits 1, Bits 2)";
            }

            leaf synch-switch-type {
              type synct:synch-switch-type-t;
              mandatory true;
              description "Synch Switch Type";
            }

            uses synch-reference-source-grp;
          }

          output {
            uses ccbog:rpc-status;
          }
        }

        action release-reference-source {
          description "Action to release switch source mode of Clock reference";

          input {
            leaf reference-clock {
              type synct:reference-clock-t;
              mandatory true;
              description "Refence Clock Type (NE, Bits 1, Bits 2)";
            }
          }

          output {
            uses ccbog:rpc-status;
          }
        }

        action on-demand-report {
            description "Action to acquire Synchronization Source Report";

            output {
              uses timing-report-response-grp;
            }
          }
      }
    }

    grouping reference-info-list-grp {
        description "Reference info list group";
        container reference-info-list {
            description "Reference info list container";
            list reference-info {
               description "Reference info list";
                leaf reference-number {
                    type uint16;
                    description "Reference number";
                }
                leaf admin-status {
                    type cct:admin-state-t;
                    description "Admin status";
                }
                leaf is-protect {
                    type boolean;
                    description "Is protect";
                }
                leaf stable-time {
                    type yang:date-and-time;
                    description "Stable time";
                }
                leaf current-selected {
                    type boolean;
                    description "Current selected";
                }
                leaf ssm-on {
                    type boolean;
                    description "Ssm on";
                }
                leaf ssm-quality {
                    type cct:clock-source-quality-level-t;
                    description "Ssm quality";
                }
                leaf reference-condition {
                    type synct:reference-condition-t;
                    description "Reference condition";
                }
                leaf is-ssm-valid {
                    type boolean;
                    description "Ssm validity";
                }
                leaf ssm-stable-time {
                    type yang:date-and-time;
                    description "Ssm stable time";
                }
                leaf timing-protocol {
                    type synct:timing-protocol-t;
                    description "Timing protocol";
                }
                uses synch-reference-source-grp;
            }
        }
    }

    grouping on-demand-report-list {
        description "Timing - On Demand report list group";
        container on-demand-reports {
           description "Timing - On Demand report list container";
            list on-demand-report {
                description "Timing - On Demand report list";
                leaf reference-clock {
                    type synct:reference-clock-t;
                    description "Reference Tyep (NE, Bits 1, Bits 2";
                }
                leaf timing-mode {
                    type synct:timing-mode-t;
                    description "Ting Mode";
                }
                leaf timing-state {
                    type synct:timing-state-t;
                    description "Timing State";
                }
                leaf ts-stable-time {
                    type yang:date-and-time;
                    description "Stable Time";
                }
                leaf switch-type {
                    type synct:synch-switch-type-t;
                    description "Switch type";
                }
                uses reference-info-list-grp;
            }
        }
    }

    grouping timing-report-response-grp {
      description "Timing - Report Response group";
      container timing-report-response {
        description "Timing - Report Response container";
        uses ccbog:rpc-status;
        uses on-demand-report-list;
      }
    }

    grouping facility-type-grp {
      description "Timing - Bits Facility Type grouping";
      
      leaf facility-type {
        type synct:bits-facility-t;
        config true;
        description "Bits Facility Type";
      }
    }

    grouping bit-state-grp {
      description "Timing - Bit State grouping";
      
      leaf bit-state {
        type cct:admin-state-t;
        config true;
        description "Bit State";
      }
    }

    grouping coding-grp {
      description "Timing - Coding grouping";
      
      leaf coding-type {
        type synct:line-coding-t;
        config true;
        description "Coding Type";
      }
    }

    grouping framing-grp {
      description "Timing - Framing grouping";
      
      leaf framing-type {
        type synct:line-type-t;
        config true;
        description "Framing Type";
      }
    }

    grouping bits-ssm-grp {
      description "Timing - Bits sync msg enabled / assumed quality grouping";
      
      leaf sync-messaging {
        type boolean;
        config true;
        description "Synch Message Enabled";
      }

      leaf admin-ssm-bits {
        type cct:clock-source-quality-level-t;
        config true;
        description "Assumed Quality";
      }
    }

    grouping ais-threshold-grp {
      description "Timing - Ais Threshold grouping";

      leaf ais-threshold {
        type cct:clock-source-quality-level-t;
        config true;
        description "AIS Threshold";
      }
    }

    grouping cable-type-grp {
      description "Timing - Cable Type grouping";
      
      leaf cable-type {
        type synct:cable-type-t;
        config true;
        description "Cable Type";
      }
    }

    grouping sa-bit-grp {
      description "Timing - Sa Bit grouping";
      
      leaf sa-bit {
        type synct:sa-bit-t;
        config true;
        description "Sa Bit";
      }
    }

    grouping bits-lbo-grp {
      description "Timing - Sa Bit grouping";
      
      leaf lbo {
        type synct:lbo-t;
        config true;
        description "Bits LBO";
      }
    }

    grouping facility-bits-common-grp {
      description "Timing - Facility Bits Common grouping";

      uses sa-bit-grp;
      uses cable-type-grp;
    }

    grouping facility-bits-in-grp {
      description "Timing - Facility Bits In grouping";

      container bits-in {
        description "Timing - Facility Bits In container";
        uses facility-type-grp;
        uses bit-state-grp;
        uses coding-grp;
        uses framing-grp;
        uses bits-ssm-grp;
      }
    }

    grouping facility-bits-out-grp {
      description "Timing - Facility Bits Out grouping";

      container bits-out {
        description "Timing - Facility Bits Out container";
        uses facility-type-grp;
        uses bit-state-grp;
        uses coding-grp;
        uses framing-grp;
        uses ais-threshold-grp;
        uses bits-lbo-grp {
          when "(../../../../chassis-type = 'cet:NCS2006-ANSI' or ../../../../chassis-type = 'cet:NCS2015-ANSI')
                and (../../../general/current-timing-standard = 'ccet:ansi' or not(../../../general/current-timing-standard))";
        }
      }
    }

    grouping timing-facility-bits-elem-grp {
      description "Timing - Facility Bits Elem grouping";

      uses facility-bits-common-grp {
        when "((../../../chassis-type = 'cet:NCS2006-ANSI' or ../../../chassis-type = 'cet:NCS2015-ANSI') and
               (../../general/current-timing-standard = 'ccet:etsi')
              ) or
              (../../../chassis-type = 'cet:NCS2006-ETSI' or ../../../chassis-type = 'cet:NCS2015-ETSI')";
      }
      uses facility-bits-in-grp;
      uses facility-bits-out-grp;
    }

    grouping timing-facility-bits-grp {
      description "Timing - Facility Bits grouping";

      container bits-facilities {
        description "Bits Facilities grouping";
        container bits-one {
          description "Bits One container";
          uses timing-facility-bits-elem-grp;
        }
        container bits-two {
          description "Bits Two container";
          uses timing-facility-bits-elem-grp;
        }
      }
    }

    grouping timing-grp {
      description "Timing grouping";
      container timing {
        description "Timing";
        uses timing-general-grp;
        uses timing-facility-bits-grp;
        uses timing-actions-grp ;
      }
   }
}
