module cisco-svo-aaa-compl {
    yang-version 1.1;
    namespace "http://cisco.com/yang/svo/aaa-compl";
    prefix svo-a2a;

    import cisco-svo-aaa { prefix aaa; }
    import tailf-common { prefix tailf; }

    tailf:export none;

    organization
        "Cisco Systems, Inc.";

    contact
        "Cisco Systems, Inc. Customer Service Postal: 170 West Tasman
        Drive San Jose, CA 95134 Tel: +1 800 553-NETS E-mail: cs-yang@cisco.com";

    description
        "YANG definition for SVO users account";

    revision 2020-12-04 { 
       description "Model version for SVO Release 12.1.0 "; 
       reference cisco-svo-aaa-compl.yang; 
    }


    container auth-compl {
        uses aaa:users-compl;  
    }
    
    container auth-compl-oper {
        container users {
            list user {
                key user-name;
                max-elements 500;
                leaf user-name {
                    type string;
                    config false;
                }
                uses aaa:user-complementary-grp-oper;
            }
        }        
        config false;
        tailf:cdb-oper {
            tailf:persistent true;
        } 
    }
}
