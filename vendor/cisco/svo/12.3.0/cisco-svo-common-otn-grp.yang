module cisco-svo-common-otn-grp {
  yang-version 1.1;
  namespace "http://cisco.com/yang/svo/common-otn-grp";
  prefix ccotng;
  
  import org-openroadm-otn-common { prefix org-openroadm-otn-common; revision-date 2018-09-28; }
  import org-openroadm-otn-common-types { prefix org-openroadm-otn-common-types; revision-date 2018-09-28; }
  import cisco-svo-common-otn-types { prefix ccotnt; }
  import cisco-svo-common-types { prefix ct; }
	  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO OTN Config.";

  revision 2021-12-25 {
  	description "Model version for SVO Release 12.3.0";
  	reference cisco-svo-common-otn-grp.yang;
  }
  
    revision 2020-12-04 { 
       description "Model version for SVO Release 12.1.0 "; 
       reference cisco-svo-common-otn-grp.yang; 
    }
 

  grouping legacy-trail-trace {
    description "Optical Transport Network (OTN) old G.709 TTI config and oper data management";
    leaf tx-tti {
      type string {
        length "0 .. 64";
      }
      description
        "The provisioned 64 character transmit TTI. Implementations is supporting cards compliant to the old ITU-T G.709";
    }

    leaf expected-tti {
      type string {
        length "0 .. 64";
      }
      description
        "The provisioned 64 character expected TTI, to be compared with accepted TTI";
    }
    leaf tim-act-enabled {
      type boolean;
      default "false";
      description
        "Enables TTI Mismatch consequent actions.";
    }
    leaf tim-detect-mode {
      type enumeration {
        enum "Disabled" {
          description
            "TTI is ignored";
        }
        enum "Enabled" {
          description
            "Expected TTI is compared to the Accepted TTI";
        }
      }
      default "Disabled";
    }
  }

  grouping tti-cfg-grp {
    uses org-openroadm-otn-common:trail-trace;
  }

  grouping legacy-tti-cfg-grp {
    uses legacy-trail-trace;
  }
  
  grouping sync-cfg-grp {
    description "Optical Transport Network (OTN) Parameters";

    leaf sync-msg-in {
      type boolean;
      description "OTN Sync MSG IN";
    }
    leaf admin-ssm-in {
      type enumeration {
        enum "G811";
        enum "STU";
        enum "G812T";
        enum "G812L";
        enum "SETS";
        enum "DUS";
        enum "PRS";
        enum "ST2";
        enum "ST3E";
        enum "ST3";
        enum "SMC";
        enum "ST4";
        enum "RES";
        enum "STU_SDH";
        enum "DUS_SDH";
        enum "SSM_FAILED";
        enum "RES_SDH";
        enum "TNC";
      }
      description "
      Synchronization byte (ssm) values, identify the 
      synchronization quality G811 = highest DUS = lowest.";
    }
  }


  grouping prbs-cfg {
    leaf generator-pattern {
     type ccotnt:prbs-pattern;
     default PRBS_NONE;
     description "Activate prbs pattern generator";
    }
  }

  grouping squelch-odu {
     leaf squelch-mode {
      type ct:squelch-odu-t;
      default "Ais";
    }

    leaf squelch-hold-off-time {
      type ct:squelch-hold-off-time-t;
      default "Disable";
    }
  }

  grouping parent-odu-allocation {
    description
      "parent odu allocation group";
    container parent-odu-allocation {
      config false;
      presence "Explicit assignment of parent ODU trib-slot and trib-port allocation. ";
      description
        "parent odu allocation";
      leaf trib-port-number {
        type uint16 {
          range "1 .. 80";
        }
        mandatory true;
        description
          "Assigned tributary port number in parent OPU";
      }
      choice trib-slots-choice {
        description
          "trib slot selection";
        case opu {
          leaf-list trib-slots {
            type uint16 {
              range "1 .. 80";
            }
            min-elements 1;
            max-elements 80;
            description
              "Assigned trib slots occupied in parent OPU MSI";
          }
        }
        case opucn {
          leaf-list opucn-trib-slots {
            type org-openroadm-otn-common-types:opucn-trib-slot-def;
            description
              "Specify the list of OPUCn 5G tributary slots in the form of
               TS #A.B (G.709 Figure 20-9) in the case of provisioning the low
                order ODUk to the parent server ODUCn";
          }
        }
      }
    }
  }

}
