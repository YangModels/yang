module cisco-svo-common-types {
    yang-version 1.1;
    namespace "http://cisco.com/yang/svo/common-types";
    prefix cct;

    import tailf-common { prefix tailf; }

    organization
        "Cisco Systems, Inc.";

    contact
        "Cisco Systems, Inc.
     Customer Service

     Postal: 170 West Tasman Drive
     San Jose, CA 95134

     Tel: +1 800 553-NETS

     E-mail: cs-yang@cisco.com";

    description "
    Cisco Common Types, used inside both,
    the equipment and the network modules and them
    submodules.";

	revision 2021-12-25 {
		description "Model version for SVO Release 12.3.0 
			obsolete : oxc-role-t
		";
		reference cisco-svo-common-types.yang;
	}

   revision 2021-04-16 { 
      description "Model version for SVO Release 12.2.0 "; 
      reference cisco-svo-common-types.yang; 
   }
 

    revision 2020-12-04 { 
       description "Model version for SVO Release 12.1.0 "; 
       reference cisco-svo-common-types.yang; 
    }

	
    typedef host-platform {
      description "Describes the possible platforms able to run an SVO application";
      type enumeration {
	enum "svo-card" {
	  description "The NCS2K-SVO-K9 card";
	  value 1;
	}
	enum "external-server" {
	  description "Any HW running a Linux OS";
	  value 2;
        }
      }
    }

    typedef overclock-t {
        type enumeration {
            enum "On" {
                description "Over-clock On";
            }
            enum "Off" {
                description "Over-clock Off";
            }
            enum "NA" {
                description "Over-clock Status Not Available";
            }
        }
        description "Over-clock Type";
    }

    typedef na-t {
        type enumeration {
            enum "NA" {
                description "Not Available";
            }
        }
        description "
      Typedef to be used when an operational
      value is not available.";
    }

    typedef hhmm-t {
        type string {
            pattern '\d{2}:\d{2}';
        }
        description "Common Hours/Minute in the HH:mm format";
    }

    typedef hhmmss-t {
        type string {
            pattern '\d{2}:\d{2}:\d{2}';
        }
        description "Common Hours/Minute in the HH:mm:ss format";
    }

    typedef bw-t {
        type decimal64 {
            fraction-digits 2;
            range "0..4800.00";
        }
        units Mbps;
        description "Bandwidth expressed in Mbps";
    }

    typedef date-time-t {
        type string {
            pattern '\d{4}-\d{2}-\d{2}T\d{2}:\d{2}:\d{2}';
        }
        description "
      Date Time in milliseconds, using the pattern
      yyyy-MM-dd'T'HH:mm:ss";
    }

    typedef cd-working-range-t {
        type union {
            type enumeration {
                enum "NA" {
                    description "Not Available";
                }
            }
            type int32 {
                range "-300000..300000";
            }
        }
        description "
      Interface Dispersion Compensation range
      in pSec/nm, this can be negative or positive";
    }

    typedef tx-power-t {
        type decimal64 {
            fraction-digits 2;
            range "-10..30";
        }
        description "Interface Transmit power in dB";
    }

    typedef termination-mode-t {
        type enumeration {
            enum "Transparent" {
                description "Transparent Termination Mode";
            }
            enum "Section" {
                description "Section Termination Mode";
            }
            enum "Line" {
                description "Line Termination Mode";
            }
        }
        description "Line termination mode ";
    }

    typedef video-type-t {
        type enumeration {
            enum "None" {
                description "No Video Type Set.";
            }
            enum "PAL" {
                description "PAL Video Type";
            }
            enum "NTSC" {
                description "NTSC Video Type";
            }
        }
        description "Video Type Format (PAL, NTSC)";
    }

    typedef admin-state-t {
        type enumeration {
          enum In-Service;
          enum Out-Of-Service;
          enum Maintenance;
          enum Automatic-In-Service;
        }
        description "Admin State Type";
      }
    
    typedef reach-t {
        type enumeration {
            enum "NA" {
                description "NA Reach Type";
            }
            enum "Auto Provision" {
                description "Auto Provision Reach Type";
            }
            enum "SR";
            enum "SR 1";
            enum "SR 2";
            enum "SR 3";
            enum "SR 5";
            enum "IR 1";
            enum "IR 2";
            enum "IR 3";
            enum "IR 5";
            enum "LR";
            enum "LR 1";
            enum "LR 2";
            enum "LR 3";
            enum "LR 5";
            enum "P1L1";
            enum "V2";
            enum "V3";
            enum "I1";
            enum "I2";
            enum "I3";
            enum "I5";
            enum "S1";
            enum "S2";
            enum "S3";
            enum "S5";
            enum "L1";
            enum "L2";
            enum "L3";
            enum "L5";
            enum "SX";
            enum "LX";
            enum "CX";
            enum "T";
            enum "DX";
            enum "HX";
            enum "ZX";
            enum "VX";
            enum "EW";
            enum "LW";
            enum "SW";
            enum "LRM";
            enum "ER";
            enum "SM";
            enum "MM";
            enum "MX";
            enum "ZR";
            enum "CWDM";
            enum "DWDM";
            enum "VSR";
            enum "CWDM40km";
            enum "ULH";
            enum "P1S1 1D1";
            enum "P1L1 1D2";
            enum "P1I1 2D1";
            enum "P1S1 2D1";
            enum "P1L1 2D2";
            enum "CX1";
            enum "TEN_GE_ER";
            enum "TEN_GE_SR";
            enum "TEN_GE_LR";
            enum "TEN_GE_LRM";
            enum "TEN_GE_ZR";
            enum "GE_EX";
            enum "GE_BX";
            enum "FE_BX";
            enum "FX";
            enum "LX_10";
            enum "SC";
            enum "100GBASE-SR10";
            enum "100GBASE-LR4";
            enum "40GBASE-FR";
            enum "40GBASE-LR4";
            enum "VSR2000-3R2";
            enum "C4S1-2D1";
            enum "4I1-9D1F";
            enum "SR-MM";
            enum "P1S1 2D2B";
            enum "10GFC-SW";
            enum "10GFC-LW";
            enum "10GFC-EW";
            enum "10GFC-ZW";
            enum "8GFC-SW";
            enum "8GFC-LW";
            enum "40GBASE-SR4";
            enum "100GBASE-SR4";
            enum "16GFC-SW";
            enum "MSA-CWDM4";
            enum "16GFC-LW";
            enum "MSA-CWDM4-S";
            enum "FR-S";
            enum "DR4-S";
            enum "LR8-S";
            enum "FR4-S";
            enum "AOC";
	    enum "CPAK-FR";
	    enum "40GBASE-SRBD";
	    enum "100GBASE-SRBD"; 
        }
        description "Interfaces Reach description: look at the data-sheet";
    }

    typedef squelch-ethernet-t {
        type enumeration {
            enum "Disable" {    
                value 0;
                description "No Squelch";
            }
            enum "Squelch" {
                value 2;
                description "Turn off the Client interface";
            }
            enum "LF" {
                value 4;
                description "Local Fault";
            }
        }
        description "Squelch of client interface upon Trunk LOS";
    }

    typedef squelch-odu-t {
        type enumeration {
            enum "Ais" {
                value 1;
                description "Insert AIS to the Client";
            }            

            enum "Squelch" {
                value 2;
                description "Turn off the Client interface";
            }
        }
        description "Squelch of client interface upon Trunk LOS";
    }

    typedef squelch-sonet-sdh-t {
        type enumeration {
            enum "None" {
                value 0;
                description "No Squelch";
            }

            enum "Ais" {
                value 1;
                description "Insert AIS to the Client";
            }

            enum "Squelch" {
                value 2;
                description "Turn off the Client interface";
            }
        }
        description "Squelch of client interface upon Trunk LOS";
    }

    typedef squelch-hold-off-time-t {
        type enumeration {
            enum "Disable" {                
                description "No Squelch hold off time";
            }
            enum "50-ms" {
                description "50 ms";
            }
            enum "100-ms" {
                description "100 ms";
            }
            enum "250-ms" {
                description "250 ms";
            }
            enum "500-ms" {
                description "500 ms";
            }
        }
        description "Squelch of client interface upon Trunk LOS";
    }

	typedef protection-level-t {
	    type enumeration {
          enum "line" {
            value 1;
          }
          enum "path" {
            value 2;
          }
        }	

        description
          "Designates protection group as Line or Path";
	}

	typedef switching-direction-t {
        type enumeration {
            enum "unidirectional-switching" {
              value 1;
            }
            enum "bidirectional-switching" {
              value 2;
            }
          }
          description "Bidirectional refers to APS signaling enabled (G.873.1 Table 7-1 Table 8-1).";
	}

	typedef protection-mode-t {
        type enumeration {
            enum "SNC/Ne" {
              value 1;
              description "applicable to Odu 1 +1 line or path switching";
            }
            enum "SNC/Ns" {
              value 2;
              description "applicable to Odu 1 +1 line or path switching";
            }
            enum "SNC/S" {
              value 3;
              description "applicable to Odu 1 +1 line or path switching";
            }
            enum "SNC/I" {
              value 4;
              description "applicable to Odu 1 +1 line switching only";
            }
            enum "CL-SNCG/I" {
              value 5;
              description "applicable to Odu 1 +1 line switching only";
            }
          }
          description "Protection mode";
	}
	
	typedef protection-level-trigger-t {
        type enumeration {
            enum "OTUk/ODUkA-SSF-SSD" {
                value 1;
                description "applicable to SNC/I";
            }
            enum "ODUkP/ODUjA-SSF-SSD" {
                value 2;
                description "applicable to CL-SNCG/I";
            }
            enum "ODUP-SSF-SSD" {
                value 3;
                description "applicable to SNC/Ne";
            }
            enum "ODUT1" {
                value 4;
                description "applicable to SNC/Ns or SNC/S";
            }
            enum "ODUT2" {
                value 5;
                description "applicable to SNC/Ns or SNC/S";
            }
            enum "ODUT3" {
                value 6;
                description "applicable to SNC/Ns or SNC/S";
            }
            enum "ODUT4" {
                value 7;
                description "applicable to SNC/Ns or SNC/S";
            }
            enum "ODUT5" {
                value 8;
                description "applicable to SNC/Ns or SNC/S";
            }
            enum "ODUT6" {
                value 9;
                description "applicable to SNC/Ns or SNC/S";
            }
        }
        description
                "Indicates switch trigger.";
    }

	typedef wait-restore-timer-t {
        type uint8 {
          range "1..12";
        }
        units "minutes";
        default "5";
        description
          "Wait to restore time in minutes";
	}
	
	typedef reversion-pulse-width-t {
        type uint8 {
        	range "10..200";
        }
	    units "seconds";
	    description "reversion pulse width in seconds";
	}
	
    typedef holdoff-timer-t {
        type uint8 {
          range "0 | 20 | 100";
        }
        units "milliseconds";
        default "0";
        description
          "switch hold-off time in milliseconds";
      }
    
    typedef holdoff-multiplier-t {
        type uint8 {
          range "1 .. 100";
        }
        default "1";
        description
          "switch holdoff time multiplier x100 milliseconds";
     }
	
	typedef switch-status-t {
		type enumeration {
			enum "None" {
				description "No status";
			}
			enum "Locked-Out" {
				description "Protection is locked out";
			}
			enum "Switched-Force" {
				description "Protection switch has been forced";
			}
			enum "Switched-Manual" {
				description "Protection manually operated";
			}
			enum "Switched-Auto" {
				description "Protection switched automatically";
			}			
			enum "Released" {
				description "Released any previous operation";
			}
		}
		description "Current status of the protection switch";
	}
	
	typedef switch-action-t {
        type enumeration {
            enum "Lock-Out" {
                value 1;
            }
            enum "Force-Switch" {
                value 2;
            }
            enum "Manual-Switch" {
                value 3;
            }
            enum "Release" {
                value 4;
            }
        }
        description "Command to control the protection switch";

    }
	
    typedef direction {
        type enumeration {
          enum "TX" {
            value 1;
            description "Transmit port";
          }
          enum "RX" {
            value 2;
            description "Receive port";
          }
          enum "Bidirectional" {
            value 3;
            description "Bidirectional port";
          }
          enum "NotApplicable" {
            value 4;
            description "Port has o direction";
          }
        }
        description "Optical Direction";
      }

    typedef oxc-role-t {
        status obsolete;
        type enumeration {
            enum "AddDrop" {
                description "Port can be used a local ingress or egress point of an Optical X-Connection";
            }
            enum "Internal" {
                description "Port cannot be an end-point for an Optical X-Connection";
            }
            enum "Line" {
                description "Port defines a Degree and hence it faces the transmission line";
            }

        }
        description "Port role for a Service of type Optical X-Connection";
    }

    typedef amplifierControlMode-t {
        type enumeration {
            enum "Channel Power" {
                description "Amplifier will maintain the request power per channel setpoint";
            }
            enum "Total Power"{
                description "Amplifier will maintain the requested total power regardless the number of channel";
            }
            enum "Optimized"{
                description "Identical to 'Channel Power', but setpoint is automatically optimised by the node";
            }
            enum "Fixed Gain"{
                description "Amplifier will maintain the reuested gain regardless of input power level";
            }
            enum "Start and Hold"{
                description "Amplifier will evaluate the gain at first channel activation (based on the requested channel power)
            and will then keep the evaluated gain regardless of input power variation";
            }
        }
        description "Amplifier control mode strategy";
    }

    typedef amplifierStatus-t {
        type enumeration {
            enum "OFF - Not In Service"{
                description "Either input or output port is not In-Service status";
            }
            enum "OFF - ALS Safety"{
                description "Safety loop is not satisfied and amplifier is kept off to prevent hazardous situations";
            }
            enum "OFF - No Input Power"{
                description "Safety loop is satisfied, but input power is missing";
            }
            enum "OFF - OSRI"{
                description "User has requested to shut down the amplifier";
            }
            enum "OFF - Waiting To Start"{
                description "Amplifier is scheduled to start";
            }            
            enum "APR"{
                description "Amplifier restart pulse";
            }
            enum "ON - Operative"{
                description "Amplifier in normal working condition";
            }
        }
        description "Reported Amplifier Status; provides the amplifier current status and the reason for the current status";
    }

    typedef voaWorkingMode-t {
        type enumeration {
            enum "Constant Power"{
                description "VOA is controlled with an output power setpoint";
            }
            enum "Constant Attenuation"{
                description "VOA is controlled with an attenuation setpoint";
            }
            enum "AVS"{
                description "Automatic VOA Shutdown";
            }
        }
        description "VOA working mode";
    }

    typedef ampli-role-t {
        type enumeration {
            enum "Preamplifier"{
                description "For Amplifier start-up only input power is checked, no other safety check performed";
            }
            enum "Booster"{
                description "Amplifier is facing the line hence ALS safety is enabled";
            }
        }
        description "Role of amplifier";
    }

    typedef gain-range-t {
        type enumeration {
            enum "Gain Range 1"{
                description "Low Gain Range";
            }
            enum "Gain Range 2"{
                description "High Gain Range";
            }
            enum "No Gain Range"{
                description "Gain Range is not defined/not applicable";
            }
        }
        description "Gain range of the amplifier";
    }

    typedef raman-pumping-scheme-t {
    	type enumeration {
    		enum "Counter-Propagating" {
    			description "Pumps power is sent into the transmission fibre from the receive end of the span, 
    				counter-propagating to optical channels flow";
    		}
    		enum "Co-Propagating" {
    			description "Pumps power is sent into the transmission fibre from the transmit end of the span, 
    				co-propagating with optical channels flow";
    		}
    	}
    	description "Raman amplifier pumping scheme";
    }
    
	typedef raman-calibration-type-t {
		type enumeration {
			enum "Manual" {
				description "Manual Raman calibration; need user intervention and specific instruments to be completed";
			}
			enum "Automatic" {
				description "Automatic Raman calibration; no user intervention is required; calibration is run 
				automatically whenever needed";
			}
			enum "No-Calibration" {
				description "Raman Calibration is disabled, the cards will be controlled directly with pumps setpoint 
				configuration (if supported)";
			}
		}
		description "Raman amplifier calibration type";
	
	}

	typedef raman-calibration-director-t {
		type enumeration {
			enum "Device" {
				description "Automatic Raman calibration is managed by the device itself autonomously";
			}
			enum "Orchestrator" {
				description "Automatic Raman calibration is managed by the Node Orchestrator";
			}
		}
		description "Raman amplifier calibration type";
	
	}


	typedef raman-automatic-calib-status-t {
		type enumeration {
			enum "Not Scheduled" {
				description "Raman automatic calibration still not scheduled - Raman Amplifier is off";
			}
			enum "Invalid" {
				description "Raman automatic calibration reports invalid data";
			}		
			enum "Pending" {
				description "Raman automatic calibration is scheduled and pending";
			}
			enum "Running On User Request" {
				description "Raman automatic calibration is running on user request";
			}			
			enum "Running" {
				description "Raman automatic calibration is running automatically";
			}					
			enum "Failed" {
				description "Raman automatic calibration failed";
			}
			enum "Terminated" {
				description "Raman automatic calibration terminated - will be re-scheduled shortly";
			}			
			enum "Completed" {
				description "Raman automatic calibration complted";
			}			
		}
	}

	typedef raman-automatic-calib-pwr-src-t {
		type enumeration {
			enum "Broadband Optical Power" {
				description "Raman automatic calibration used broadband optical power, 
				typically ASE generated by an optical amplifier";
			}		
			enum "Active Optical Services" {
				description "Raman automatic calibration used the active services";
			}		
			enum "Active Optical Services (Unbalanced)" {
				description "Raman automatic calibration used the active services, 
				but they do not properly cover the whole C-Band spectrum";
			}	
		}
	}

	typedef raman-calib-result-t {
        type enumeration {
            enum "No Target Gain" {
                description
                  "Raman target gain is not configured";
            }
            enum "Not Enough Gain" {
                description
                  "Raman gain obtained from calibration is too low";
            }
            enum "Lower Than Target Gain" {
                description
                  "Raman gain obtained from calibration is below the target but still acceptable";
            } 
            enum "Lower Than Target Gain (Need Accept)" {
                description
                  "Raman gain obtained from calibration is below the target but might still be acceptable 
                	- user needs to accept the result";
            }
            enum "Lower Than Target Gain (Accepted)" {
                description
                  "Raman gain obtained from calibration is below the target and user acknowledged";
            }
            enum "Target Gain Reached" {
                description
                  "Target Raman gain is reachable";
            }
            enum "User Override" {
            	description
            		"User has overridden calibration result and using manually configured pumps setpoint";
            }
            enum "Higher Than Target Gain" {
                description
                  "Raman gain obtained from calibration is above the target but still acceptable";
            }
            enum "Too Much Gain" {
                description
                  "Raman gain obtained from calibration is too high";
            } 
        }
    }

    typedef raman-manual-calib-status-t {
        type enumeration {
            enum "Not Calibrated" {
                description
                  "Raman calibration never run";
            }
            enum "In Progress" {
                description
                  "Raman calibration is being run by user";
            }
            enum "Completed" {
                description
                  "Raman calibration completed";
            }
            enum "Using pumps-power-setpoint" {
                description
                  "Raman pumps are regulated as per user configuration";
            }
        }
    }
	
	typedef raman-pumps-debug-status-t {
		type enumeration {
			enum "Raman Pumps Off" {
				description "Raman pumps are off";
			}
			enum "Init In Progress" {
				description "Raman pumps are starting-up";
			}	
			enum "Raman Pumps Ready" {
				description "Raman pumps are ready to start-up";
			}
			enum "Raman Pumps APR" {
				description "Raman pumps are in low power eye-safe APR mode";
			}
			enum "Raman Pumps On" {
				description "Raman pumps are on";
			}
			enum "Internal Failure" {
				description "Raman card has an internal failure";
			}
			enum "High Back-Reflection" {
				description "Raman pumps are off due to excessive back-reflection";
			}
			enum "FPGA Failure" {
				description "Raman card has an internal FPGA failure";
			}
		}
	}
	
    typedef als-support-t {
        type enumeration {
            enum "None"{
                description "No safety feature supported";
            }
            enum "ALS"{
                description "Automatic Laser Shutdown is supported";
            }
            enum "OSRI"{
                description "Optical Safety Remote Interlock is supported";
            }
            enum "ALS-OSRI"{
                description "Automatic Laser Shutdown and Optical Safety Remote Interlock are supported";
            }
        }
        description "Safety feature supported by device";
    }


    typedef als-mode-t {
        type enumeration {
            enum "ALS-Disabled"{
                description "ALS does NOT shut down the amplifier upon LOS";
            }
            enum "Automatic Restart"{
                description "ALS will automatically restart the amplifier in case of LOS clear";
            }
            enum "Manual Restart"{
                description "ALS does NOT restart the laser to re-establish the transmission; the operator must manually request an amplifier restart";
            }
        }
        description "Automatic Laser Shutdown restart policy";
    }

    typedef als-status-t {
        type enumeration {
        enum "Shutdown"{
            description "Device is shut down due to safety concerns (e.g. fiber cut)";
        }
        enum "Working"{
            description "Device is working normally, all safety requirements are met";
        }
         }
        description "ALS reported status";
    }

    typedef recovery-pulse-interval-t {
        type uint32 {
            range "60..2000";
        }
        units "seconds";
        description "Timing in seconds in the range 60..2000";
    }

    typedef recovery-pulse-width-t {
        type decimal64 {
            fraction-digits 1;
            range "2..100";
        }
        units "seconds";
        description "Timing in seconds in the range 2..100";
    }

    typedef osri-mode-t {
        type enumeration {
            enum "OSRI-OFF"{
                description "Device can start normally";
            }
            enum "OSRI-ON"{
                description "Device is kept shut down";
            }
        }
        description "Optical Safety Remote Interlock; manual shut down of the device";
    }

    typedef active-channel-t {
        type union {
            type na-t;
            type uint8 {
                range "0..200";
            }
        }
        description "Number of channels active on a span - and on an amplifier ";
    }

	typedef unit-of-measure-t {
		type enumeration {
	 		enum "Logarithmic-dBm" {
				description "Logarithmic unit, dBm";
			}
			enum "Linear-mW" {
				description "Linear unit, mW";
			}
		}
		description "Unit of measure used for reported power levels";
	} 

	typedef pump-id-t {
		type uint32 {
			range "1..5";
		}
		description "Raman pump identifier, from 1 to 5";
	}

	typedef id-t {
		type uint32 {
		}
		description "Generic ordinal for list";
	} 

    typedef db-oper-t {
        type decimal64 {
            fraction-digits 2;
        }
        units "dB";
    }	

    typedef dbm-oper-t {
        type decimal64 {
            fraction-digits 2;
        }
        units "dBm";
    }	

    typedef psd-oper-t {
        type decimal64 {
            fraction-digits 2;
        }
        units "dBm/GHz";
    }

    typedef mw-oper-t {
        type decimal64 {
            fraction-digits 2;
        }
        units "mW";
    }

	typedef pwr-oper-t {
        type decimal64 {
            fraction-digits 2;
        }
        units "dbm or mW";
        description "Power level";
    }

    typedef gain-t {
        type decimal64 {
            fraction-digits 2;
            range "0..50";
        }
        units "dB";
        description "Gain";
    }

    typedef gain-threshold-t {
        type decimal64 {
            fraction-digits 2;
            range "-5..55";
        }
        units "dB";
        description "Gain Threshold";
    }

    typedef tilt-t {
        type decimal64 {
            fraction-digits 2;
            range "-5..5";
        }
        units "dB";
        description "Tilt";
    }

    typedef signal-output-power-t {
        type decimal64 {
            fraction-digits 2;
            range "-10..30";
        }
        units "dBm";
        description "Output Power provisioning ";
    }

    typedef channel-output-power-t {
        type decimal64 {
            fraction-digits 2;
            range "-30..10";
        }
        units "dBm";
        description "Channel power provisioning [50 GHz bandwidth]";
    }

    typedef power-spectral-density-t {
        type decimal64 {
            fraction-digits 2;
            range "-50..20";
        }
        units "dBm/GHz";
        description "Power Spectral Density";
    }

    typedef laser-bias-t {
        type decimal64 {
          fraction-digits 1;
          range "0..max";
        }
        description "Laser Bias Type.";
      }

    typedef dgd-t {
      type decimal64 {   // ps
        fraction-digits 2;
        range "0..max";
      }
      units "ps";
      description "Differential Group Delay.";
    }

    typedef osnr-t {
      type decimal64 {   // dB
        fraction-digits 2;
        range "-100..100";
      }
      units "dB";
      description "Optical Signal to Noise Ratio.";
    }

    typedef cd-t {
      type int32 {   // ps/nm
        range "-300000..300000";
      }
      units "ps/nm";
      description "Chromatic Dispersion.";
    }

    typedef sopmd-t {
      type decimal64 {   // ps^2
        fraction-digits 2;
        range "0..max";
      }
      units "ps^2";
      description "Second Order Polarization Mode Dispersion.";
    }

    typedef pcr-t {
      type decimal64 {   // 10*rad/s
        fraction-digits 2;
        range "min..max";
      }
      units "10*rad/s";
      description "Polarization Change Rate.";
    }

    typedef pdl-t {
      type decimal64 {   // 10*rad/s
        fraction-digits 2;
        range "min..max";
      }
      units "dB";
      description "Polarization Dependent Loss.";
    }
    
    typedef q-factor-t {
      type decimal64 {   
        fraction-digits 2;
      }
      units "dB";
      description "Quality Factor.";
    }
    
     typedef temp-t {
      type decimal64 {
            fraction-digits 2;
        }
      units "Celsius";
      description "Temperature";
    }
    
    typedef cfo-t {
      type int32 {   // ps/nm
        range "-300000..300000";
      }
      units "MHz";
      description "Central Frequency Offset";
    }
    
    typedef psd-threshold-t {
        type decimal64 {
            fraction-digits 2;
            range "-80..30";
        }
        units "dBm/GHz";
        description "Power Spectral Density threshold";
    }

    typedef laser-bias-threshold-t {
        type decimal64 {
            fraction-digits 1;
            range "0..100";
        }
        units "percentage";
        description "Power Spectral Density threshold";
    }

    typedef dbm-t {
        type decimal64 {
            fraction-digits 2;
            range "-71..30";
        }
        units "dBm";
        description "Power level";
    }

	typedef mw-t {
        type decimal64 {
            fraction-digits 2;
            range "0..1500";
        }
        units "mW";
        description "Power level";
    }

	typedef any-power-t {
        type decimal64 {
            fraction-digits 2;
            range "-71..1500";
        }
        units "dbm or mW";
        description "Power level";
    }

    typedef dbm-threshold-t {
        type decimal64 {
            fraction-digits 2;
            range "-71..35";
        }
        units "dBm";
        description "Power level threshold";
    }

    typedef any-threshold-t {
        type decimal64 {
            fraction-digits 2;
            range "-75..2000";
        }
        units "dBm or mW";
        description "Power level threshold";
    }

    typedef db-t {
        type decimal64 {
            fraction-digits 2;
            range "-71..30";
        }
        units "dB";
        description "Value in dB";
    }

    typedef attenuation-t {
        type decimal64 {
            fraction-digits 2;
            range "0..100";
        }
        units "dB";
        description "Attenuation value";
    }

    typedef attenuator-t {
        type decimal64 {
            fraction-digits 1;
            range "0..30";
        }
        units "dB";
        description "Attenuation value (attenuator) applied after the Amplifier ";
    }

    typedef insertion-loss-t {
       type decimal64 {
            fraction-digits 2;
            range "0..30";
        }
        units "dB";
        description "Insertion loss";
    }

    typedef enabling-status-t {
        type enumeration {
            enum "enabled"{
                description "The feature is enabled";
            }
            enum "disabled"{
                description "The feature is disabled";
            }
        }
        description "Enabling or Disabling a specific feature";
    }

    typedef length-km-t {
        type decimal64 {
            fraction-digits 2;
            range "0..1000";
        }
        units "km";
        description "Length expressed in km";
    }

    typedef pmd-coeff-t {
        type decimal64 {
            fraction-digits 2;
            range "0..100";
        }
        units "ps/sqrt(km)";
        description "Polarization Mode Dispersion (PMD) coefficient expressed in ps/sqrt(km)";
    }

    typedef wavelength-nm-t {
        type decimal64 {
            fraction-digits 2;
        }
        units "nm";
        description "Wavelength expressed in nm";
    }
    
    typedef small-number-t {
        type decimal64 {
            fraction-digits 17;
        }
 
        description "Representation of small number (down to E-15)";
    }

   identity common-hw-identity {
     description "Common indetity used for all indentity referenced by capabilities action";
   }


    // CISCO RPC (Equipment and Network)
    // common definitions
    identity rpc-response-status {
        description "parent type";
    }

    identity rpc-successful-response-status {
        base rpc-response-status;
        description "OK";
    }

    identity rpc-error-response-status {
        base rpc-response-status;
        description "Generic Error";
    }

    identity rpc-internal-server-error-response-status {
        base rpc-error-response-status;
        description "Internal Server Error";
    }

    identity rpc-unreachable-node-error-response-status {
        base rpc-error-response-status;
        description "Unreachable Node";
    }


    identity fec-type {
        base common-hw-identity;
        description "Indicates the current fec type.";
    }
    identity sd-fec-type {
        base common-hw-identity;
        description "Indicates the current sd fec type.";
    }

    identity STANDARD_FEC {
        base fec-type;
        description "Standard fec type";
    }

    identity EFEC {
        base fec-type;
        description "Enhanced";
    }

    identity EFEC_I4 {
        base fec-type;
        description "Enhanced I4";
    }

    identity EFEC_I7 {
        base fec-type;
        description "Enhanced I7";
    }

    identity DISABLE_FEC {
        base fec-type;
        description "Disable";
    }

    identity HG_FEC_7 {
        base fec-type;
        description "7% High Gain FEC";
    }

    identity HG_FEC_20 {
        base fec-type;
        description "20% High Gain FEC";
    }

    identity SD_FEC_20 {
        base sd-fec-type;
        description "20% Soft Decision FEC";
    }

    identity SD_FEC_7 {
        base sd-fec-type;
        description "7% Soft Decision FEC";
    }

    identity SD_FEC_15_DE_OFF {
        base sd-fec-type;
        description "15% Soft Decision FEC DE OFF";
    }

    identity SD_FEC_25_DE_OFF {
        base sd-fec-type;
        description "25% Soft Decision FEC DE OFF";
    }

    identity SD_FEC_15_DE_ON {
        base sd-fec-type;
        description "15% Soft Decision FEC DE ON";
    }

    identity SD_FEC_25_DE_ON {
        base sd-fec-type;
        description "25% Soft Decision FEC DE ON";
    }
     identity OFEC_15_DE_ON {
        base sd-fec-type;
        description "15% Open FEC DE ON";
    }
     identity CFEC_15_DE_ON {
       base sd-fec-type;
        description "15% Concatenated FEC DE ON";
    }

    identity SD_FEC_27 {
        base sd-fec-type;
        description "27% Soft Decision FEC";
    }

    identity UNSUPPORTED_FEC {
        base sd-fec-type;
        description "Unsupported FEC";
    }

    identity SD_FEC_NONE {
        base sd-fec-type;
        description "Unsupported FEC";
    }

  typedef Optics-fec {
    type enumeration {
      enum fec-none {
        value 0;
        description "No Fec";
      }
      enum fec-h15 {
        value 1;
        description "Enhanced H15";
      }
      enum fec-h25 {
        value 2;
        description "Enhanced H25";
      }
      enum fec-h15-de {
        value 4;
        description "Enhanced H15 DE";
      }
      enum fec-h25-de {
        value 8;
        description "Enhanced H25 DE";
      }
      enum fec-not-set {
        value 32;
        description "Disable the FEC";
      }
      enum fec-1i7 {
        value 128;
        description "Enhanced 1I7";
      }
      enum fec-1i4 {
        value 256;
        description "Enhanced 1I4";
      }
      enum fec-swizzle {
        value 512;
        description "Enhanced Swizzle";
      }
      enum fec-hg20 {
        value 1024;
        description "Enhanced HG20";
      }
      enum fec-hg7 {
        value 2048;
        description "Enhanced HG7";
      }
      enum fec-sd20 {
        value 4096;
        description "SoftDecision 20";
      }
      enum fec-sd7 {
        value 8192;
        description "SoftDecision 7";
      }
      enum fec-sd15 {
        value 16384;
        description "SoftDecision 15";
      }
      enum fec-sd27 {
        value 32768;
        description "SoftDecision 27";
      }
      enum fec-sd15-de {
        value 65536;
        description "SoftDecision 15 with DE";
      }
      enum fec-staircase-de {
        value 131072;
        description "Enhanced Staircase FEC with DE";
      }
      enum fec-ofec {
        value 262144;
        description "OFEC";
      }
      enum fec-cfec {
        value 524288;
        description "CFEC";
      }
      enum fec-stndrd {
        value 1048576;
        description "Standard";
      }
      enum fec-all {
        value 2097152;
        description "All";
      }
    }
    description "Optics fec";
  }

    typedef degree-uid-t {
        type uint32 {
            range "0..1999";
        }
        description "Degree Identifier; 0 is equal to unassigned";
    }

    typedef Pwr-Ctrl-progress-status-t {
        type enumeration {
        enum "completed"{
            description "Power Control has completed all regulations";
        }
        enum "terminated"{
            description "Power Control regulation terminated due to alarms or out of range setpoint";
        }
        enum "running"{
            description "Power Control is regulating the link";
        }
         }
        description "Current progress status of Link Power Control";
    }

    typedef Pwr-Ctrl-status-t {
        type enumeration {
        enum "not-applicable"{
            description "Power Control is not applicable in this link";
        }
        enum "enabled"{
            description "Power Control is enabled and scheduled to automatically run";
        }
        enum "disabled-internal"{
            description "Power Control cannot run due to incomplete link configuration";
        }
        enum "disabled-user"{
            description "Power Control has been disabled by the user";
        }
        enum "passive"{
            description "Power Control is running on a passive only link";
        }
         }
        description "Current status of Link Power Control";

    }

    typedef Pwr-Ctrl-Admin-status-t {
        type enumeration {
        enum "force-disabled"{
            description "Power Control is disabled by the user";
        }
        enum "automatic-enabled"{
            description "Power Control is automatically managed by the nodes";
        }
        }
        description "Administrative status of Link Power Control";
    }


    typedef fiber-type-t {
      type enumeration {
        enum "G652-SMF" {
          description "G652 Standard Single Mode Fiber";
        }
        enum "G652-SMF-28E" {
          description "G652 SMF-28E fiber";
        }
        enum "E-LEAF" {
          description "G655 Second generation LEAF fiber";
        }
        enum "FreeLight" {
          description "G655 FreeLight (LEAF) fiber";
        }
        enum "TrueWave-RS" {
          description "G655 TrueWave-RS fiber";
        }
        enum "TrueWave-Reach" {
          description " G655 TrueWave-Reach fiber ";
        }
        enum "TrueWave-Plus" {
          description " G655 TrueWave-Plus fiber ";
        }
        enum "TrueWave-Minus" {
          description " G655 TrueWave-Minus fiber ";
        }
        enum "TrueWave" {
          description " G655 TrueWave fiber ";
        }
        enum "TeraLight" {
          description "G655 TeraLight fiber";
        }
        enum "MetroCor" {
          description "MetroCor fiber";
        }
        enum "SMF-LS" {
          description "G655 SMF-LS fiber";
        }
        enum "G653-DSF" {
          description "G653 Dispersion Shifter fiber";
        }
      }
      description "Fiber Type used on the Span";
    }

    typedef service-spacing-t {
        type enumeration {
            enum "fixed-grid"{
                description "Standard ITU grid with 50 GHz or 100 GHz spacing";
            }
            enum "flexible-grid"{
                description "Free circuit allocation with granularity of 12.5 GHz";
            }
        }
        description "Type of planned services wavelength allocation";
    }

    typedef fixed-grid-spacing-t {
        type enumeration {
            enum "50-ghz"{
                description "50 GHz: allowing max 96 services";
            }
            enum "100-ghz"{
                description "100 GHz: allowing max 48 services";
            }
        }
        description "ITU Fixed grid spacing";
    }

    typedef flexible-grid-spectrum-occupancy-t {
        type uint32 {
            range "50..91";
        }
        description "percentage of spectrum occupied by actual services versus guardbands;
            e.g. 82% means that for every 100 GHz of spectrum, 82 GHz is used to carry actual services
            while 18 GHz is reserved for guardbands between services";
    }

    typedef time-zone {
        type string {
            length "1..100";
        }
        description "IANA time zone excluding GMT/UTC/UT time zone fixed offset definition.
            Must be present in a set of time zone identifiers returned by a java call java.time.ZoneId.getAvailableZoneIds()
            Additionally parsed/validated by java call java.time.ZoneId.of(string).
            For detailed info look at the javadoc of
            https://docs.oracle.com/javase/8/docs/api/java/time/ZoneId.html#getAvailableZoneIds--
            https://docs.oracle.com/javase/8/docs/api/java/time/ZoneId.html#of-java.lang.String-
        ";
    }

    typedef vdc-th-t {
        type decimal64 {
            fraction-digits 1;
             range "-72.0 | -71.5 | -71.0 | -70.5 | -70.0 | -69.5 | -69.0 | -68.5 | -68.0 | -67.5 | -67.0 | -66.5 |
                    -66.0 | -65.5 | -65.0 | -64.5 | -64.0 | -63.5 | -63.0 | -62.5 | -62.0 | -61.5 | -61.0 | -60.5 |
                    -60.0 | -59.5 | -59.0 | -58.5 | -58.0 | -57.5 | -57.0 | -56.5 | -56.0 | -55.5 | -55.0 | -54.5 |
                    -54.0 | -53.5 | -53.0 | -52.5 | -52.0 | -51.5 | -51.0 | -50.5 | -50.0 | -49.5 | -49.0 | -48.5 |
                    -48.0 | -47.5 | -47.0 | -46.5 | -46.0 | -45.5 | -45.0 | -44.5 | -44.0 | -43.5 | -43.0 | -42.5 |
                    -42.0 | -41.5 | -41.0 | -40.5";
        }
        units "Vdc";
        description "Voltage th";
    }

    typedef mv-t {
        type uint32;
        units "mV";
        description "Voltage";
    }

    typedef temperature-t {
        type int32;
        units "Celsius";
        description "Temperature";
    }

    typedef voltage-type {
        type enumeration {
          enum "unknown" {
            value 0;
            description "Unknown Chassis voltage";
          }
          enum "V48" {
            value 1;
            description "V48";
          }
          enum "V60" {
            value 2;
            description "V60";
          }
          enum "Mixed" {
            value 3;
            description "Mixed";
          }
          enum "V54" {
            value 4;
            description "V54";
          }
        }
        description "Voltage Type";
      }

    typedef cooling-profile-t {

        type enumeration {
          enum "low" {
            value 1;
            description "low";
          }
          enum "medium" {
            value 2;
            description "medium";
          }
          enum "high" {
            value 3;
            description "high";
          }
        }
        description "Cooling profile type";
      }

    typedef span-loss-measure-ch-t {
        type enumeration {
            enum "NoCheck"{
                description "Span loss measurement Not Checked";
            }
            enum "OSC"{
                description "Span loss measurement via OSC channel";
            }
            enum "Channel"{
                description "Span loss measurement via optical channel";
              }
            enum "Channel-Raman-On"{
                description "Span loss measurement via optical channel with Raman amplification";
            }
            enum "Raman-Off"{
                description "Span loss measurement during Raman wizard/calibration";
            }
        }
        description "Current measurement of the optical link power loss";
    }


    typedef cooling-profile-control-t {
        type enumeration {
          enum "manual-control" {
            value 0;
            description "manual cooling control";
          }
          enum "auto-control" {
            value 1;
            description "automatic cooling control";
          }
        }
        description "Cooling profile control type";
      }

    typedef psu-id-t {
        type uint8 {
            range "1..4";
        }
        description "PSU identifier";
    }

    typedef psu-config-type-t {
        type enumeration {
          enum "none" {
            value 0;
            description "none";
          }
          enum "work" {
            value 1;
            description "work";
          }
          enum "protect" {
            value 2;
            description "protected";
          }
          enum "both" {
            value 3;
            description "both";
          }
        }
        description "Power Supply Unit (PSU) Configuration";
      }

    // Referenced from: org-openroadm-gcc-interfaces.yang
    // Enum type      : gcc-interfaces:gcc:gcc-channel-type
    typedef gcc-channel-t {
        type enumeration {
            enum "gcc0" {
                value 1;
                description "OTU GCC0 channel";
            }
            enum "gcc1" {
                value 2;
                description "ODU GCC1 channel";
            }
            enum "gcc2" {
                value 3;
                description "ODU GCC2 channel";
            }
            enum "gcc1-gcc2" {
                value 4;
                description "Combined ODU GCC channel";
            }
        }
        description "GCC channel on OTN interface";
    }

   typedef clock-source-quality-level-t {
          type enumeration {
            enum PRS {
                value 0;
                description "Primary Reference Source, Stratum 1 Traceable";
            }
            enum STU {
                value 1;
                description "Synchronized, Traceability Unknown";
            }
            enum ST2 {
                value 2;
                description "Stratum 2 Traceable";
            }
            enum TNC {
                value 3;
                description "Transit Node Clock (2nd generation only)";
            }
            enum ST3E {
                value 4;
                description "Stratum 3E Traceable (2nd generation only)";
            }
            enum ST3 {
                value 5;
                description "Stratum 3 Traceable";
            }
            enum SMC {
                value 6;
                description "Sonet Minimum Clock Traceable";
            }
            enum ST4 {
                value 7;
                description "Stratum 4 Traceable";
            }
            enum DUS {
                value 8;
                description "Don't Use for Synchronization";
            }
            enum RES {
                value 9;
                description "Reserved for network synchronization use";
            }
            enum G811 {
                value 10;
                description "G811 standard";
            }
            enum STU-SDH {
                value 11;
                description "Synchronized, Traceability Unknown - SDH";
            }
            enum G812T {
                value 12;
                description "G812T standard";
            }
            enum G812L {
                value 13;
                description "G812L standard";
            }
            enum SETS {
                value 14;
                description "Synchronous Equipment Timing Source";
            }
            enum DUS-SDH {
                value 15;
                description "Don't Use for Synchronization - SDH";
            }
            enum SSM-FAILED {
                value 16;
                description "Used when the LOS/LOF/AIS is present";
            }
            enum RES-SDH {
                value 17;
                description "Reserved for network synchronization use - SDH";
            }
          }
          description "Clock Source Quality Level
              PRS  - Primary Reference Source, Stratum 1 Tracable
              STU  - Synchronized, Tracability Unknown
              ST2  - Stratum 2 Tracable
              TNC  - Transit Node Clock (2nd generation only)
              ST3E - Stratum 3E Tracable (2nd generation only)
              ST3  - Stratum 3 Tracable
              SMC  - Sonet Minimum Clock Tracable
              ST4  - Stratum 4 Tracable
              DUS  - Don't Use for Synchronization
              RES  - Reserved for network synchronization use.
              G811 -  G811 standard
              STU_SDH - Synchronized, Tracability Unknown
              G812T - G812T standard
              G812L - G812L standard
              SETS - Synchronous Equipment Timing Source
              DUS_SDH  - Don't Use for Synchronization - SDH
              SSM_FAILED  - Used when the LOS/LOF/AIS is present.
              RES_SDH  - Reserved for network synchronization use - SDH.
              The order of preference is PRS, STU, ST2, TNC, ST3E, ST3, SMC, ST4.
              When RES is received it is reassigned to be above, below, or in between one of these values.
              TNC and ST3E are only applicable if the node has been provisioned to operated with the Generation 2
              synchronization message set.
              The order of preference for SDH is G811, STU_SDH, G812T, G812L, SETS, DUS_SDH, RES_SDH.";
        }


        typedef timing-source-t {
            type enumeration {
              enum System-Clock;
              enum Internal-Clock;
            }
            description "Timing source reference type";
        }
}
