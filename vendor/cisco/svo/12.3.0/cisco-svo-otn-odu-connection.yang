module cisco-svo-otn-odu-connection {
    yang-version 1.1;
    namespace "http://cisco.com/yang/svo/otn-odu-connection";
    prefix svo-odu-conn;

    import cisco-svo-common-equipment-types { prefix ccet; }
    import cisco-svo-common-types { prefix cct; }
    import cisco-svo-common-base-opt-oper-grp { prefix ccboog; }
    import org-openroadm-otn-common-types { prefix org-openroadm-otn-common-types; revision-date 2018-09-28; }


    organization
        "Cisco Systems, Inc.";

    contact
        "Cisco Systems, Inc. Customer Service Postal: 170 West Tasman
        Drive San Jose, CA 95134 Tel: +1 800 553-NETS E-mail: cs-yang@cisco.com";

    description
        "YANG definition for SVO otn ODU cross connections";

  revision 2021-12-25 {
  	description "Model version for SVO Release 12.3.0";
  	reference cisco-svo-otn-odu-connection.yang;
  }
  
    revision 2020-12-04 { 
       description "Model version for SVO Release 12.1.0 "; 
       reference cisco-svo-otn-odu-connection.yang; 
    }
 

    grouping odu-path-def {
        leaf if-name {
            type ccet:port-name-t;
            description "should be name of existing interface";
        }
    }

    grouping otn-odu-connection-group {
        description "ODU connections list";

        list odu-connection {
            key "connection-name";

            leaf connection-name {
                type string;
                mandatory true;
                description
                    "odu-connection share the same resource-type and resource definition (e.g. connection)";
            }
            leaf odu-rate {
                type identityref {
                    base org-openroadm-otn-common-types:odu-rate-identity;
                }
		description "odu-rate";
            }
            leaf circuit-id {
                type string {
                    length "0..130" {
			error-message "Allowed characters are 0..130";
		    }
                }
                description "Name of the circuit the oxc belongs to. Shall be up to  130 characters, ISO 8859-1";
            }
            leaf direction {
                type enumeration {
                    enum "unidirectional" {
                        value 1;
                    }
                    enum "bidirectional" {
                        value 2;
                    }
                }
                default "bidirectional";
                description
                    "Directionality of connection. If bidirectional, both directions are created.";
            }
            leaf admin-state {
                type cct:admin-state-t;
	        default In-Service;
            }

            uses ccboog:oper-state-grp;
		
            list src-if-list {
                key "if-name";
                min-elements 1;
                uses odu-path-def;
                ordered-by user;
                description "ODU Interface name. It's typically related to Xponder's Client or Trunk ports.";
            }

            list dst-if-list {
                key "if-name";
                min-elements 1;
                uses odu-path-def;
                ordered-by user;
                description "ODU Interface name. It's typically  related to Xponder's Client or Trunk ports.";
            }

	    leaf protection-ref {
		config false;
                type ccet:port-name-t;
                description
                    "Primary interface must be given for protected circuits";
            }
      }    
  }    
}
