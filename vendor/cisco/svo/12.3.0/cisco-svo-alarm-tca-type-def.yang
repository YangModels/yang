submodule cisco-svo-alarm-tca-type-def {

  belongs-to cisco-svo-alarm-tca-type {
    prefix svo-al-tca-t;
  }

  import tailf-ncs-alarms {
    prefix al;
  }


  organization
    "Cisco Systems, Inc.";

  contact
    "Cisco Systems, Inc.
    Customer Service

    Postal: 170 West Tasman Drive
    San Jose, CA 95134

    Tel: +1 800 553-NETS

    E-mail: cs-yang@cisco.com";

  description
    "This module defines the root of svo alarms under the 
      alarm-type under the module tailf-ncs-alarms";

    revision 2020-12-04 { 
       description "Model version for SVO Release 12.1.0 "; 
       reference cisco-svo-alarm-tca-type-def.yang; 
    }
 

  identity svo-alarm-tca-type {
    description "Root of svo alarm transient type";
    base al:alarm-type;
  }

  typedef svo-alarm-tca-type-t {
    type identityref {
      base svo-alarm-tca-type;
    }
  }
}
