module org-openroadm-common-types {
  namespace "http://org/openroadm/common-types";
  prefix org-openroadm-common-types;

  organization
    "Open ROADM MSA";
  contact
    "OpenROADM.org";
  description
    "YANG definitions of common types.
       
      Copyright of the Members of the Open ROADM MSA Agreement dated (c) 2016, 
      AT&T Intellectual Property.  All other rights reserved.
      
      Redistribution and use in source and binary forms, with or without modification, 
      are permitted provided that the following conditions are met:
      
      * Redistributions of source code must retain the above copyright notice, this 
        list of conditions and the following disclaimer.
      * Redistributions in binary form must reproduce the above copyright notice, 
        this list of conditions and the following disclaimer in the documentation and/or 
        other materials provided with the distribution.
      * Neither the Members of the Open ROADM MSA Agreement nor the names of its 
        contributors may be used to endorse or promote products derived from this software 
        without specific prior written permission.
      
      THIS SOFTWARE IS PROVIDED BY THE MEMBERS OF THE OPEN ROADM MSA  AGREEMENT ''AS IS'' 
      AND ANY EXPRESS OR IMPLIED WARRANTIES, INCLUDING, BUT NOT LIMITED TO, THE IMPLIED 
      WARRANTIES OF MERCHANTABILITY AND FITNESS FOR A PARTICULAR PURPOSE ARE DISCLAIMED. 
      IN NO EVENT THE MEMBERS OF THE OPEN ROADM MSA  AGREEMENT BE LIABLE FOR ANY DIRECT, 
      INDIRECT, INCIDENTAL, SPECIAL, EXEMPLARY, OR CONSEQUENTIAL DAMAGES (INCLUDING, BUT 
      NOT LIMITED TO, PROCUREMENT OF SUBSTITUTE GOODS OR SERVICES;  LOSS OF USE, DATA, 
      OR PROFITS; OR BUSINESS INTERRUPTION) HOWEVER CAUSED AND ON ANY THEORY OF LIABILITY, 
      WHETHER IN CONTRACT, STRICT LIABILITY, OR TORT (INCLUDING NEGLIGENCE OR OTHERWISE) 
      ARISING IN ANY WAY OUT OF THE USE OF THIS SOFTWARE, EVEN IF ADVISED OF THE 
      POSSIBILITY OF SUCH DAMAGE";

  revision 2018-09-28 {
    description
      "Version 4.0.0";
  }
  revision 2018-03-30 {
    description
      "Version 3.0.0";
  }
  revision 2017-12-15 {
    description
      "Version 2.2";
  }
  revision 2017-09-29 {
    description
      "Version 2.1";
  }
  revision 2017-06-26 {
    description
      "Version 2.0";
  }
  revision 2016-10-14 {
    description
      "Version 1.2";
  }

  typedef activate-notification-type {
    type enumeration {
      enum "activate" {
        value 1;
        description
          "software or database activation";
      }
      enum "commit" {
        value 2;
        description
          "commit the software or database. 
           For software activate, this event can happen in the following scenarios:
             1) immediately when user issue sw-activate command without validationTimer
                or if the validationTimer is specified as 00-00-00;
             2) when user issue cancel-validation-timer before it expires and with accept=true.
           For database activate, this event can occur in the following scenarios:
             1) immediately when user issue db-activate command without rollBackTimer
                or if the rollBackTimer is specified as 00-00-00;
             2) when user issue cancel-rollback-timer before it expires and with accept=true.";
      }
      enum "cancel" {
        value 3;
        description
          "cancel the database or software activation operation.
           For software activate, this event can happen in the following cases:
             1) when the validationTimer expires;
             2) when the user issues cancel-validation-timer with accept=false.  
           For database activate, this event can happen in the following cases:
             1) when the rollBackTimer expires;
             2) when the user issues cancel-rollback-timer with accept=false.";
      }
    }
    description
      "Type of notification on software or database activation events";
  }

  typedef rpc-status {
    type enumeration {
      enum "Successful" {
        value 1;
      }
      enum "Failed" {
        value 2;
      }
    }
    description
      "status of RPC ";
  }

  typedef extended-rpc-status {
    type enumeration {
      enum "Successful" {
        value 1;
      }
      enum "Failed" {
        value 2;
      }
      enum "In-progress" {
        value 3;
      }
    }
    description
      "status of RPC ";
  }

  typedef openroadm-version-type {
    type enumeration {
      enum "1.0" {
        value 1;
        description
          "value for 1.0";
      }
      enum "2.0" {
        value 2;
        description
          "value for 2.0";
      }
      enum "2.1" {
        value 3;
        description
          "value for 2.1";
      }
      enum "2.2" {
        value 4;
        description
          "value for 2.2";
      }
      enum "3.0" {
        value 5;
        description
          "value for 3.0";
      }
      enum "3.1" {
        value 6;
        description
          "value for 3.1";
      }
      enum "4.0" {
        value 7;
        description
          "value for 4.0";
      }
    }
    description
      "OpenROADM version enum type";
  }

  grouping rpc-response-status {
    leaf status {
      type rpc-status;
      mandatory true;
      description
        "Successful or Failed";
    }
    leaf status-message {
      type string;
      description
        "Gives a more detailed status";
    }
  }

  grouping extended-rpc-response-status {
    leaf status {
      type extended-rpc-status;
      mandatory true;
      description
        "Successful, Failed or In-progress";
    }
    leaf status-message {
      type string;
      description
        "Gives a more detailed status.";
    }
  }
}
