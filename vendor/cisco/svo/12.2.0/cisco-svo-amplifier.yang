module cisco-svo-amplifier {
    yang-version 1.1;
    namespace "http://cisco.com/yang/svo/amp";
    prefix svo-amp;

    import cisco-svo-common-equipment-types { prefix ccet; }
    import cisco-svo-common-types { prefix cct; }
    import cisco-svo-common-amplifier-grp { prefix ccag; }
    
    import cisco-svo-common-amplifier-oper-grp { prefix ccaog; }
    import cisco-svo-common-amplifier-live-grp { prefix ccalg; }

    organization
        "Cisco Systems, Inc.";

    contact
        "Cisco Systems, Inc. Customer Service Postal: 170 West Tasman
        Drive San Jose, CA 95134 Tel: +1 800 553-NETS E-mail: cs-yang@cisco.com";

    description
        "YANG definition for device interfaces";

   revision 2021-04-16 { 
      description "Model version for SVO Release 12.2.0 "; 
      reference cisco-svo-amplifier.yang; 
   }
 

    revision 2020-12-04 { 
       description "Model version for SVO Release 12.1.0 "; 
       reference cisco-svo-amplifier.yang; 
    }
 

    grouping amp-grp {
		description "Optical amplifier grouping";
        list amplifier {
            key "ingress-if egress-if";
            description "List of amplifiers defined on the interfaces";

         	//oper data
            leaf uid {
                type leafref {
                    path "../../chassis/uid";
                }
                config false;
                description "Identifier of the linked chassis, same device the interface is based on";
            }
            leaf ingress-if {          
            	type ccet:port-name-t; 
                description "Identifier of the amplifier input interface";
            }

            leaf egress-if {
            	type ccet:port-name-t; 
                description "Identifier of the amplifier output interface";
            }

            container supporting-module {

                leaf module-id {
                     type leafref {
                        path "../../../chassis[uid=current()/../../uid]/module/slot";
                    }
                    config false;
                    description "Identifier of the linked module.";
                }
                description "Identifier of the link supporting module.";
            }

            uses ccag:amp-optics-params-grp;
            uses ccaog:amp-optics-oper-grp;
            uses ccalg:ampli-live-data;
        }
    }
    
    grouping manual-calibration-grp {
        container manual-calibration {
            uses ccag:manual-raman-calib-params-grp;
            uses ccaog:manual-raman-calib-oper-grp;
            uses ccag:manual-raman-calib-actions-grp;
        }
    }

    grouping automatic-calibration-grp {
        container automatic-calibration {
            uses ccaog:automatic-raman-calib-oper-grp;
            uses ccag:automatic-raman-calib-actions-grp;
        }
    }

    grouping raman-amp-grp {
        description
          "Optical amplifier grouping";
        list raman-amplifier {
            key "raman-if";
            description
              "List of Raman amplifiers defined on the interfaces";

            // oper data
            leaf uid {
                type leafref {
                    path "../../chassis/uid";
                }
                config false;
                description
                  "Identifier of the linked chassis, same device the interface is based on";
            }

            leaf raman-if {
                type ccet:port-name-t;
                description
                  "Identifier of the Raman port interface";
            }

            container supporting-module {

                leaf module-id {
                    type leafref {
                        path "../../../chassis[uid=current()/../../uid]/module/slot";
                    }
                    config false;
                    description
                      "Identifier of the linked module.";
                }
                description
                  "Identifier of the link supporting module.";
            }

            uses ccag:rmn-amp-optics-params-grp;
            uses ccaog:rmn-amp-optics-oper-grp;
            uses ccalg:rmn-ampli-live-data;

            leaf calibration-type {
                type cct:raman-calibration-type-t;
                description
                  "Select the tye of Raman calibration";
            }

            uses manual-calibration-grp {
                when "calibration-type = 'Manual'";
            }

            uses automatic-calibration-grp {
                when "calibration-type = 'Automatic'";
            }
            
            container debug-tools {
            	uses ccag:raman-debug-tools-grp;
            }
        }
    }
}
