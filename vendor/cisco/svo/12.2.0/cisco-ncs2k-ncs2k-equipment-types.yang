module cisco-ncs2k-ncs2k-equipment-types {

  yang-version 1.1;
  namespace "http://cisco.com/yang/ncs2k/ncs2k-equipment-types";
  prefix ncs2k-2kcet;
  
  import tailf-common { prefix tailf; }
  import cisco-ncs2k-common-eei-types { prefix ncs2k-ceeit; }
  
  organization
    "Cisco Systems, Inc.";

  contact
    "Cisco Systems, Inc.
     Customer Service

     Postal: 170 West Tasman Drive
     San Jose, CA 95134

     Tel: +1 800 553-NETS

     E-mail: cs-yang@cisco.com";

  description "
    This module defines the basic cisco equipment types for NCS2K platform.";

    revision 2020-12-04 { 
       description "Model version for SVO Release 12.1.0 "; 
       reference cisco-ncs2k-ncs2k-equipment-types.yang; 
    }
 
  
  grouping equipment-entity-index-grp {
	  description "
	  	Equipment entity index reusable grouping";
	
	  leaf equipment-entity-index {
		  type ncs2k-ceeit:equipment-entity-index-t;
		  config false;
		  tailf:cli-show-template '$(.|hex)';
	  }
  }
  
}
