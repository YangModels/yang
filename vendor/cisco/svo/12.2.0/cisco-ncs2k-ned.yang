module cisco-ncs2k-ned {
  yang-version 1.1;
  namespace "http://cisco.com/yang/ncs2k/ned";
  prefix ncs2k-ned;

  import tailf-ncs-ned { prefix ned; }

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "YANG definition for NSC2K platform: NED identification class.";

  revision 2020-12-04 { 
      description "Model version for SVO Release 12.1.0 "; 
      reference cisco-ncs2k-ned.yang; 
  }
  

  identity cisco-ncs2k-ned-id {
    base ned:generic-ned-id;
  }
}
