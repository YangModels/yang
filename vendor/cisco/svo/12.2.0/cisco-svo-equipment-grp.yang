module cisco-svo-equipment-grp {
  yang-version 1.1;
  namespace "http://cisco.com/yang/svo/equipment-grp";
  prefix svo-eq-grp;


  import tailf-common { prefix tailf; }
  import ietf-inet-types { prefix inet; }
  import tailf-ncs { prefix ncs; }

  import cisco-svo-common-types { prefix cct; }
  import cisco-svo-common-equipment-types { prefix ccet; }
  import cisco-svo-common-sync-grp { prefix ccsync; }
  import cisco-svo-common-base-opt-grp { prefix ccbog; }
  import cisco-svo-common-equipment-grp { prefix cceqptg; }
  import cisco-svo-common-monitor-grp { prefix ccmg; }
  import cisco-svo-common-cv-grp { prefix cccv; }

  import cisco-svo-common-mfg-oper-grp { prefix ccmog; }
  import cisco-svo-common-equipment-oper-grp { prefix cceqptog; }
  import cisco-svo-common-passive-unit-live-grp { prefix ccpulg; }
  import cisco-svo-common-monitor-live-grp { prefix ccmlg; }
  import cisco-svo-common-alarm-extender { prefix svo-alarm-extender; }

  import cisco-svo-node-grp {prefix svo-node-grp; }

  import cisco-svo-equipment-oper-grp { prefix ceqog; }
  import cisco-svo-ancillary-oper-grp { prefix cancog; }

  import cisco-ncs2k-equipment-types { prefix cet; }
  import cisco-svo-controller-ned { prefix ncs2k-ctrl-ned; }
  import cisco-svo-common-cv-live-grp {prefix ccvlv; }
  import cisco-ncs2k-ned { prefix ncs2k-ned; }

  organization
    "Cisco Systems, Inc.";

  contact
    "Cisco Systems, Inc.
     Customer Service

     Postal: 170 West Tasman Drive
     San Jose, CA 95134

     Tel: +1 800 553-NETS

     E-mail: cs-yang@cisco.com";

  description
    "Grouping YANG definition for SVO data-path related equipments, chassis, optical line cards,
     pluggable modules, ports and internal fiber links.";

   revision 2021-04-16 { 
      description "Model version for SVO Release 12.2.0 "; 
      reference cisco-svo-equipment-grp.yang; 
   }
 

    revision 2020-12-04 { 
       description "Model version for SVO Release 12.1.0 "; 
       reference cisco-svo-equipment-grp.yang; 
    }
 
    
  
  // BEGIN Duplicated from cisco-ncs2k-equipment-grp

  grouping port-content {

    leaf port-type {
      type identityref {
        base ccet:port-type;
      }
      mandatory true;
      description "Port Type";
    }

    leaf number-of-lanes {
      type uint8 {
        range "1 | 4 | 10";
      }
      when "re-match(../../slot,'[0-9]+[-]{1}[0-9]+')";
      description "Number of lanes, mandatory for configurable port";
    }
  }

  grouping internal-links-config-grp {
  }

  grouping general {
    leaf lcd-setting {
        description "Set the different state of the LCD
                        It could be use for some configuration,
                        Could be in read only mode for that configuration,
                        Show nothing.";
        type ccet:lcd-setting-t;
    }

    leaf cooling-profile-control {
        description "cooling-profile-control";
        type cct:cooling-profile-control-t;
    }
  }

  grouping card-type-grp {
    leaf module-type {
      type identityref {
        base ccet:card-type;
      }
      mandatory true;
      description "Module type for a card";

      must "current() != 'cet:TNC'"
          + " and current() != 'cet:TSC'"
          + " and current() != 'cet:TNCS-2O'"
          + " or ../../chassis-type != 'cet:NCS2006-ETSI'"
          + " and ../../chassis-type != 'cet:NCS2006-ANSI'"
          + " or re-match(current()/../slot,'([1]|[8])')" {
              error-message "Cards of type TNC/TSC must have slot equal to 1 or 8 for chassis-types M6";
      }

      must "current() != 'cet:TNC'"
          + " and current() != 'cet:TNCS-2O'"
          + " or ../../chassis-type != 'cet:NCS2015-ETSI'"
          + " and ../../chassis-type != 'cet:NCS2015-ANSI'"
          + " or re-match(current()/../slot,'[1]|([1][7])')" {
              error-message "Cards of type TNC must have slot either equal to 1 or to 17 for chassis-type M15";
      }

      must "current() = 'cet:TNC'"
           + " or current() = 'cet:TNCS-2O'"
           + " or current() = 'cet:FILLER'"
           + " or ../../chassis-type != 'cet:NCS2015-ETSI'"
           + " and ../../chassis-type != 'cet:NCS2015-ANSI'"
           + " or re-match(current()/../slot,'[2-9]|([1][0-6])')" {
              error-message "Cards of type != [TNC,FILLER] must have slot in range 2 to 16 for chassis-type M15";
      }

      must "current() = 'cet:TNC'"
           + " or current() = 'cet:TNCS-2O'"
           + " or current() = 'cet:TSC'"
           + " or current() = 'cet:FILLER'"
           + " or ../../chassis-type != 'cet:NCS2006-ETSI'"
           + " and ../../chassis-type != 'cet:NCS2006-ANSI'"
           + " or re-match(current()/../slot,'[2-7]')" {
              error-message "Cards of type != [TNC,TSC,FILLER] must have slot in range 2 to 7 for chassis-type M6";
      }

      must "../../chassis-type != 'cet:NCS2015-ANSI' and ../../chassis-type != 'cet:NCS2015-ETSI'"
          + " or current() != 'cet:TSC'"
          + " and current() != 'cet:_15454-32-WSS'"
          + " and current() != 'cet:_15454-32-DMX'"
          + " and current() != 'cet:_15454-40-WSS-C'"
          + " and current() != 'cet:_15454-40-DMX-C'"
          + " and current() != 'cet:_15454-40-MUX-C'"
          + " and current() != 'cet:_15454-40-WXC-C'"
          + " and current() != 'cet:_15454-10MEX-L1-C'" {
             error-message "Not allowed card type for M15 ncs2k chassis";
      }
    }

    leaf timing-source {
        when "../module-type = 'cet:_15454-40E-MXP-C'"
          +  " or ../module-type = 'cet:_15454-40G-MXP-C'"
          +  " or ../module-type = 'cet:_15454-40E-TXP-C'"
          +  " or ../module-type = 'cet:_15454-40G-TXP-C'";

        type cct:timing-source-t;
        default System-Clock;
        description "Timing Source";
    }

    leaf card-mode {
      type identityref {
        base ccet:card-mode;
      }
      mandatory true;
      description "Card mode applicable to TXP/MXP module";
      when "derived-from(../module-type, 'ccet:card-with-card-mode')";

      must "../module-type != 'cet:TNC' or current() = 'cet:TNC-MODE' or current() = 'cet:TNCO-MODE'" {
        error-message "Allowed card-mode values for TNC card are TNC-MODE and TNCO-MODE";
      }

      must "../module-type != 'cet:_15454_PSM' or current() = 'cet:PSM_NORMAL' or current() = 'cet:PSM_STANDALONE'" {
        error-message "Allowed card-mode values for PSM card are PSM_NORMAL and PSM_STANDALONE";
      }

      must "../module-type != 'cet:_15454-40E-MXP-C _15454_40ME_MXP_C' or current() = 'cet:XM_40G_OTU3' or current() = 'cet:XM_40G_OTU3E2'" {
        error-message "Allowed card-mode values for _15454_40E_MXP_C card are XM_40G_OTU3 and XM_40G_OTU3E2";
      }

      must "../module-type != 'cet:_15454-40G-MXP-C' or current() = 'cet:XM_40G_OTU3' or current() = 'cet:XM_40G_OTU3E2'" {
        error-message "Allowed card-mode values for _15454_40G_MXP_C card are XM_40G_OTU3 and XM_40G_OTU3E2";
      }

      must "../module-type != 'cet:_15454_10DME_C' or current() = 'cet:MXPMR10DME_PG1_FCGEISC_PG2_FCGEISC' or current() = 'cet:MXPMR10DME_PG1_FCGEISC_PG2_4GFC'"
        + " or current() = 'cet:MXPMR10DME_PG1_4GFC_PG2_FCGEISC' or current() = 'cet:MXPMR10DME_PG1_4GFC_PG2_4GFC'" {
        error-message "Allowed card-mode values for _15454_10DME_C card are MXPMR10DME_PG1_FCGEISC_PG2_FCGEISC, MXPMR10DME_PG1_FCGEISC_PG2_4GFC, MXPMR10DME_PG1_4GFC_PG2_FCGEISC and MXPMR10DME_PG1_4GFC_PG2_4GFC";
      }

      must "../module-type != 'cet:_15454_10GE_XP' or current() = 'cet:XP10GE_TXP' or current() = 'cet:XP10GE_TXP_L2_SWITCH'" {
        error-message "Allowed card-mode values for _15454_10GE_XP card are XP10GE_TXP and XP10GE_TXP_L2_SWITCH";
      }

      must "../module-type != 'cet:_15454_OTU2_XP' or current() = 'cet:OTU2XP_2XP' or current() = 'cet:OTU2XP_EFEC_REG' or current() = 'cet:OTU2XP_SPLITTER'"
        + " or current() = 'cet:OTU2XP_XP_REG' or current() = 'cet:OTU2XP_REG_XP' or current() = 'cet:OTU2XP_2REG' or current() = 'cet:OTU2XP_LANWAN' or current() = 'cet:OTU2XP_LANWAN_SPLITTER'" {
        error-message "Allowed card-mode values for _15454_OTU2_XP card are OTU2XP_2XP, OTU2XP_XP_REG, OTU2XP_REG_XP, OTU2XP_2REG, OTU2XP_2XP, OTU2XP_EFEC_REG, OTU2XP_SPLITTER, OTU2XP_LANWAN and OTU2XP_LANWAN_SPLITTER";
      }

      must "../module-type != 'cet:_15454_GE_XP' or current() = 'cet:GEXP_MXP' or current() = 'cet:GEXP_2MXP' or current() = 'cet:GEXP_MXP_L2_SWITCH'" {
        error-message "Allowed card-mode values for _15454_GE_XP card are GEXP_MXP, GEXP_2MXP and GEXP_MXP_L2_SWITCH";
      }

      must "../module-type != 'cet:_15454_80_WXC_C' or current() = 'cet:WXC_BIDI' or current() = 'cet:WXC_MUX' or current() = 'cet:WXC_DEMUX'" {
        error-message "Allowed card-mode values for 80-WXC card are WXC_BIDI, WXC_MUX and WXC_DEMUX";
      }

    }
  }

  grouping ppm-type-grp {
    leaf ppm-module-type {
      status deprecated;
      type identityref {
         base ccet:ppm-type;
      }
      mandatory true;
      description "Module type for PPM";
    }

    leaf parent-module {
      type leafref {
        path "../../module/slot";
      }

      must "deref(current())/../module-type" {
        tailf:dependency "../../module/module-type";
      }

      must "starts-with(../slot, concat(current(),'-'))" {
        error-message "wrong Parent Module, it must point to correct module (same slot as PPM)";
      }

      mandatory true;
      description "Parent module, valid in case of ppm only";
    }
  }

  grouping passive-shelf-grp {
    leaf mf-6ru-passive-module-type {
      status deprecated;
      type identityref {
        base cet:mf-6ru-passive-type;
      }
      mandatory true;
      when "../../chassis-type = 'cet:NCS2K-MF-6RU'";
      description "Module type for Passive Cards";
    }

    leaf mf10-6ru-passive-module-type {
      status deprecated;
      type identityref {
        base cet:mf10-6ru-passive-type;
      }
      mandatory true;
      when "../../chassis-type = 'cet:NCS2K-MF10-6RU'";
      description "Module type for Passive Cards";
    }

    leaf passive-unit-id {
      type ccet:passive-unit-id-t;
      mandatory true;
      description "
        passive-unit-id is the unique index that identifies
        the passive-unit in the node.
        The passive-unit-id is unique in the node, so,
        multi-rack nodes do not have passive-unit-id duplicated";
    }
  }

  grouping module-content {
    uses card-type-grp {
      when "derived-from(../chassis-type, 'cet:ncs2k-chassis') and not(re-match(./slot,'[0-9]+[-]{1}[0-9]+'))";
    }

    uses ppm-type-grp {
      when "derived-from(../chassis-type, 'cet:ncs2k-chassis') and re-match(./slot,'[0-9]+[-]{1}[0-9]+')";
    }

    uses passive-shelf-grp {
      when "../chassis-type = 'cet:NCS2K-MF10-6RU' or ../chassis-type = 'cet:NCS2K-MF-6RU'";
    }

    leaf admin-state {
      type cct:admin-state-t;
      // admin-state is configurable for cards and ppm's
      description "Admin State";
      when "derived-from(../../chassis-type, 'cet:ncs2k-chassis')";
    }
  }

  grouping fm-content {
    leaf mode {
      type identityref {
        base ccet:functional-mode;
      }
      mandatory true;
      description "Functional module mode applicable to TXP/MXP module groups";
    }

    list peer-module {
      key slot;

      leaf slot {
        type leafref {
          path "../../../module/slot";
        }
        must "deref(current())/../module-type" {
          tailf:dependency "../../../module/module-type";
        }
        mandatory true;
        description "Peer module to configure the functional module group. Must be a card";
      }

      leaf order {
        type enumeration {
          enum lower-peer;
          enum higher-peer;
        }
        when "../../mode = 'cet:CFP-TXP'";
        mandatory true;
      }

      leaf submode {
        type enumeration {
          enum OPM-10x10G;
          enum OPM-2x40G-2x10G;
        }
        when "../../mode = 'cet:MXP-200G'";
        mandatory true;
      }
    }

    list slice {
      key index;

      leaf index {
        type uint8 {
          range 1..4;
        }
      }

      when "deref(../primary-module-id)/../module-type = 'cet:NCS2K-400G-XP' or deref(../primary-module-id)/../module-type = 'cet:NCS2K-1.2T-MXP' " {
        tailf:dependency "../../module/module-type";
      }

      leaf submode {
        type identityref {
          base ccet:slice-mode;
        }
        mandatory true;
        description "Submode for a slice of 400G or 1.2T card";
      }
    }

    list trunk {
      key slot;

      when "re-match(../primary-module-id,'[0-9]+[-]{1}[0-9]+')";

      leaf slot {
        type leafref {
          path "../../../module/slot";
        }
        must "deref(current())/../ppm-module-type" {
          tailf:dependency "../../../module/ppm-module-type";
        }
        must "deref(current())/../parent-module=deref(../../primary-module-id)/../parent-module" {
          tailf:dependency "../../../module/parent-module";
        }
        description "Trunk ports used in functional module group. Must be an PPM";
      }
    }

    list client {
      key slot;

      when "re-match(../primary-module-id,'[0-9]+[-]{1}[0-9]+')";

      leaf slot {
        type leafref {
          path "../../../module/slot";
        }
        must "deref(current())/../ppm-module-type" {
          tailf:dependency "../../../module/ppm-module-type";
        }
        must "deref(current())/../parent-module=deref(../../primary-module-id)/../parent-module" {
          tailf:dependency "../../../module/parent-module";
        }
        description "Client port used in functional module group. Must be an PPM";
      }
    }
  }


  // END Duplicated from cisco-ncs2k-equipment-grp

  grouping usb-association-passive-shelf-grp {
    uses cceqptg:usb-port-association-info-grp {
      augment usb-port-association-info {
        leaf uid {
            type ccet:uid-t;
            description " uid is the unique index that identifies the chassis in the node.
                                The uid is unique in the node, so, multi-rack nodes do not have
                                chassis-id duplicated";
        }
      }
    }
  }

  grouping port-list {
    list port {
      key port-id;
      description "
        List of configured (provisioned or pre-provisioned)
        ports";

      leaf port-id {
        type ccet:port-id-t;
        description "Port identifier";
      }

      uses svo-eq-grp:port-content;
      uses port-content-oper;

      list lane {
        key lane-id;
        description "List of lanes";
        leaf lane-id {
          type ccet:lane-id-t;
          description "Port Lane identifier";
        }

        uses cceqptog:lane-content-oper;
      }
    }
  }

  grouping port-content-oper {

    leaf port-name {
      type ccet:port-name-t;
      config false;
      description "Portname with syntax UId/[Slot-Id/]Port-Id.";
    }

    leaf port-number {
        type uint16;
        config false;
        description "Port number";
    }

    leaf direction {
      type cct:direction;
      config false;
      description "Port direction: RX, TX, BIDI";
    }

    uses cceqptog:mpo-addressing;
  }

  typedef admin-state {
    type enumeration {
      enum locked {
        description
          "When a device is admistratively locked, it is not possible
           to modify its configuration, and no changes are ever
           pushed to the device.";
        tailf:code-name 'adm_locked';
        tailf:info "Device is locked for config and southbound traffic";
      }
      enum unlocked {
        description
          "Device is assumed to be operational.
           All changes are attempted to be sent southbound.";
        tailf:code-name 'adm_unlocked';
        tailf:info "Device is open for config and southbound traffic";
      }
    }
    description "the admin state type for subtended devices";
  }

  grouping action-2k {
    action change-ip-address {
      description "Action for changing NCS2K IPv4/IPv6 address";
      input {
        container ipv4 {
          description "The new NCS2K node IPv4 address";
          uses cceqptg:ipv4-grp;
        }
        container ipv6 {
          presence "The new NCS2K node IPv6 address, This is optional if the node is IPv4 only";
          uses cceqptg:ipv6-grp;
        }
      }
      output {
        uses ccbog:rpc-status;
      }
    }

    action resync-all {
      description "sync all the configuration and operational data from the device";
      output {
        uses ccbog:rpc-status;
      }
    }

    container wson-sson {
      description "wson/sson actions container";
      uses wson-sson-actions-grp;
    }

  }

  grouping action-controller {
    action fetch-host-keys {
      description "Retrieve the SSH host keys from the device";
      output {
        uses ncs:fetch-ssh-host-keys-result;
      }
    }
    action check-sync {
      description
        "Perform a cheap sync check, checking if NCS's
          configuration is in sync with this device's configuration,
          using device-specific mechanisms.  If the device
          doesn't support cheap sync check, 'check-sync' returns
          'unsupported'.";
      tailf:info "Check if the NCS config is in sync with the device";
      output {
        uses ncs:check-sync-result;
      }
    }
  }

  grouping action-sync-from {
    action sync-from {
      description "sync the configuration data from the device";
      output {
        uses ncs:sync-result;
      }
    }
  }

  grouping controller-specific {
    leaf port {
      tailf:info "Port for the management interface";
      type inet:port-number;
      mandatory true;
      description
        "Port for the management interface on the device.  If this leaf is
          not configured, NCS will use a default value based on the type
          of device.  For example, a NETCONF device uses port 830, a
          CLI device over SSH uses port 22, and a SNMP device uses port 161.";
    }
  }

  grouping passive-equipments-action-grp {
    description "Grouping for passive actions";
    action blink-led {
      description "Action to blink led on passive card  ";
      output {
        uses ccbog:rpc-status;
      }
    }
  }

  grouping passive-unit-equipments-action-grp {
    description "Grouping for passive actions";
    action blink-led {
      description "Action to blink led passive unit ";
      output {
        uses ccbog:rpc-status;
      }
    }
  }

  grouping module-actions-grp {
    description "Grouping for action on cards";
    action delete {
      description "Action to do a software reset on a card ";
      output {
        uses ccbog:rpc-status;
      }
    }

    action obfl {
      description "Action to activate the obfl on a card
                      possible messages are:
                      success = 'OBFL started for the card'

                      error:
                      1) 'Error during operation - OBFL not supported'
                      2) 'Error during operation - Card not ready for OBFL'
                      3) 'Error during operation - OBFL already running'";

      output {
        uses ccbog:rpc-status;
      }
    }
    
     action fpdupgrade {
      description "Action to do a fpd firmware upgrade on a card ";
      output {
        uses ccbog:rpc-status;
      }
    }
  }

  grouping chassis-actions-grp {
    description "Grouping for action on chassis";
    action delete-chassis {
      description "Action to do an unprovision on chassis ";
      output {
        uses ccbog:rpc-status;
      }
    }
  }

  grouping deleted-chassis-actions-grp {
    description "Grouping for delete-action on cards";
    action undelete-chassis {
      description "Action to move existing chassis from DELETED state";
      output {
        uses ccbog:rpc-status;
      }
    }
  }

  grouping wson-sson-actions-grp {
    description "wson/sson actions group";
    action wson-sson-activate {
      description "Change NCS2K status of WSON/SSON control plane to be active";
      output {
        uses ccbog:rpc-status; // should be ok or failure due to any reason (ie CP services present)
      }
    }

    action wson-sson-de-activate {
      description "Change NCS2K status of WSON/SSON control plane to be shut down";
      output {
        uses ccbog:rpc-status; // should be ok or failure due to any reason (ie CP services present)
      }
    }
  }

  grouping card-actions-grp {
    description "Grouping for reset-action on cards";
    action reset {
      description "Action to do a software reset on a card ";
      output {
        uses ccbog:rpc-status;
      }
    }

    action hwreset {
      description "Action to do a hw reset on a card ";
      output {
        uses ccbog:rpc-status;
      }
    }
    
  }

  grouping deleted-card-actions-grp {
    description "Grouping for delete-action on cards";
    action undelete-card {
      description "Action to move existing card from DELETED state";
      input {
        leaf module-type {
          type identityref {
            base ccet:card-type;
          }
          mandatory true;
          description "Module type on which action is applied";
        }
      }
      output {
        uses ccbog:rpc-status;
      }
    }
  }

  grouping deleted-ppm-actions-grp {
    description "Delete a Pluggable Port Module";
    action undelete-ppm {
      description "Action to move existing PPM from DELETED state";
      output {
        uses ccbog:rpc-status;
      }
    }
  }

  grouping equipment-grp {
    description "SVO equipment grouping";

    list devices {
      key "device";
      unique "address";
      description "List of entry physical node controlled by SVO.
                   Any devices shall have its name.
                   Different IP to avoid any ip duplicated address on the internal SVO network.";

      leaf device {
        tailf:info "A string uniquely identifying the managed device";
        type string;
        description
          "A string uniquely identifying the managed device.";
      }

      leaf address {
        tailf:info "IP address or host name for the management interface";
        type inet:host;
        mandatory true;
        description
          "IP address or host name for the management interface on the device.";
      }

      leaf admin-state {
        type admin-state;
        default unlocked;
        tailf:info "Controls configuration and southbound communication";
        description "Admin status for subtended device ";
      }

      uses svo-node-grp:ne-type;

      leaf uptime {
      	type string;
        config false;
        description "2K node uptime (live data)";
      }

      leaf first-active-chassis-uid {
       	type ccet:uid-t;
	// mandatory true;
	default 1;
      }

      uses svo-eq-grp:general {
        when "derived-from-or-self(device-type/generic/ned-id, 'ncs2k-ned:cisco-ncs2k-ned-id')";
      }

      uses cceqptog:node-info-oper {
        when "derived-from-or-self(device-type/generic/ned-id, 'ncs2k-ned:cisco-ncs2k-ned-id')";
      }

      uses controller-specific {
        when "derived-from-or-self(device-type/netconf/ned-id, 'ncs2k-ctrl-ned:cisco-svo-controller-ned-id')";
      }

      container commands {

        description "Actions from SVO ";
        // uses node-actions:actions-group;

        container node {
          description "Actions from SVO as a node ";

          uses action-2k {
            when "derived-from-or-self(../../device-type/generic/ned-id, 'ncs2k-ned:cisco-ncs2k-ned-id')";
          }

          uses action-controller {
            when "derived-from-or-self(../../device-type/netconf/ned-id, 'ncs2k-ctrl-ned:cisco-svo-controller-ned-id')";
          }

          uses action-sync-from {
            when "derived-from-or-self(../../device-type/netconf/ned-id, 'ncs2k-ctrl-ned:cisco-svo-controller-ned-id')";
          }
        }
      }
    }

    list passive-unit {
      key "uid";
      unique "passive-unit-id device";
      description "List of standalone passive units";

      leaf uid {
        type ccet:passive-unit-uid-t;
        description "the unique indentifier of passive-unit in svo across physical devices";
      }

      leaf display-name {
        type string;
        description "user-defined custom non-unique mnemonic path";
      }

      leaf passive-unit-id {
        type ccet:passive-unit-id-t;
        mandatory true;
        description " passive-unit-id is the unique index that identifies the passive-unit
                in the node. The passive-unit-id is unique in the node, so, multi-rack
                nodes do not have passive-unit-id duplicated";
      }

      leaf device {
        type leafref {
            path '/ncs:devices/ncs:device/ncs:name';
        }
        mandatory true;

        description "Device to which the passive unit is associated";
      }

      uses cceqptg:position-in-rack;

      leaf slot {
        type ccet:passive-unit-slot-t;
        mandatory true;
        description "Slot identifier";
      }

      leaf passive-unit-type {
        type identityref {
          base ccet:ru-passive-type;
        }
        mandatory true;
        description "Module type";
      }

      leaf mech-unit-subtype {
        type identityref {
          base ccet:mech-unit-subtype;
        }
        when "../passive-unit-type = 'cet:MECH_UNIT'";
        mandatory true;
        description "MECH_UNIT subtype";
      }

      leaf dcu-subtype {
        type identityref {
          base ccet:dcu-subtype;
        }
        when "../passive-unit-type = 'cet:PASSIVE_DCU'";
        mandatory true;
        description "PASSIVE DCU subtype";
      }

      leaf ru-occupation {
        type ccet:ru-occupation-t;
        when "../passive-unit-type = 'cet:MECH_UNIT' and ../mech-unit-subtype = 'cet:ALIEN_SHELF'";
        must "../passive-unit-type != 'cet:MECH_UNIT' or ../mech-unit-subtype != 'cet:ALIEN_SHELF' or
              (current() <= 40 and ../../node-information/tdm-terminology-type = 'ccet:etsi') or
              (current() <= 44 and ../../node-information/tdm-terminology-type = 'ccet:ansi')" {
          error-message "Max occupancy is 40 (ETSI) or 44 (ANSI)";
        }
        mandatory true;
        description "Number of used Rack Units for Alien Shelf";
      }

      leaf parent-unit {
        type leafref {
          path "../../passive-unit/passive-unit-id";
        }

        when "../passive-unit-type = 'cet:_15216-MD-ID-50' or ../passive-unit-type = 'cet:_15216-MD-48-CM' or ../passive-unit-type = 'cet:_15216-MD-48-CME'";

        must "count(../../passive-unit[device=current()/../device]/parent-unit[current()=.])=1" {
          error-message "only one child allowed for a given parent";
        }
        must "../../passive-unit[passive-unit-id=current()]/device = current()/../device" {
          error-message "parent unit must belong to the same physical device";
        }
        must "(current() != ../passive-unit-id)
              and
              ((../passive-unit-type = 'cet:_15216-MD-ID-50'
                   and
                   (../../passive-unit[device=current()/../device][passive-unit-id = current()]/passive-unit-type = 'cet:_15216-MD-40-ODD' or
                    ../../passive-unit[device=current()/../device][passive-unit-id = current()]/passive-unit-type = 'cet:_15216-MD-40-EVEN')
               )
               or
               ((../passive-unit-type = 'cet:_15216-MD-48-CM' or ../passive-unit-type = 'cet:_15216-MD-48-CME')
                   and
                   (../../passive-unit[device=current()/../device][passive-unit-id = current()]/passive-unit-type = 'cet:_15216-MD-40-ODD'  or
                    ../../passive-unit[device=current()/../device][passive-unit-id = current()]/passive-unit-type = 'cet:_15216-MD-40-EVEN' or
                    ../../passive-unit[device=current()/../device][passive-unit-id = current()]/passive-unit-type = 'cet:_15216-MD-48-ODD'  or
                    ../../passive-unit[device=current()/../device][passive-unit-id = current()]/passive-unit-type = 'cet:_15216-MD-48-EVEN' or
                    ../../passive-unit[device=current()/../device][passive-unit-id = current()]/passive-unit-type = 'cet:_15216-MD-48-ODDE' or
                    ../../passive-unit[device=current()/../device][passive-unit-id = current()]/passive-unit-type = 'cet:_15216-MD-48-EVENE' or
                    ../../passive-unit[device=current()/../device][passive-unit-id = current()]/passive-unit-type = 'cet:NCS1K-MD-64-C')
               )
              )
              and
              (../rack-id     = ../../passive-unit[device=current()/../device][passive-unit-id = current()]/rack-id     and
               ../ru-position = ../../passive-unit[device=current()/../device][passive-unit-id = current()]/ru-position and
               ../slot        = ../../passive-unit[device=current()/../device][passive-unit-id = current()]/slot
              )" {
          error-message "_15216-MD-ID-50 can be placed into _15216-MD-40-ODD or _15216-MD-40-EVEN; " +
                        "_15216-MD-48-CM and _15216-MD-48-CME can be placed into _15216-MD-40-ODD, _15216-MD-40-EVEN, " +
                        "_15216-MD-48-ODD, _15216-MD-48-EVEN, _15216-MD-48-ODDE, _15216-MD-48-EVENE or NCS1K-MD-64-C. " +
                        "In all cases rack unit position and slot must be the same";
        }
        mandatory true;
        description "Parent unit, valid in case of subslot";
      }

      leaf actual-ru-occupation {
        type ccet:ru-occupation-t;
        config false;
        description "Actual number of used Rack Units";
      }

      uses cceqptog:equipment-properties-oper;

      container usb-port-association-info-oper {
        description "Oper data for passive USB";
        uses ceqog:usb-port-association-info-grp-oper;
        uses ccpulg:led-status;
      }

      uses cceqptg:usb-port-association-info-grp {
        augment usb-port-association-info {
          leaf uid {
            type ccet:uid-t;
            description " uid is the unique index that identifies the chassis in the node.
                                            The uid is unique in the node, so, multi-rack nodes do not have
                                            chassis-id duplicated";
          }
        }
      }

      uses port-list;

      container commands {
        description "Actions available for passive unit(s)";
        uses passive-unit-equipments-action-grp ;
      }
    }

    list chassis {
      key "uid";
      unique "chassis-id device";
      description "List of the chassis constituting the node";

      leaf uid {
        type ccet:chassis-uid-t;
        description " the unique indentifier of chassis in svo across physical devices";
      }

      leaf display-name {
        type string;
        description "user-defined custom non-unique mnemonic path";
      }

      leaf device {
        type leafref {
          path '/ncs:devices/ncs:device/ncs:name';
        }
        mandatory true;

        // must "deref(current())/../ncs:device-type/ncs:generic/ncs:ned-id = 'ncs2k-ned:cisco-ncs2k-ned-id'" {
        //   error-message "Invalid device for this role";
        //   tailf:dependency ".";
        // }
        description "Device to which the chassis is associated";
      }

      leaf chassis-id {
        type ccet:chassis-id-t;
        mandatory true;
        description " chassis-id is the unique index that identifies the chassis in the node.";
      }

      uses cceqptg:position-in-rack;

      leaf actual-ru-occupation {
        type ccet:ru-occupation-t;
        config false;
        description "Actual number of used Rack Units";
      }

      leaf chassis-type {
        type identityref {
          base ccet:chassis-type;
        }
        mandatory true;
        description "Chassis Type";
      }

      must "derived-from(chassis-type, 'cet:ncs2k-chassis') or derived-from(chassis-type,
            'ccet:passive-chassis')" {
        error-message "Abstract chassis types are not allowed";
      }

      must "not(derived-from(chassis-type, 'cet:ncs2k-chassis')) or current()/chassis-id
            < 1000" {
        error-message "Only Passive Chassis are allowed for selected chassis Id";
      }

      must "not(derived-from(chassis-type, 'ccet:passive-chassis')) or current()/chassis-id
            > 1000" {
        error-message "Passive Chassis not allowed for selected chassis Id";
      }

      uses cceqptog:equipment-state-oper-grp;
      uses ccmog:equipment-manufacturing-data-oper-grp {
        when "derived-from(chassis-type, 'ccet:passive-chassis')";
      }

      uses cancog:ancillary-grp {
        when "chassis-type='cet:NCS2006-ANSI' or chassis-type='cet:NCS2006-ETSI'
                or chassis-type='cet:NCS2015-ANSI' or chassis-type='cet:NCS2015-ETSI'";
        augment "ancillary/ecu-slot/ecu/usb-uts-module/usb-port/associated-passive" {
          leaf uid {
            type ccet:uid-t;
            description " uid is the unique index that identifies the chassis in the node.
                          The uid is unique in the node, so, multi-rack nodes do not have
                          chassis-id duplicated";
          }
        }
      }

      uses cancog:ancillary-passive-grp {
        when "chassis-type='cet:NCS2K-MF10-6RU' or chassis-type='cet:NCS2K-MF-6RU'";
        augment "ancillary-passive/usb-uts-passive-module/usb-passive-port/associated-passive" {
          leaf uid {
            type ccet:uid-t;
            description " uid is the unique index that identifies the chassis in the node.
                          The uid is unique in the node, so, multi-rack nodes do not have
                          chassis-id duplicated";
          }
        }
      }

      container commands {
        uses chassis-actions-grp {
          when "derived-from(../chassis-type, 'cet:ncs2k-chassis') and ../equipment-state/eqp-state = 'active'";
        }
        uses deleted-chassis-actions-grp {
          when "derived-from(../chassis-type, 'cet:ncs2k-chassis')  and ../equipment-state/eqp-state = 'deleted'";
        }
      }

      container monitor {
        description "Monitoring capabilties ";

        uses ccmg:monitor-config-params-grp {
          when "../chassis-type = 'cet:NCS2006-ANSI' or ../chassis-type = 'cet:NCS2006-ETSI' or ../chassis-type = 'cet:NCS2015-ANSI' or ../chassis-type = 'cet:NCS2015-ETSI'";
        }
        // must "../ancillary/backplane-module/manufacturing-data/actual-type and string-length(../ancillary/backplane-module/manufacturing-data/actual-type)>0";
        uses ccmg:cooling-profile-grp{
          when "(../chassis-type = 'cet:NCS2006-ANSI' or ../chassis-type = 'cet:NCS2006-ETSI')";
        }
        uses ccmlg:monitor-live-data-grp {
          when "(../chassis-type = 'cet:NCS2006-ANSI' or ../chassis-type = 'cet:NCS2006-ETSI' or ../chassis-type = 'cet:NCS2015-ANSI' or ../chassis-type = 'cet:NCS2015-ETSI')";
        }
      }

      uses ccsync:timing-grp {
        when "chassis-type = 'cet:NCS2015-ANSI' or chassis-type = 'cet:NCS2015-ETSI' or chassis-type = 'cet:NCS2006-ANSI' or chassis-type = 'cet:NCS2006-ETSI'";
      }

      uses cceqptg:usb-port-association-info-grp {
        when "chassis-type='cet:NCS2K-MF10-6RU' or chassis-type='cet:NCS2K-MF-6RU'";

        augment usb-port-association-info {
          leaf uid {
            type ccet:uid-t;
            description " uid is the unique index that identifies the chassis in the node.
                                    The uid is unique in the node, so, multi-rack nodes do not have
                                    chassis-id duplicated";
          }
        }
      }

      list module {
        must "(../chassis-type != 'cet:NCS2006-ANSI'"
        + " and ../chassis-type != 'cet:NCS2006-ETSI')"
        + " or re-match(current()/slot,'([1-8]{1})(-[1-9]{1}([0-9]{1})?)?')" {
          error-message "Slot must be in range from 1 to 8 for chassis-types M6 (ETSI
                    and ANSI)";
        }

        must "(../chassis-type != 'cet:NCS2015-ANSI'"
        + " and ../chassis-type != 'cet:NCS2015-ETSI')"
        + " or re-match(current()/slot,'([1-9]{1}|([1][0-7]))(-[1-9]{1}([0-9]{1})?)?')" {
          error-message "Slot must be in range from 1 to 17 for chassis-types M15 (ETSI
                    and ANSI)";
        }

        must "(../chassis-type != 'cet:NCS2006-ANSI'"
        + " and ../chassis-type != 'cet:NCS2006-ETSI')"
        + " or re-match(current()/slot,'([1-8]{1})(-[1-9]{1}([0-9]{1})?)?')" {
          error-message "Slot must be in range from 1 to 8 for chassis-types M6 (ETSI
                    and ANSI)";
        }

        must "(../chassis-type != 'cet:NCS2015-ANSI'"
        + " and ../chassis-type != 'cet:NCS2015-ETSI')"
        + " or re-match(current()/slot,'([1-9]{1}|([1][0-7]))(-[1-9]{1}([0-9]{1})?)?')" {
          error-message "Slot must be in range from 1 to 17 for chassis-types M15 (ETSI
                    and ANSI)";
        }

        key slot;
        description "List of the modules, cards and ppm";

        leaf slot {
          type ccet:slot-t;
          description "Slot identifier 1:999 or ppmSlot identifier 1:999-1:99";
        }

        uses svo-eq-grp:module-content;

        uses usb-association-passive-shelf-grp {
            when "../chassis-type = 'cet:NCS2K-MF10-6RU' or ../chassis-type = 'cet:NCS2K-MF-6RU'";
        }

        uses ceqog:module-content-oper;

        container usb-port-association-info-oper {
          when "../../chassis-type = 'cet:NCS2K-MF10-6RU' or ../../chassis-type = 'cet:NCS2K-MF-6RU'";
          config false;
          description "Oper data for USB";
          uses ceqog:module-content-oper-usb-association;
          uses ccpulg:led-status;
        }

        uses ceqog:fpd-version-grp;

        uses port-list;

        container commands {
          description "Commands for Modules";

          uses passive-equipments-action-grp {
            when "derived-from(../../chassis-type, 'ccet:passive-chassis')";
          }

          uses card-actions-grp {
            when "derived-from(../../chassis-type, 'cet:ncs2k-chassis') and not(derived-from(../module-type, 'ccet:oper-card-type')) and derived-from(../module-type, 'ccet:card-type') and ../manufacturing-data/actual-type and not(../module-type = 'ccet:UNKNOWN-CARD')";
          }

          uses module-actions-grp {
            when "derived-from(../../chassis-type, 'cet:ncs2k-chassis')"
            + " and not(derived-from(../module-type, 'ccet:oper-card-type'))"
            + " and ../equipment-state/eqp-state != 'deleted'"
            + " and ../equipment-state/eqp-state != 'loading'";
          }

          uses deleted-card-actions-grp {
            when "derived-from(../../chassis-type, 'cet:ncs2k-chassis') and not(derived-from(../module-type, 'ccet:oper-card-type')) and not(re-match(../slot,'[0-9]+[-]{1}[0-9]+')) and ../equipment-state/eqp-state = 'deleted' and not(../module-type = 'ccet:UNKNOWN-CARD')";
          }

          uses deleted-ppm-actions-grp {
            when "derived-from(../../chassis-type, 'cet:ncs2k-chassis') and not(derived-from(../module-type, 'ccet:oper-card-type')) and re-match(../slot,'[0-9]+[-]{1}[0-9]+') and ../equipment-state/eqp-state = 'deleted'" ;
          }
        }
      }

      list functional-module-group {
        when "derived-from(../chassis-type, 'cet:ncs2k-chassis')";

        key primary-module-id;

        leaf primary-module-id {
          type leafref {
            path "../../module/slot";
          }
          description "Primary Module (card or PPM with trunk port) to configure the
                    card mode";
        }

        uses svo-eq-grp:fm-content;
        description "List of Functional Modes";
      }
      uses svo-alarm-extender:alarm-extender-params-grp;
    }
  }

  grouping internal-links-grp {
    description "SVO internal links";

    list internal-link {
      key "src-port-name dst-port-name";
      description "Internal patchcord";

      leaf src-port-name {
        type ccet:port-name-t;
        description
          "Identifier of the source portname in the format uid/[slot-id/]port-id.";
      }

      leaf dst-port-name {
        type ccet:port-name-t;
        description
          "Identifier of the destination portname in the format uid/[slot-id/]port-id.";
      }

      uses svo-eq-grp:internal-links-config-grp;
      uses cceqptog:internal-links-oper-grp;
    }
  }

  grouping external-links-grp {
    description "Fiber links among devices managed by the same SVO";
    container interdevice-link {
      tailf:hidden full;
      description "inter-device link definitions";

      list internal-link {
        key "src-port-name dst-port-name";
        description "Internal patchcord";

        leaf src-port-name {
          type ccet:port-name-t;
          description
            "Identifier of the source portname in the format uid/[slot-id/]port-id.";
        }

        leaf dst-port-name {
          type ccet:port-name-t;
          description
            "Identifier of the destination portname in the format uid/[slot-id/]port-id.";
        }
      }
    }
  }

  grouping node-connection-verification-grp {
    container connection-verification {
      uses cceqptog:node-connection-verification-oper-grp;
      uses ccvlv:cv-live-grp;
      uses cccv:cv-config-grp;
      uses cccv:cv-actions-grp;
    }
  }

}
