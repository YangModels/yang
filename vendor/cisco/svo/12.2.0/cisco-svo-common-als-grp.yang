module cisco-svo-common-als-grp {
    yang-version 1.1;
    namespace "http://cisco.com/yang/svo/common-als-grp";
    prefix "ccalsg";

    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description " Cisco Common ALS grouping Config";

    revision 2020-12-04 { 
       description "Model version for SVO Release 12.1.0 "; 
       reference cisco-svo-common-als-grp.yang; 
    }
 

    grouping als-optics-params {
    	description "ALS configuration parameters grouping";
        leaf mode {
            type cct:als-mode-t;
            description "ALS Mode";
        }

        leaf recovery-pulse-interval {
            type cct:recovery-pulse-interval-t;
            description "Recovery pulse interval in seconds";
        }

        leaf recovery-pulse-duration {
            type cct:recovery-pulse-width-t;
            description "Recovery pulse duration in seconds";
        }
        
    }
    
    grouping als-osri-params {
    	description "ALS operational data grouping";
    	leaf osri {
        	type cct:osri-mode-t;
        	description "Optical Safety Remote Interlock - manual request to shut down the amplifier";
        }
    }
}
