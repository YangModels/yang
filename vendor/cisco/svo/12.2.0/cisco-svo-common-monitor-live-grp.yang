module cisco-svo-common-monitor-live-grp {

    yang-version 1.1;
    namespace "http://cisco.com/yang/svo/common-monitor-live-grp";
    prefix "ccmlg";

    import cisco-svo-common-types { prefix cct; }
    import cisco-ncs2k-equipment-types { prefix cet; }

    organization
        "Cisco Systems, Inc.";

    contact
        "Cisco Systems, Inc. Customer Service Postal: 170 West Tasman
        Drive San Jose, CA 95134 Tel: +1 800 553-NETS E-mail: cs-yang@cisco.com";

    description " Cisco Common Monitor Live Data";

    revision 2020-12-04 { 
       description "Model version for SVO Release 12.1.0 "; 
       reference cisco-svo-common-monitor-live-grp.yang; 
    }
 
    
    grouping monitor-live-data-max-power-grp {
      leaf max-power {
          type uint32;
          units "W";
          config false;
          description "Max power";
      }
    }

    grouping monitor-live-data-psu-grp {
      list psu-voltage {
        key psu-id;
        description "List of the PSU Voltage";

        leaf psu-id {
          type cct:psu-id-t;
          description "PSU identifier";
        }

        leaf voltage-working {
            type cct:mv-t;
            config false;
            description "Voltage Psu Working";
        }

        leaf voltage-protected {
            type cct:mv-t;
            config false;
            description "Voltage Psu Protected";
        }
      }
    }

    grouping monitor-common-voltage-live-grp {
    	description "Chassis monitor live data common voltage grouping";
      leaf voltage-a {
          type cct:mv-t;
          config false;
          description "Voltage A";
      }

      leaf voltage-b {
          type cct:mv-t;
          config false;
          description "Voltage B";
      }
    }

    grouping monitor-common-live-grp {
    	description "Chassis monitor live data common data grouping";
      leaf environment-type {
          type string;
          config false;
          description "Power Monitor environment type";
      }

      leaf total-power-consumption {
          type uint32;
          units "W";
          config false;
          description "Total power consumption";
      }
      leaf chassis-temperature {
        type cct:temperature-t;
        config false;
        description "Chassis temperature";
      }
    }
    
    grouping monitor-live-data-grp {
      description "Chassis monitor live data grouping";
      
      uses monitor-common-live-grp;
      uses monitor-live-data-max-power-grp {
        when "../chassis-type = 'cet:NCS2015-ANSI' or ../chassis-type = 'cet:NCS2015-ETSI'";
      }
      container voltage {
          description "Chassis monitor voltage grouping";
          
          uses monitor-common-voltage-live-grp;
          uses monitor-live-data-psu-grp;
      }
    }
    
}
