module cisco-svo-common-if-ethernet-csmacd-oper-grp {

  yang-version 1.1;
  namespace "http://cisco.com/yang/svo/common-if-ethernet-csmacd-oper-grp";
  prefix ccifethog;
  

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines NCS2K Ethernet Interfaces";

    revision 2020-12-04 { 
       description "Model version for SVO Release 12.1.0 "; 
       reference cisco-svo-common-if-ethernet-csmacd-oper-grp.yang; 
    }
 

  
  grouping eth-oper-attributes {
    description "Ethernet operational data";
    leaf curr-speed {
      type string;
      config false;
      description
        "speed (UNKNOWN/AUTO/10/100/1000/10000) corresponding to the interface";
    }
    leaf curr-duplex {
      type string;
      config false;
      description
        "duplex (HALF/FULL) corresponding to the interface";
    }
    leaf supports-mapping-mode {
      type boolean;
      config false;
      description "True if it's possible changing the payload mapping mode";
    }
  }

}
