module cisco-svo-cache-shelf-abstractor {
  namespace "http://cisco.com/yang/svo/cache";
  prefix svo-cache;

  import tailf-common { prefix tailf; }
  
  import cisco-svo-common-equipment-types { prefix ccet; }

  tailf:export none;

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "Grouping YANG definition internal links.";

    revision 2020-12-04 { 
       description "Model version for SVO Release 12.1.0 "; 
       reference cisco-svo-cache-shelf-abstractor.yang; 
    }
 

  container virtual-shelf {
    leaf transaction-handle {
      type int32;
      description "transaction handle";
      default -2;
    }

    leaf time-reference {
      type string;
      description "utc time stamp handle";
      default "2000/1/1/0/0/0";
    }

    list chassis-from-uid {
      key uid;
      unique "device lid";

      leaf uid {
        type ccet:chassis-uid-t;
        mandatory true;
        description "chassis global unique indentifier";
      }

      leaf device {
        type string;
        description "Identifier of the device.";
      }

      leaf lid {
        type ccet:chassis-id-t;
        description "the unique index that identifies the chassis in the device.";
      }
    }

    list passive-from-uid {
      key uid;
      unique "device lid";

      leaf uid {
        type ccet:passive-unit-uid-t;
        mandatory true;
        description "passive unit global unique indentifier";
      }

      leaf device {
        type string;
        description "Identifier of the device.";
      }

      leaf lid {
        type ccet:passive-unit-id-t;
        description "the unique index that identifies the chassis in the device.";
      }
    }
  }
}
