module cisco-svo-otn-odu-connection {
    yang-version 1.1;
    namespace "http://cisco.com/yang/svo/otn-odu-connection";
    prefix svo-odu-conn;

    organization
        "Cisco Systems, Inc.";

    contact
        "Cisco Systems, Inc. Customer Service Postal: 170 West Tasman
        Drive San Jose, CA 95134 Tel: +1 800 553-NETS E-mail: cs-yang@cisco.com";

    description
        "YANG definition for SVO otn ODU cross connections";

    revision 2020-12-04 { 
       description "Model version for SVO Release 12.1.0 "; 
       reference cisco-svo-otn-odu-connection.yang; 
    }
 

    grouping odu-path-def {
        leaf if-name {
                type leafref {
                    path "../../../interface/name";
                }
                description "reference to existing interface";
        }
    }

    grouping otn-odu-connection-group {
        description "ODU connections list";

        list odu-connection {
            key "connection-name";

            leaf connection-name {
                type string;
                description
                    "odu-connection share the same resource-type and resource definition (e.g. connection)";
            }

            leaf direction {
                type enumeration {
                    enum "unidirectional" {
                        value 1;
                    }
                    enum "bidirectional" {
                        value 2;
                    }
                }
                default "bidirectional";
                description
                    "Directionality of connection. If bidirectional, both directions are created.";
            }

            list src-if-list {
                key "if-name";
                uses odu-path-def;
                description "ODU Interface name. It's typically related to Xponder's Client or Trunk ports.";
            }

            list dst-if-list {
                key "if-name";
                uses odu-path-def;
                description "ODU Interface name. It's typically  related to Xponder's Client or Trunk ports.";
            }
          }
    }    
    
}
