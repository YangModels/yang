module cisco-svo-common-protection-group-oper-grp {

    yang-version 1.1;
    namespace "http://cisco.com/yang/svo/common-protection-group-oper-grp";
    prefix "coprt-grp";

    import cisco-svo-common-types { prefix cct; } 
    import cisco-svo-common-equipment-types { prefix ccet; }
    
    
    organization
        "Cisco Systems, Inc.";

    contact
        "Cisco Systems, Inc.
     Customer Service
     
     Postal: 170 West Tasman Drive
     San Jose, CA 95134
     
     Tel: +1 800 553-NETS
     
     E-mail: cs-yang@cisco.com";

    description "
    YANG model definition for SVO Protection Groups";

    revision 2020-12-04 { 
       description "Model version for SVO Release 12.1.0 "; 
       reference cisco-svo-common-protection-group-oper-grp.yang; 
    }
  
    
    grouping protection-group-oper-grp {
    	
    	list active-interfaces {
    		key "id";
    		
    		leaf id {
    			type uint8;
    			config false;
	            description "Ordinal Identifier - used for sorting";
	        }
	    	
	    	leaf interface {
	            type ccet:port-name-t;
	            config false;
	            description "Active interface";
	    	}
	    	
	    	leaf status {
	    		type cct:switch-status-t;
	    		config false;
	    		description "Status of the protection switch";
	    	} 

			config false;
    		description "List of current active interfaces";
    	}   	
    }
}
