module cisco-svo-common-amplifier-grp {
    yang-version 1.1;
    namespace "http://cisco.com/yang/svo/common-amplifier-grp";
    prefix "ccag";

    import cisco-svo-common-types { prefix cct; }
    import cisco-svo-common-base-opt-grp { prefix ccbog; }

    organization
        "Cisco Systems, Inc.";

    contact
        "Cisco Systems, Inc. Customer Service Postal: 170 West Tasman
        Drive San Jose, CA 95134 Tel: +1 800 553-NETS E-mail: cs-yang@cisco.com";

    description " CISCO Common Amplifier Config Data grouping";

   revision 2021-04-16 { 
      description "Model version for SVO Release 12.2.0 "; 
      reference cisco-svo-common-amplifier-grp.yang; 
   }
 

    revision 2020-12-04 { 
       description "Model version for SVO Release 12.1.0 "; 
       reference cisco-svo-common-amplifier-grp.yang; 
    }
 

    grouping amp-optics-params-grp {
    	description "Amplifier configuration parameters grouping";
       
        leaf control-mode {
            type cct:amplifierControlMode-t;
            mandatory true;
            description "Amplifier control mode";
        }

        leaf role {
            type cct:ampli-role-t;
            description "Amplifier role";
         }
        
        leaf psd-setpoint {
            type cct:power-spectral-density-t;
            description "Power Spectral Density setpoint - Required in all control modes but Total Power";
        }

        leaf total-power-setpoint {
            type cct:signal-output-power-t;
            description "Total output power set value - Required when operating in Total Power mode";
        }

        leaf gain-setpoint {
            type cct:gain-t;
            description "Gain set-point - Required when Operating in Fixed Gain mode";
        }

        leaf gain-range {
            type cct:gain-range-t;
            description "Gain Range - Required by amplifier with switcheable gain";
        }

        leaf tilt-setpoint {
            type cct:tilt-t;
            description "Amplifier tilt set-point - Required in all Operating modes";
        }
    }
    
    grouping rmn-amp-optics-params-grp {
        description
          "Raman amplifier configuration parameters grouping";

        leaf gain-setpoint {
            type cct:gain-t;
            mandatory true;
            description
              "Raman amplifier gain set-point";
        }

        leaf tilt-setpoint {
            type cct:tilt-t;
            default "0.0";
            description
              "Raman amplifier tilt set-point";
        }

        list pumps-power-setpoint {
            key "pump-id";
            description
              "List of single Raman pump power setpoint";

            leaf pump-id {
                type cct:pump-id-t;
                description
                  "Ordinal id of the Raman pump";
            }

            leaf pump-power {
                type cct:mw-t;
                mandatory true;
                description
                  "Single pump power set-point";
            }
        }
        
        action manual-safety-restart {
            description
              "Manually reset all safety mechanism on Raman amplifier and start the pumps from scratch; it is services affecting";
            output {
                uses ccbog:rpc-status;
            }
        } 
    }

    grouping manual-raman-calib-params-grp {
        description
          "Manual Raman calibration configuration parameters grouping";

        leaf unsaturated-gain-setpoint {
            type cct:gain-t;
            description
              "Target unsaturated Raman Gain - required only by Co-propagating Raman amplifiers";
        }
    }

    grouping manual-raman-calib-actions-grp {
        action test-point-pump-1-low {
            description
              "Turns on only Pump 1 at low level to allow measurement of incoming probe signal power level - 
            	high frequency probe signal (step 1 of 4)";
            output {
                uses ccbog:rpc-status;
            }
        }

        action test-point-pump-1-high {
            description
              "Turns on only Pump 1 at high level to allow measurement of incoming probe signal power level - 
            	high frequency probe signal (step 2 of 4)";
            output {
                uses ccbog:rpc-status;
            }
        }

        action test-point-pump-2-low {
            description
              "Turns on only Pump 2 at low level to allow measurement of incoming probe signal power level - 
            	low frequency probe signal (step 3 of 4)";
            output {
                uses ccbog:rpc-status;
            }
        }

        action test-point-pump-2-high {
            description
              "Turns on only Pump 2 at high level to allow measurement of incoming probe signal power level - 
            	low frequency probe signal (step 4 of 4)";
            output {
                uses ccbog:rpc-status;
            }
        }

        action calibrate-pumps {
            description
              "After completing the previous four steps, evaluates the target Raman pumps power and, if obtained gain is 
            	reasonably close to target target value; otherwise will notify the error";
            input {
                uses ccbog:manual-raman-calibration-four-corners-grp;
            }
            output {
                uses ccbog:rpc-status;
                
                leaf obtained-gain {
                    type cct:gain-t;
                    description "Obtained Raman gain value";
                }
                
                leaf obtained-tilt {
                    type cct:gain-t;
                    description "Obtained Raman tilt value";
                }              
               
                leaf result {
                    type cct:raman-calib-result-t;
                    description
                      "Raman Gain result";
                }
            }
        }
        
         action terminate {
            description
              "Terminate the running calibration and restore previous values";
            output {
                uses ccbog:rpc-status;
            }
        }       
    }

    grouping automatic-raman-calib-actions-grp {
        action run-calibration {
            description
              "Manually trigger an automatic calibration run";
            output {
                uses ccbog:rpc-status;
            }
        }

        action accept-degraded-gain {
            description
              "Accept the calibration result if obtained gain is below target but still usable";
            output {
                uses ccbog:rpc-status;
            }
        }

        action get-all-calibration-reports {
            description
              "Get the full list of historcal calibrations (incuding current)";
            output {
                uses ccbog:rpc-status;
                uses ccbog:automatic-raman-calibration-report-grp;
            }
        }

        action get-last-calibration-error {
            description
              "Retrieve the last error if latest calibration failed";
            output {
                uses ccbog:rpc-status;
                leaf last-calibration-error {
                    type string;
                }
            }
        }
    }
    
    grouping raman-debug-tools-grp {
    	action get-debug-data {
    		description "Retrieve debug values from Raman Card";
    		output {
    		    uses ccbog:rpc-status;
                uses ccbog:raman-debug-data-grp;  		
    		}
    		
    	}
    	
    	action enable-pumps-debug-mode {
    	    description "Turn on Raman Pumps at APR level to retrieve debug data and/or help with in-field troubleshooting";
    		output {
    		    uses ccbog:rpc-status; 		
    		}
    	}
    	
    	action disable-pumps-debug-mode {
    	    description "Reset Raman Pumps to standard operating mode";
    		output {
    		    uses ccbog:rpc-status; 		
    		}
    	}
    	
    }
}
