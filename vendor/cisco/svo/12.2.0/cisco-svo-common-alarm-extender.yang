module cisco-svo-common-alarm-extender {
    yang-version 1.1;
    namespace "http://cisco.com/yang/svo/common-alarm-extender";
    prefix svo-alarm-extender;

    import cisco-svo-common-alarm-extender-types { prefix alext-types;}
    import cisco-ncs2k-equipment-types { prefix cet; }

    organization
        "Cisco Systems, Inc.";

    contact
        "Cisco Systems, Inc.
        Customer Service

        Postal: 170 West Tasman Drive
        San Jose, CA 95134

        Tel: +1 800 553-NETS

        E-mail: cs-yang@cisco.com";

    description
        "YANG definition for Alarm extender feature";

    revision 2020-12-04 { 
       description "Model version for SVO Release 12.1.0 "; 
       reference cisco-svo-common-alarm-extender.yang; 
    }
 


    grouping external-alarm-list-content-grp {
        leaf external-alarm-index {
            type uint32 {
                range "1..14";
            } 
        }

        leaf external-alarm-type {
            type alext-types:alarm-type;
        }
        leaf raised {
            type boolean;
        }

        leaf virtual-wire {
            type alext-types:virtual-wire;
        }

        leaf description {
            type string;
        }

        leaf provisioned {
            type boolean;
            default false;
        }    

        leaf severity {
            type alext-types:severity-t;
        }

    }

    grouping external-control-list-content-grp {

        leaf external-control-index {
            type uint32 {
                range "1..4";
            }
        }

        leaf external-control-type {
            type alext-types:external-control-type;

        } 

        leaf description {
            type string;
        }

        leaf provisioned {
            type boolean;
            default false;
        }

        leaf trigger-info {
            type alext-types:trigger-info-t;
        }
    }

    grouping user-defined-alarm-content-grp {
        leaf user-defined-alarm-index {
            type uint32 {
                range "1..50";
            }
        }
        leaf name {
            type string;
        }
    }

    grouping external-alarm-grp {

        list external-alarm-list {
            key "external-alarm-index";
            uses external-alarm-list-content-grp;
        }      
    }

    grouping external-control-grp {
        list external-control-list {
            key "external-control-index";
            uses external-control-list-content-grp;
        }      
    }
    grouping user-defined-alarm-grp {
        list user-defined-alarm-list {
            key "user-defined-alarm-index";
            uses user-defined-alarm-content-grp;
        }
    }

    grouping alarm-extender-params-grp {
        container alarm-extender {
            when "derived-from(../chassis-type, 'cet:ncs2k-chassis')";
            leaf dry-contact-mode {
                type boolean;
                default false;
            }
            uses external-alarm-grp;
            uses external-control-grp;
            uses user-defined-alarm-grp;
        }
   }
   
    grouping alarm-extender-grp {

        uses alarm-extender-params-grp;

    }
}
