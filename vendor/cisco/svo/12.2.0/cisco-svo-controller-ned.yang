module cisco-svo-controller-ned {

  namespace "http://cisco.com/yang/svo/controller-ned";
  prefix cisco-svo-controller-ned;

  import tailf-ncs-ned {
    prefix ned;
  }

  organization 
    "Cisco Systems, Inc.";

  contact 
    "Cisco Systems, Inc.
     Customer Service
     
     Postal: 170 West Tasman Drive
     San Jose, CA 95134
     
     Tel: +1 800 553-NETS
     
     E-mail: cs-yang@cisco.com";

  description 
    "YANG definition for Cisco SVO Controller: ned identification class.";

  revision 2020-12-04 { 
    description "Model version for SVO Release 12.1.0 "; 
    reference cisco-svo-controller-ned; 
  }

  identity cisco-svo-controller-ned-id {
    base ned:netconf-ned-id;
  }
}
