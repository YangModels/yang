/*
 * BEWARE BEWARE BEWARE BEWARE BEWARE BEWARE BEWARE BEWARE BEWARE
 * This file has been auto-generated by the python alarm dictionary parser: DO NOT EDIT
 * See: python main_svo_generator.py
 * Source: alarm_dictionary
 * BEWARE BEWARE BEWARE BEWARE BEWARE BEWARE BEWARE BEWARE BEWARE
*/
submodule cisco-svo-pm-rmon-alarm-types {

  belongs-to cisco-svo-alarm-tca-type {
    prefix svo-al-tca-t;
  }

  include cisco-svo-alarm-tca-type-def;
  organization
    "Cisco Systems, Inc.";

  contact
    "Cisco Systems, Inc.
    Customer Service

    Postal: 170 West Tasman Drive
    San Jose, CA 95134

    Tel: +1 800 553-NETS

    E-mail: cs-yang@cisco.com";

  description
    "This module defines the pm rmon alarm types";

   revision 2021-04-16 { 
      description "Model version for SVO Release 12.2.0 "; 
      reference cisco-svo-pm-rmon-alarm-types.yang; 
   }
 

  revision 2020-12-04 {
    description "Model version for SVO Release 12.1.0";
    reference cisco-svo-pm-rmon-alarm-types.yang;
  }

  identity pm-rmon-alarm-type {
    description "Root of pm rmon alarm type";
    base svo-al-tca-t:svo-alarm-tca-type;
  }

  identity T-ifInOctets {
    description "RMON Performance Monitor Threshold Crossing Alert";
    base pm-rmon-alarm-type;
  }

  identity T-ifInUcastPkts {
    description "RMON Performance Monitor Threshold Crossing Alert";
    base pm-rmon-alarm-type;
  }

  identity T-ifInMulticastPkts {
    description "RMON Performance Monitor Threshold Crossing Alert";
    base pm-rmon-alarm-type;
  }

  identity T-ifInBroadcastPkts {
    description "RMON Performance Monitor Threshold Crossing Alert";
    base pm-rmon-alarm-type;
  }

  identity T-ifInDiscards {
    description "RMON Performance Monitor Threshold Crossing Alert";
    base pm-rmon-alarm-type;
  }

  identity T-ifInErrors {
    description "RMON Performance Monitor Threshold Crossing Alert";
    base pm-rmon-alarm-type;
  }

  identity T-ifOutOctets {
    description "RMON Performance Monitor Threshold Crossing Alert";
    base pm-rmon-alarm-type;
  }

  identity T-ifOutUcastPkts {
    description "RMON Performance Monitor Threshold Crossing Alert";
    base pm-rmon-alarm-type;
  }

  identity T-ifOutMulticastPkts {
    description "RMON Performance Monitor Threshold Crossing Alert";
    base pm-rmon-alarm-type;
  }

  identity T-ifOutBroadcastPkts {
    description "RMON Performance Monitor Threshold Crossing Alert";
    base pm-rmon-alarm-type;
  }

  identity T-ifOutDiscards {
    description "RMON Performance Monitor Threshold Crossing Alert";
    base pm-rmon-alarm-type;
  }

  identity T-dot3StatsAlignmentErrors {
    description "RMON Performance Monitor Threshold Crossing Alert";
    base pm-rmon-alarm-type;
  }

  identity T-dot3StatsFCSErrors {
    description "RMON Performance Monitor Threshold Crossing Alert";
    base pm-rmon-alarm-type;
  }

  identity T-dot3StatsSingleCollisionFrames {
    description "RMON Performance Monitor Threshold Crossing Alert";
    base pm-rmon-alarm-type;
  }

  identity T-dot3StatsMultipleCollisionFrames {
    description "RMON Performance Monitor Threshold Crossing Alert";
    base pm-rmon-alarm-type;
  }

  identity T-dot3StatsDeferredTransmissions {
    description "RMON Performance Monitor Threshold Crossing Alert";
    base pm-rmon-alarm-type;
  }

  identity T-dot3StatsLateCollisions {
    description "RMON Performance Monitor Threshold Crossing Alert";
    base pm-rmon-alarm-type;
  }

  identity T-dot3StatsExcessiveCollisions {
    description "RMON Performance Monitor Threshold Crossing Alert";
    base pm-rmon-alarm-type;
  }

  identity T-dot3StatsFrameTooLong {
    description "RMON Performance Monitor Threshold Crossing Alert";
    base pm-rmon-alarm-type;
  }

  identity T-dot3StatsCarrierSenseErrors {
    description "RMON Performance Monitor Threshold Crossing Alert";
    base pm-rmon-alarm-type;
  }

  identity T-dot3StatsSQETestErrors {
    description "RMON Performance Monitor Threshold Crossing Alert";
    base pm-rmon-alarm-type;
  }

  identity T-etherStatsUndersizePkts {
    description "RMON Performance Monitor Threshold Crossing Alert";
    base pm-rmon-alarm-type;
  }

  identity T-etherStatsFragments {
    description "RMON Performance Monitor Threshold Crossing Alert";
    base pm-rmon-alarm-type;
  }

  identity T-etherStatsPkts64Octets {
    description "RMON Performance Monitor Threshold Crossing Alert";
    base pm-rmon-alarm-type;
  }

  identity T-etherStatsPkts65to127Octets {
    description "RMON Performance Monitor Threshold Crossing Alert";
    base pm-rmon-alarm-type;
  }

  identity T-etherStatsPkts128to255Octets {
    description "RMON Performance Monitor Threshold Crossing Alert";
    base pm-rmon-alarm-type;
  }

  identity T-etherStatsPkts256to511Octets {
    description "RMON Performance Monitor Threshold Crossing Alert";
    base pm-rmon-alarm-type;
  }

  identity T-etherStatsPkts512to1023Octets {
    description "RMON Performance Monitor Threshold Crossing Alert";
    base pm-rmon-alarm-type;
  }

  identity T-etherStatsPkts1024to1518Octets {
    description "RMON Performance Monitor Threshold Crossing Alert";
    base pm-rmon-alarm-type;
  }

  identity T-etherStatsBroadcastPkts {
    description "RMON Performance Monitor Threshold Crossing Alert";
    base pm-rmon-alarm-type;
  }

  identity T-etherStatsMulticastPkts {
    description "RMON Performance Monitor Threshold Crossing Alert";
    base pm-rmon-alarm-type;
  }

  identity T-etherStatsOversizePkts {
    description "RMON Performance Monitor Threshold Crossing Alert";
    base pm-rmon-alarm-type;
  }

  identity T-etherStatsJabbers {
    description "RMON Performance Monitor Threshold Crossing Alert";
    base pm-rmon-alarm-type;
  }

  identity T-etherStatsOctets {
    description "RMON Performance Monitor Threshold Crossing Alert";
    base pm-rmon-alarm-type;
  }

  identity T-etherStatsCollisions {
    description "RMON Performance Monitor Threshold Crossing Alert";
    base pm-rmon-alarm-type;
  }

  identity T-etherStatsCollisionFrames {
    description "RMON Performance Monitor Threshold Crossing Alert";
    base pm-rmon-alarm-type;
  }

  identity T-etherStatsCRCAlignErrors {
    description "RMON Performance Monitor Threshold Crossing Alert";
    base pm-rmon-alarm-type;
  }

  identity T-etherStatsDropEvents {
    description "RMON Performance Monitor Threshold Crossing Alert";
    base pm-rmon-alarm-type;
  }

  identity T-receivePauseFrames {
    description "RMON Performance Monitor Threshold Crossing Alert";
    base pm-rmon-alarm-type;
  }

  identity T-transmitPauseFrames {
    description "RMON Performance Monitor Threshold Crossing Alert";
    base pm-rmon-alarm-type;
  }

  identity T-receivePktsDroppedInternalCongestion {
    description "RMON Performance Monitor Threshold Crossing Alert";
    base pm-rmon-alarm-type;
  }

  identity T-transmitPktsDroppedInternalCongestion {
    description "RMON Performance Monitor Threshold Crossing Alert";
    base pm-rmon-alarm-type;
  }

  identity T-txTotalPkts {
    description "RMON Performance Monitor Threshold Crossing Alert";
    base pm-rmon-alarm-type;
  }

  identity T-rxTotalPkts {
    description "RMON Performance Monitor Threshold Crossing Alert";
    base pm-rmon-alarm-type;
  }

  identity T-hdlcPktDrops {
    description "RMON Performance Monitor Threshold Crossing Alert";
    base pm-rmon-alarm-type;
  }

  identity T-receiveControlFrames {
    description "RMON Performance Monitor Threshold Crossing Alert";
    base pm-rmon-alarm-type;
  }

  identity T-receiveUnknownOpcodeFrames {
    description "RMON Performance Monitor Threshold Crossing Alert";
    base pm-rmon-alarm-type;
  }

  identity T-ifInErrorBytePkts {
    description "RMON Performance Monitor Threshold Crossing Alert";
    base pm-rmon-alarm-type;
  }

  identity T-ifInFramingErrorPkts {
    description "RMON Performance Monitor Threshold Crossing Alert";
    base pm-rmon-alarm-type;
  }

  identity T-ifInJunkInterPkts {
    description "RMON Performance Monitor Threshold Crossing Alert";
    base pm-rmon-alarm-type;
  }

  identity T-ifOutErrors {
    description "RMON Performance Monitor Threshold Crossing Alert";
    base pm-rmon-alarm-type;
  }

  identity T-gfpStatsRxSBitErrors {
    description "RMON Performance Monitor Threshold Crossing Alert";
    base pm-rmon-alarm-type;
  }

  identity T-gfpStatsRxMBitErrors {
    description "RMON Performance Monitor Threshold Crossing Alert";
    base pm-rmon-alarm-type;
  }

  identity T-gfpStatsRxTypeInvalid {
    description "RMON Performance Monitor Threshold Crossing Alert";
    base pm-rmon-alarm-type;
  }

  identity T-gfpStatsRxCRCErrors {
    description "RMON Performance Monitor Threshold Crossing Alert";
    base pm-rmon-alarm-type;
  }

  identity T-gfpStatsRxCIDInvalid {
    description "RMON Performance Monitor Threshold Crossing Alert";
    base pm-rmon-alarm-type;
  }

  identity T-gfpStatsLFDRaised {
    description "RMON Performance Monitor Threshold Crossing Alert";
    base pm-rmon-alarm-type;
  }

  identity T-gfpStatsCSFRaised {
    description "RMON Performance Monitor Threshold Crossing Alert";
    base pm-rmon-alarm-type;
  }

  identity T-gfpStatsRxFrame {
    description "RMON Performance Monitor Threshold Crossing Alert";
    base pm-rmon-alarm-type;
  }

  identity T-gfpStatsTxFrame {
    description "RMON Performance Monitor Threshold Crossing Alert";
    base pm-rmon-alarm-type;
  }

  identity T-gfpStatsRxOctets {
    description "RMON Performance Monitor Threshold Crossing Alert";
    base pm-rmon-alarm-type;
  }

  identity T-gfpStatsTxOctets {
    description "RMON Performance Monitor Threshold Crossing Alert";
    base pm-rmon-alarm-type;
  }

  identity T-gfpStatsRoundTripLatency {
    description "RMON Performance Monitor Threshold Crossing Alert";
    base pm-rmon-alarm-type;
  }

  identity T-mediaIndStatsRxFramesTruncated {
    description "RMON Performance Monitor Threshold Crossing Alert";
    base pm-rmon-alarm-type;
  }

  identity T-mediaIndStatsRxFramesTooLong {
    description "RMON Performance Monitor Threshold Crossing Alert";
    base pm-rmon-alarm-type;
  }

  identity T-mediaIndStatsRxFramesBadCRC {
    description "RMON Performance Monitor Threshold Crossing Alert";
    base pm-rmon-alarm-type;
  }

  identity T-mediaIndStatsTxFramesBadCRC {
    description "RMON Performance Monitor Threshold Crossing Alert";
    base pm-rmon-alarm-type;
  }

  identity T-gfpStatsRxDistanceExtBuffers {
    description "RMON Performance Monitor Threshold Crossing Alert";
    base pm-rmon-alarm-type;
  }

  identity T-gfpStatsTxDistanceExtBuffers {
    description "RMON Performance Monitor Threshold Crossing Alert";
    base pm-rmon-alarm-type;
  }

  identity T-fibreStatsLinkRecoveries {
    description "RMON Performance Monitor Threshold Crossing Alert";
    base pm-rmon-alarm-type;
  }

  identity T-fibreStatsRXCredits {
    description "RMON Performance Monitor Threshold Crossing Alert";
    base pm-rmon-alarm-type;
  }

  identity T-fibreStatsTXCredits {
    description "RMON Performance Monitor Threshold Crossing Alert";
    base pm-rmon-alarm-type;
  }

  identity T-fibreStatsZeroTxCredits {
    description "RMON Performance Monitor Threshold Crossing Alert";
    base pm-rmon-alarm-type;
  }

  identity T-8b10bInvalidOrderedSets {
    description "RMON Performance Monitor Threshold Crossing Alert";
    base pm-rmon-alarm-type;
  }

  identity T-8b10bStatsEncodingDispErrors {
    description "RMON Performance Monitor Threshold Crossing Alert";
    base pm-rmon-alarm-type;
  }

  identity T-8b10bIdleOrderedSets {
    description "RMON Performance Monitor Threshold Crossing Alert";
    base pm-rmon-alarm-type;
  }

  identity T-8b10bNonIdleOrderedSets {
    description "RMON Performance Monitor Threshold Crossing Alert";
    base pm-rmon-alarm-type;
  }

  identity T-8b10bDataOrderedSets {
    description "RMON Performance Monitor Threshold Crossing Alert";
    base pm-rmon-alarm-type;
  }

  identity T-8b10bLossOfSync {
    description "RMON Performance Monitor Threshold Crossing Alert";
    base pm-rmon-alarm-type;
  }

  identity T-hdlcInOctets {
    description "RMON Performance Monitor Threshold Crossing Alert";
    base pm-rmon-alarm-type;
  }

  identity T-hdlcRxAborts {
    description "RMON Performance Monitor Threshold Crossing Alert";
    base pm-rmon-alarm-type;
  }

  identity T-hdlcOutOctets {
    description "RMON Performance Monitor Threshold Crossing Alert";
    base pm-rmon-alarm-type;
  }

  identity T-mediaIndStatsRxShortPkts {
    description "RMON Performance Monitor Threshold Crossing Alert";
    base pm-rmon-alarm-type;
  }

  identity T-mediaIndStatsOversizeDropped {
    description "RMON Performance Monitor Threshold Crossing Alert";
    base pm-rmon-alarm-type;
  }

  identity T-etherStatsPkts {
    description "RMON Performance Monitor Threshold Crossing Alert";
    base pm-rmon-alarm-type;
  }

  identity T-dot3StatsInternalMacTxErrors {
    description "RMON Performance Monitor Threshold Crossing Alert";
    base pm-rmon-alarm-type;
  }

  identity T-dot3StatsInternalMacRxErrors {
    description "RMON Performance Monitor Threshold Crossing Alert";
    base pm-rmon-alarm-type;
  }

  identity T-dot3StatsSymbolErrors {
    description "RMON Performance Monitor Threshold Crossing Alert";
    base pm-rmon-alarm-type;
  }

  identity T-ifOutOversizePkts {
    description "RMON Performance Monitor Threshold Crossing Alert";
    base pm-rmon-alarm-type;
  }

  identity T-gfpStatsRxSblkCRCErrors {
    description "RMON Performance Monitor Threshold Crossing Alert";
    base pm-rmon-alarm-type;
  }

  identity T-mediaIndStatsTxFramesTooLong {
    description "RMON Performance Monitor Threshold Crossing Alert";
    base pm-rmon-alarm-type;
  }

  identity T-ifInPayloadCrcErrors {
    description "RMON Performance Monitor Threshold Crossing Alert";
    base pm-rmon-alarm-type;
  }

  identity T-ifOutPayloadCrcErrors {
    description "RMON Performance Monitor Threshold Crossing Alert";
    base pm-rmon-alarm-type;
  }

  identity T-fibreStatsRxRecvrReady {
    description "RMON Performance Monitor Threshold Crossing Alert";
    base pm-rmon-alarm-type;
  }

  identity T-fibreStatsTxRecvrReady {
    description "RMON Performance Monitor Threshold Crossing Alert";
    base pm-rmon-alarm-type;
  }

  identity T-8b10bInvalidOrderedSetsDispErrorsSum {
    description "RMON Performance Monitor Threshold Crossing Alert";
    base pm-rmon-alarm-type;
  }

  identity T-rprIfStatsInOctets {
    description "RMON Performance Monitor Threshold Crossing Alert";
    base pm-rmon-alarm-type;
  }

  identity T-rprIfStatsInFrames {
    description "RMON Performance Monitor Threshold Crossing Alert";
    base pm-rmon-alarm-type;
  }

  identity T-rprIfStatsOutOctets {
    description "RMON Performance Monitor Threshold Crossing Alert";
    base pm-rmon-alarm-type;
  }

  identity T-rprIfStatsOutFrames {
    description "RMON Performance Monitor Threshold Crossing Alert";
    base pm-rmon-alarm-type;
  }

  identity T-rprPortCounterError {
    description "RMON Performance Monitor Threshold Crossing Alert";
    base pm-rmon-alarm-type;
  }

  identity T-rprSpanStatsInUcastClassCFrames {
    description "RMON Performance Monitor Threshold Crossing Alert";
    base pm-rmon-alarm-type;
  }

  identity T-rprSpanStatsOutUcastClassCFrames {
    description "RMON Performance Monitor Threshold Crossing Alert";
    base pm-rmon-alarm-type;
  }

  identity T-rprSpanStatsInUcastClassCOctets {
    description "RMON Performance Monitor Threshold Crossing Alert";
    base pm-rmon-alarm-type;
  }

  identity T-rprSpanStatsOutUcastClassCOctets {
    description "RMON Performance Monitor Threshold Crossing Alert";
    base pm-rmon-alarm-type;
  }

  identity T-rprSpanStatsInMcastClassCFrames {
    description "RMON Performance Monitor Threshold Crossing Alert";
    base pm-rmon-alarm-type;
  }

  identity T-rprSpanStatsOutMcastClassCFrames {
    description "RMON Performance Monitor Threshold Crossing Alert";
    base pm-rmon-alarm-type;
  }

  identity T-rprSpanStatsInMcastClassCOctets {
    description "RMON Performance Monitor Threshold Crossing Alert";
    base pm-rmon-alarm-type;
  }

  identity T-rprSpanStatsOutMcastClassCOctets {
    description "RMON Performance Monitor Threshold Crossing Alert";
    base pm-rmon-alarm-type;
  }

  identity T-rprSpanStatsInUcastClassBEirFrames {
    description "RMON Performance Monitor Threshold Crossing Alert";
    base pm-rmon-alarm-type;
  }

  identity T-rprSpanStatsOutUcastClassBEirFrames {
    description "RMON Performance Monitor Threshold Crossing Alert";
    base pm-rmon-alarm-type;
  }

  identity T-rprSpanStatsInUcastClassBEirOctets {
    description "RMON Performance Monitor Threshold Crossing Alert";
    base pm-rmon-alarm-type;
  }

  identity T-rprSpanStatsOutUcastClassBEirOctets {
    description "RMON Performance Monitor Threshold Crossing Alert";
    base pm-rmon-alarm-type;
  }

  identity T-rprSpanStatsInMcastClassBEirFrames {
    description "RMON Performance Monitor Threshold Crossing Alert";
    base pm-rmon-alarm-type;
  }

  identity T-rprSpanStatsOutMcastClassBEirFrames {
    description "RMON Performance Monitor Threshold Crossing Alert";
    base pm-rmon-alarm-type;
  }

  identity T-rprSpanStatsInMcastClassBEirOctets {
    description "RMON Performance Monitor Threshold Crossing Alert";
    base pm-rmon-alarm-type;
  }

  identity T-rprSpanStatsOutMcastClassBEirOctets {
    description "RMON Performance Monitor Threshold Crossing Alert";
    base pm-rmon-alarm-type;
  }

  identity T-rprSpanStatsInUcastClassBCirFrames {
    description "RMON Performance Monitor Threshold Crossing Alert";
    base pm-rmon-alarm-type;
  }

  identity T-rprSpanStatsOutUcastClassBCirFrames {
    description "RMON Performance Monitor Threshold Crossing Alert";
    base pm-rmon-alarm-type;
  }

  identity T-rprSpanStatsInUcastClassBCirOctets {
    description "RMON Performance Monitor Threshold Crossing Alert";
    base pm-rmon-alarm-type;
  }

  identity T-rprSpanStatsOutUcastClassBCirOctets {
    description "RMON Performance Monitor Threshold Crossing Alert";
    base pm-rmon-alarm-type;
  }

  identity T-rprSpanStatsInMcastClassBCirFrames {
    description "RMON Performance Monitor Threshold Crossing Alert";
    base pm-rmon-alarm-type;
  }

  identity T-rprSpanStatsOutMcastClassBCirFrames {
    description "RMON Performance Monitor Threshold Crossing Alert";
    base pm-rmon-alarm-type;
  }

  identity T-rprSpanStatsInMcastClassBCirOctets {
    description "RMON Performance Monitor Threshold Crossing Alert";
    base pm-rmon-alarm-type;
  }

  identity T-rprSpanStatsOutMcastClassBCirOctets {
    description "RMON Performance Monitor Threshold Crossing Alert";
    base pm-rmon-alarm-type;
  }

  identity T-rprSpanStatsInUcastClassAFrames {
    description "RMON Performance Monitor Threshold Crossing Alert";
    base pm-rmon-alarm-type;
  }

  identity T-rprSpanStatsOutUcastClassAFrames {
    description "RMON Performance Monitor Threshold Crossing Alert";
    base pm-rmon-alarm-type;
  }

  identity T-rprSpanStatsInUcastClassAOctets {
    description "RMON Performance Monitor Threshold Crossing Alert";
    base pm-rmon-alarm-type;
  }

  identity T-rprSpanStatsOutUcastClassAOctets {
    description "RMON Performance Monitor Threshold Crossing Alert";
    base pm-rmon-alarm-type;
  }

  identity T-rprSpanStatsInMcastClassAFrames {
    description "RMON Performance Monitor Threshold Crossing Alert";
    base pm-rmon-alarm-type;
  }

  identity T-rprSpanStatsOutMcastClassAFrames {
    description "RMON Performance Monitor Threshold Crossing Alert";
    base pm-rmon-alarm-type;
  }

  identity T-rprSpanStatsInMcastClassAOctets {
    description "RMON Performance Monitor Threshold Crossing Alert";
    base pm-rmon-alarm-type;
  }

  identity T-rprSpanStatsOutMcastClassAOctets {
    description "RMON Performance Monitor Threshold Crossing Alert";
    base pm-rmon-alarm-type;
  }

  identity T-rprSpanStatsInCtrlFrames {
    description "RMON Performance Monitor Threshold Crossing Alert";
    base pm-rmon-alarm-type;
  }

  identity T-rprSpanStatsOutCtrlFrames {
    description "RMON Performance Monitor Threshold Crossing Alert";
    base pm-rmon-alarm-type;
  }

  identity T-rprSpanStatsInOamEchoFrames {
    description "RMON Performance Monitor Threshold Crossing Alert";
    base pm-rmon-alarm-type;
  }

  identity T-rprSpanStatsOutOamEchoFrames {
    description "RMON Performance Monitor Threshold Crossing Alert";
    base pm-rmon-alarm-type;
  }

  identity T-rprSpanStatsInOamFlushFrames {
    description "RMON Performance Monitor Threshold Crossing Alert";
    base pm-rmon-alarm-type;
  }

  identity T-rprSpanStatsOutOamFlushFrames {
    description "RMON Performance Monitor Threshold Crossing Alert";
    base pm-rmon-alarm-type;
  }

  identity T-rprSpanStatsInOamOrgFrames {
    description "RMON Performance Monitor Threshold Crossing Alert";
    base pm-rmon-alarm-type;
  }

  identity T-rprSpanStatsOutOamOrgFrames {
    description "RMON Performance Monitor Threshold Crossing Alert";
    base pm-rmon-alarm-type;
  }

  identity T-rprSpanStatsInTopoAtdFrames {
    description "RMON Performance Monitor Threshold Crossing Alert";
    base pm-rmon-alarm-type;
  }

  identity T-rprSpanStatsOutTopoAtdFrames {
    description "RMON Performance Monitor Threshold Crossing Alert";
    base pm-rmon-alarm-type;
  }

  identity T-rprSpanStatsInTopoChkSumFrames {
    description "RMON Performance Monitor Threshold Crossing Alert";
    base pm-rmon-alarm-type;
  }

  identity T-rprSpanStatsOutTopoChkSumFrames {
    description "RMON Performance Monitor Threshold Crossing Alert";
    base pm-rmon-alarm-type;
  }

  identity T-rprSpanStatsInTopoTpFrames {
    description "RMON Performance Monitor Threshold Crossing Alert";
    base pm-rmon-alarm-type;
  }

  identity T-rprSpanStatsOutTopoTpFrames {
    description "RMON Performance Monitor Threshold Crossing Alert";
    base pm-rmon-alarm-type;
  }

  identity T-rprClientStatsInUcastClassCFrames {
    description "RMON Performance Monitor Threshold Crossing Alert";
    base pm-rmon-alarm-type;
  }

  identity T-rprClientStatsOutUcastClassCFrames {
    description "RMON Performance Monitor Threshold Crossing Alert";
    base pm-rmon-alarm-type;
  }

  identity T-rprClientStatsInUcastClassCOctets {
    description "RMON Performance Monitor Threshold Crossing Alert";
    base pm-rmon-alarm-type;
  }

  identity T-rprClientStatsOutUcastClassCOctets {
    description "RMON Performance Monitor Threshold Crossing Alert";
    base pm-rmon-alarm-type;
  }

  identity T-rprClientStatsInMcastClassCFrames {
    description "RMON Performance Monitor Threshold Crossing Alert";
    base pm-rmon-alarm-type;
  }

  identity T-rprClientStatsOutMcastClassCFrames {
    description "RMON Performance Monitor Threshold Crossing Alert";
    base pm-rmon-alarm-type;
  }

  identity T-rprClientStatsInMcastClassCOctets {
    description "RMON Performance Monitor Threshold Crossing Alert";
    base pm-rmon-alarm-type;
  }

  identity T-rprClientStatsOutMcastClassCOctets {
    description "RMON Performance Monitor Threshold Crossing Alert";
    base pm-rmon-alarm-type;
  }

  identity T-rprClientStatsInUcastClassBEirFrames {
    description "RMON Performance Monitor Threshold Crossing Alert";
    base pm-rmon-alarm-type;
  }

  identity T-rprClientStatsOutUcastClassBEirFrames {
    description "RMON Performance Monitor Threshold Crossing Alert";
    base pm-rmon-alarm-type;
  }

  identity T-rprClientStatsInUcastClassBEirOctets {
    description "RMON Performance Monitor Threshold Crossing Alert";
    base pm-rmon-alarm-type;
  }

  identity T-rprClientStatsOutUcastClassBEirOctets {
    description "RMON Performance Monitor Threshold Crossing Alert";
    base pm-rmon-alarm-type;
  }

  identity T-rprClientStatsInMcastClassBEirFrames {
    description "RMON Performance Monitor Threshold Crossing Alert";
    base pm-rmon-alarm-type;
  }

  identity T-rprClientStatsOutMcastClassBEirFrames {
    description "RMON Performance Monitor Threshold Crossing Alert";
    base pm-rmon-alarm-type;
  }

  identity T-rprClientStatsInMcastClassBEirOctets {
    description "RMON Performance Monitor Threshold Crossing Alert";
    base pm-rmon-alarm-type;
  }

  identity T-rprClientStatsOutMcastClassBEirOctets {
    description "RMON Performance Monitor Threshold Crossing Alert";
    base pm-rmon-alarm-type;
  }

  identity T-rprClientStatsInUcastClassBCirFrames {
    description "RMON Performance Monitor Threshold Crossing Alert";
    base pm-rmon-alarm-type;
  }

  identity T-rprClientStatsOutUcastClassBCirFrames {
    description "RMON Performance Monitor Threshold Crossing Alert";
    base pm-rmon-alarm-type;
  }

  identity T-rprClientStatsInUcastClassBCirOctets {
    description "RMON Performance Monitor Threshold Crossing Alert";
    base pm-rmon-alarm-type;
  }

  identity T-rprClientStatsOutUcastClassBCirOctets {
    description "RMON Performance Monitor Threshold Crossing Alert";
    base pm-rmon-alarm-type;
  }

  identity T-rprClientStatsInMcastClassBCirFrames {
    description "RMON Performance Monitor Threshold Crossing Alert";
    base pm-rmon-alarm-type;
  }

  identity T-rprClientStatsOutMcastClassBCirFrames {
    description "RMON Performance Monitor Threshold Crossing Alert";
    base pm-rmon-alarm-type;
  }

  identity T-rprClientStatsInMcastClassBCirOctets {
    description "RMON Performance Monitor Threshold Crossing Alert";
    base pm-rmon-alarm-type;
  }

  identity T-rprClientStatsOutMcastClassBCirOctets {
    description "RMON Performance Monitor Threshold Crossing Alert";
    base pm-rmon-alarm-type;
  }

  identity T-rprClientStatsInUcastClassAFrames {
    description "RMON Performance Monitor Threshold Crossing Alert";
    base pm-rmon-alarm-type;
  }

  identity T-rprClientStatsOutUcastClassAFrames {
    description "RMON Performance Monitor Threshold Crossing Alert";
    base pm-rmon-alarm-type;
  }

  identity T-rprClientStatsInUcastClassAOctets {
    description "RMON Performance Monitor Threshold Crossing Alert";
    base pm-rmon-alarm-type;
  }

  identity T-rprClientStatsOutUcastClassAOctets {
    description "RMON Performance Monitor Threshold Crossing Alert";
    base pm-rmon-alarm-type;
  }

  identity T-rprClientStatsInMcastClassAFrames {
    description "RMON Performance Monitor Threshold Crossing Alert";
    base pm-rmon-alarm-type;
  }

  identity T-rprClientStatsOutMcastClassAFrames {
    description "RMON Performance Monitor Threshold Crossing Alert";
    base pm-rmon-alarm-type;
  }

  identity T-rprClientStatsInMcastClassAOctets {
    description "RMON Performance Monitor Threshold Crossing Alert";
    base pm-rmon-alarm-type;
  }

  identity T-rprClientStatsOutMcastClassAOctets {
    description "RMON Performance Monitor Threshold Crossing Alert";
    base pm-rmon-alarm-type;
  }

  identity T-rprClientStatsInBcastFrames {
    description "RMON Performance Monitor Threshold Crossing Alert";
    base pm-rmon-alarm-type;
  }

  identity T-rprClientStatsOutBcastFrames {
    description "RMON Performance Monitor Threshold Crossing Alert";
    base pm-rmon-alarm-type;
  }

  identity T-rprErrorStatsBadParityFrames {
    description "RMON Performance Monitor Threshold Crossing Alert";
    base pm-rmon-alarm-type;
  }

  identity T-rprErrorStatsBadHecFrames {
    description "RMON Performance Monitor Threshold Crossing Alert";
    base pm-rmon-alarm-type;
  }

  identity T-rprErrorStatsTtlExpFrames {
    description "RMON Performance Monitor Threshold Crossing Alert";
    base pm-rmon-alarm-type;
  }

  identity T-rprErrorStatsTooLongFrames {
    description "RMON Performance Monitor Threshold Crossing Alert";
    base pm-rmon-alarm-type;
  }

  identity T-rprErrorStatsTooShortFrames {
    description "RMON Performance Monitor Threshold Crossing Alert";
    base pm-rmon-alarm-type;
  }

  identity T-rprErrorStatsBadFcsFrames {
    description "RMON Performance Monitor Threshold Crossing Alert";
    base pm-rmon-alarm-type;
  }

  identity T-rprErrorStatsSelfSrcUcastFrames {
    description "RMON Performance Monitor Threshold Crossing Alert";
    base pm-rmon-alarm-type;
  }

  identity T-rprErrorStatsPmdAbortFrames {
    description "RMON Performance Monitor Threshold Crossing Alert";
    base pm-rmon-alarm-type;
  }

  identity T-rprErrorStatsBadAddrFrames {
    description "RMON Performance Monitor Threshold Crossing Alert";
    base pm-rmon-alarm-type;
  }

  identity T-rprErrorStatsContainedFrames {
    description "RMON Performance Monitor Threshold Crossing Alert";
    base pm-rmon-alarm-type;
  }

  identity T-rprErrorStatsScffErrors {
    description "RMON Performance Monitor Threshold Crossing Alert";
    base pm-rmon-alarm-type;
  }

  identity T-dot3StatsControlInUnknownOpCodes {
    description "RMON Performance Monitor Threshold Crossing Alert";
    base pm-rmon-alarm-type;
  }

  identity T-dot3StatsInPauseFrames {
    description "RMON Performance Monitor Threshold Crossing Alert";
    base pm-rmon-alarm-type;
  }

  identity T-dot3StatsOutPauseFrames {
    description "RMON Performance Monitor Threshold Crossing Alert";
    base pm-rmon-alarm-type;
  }

  identity T-etherStatsPkts1519to1522Octets {
    description "RMON Performance Monitor Threshold Crossing Alert";
    base pm-rmon-alarm-type;
  }

  identity T-rprErrorOversizeFrames {
    description "RMON Performance Monitor Threshold Crossing Alert";
    base pm-rmon-alarm-type;
  }

  identity T-etherStatsTxFifoOverflowEvents {
    description "RMON Performance Monitor Threshold Crossing Alert";
    base pm-rmon-alarm-type;
  }

  identity T-ifHCInOctets {
    description "RMON Performance Monitor Threshold Crossing Alert";
    base pm-rmon-alarm-type;
  }

  identity T-ifHCInUcastPkts {
    description "RMON Performance Monitor Threshold Crossing Alert";
    base pm-rmon-alarm-type;
  }

  identity T-ifHCInMulticastPkts {
    description "RMON Performance Monitor Threshold Crossing Alert";
    base pm-rmon-alarm-type;
  }

  identity T-ifHCInBroadcastPkts {
    description "RMON Performance Monitor Threshold Crossing Alert";
    base pm-rmon-alarm-type;
  }

  identity T-ifHCOutOctets {
    description "RMON Performance Monitor Threshold Crossing Alert";
    base pm-rmon-alarm-type;
  }

  identity T-ifHCOutMulticastPkts {
    description "RMON Performance Monitor Threshold Crossing Alert";
    base pm-rmon-alarm-type;
  }

  identity T-ifHCOutBroadcastPkts {
    description "RMON Performance Monitor Threshold Crossing Alert";
    base pm-rmon-alarm-type;
  }

  identity T-etherStatsHighCapacityPkts {
    description "RMON Performance Monitor Threshold Crossing Alert";
    base pm-rmon-alarm-type;
  }

  identity T-etherStatsHighCapacityOctets {
    description "RMON Performance Monitor Threshold Crossing Alert";
    base pm-rmon-alarm-type;
  }

  identity T-etherStatsHighCapacityPkts64Octets {
    description "RMON Performance Monitor Threshold Crossing Alert";
    base pm-rmon-alarm-type;
  }

  identity T-etherStatsHighCapacityPkts65to127Octets {
    description "RMON Performance Monitor Threshold Crossing Alert";
    base pm-rmon-alarm-type;
  }

  identity T-etherStatsHighCapacityPkts128to255Octets {
    description "RMON Performance Monitor Threshold Crossing Alert";
    base pm-rmon-alarm-type;
  }

  identity T-etherStatsHighCapacityPkts256to511Octets {
    description "RMON Performance Monitor Threshold Crossing Alert";
    base pm-rmon-alarm-type;
  }

  identity T-etherStatsHighCapacityPkts512to1023Octets {
    description "RMON Performance Monitor Threshold Crossing Alert";
    base pm-rmon-alarm-type;
  }

  identity T-etherStatsHighCapacityPkts1024to1518Octets {
    description "RMON Performance Monitor Threshold Crossing Alert";
    base pm-rmon-alarm-type;
  }

  identity T-cisRxReports {
    description "RMON Performance Monitor Threshold Crossing Alert";
    base pm-rmon-alarm-type;
  }

  identity T-cisRxLeaves {
    description "RMON Performance Monitor Threshold Crossing Alert";
    base pm-rmon-alarm-type;
  }

  identity T-cisTxReports {
    description "RMON Performance Monitor Threshold Crossing Alert";
    base pm-rmon-alarm-type;
  }

  identity T-cisTxLeaves {
    description "RMON Performance Monitor Threshold Crossing Alert";
    base pm-rmon-alarm-type;
  }

  identity T-cisTxGeneralQueries {
    description "RMON Performance Monitor Threshold Crossing Alert";
    base pm-rmon-alarm-type;
  }

  identity T-cisTxGroupSpecificQueries {
    description "RMON Performance Monitor Threshold Crossing Alert";
    base pm-rmon-alarm-type;
  }

  identity T-cisRxGeneralQueries {
    description "RMON Performance Monitor Threshold Crossing Alert";
    base pm-rmon-alarm-type;
  }

  identity T-cisRxGroupSpecificQueries {
    description "RMON Performance Monitor Threshold Crossing Alert";
    base pm-rmon-alarm-type;
  }

  identity T-cisRxValidPackets {
    description "RMON Performance Monitor Threshold Crossing Alert";
    base pm-rmon-alarm-type;
  }

  identity T-cisRxInvalidPackets {
    description "RMON Performance Monitor Threshold Crossing Alert";
    base pm-rmon-alarm-type;
  }

  identity T-dot3adAggPortStatsLACPDUsRx {
    description "RMON Performance Monitor Threshold Crossing Alert";
    base pm-rmon-alarm-type;
  }

  identity T-dot3adAggPortStatsLACPDUsTx {
    description "RMON Performance Monitor Threshold Crossing Alert";
    base pm-rmon-alarm-type;
  }

  identity T-crepHflRxPdus {
    description "RMON Performance Monitor Threshold Crossing Alert";
    base pm-rmon-alarm-type;
  }

  identity T-crepHflTxPdus {
    description "RMON Performance Monitor Threshold Crossing Alert";
    base pm-rmon-alarm-type;
  }

  identity T-crepLslRxPdus {
    description "RMON Performance Monitor Threshold Crossing Alert";
    base pm-rmon-alarm-type;
  }

  identity T-crepLslTxPdus {
    description "RMON Performance Monitor Threshold Crossing Alert";
    base pm-rmon-alarm-type;
  }

  identity T-mediaIndStatsTxFramesTruncated {
    description "RMON Performance Monitor Threshold Crossing Alert";
    base pm-rmon-alarm-type;
  }

  identity T-gfpRxCmfFrame {
    description "RMON Performance Monitor Threshold Crossing Alert";
    base pm-rmon-alarm-type;
  }

  identity T-gfpTxCmfFrame {
    description "RMON Performance Monitor Threshold Crossing Alert";
    base pm-rmon-alarm-type;
  }

  identity T-etherStatsPkts1519toMaxOctets {
    description "RMON Performance Monitor Threshold Crossing Alert";
    base pm-rmon-alarm-type;
  }

  identity T-mediaIndStatsTxShortPkts {
    description "RMON Performance Monitor Threshold Crossing Alert";
    base pm-rmon-alarm-type;
  }

  identity T-mediaIndStatsRxLcvErrors {
    description "RMON Performance Monitor Threshold Crossing Alert";
    base pm-rmon-alarm-type;
  }

  identity T-mediaIndStatsTxLcvErrors {
    description "RMON Performance Monitor Threshold Crossing Alert";
    base pm-rmon-alarm-type;
  }

  identity T-dot3StatsLcvErrors {
    description "RMON Performance Monitor Threshold Crossing Alert";
    base pm-rmon-alarm-type;
  }

  identity T-dot3StatsLayer1Errors {
    description "RMON Performance Monitor Threshold Crossing Alert";
    base pm-rmon-alarm-type;
  }

  identity T-gfpStatsCHecRxMBitErrors {
    description "RMON Performance Monitor Threshold Crossing Alert";
    base pm-rmon-alarm-type;
  }

  identity T-gfpStatsTHecRxMBitErrors {
    description "RMON Performance Monitor Threshold Crossing Alert";
    base pm-rmon-alarm-type;
  }

  identity T-rx8b10bWords {
    description "RMON Performance Monitor Threshold Crossing Alert";
    base pm-rmon-alarm-type;
  }

  identity T-tx8b10bWords {
    description "RMON Performance Monitor Threshold Crossing Alert";
    base pm-rmon-alarm-type;
  }

  identity T-pcs49RxErrBer {
    description "RMON Performance Monitor Threshold Crossing Alert";
    base pm-rmon-alarm-type;
  }

  identity T-pcs49RxErrDec {
    description "RMON Performance Monitor Threshold Crossing Alert";
    base pm-rmon-alarm-type;
  }

  identity T-pcsErrCount {
    description "RMON Performance Monitor Threshold Crossing Alert";
    base pm-rmon-alarm-type;
  }

  identity T-pcsErrCount2 {
    description "RMON Performance Monitor Threshold Crossing Alert";
    base pm-rmon-alarm-type;
  }

  identity T-pcsEgRxErrFrames {
    description "RMON Performance Monitor Threshold Crossing Alert";
    base pm-rmon-alarm-type;
  }

}
