module cisco-svo-common-sync-grp {
    yang-version 1.1;
    namespace "http://cisco.com/yang/svo/common-sync-grp";
    prefix "ccsync";

    import ietf-yang-types { prefix yang; }
    import org-openroadm-interfaces { prefix or-if; revision-date 2018-09-28; }
    import cisco-svo-common-types { prefix cct; }
    import cisco-svo-common-equipment-types { prefix ccet; }
    import cisco-svo-common-sync-types { prefix synct; }
    import cisco-svo-common-base-opt-grp { prefix ccbog; }
    import cisco-ncs2k-equipment-types { prefix cet; }
    
    organization
        "Cisco Systems, Inc.";

    contact
        "Cisco Systems, Inc. Customer Service Postal: 170 West Tasman
        Drive San Jose, CA 95134 Tel: +1 800 553-NETS E-mail: cs-yang@cisco.com";

    description " Cisco Common Sync Interface, used inside both, SVO and NCS2K yang models.";

    revision 2020-12-04 { 
       description "Model version for SVO Release 12.1.0 "; 
       reference cisco-svo-common-sync-grp.yang; 
    }
 

    grouping timing-standard-grp {
        description "Timing - Standard grouping";
      leaf  current-timing-standard {
        type identityref {
          base ccet:tdm-terminology-type;
        }
        default 'ccet:ansi';
        config true;
        description "Timing Standard, ANSI or ETSI. In case of ETSI NE this elemnt is not present";
      }
    }

    grouping res-quality-level-ansi-grp {
      description "Res Quality Levell (ANSI) grouping";
      leaf  res-quality-level {
        type synct:res-quality-level-t;
        default same-As-DUS;
        config true;
        description "Reserved for Network Synchronization Quality Level.
          In case of Etsi this element is not present and the associated fixed value within the NE is above G811";
      }
    }

    grouping sync-config-grp {
        description "Timing - Sync Config grouping";
      
      container sync-config {
        description "Timing - sync-config container";

        leaf  timing-mode {
          type synct:timing-mode-t;
          default external;
          config true;
          description "Timing Mode (seconds)";
        }

        leaf  ssm-message-set {
          type synct:ssm-generation-t;
          default generation-1;
          config true;
          description "Synchronization Status Message Set Generation";
        }

        uses res-quality-level-ansi-grp  {
          when "(../../../chassis-type = 'cet:NCS2006-ANSI' or ../../../chassis-type = 'cet:NCS2015-ANSI') and 
                (../current-timing-standard = 'ccet:ansi' or not(../current-timing-standard))";
        }

        leaf  reversion-mode {
          type synct:reversion-mode-t;
          default non-revertive-behaviour;
          config true;
          description "Revertive Behaviour";
        }

        leaf  reversion-time {
          type synct:reversion-time-t;
          units "second";
          default NA;
          config true;
          description "Revertive time";
        }
        
        must "(reversion-mode = 'non-revertive-behaviour' and reversion-time = 'NA') or (reversion-mode != 'non-revertive-behaviour' and reversion-time != 'NA')" {
          error-message "when reversion-mode is non-revertive-behaviour then reversion-time must be NA and viceversa";
        }

        must "((../../../chassis-type = 'cet:NCS2006-ANSI' or ../../../chassis-type = 'cet:NCS2015-ANSI') and ssm-message-set='generation-2' and 
               (../current-timing-standard = 'ccet:ansi' or not(../current-timing-standard)) and (
                res-quality-level = 'above-PRS' or res-quality-level = 'above-STU' or res-quality-level = 'above-ST2'  or
                res-quality-level = 'above-TNC' or res-quality-level = 'above-ST3E' or res-quality-level = 'above-ST3' or
                res-quality-level = 'above-SMC' or res-quality-level = 'above-ST4' or res-quality-level = 'below-ST4'  or
                res-quality-level = 'same-As-DUS'
              )) or
              (../current-timing-standard != 'ccet:ansi' or ssm-message-set!='generation-2') or
              (../../../chassis-type = 'cet:NCS2K-MF10-6RU' or ../../../chassis-type = 'cet:NCS2K-MF-6RU') or
              (../../../chassis-type = 'cet:NCS2006-ETSI' or ../../../chassis-type = 'cet:NCS2015-ETSI') or
              (not(ssm-message-set) and not(res-quality-level))" {
          error-message "when current-timing-standard is ansi and ssm is generation-2 then res-quality-level must be one of
                        above-PRS, above-STU, above-ST2, above-TNC, above-ST3E, above-ST3, above-SMC, above-ST4, below-ST4, same-AsDUS";
        }

        must "((../../../chassis-type = 'cet:NCS2006-ANSI' or ../../../chassis-type = 'cet:NCS2015-ANSI') and ssm-message-set='generation-1' and 
               (../current-timing-standard = 'ccet:ansi' or not(../current-timing-standard)) and (
                res-quality-level = 'above-PRS' or res-quality-level = 'above-STU' or res-quality-level = 'above-ST2'  or
                res-quality-level = 'above-ST3' or res-quality-level = 'above-SMC' or res-quality-level = 'above-ST4'  or
                res-quality-level = 'same-As-DUS'
              )) or
              (../current-timing-standard != 'ccet:ansi' or ssm-message-set!='generation-1') or
              (../../../chassis-type = 'cet:NCS2K-MF10-6RU' or ../../../chassis-type = 'cet:NCS2K-MF-6RU') or
              (../../../chassis-type = 'cet:NCS2006-ETSI' or ../../../chassis-type = 'cet:NCS2015-ETSI') or
              (not(ssm-message-set) and not(res-quality-level))" {
          error-message "when current-timing-standard is ansi and ssm is generation-1 then res-quality-level must be one of
                        above-PRS, above-STU, above-ST2, above-ST3, above-SMC, above-ST4, below-ST4, same-As-DUS";
        }
      }
    }

    grouping synch-reference-interface-grp {
      description "Timing - Sync Reference Interface grouping";
      container interface {
        description "Timing - Sync Reference Interface container";
        
        leaf name {
          type string;
          config true;
          description "The name of the interface.";
        }
        leaf type {
          type identityref {
            base or-if:interface-type;
          }
          config true;
          description "The type of the interface.";
        }
      }
    }

    grouping synch-reference-source-bits-grp {
      description "Timing - Sync Reference source Bits grouping";
      leaf source-type {
        type synct:synch-reference-source-t;
        default none;
        config true;
        description "Source Reference Type";
      }
      uses synch-reference-interface-grp  {
        when "source-type = 'interface'";
      }
    }

    grouping primary-bits-grp {
      description "Timing - Primary source grouping";
      container primary-source {
        description "Timing - Primary source container";
        uses synch-reference-source-bits-grp;
      }
    }

    grouping secondary-bits-grp {
      description "Timing - secondary source grouping";
      container secondary-source {
        description "Timing - secondary source container";
        uses synch-reference-source-bits-grp;
        // Check that primary and secondary if interface must be different
        must "(../primary-source/source-type != 'interface' or source-type != 'interface') or
              (not(../primary-source/source-type) or not(source-type)) or
              ((../primary-source/source-type = 'interface' and source-type = 'interface') and (../primary-source/interface/name != interface/name)) or
              ((../primary-source/source-type = 'interface' and source-type = 'interface') and (../primary-source/interface/type != interface/type))" {
          error-message "bits 1/2: primary-source and secondary-source are equal interface";
        }
      }
    }

    grouping tertiary-bits-grp {
      description "Timing - tertiary source grouping";
      container tertiary-source {
        description "Timing - tertiary source container";
        uses synch-reference-source-bits-grp;

        // Check that primary and tertiary if interface must be different
        must "(../primary-source/source-type != 'interface' or source-type != 'interface') or
              (not(../primary-source/source-type) or not(source-type)) or
              ((../primary-source/source-type = 'interface' and source-type = 'interface') and (../primary-source/interface/name != interface/name)) or
              ((../primary-source/source-type = 'interface' and source-type = 'interface') and (../primary-source/interface/type != interface/type))" {
          error-message "bits 1/2: primary-source and secondary-source are equal interface";
        }
        // Check that secondary and tertiary if interface must be different
        must "(../secondary-source/source-type != 'interface' or source-type != 'interface') or
              (not(../secondary-source/source-type) or not(source-type)) or
              ((../secondary-source/source-type = 'interface' and source-type = 'interface') and (../secondary-source/interface/name != interface/name)) or
              ((../secondary-source/source-type = 'interface' and source-type = 'interface') and (../secondary-source/interface/type != interface/type))" {
          error-message "bits 1/2: secondary-source and secondary-source are equal interface";
        }
      }
    }

    grouping sync-refs-bits-grp {
      description "Timing - sources (primary/secondary/tertiary) grouping";
      uses primary-bits-grp;
      uses secondary-bits-grp;
      uses tertiary-bits-grp;
    }

    grouping synch-reference-source-ne-grp {
      description "Timing - source reference grouping for ne section";
      leaf source-type {
        type synct:synch-reference-source-t;
        default internal-clock;
        config true;
        description "Timing - source reference type";
      }
      uses synch-reference-interface-grp  {
        when "source-type = 'interface'";
      }
    }

    grouping primary-ne-grp {
      description "Timing - source primary grouping for ne section";
      container primary-source {
        description "Timing - source primary container for ne section";
        uses synch-reference-source-ne-grp;
      }
    }

    grouping secondary-ne-grp {
      description "Timing - source secondary grouping for ne section";
      container secondary-source {
        description "Timing - source secondary container for ne section";
        uses synch-reference-source-ne-grp;

        // Check that primary and secondary if not internal-clock must be different
        must "((../primary-source/source-type!='internal-clock' and source-type!='internal-clock') and
             (../primary-source/source-type!= source-type or
              ((../primary-source/source-type='interface' and source-type='interface') and
               (../primary-source/interface/name != interface/name or ../primary-source/interface/type != interface/type)
              ))
            ) or
            not(../primary-source/source-type) or not(source-type) or
            ../primary-source/source-type='internal-clock' or
            source-type='internal-clock'" {
          error-message "ne-reference: primary-source and secondary-source are not internal-clock then could not be equals";
        }
/*
        must "((../primary-source/source-type!='none' and source-type!='none' and ../primary-source/source-type!='internal-clock' and source-type!='internal-clock') and
             (../primary-source/source-type!= source-type or
              ((../primary-source/source-type='interface' and source-type='interface') and
               (../primary-source/interface/name != interface/name or ../primary-source/interface/type != interface/type)
              ))
            ) or
            not(../primary-source/source-type) or not(source-type) or
            ../primary-source/source-type='none' or ../primary-source/source-type='internal-clock' or
            source-type='none' or source-type='internal-clock'" {
          error-message "primary-source and secondary-source are not none/internal-clock then could not be equals";
        }
*/
      }
    }

    grouping tertiary-ne-grp {
      description "Timing - source tertiary grouping for ne section";
      container tertiary-source {
        description "Timing - source tertiary container for ne section";
        uses synch-reference-source-ne-grp;

        // Check that tertiary and secondary if not internal-clock must be different
        must "((../secondary-source/source-type!='internal-clock' and source-type!='internal-clock') and
             (../secondary-source/source-type!= source-type or
              ((../secondary-source/source-type='interface' and source-type='interface') and
               (../secondary-source/interface/name != interface/name or ../secondary-source/interface/type != interface/type)
              ))
            ) or
            not(../secondary-source/source-type) or not(source-type) or
            ../secondary-source/source-type='internal-clock' or
            source-type='none' or source-type='internal-clock'" {
          error-message "ne-reference: secondary-source and tertiary-source are not internal-clock then could not be equals";
        }
/*
        must "((../secondary-source/source-type!='none' and source-type!='none' and ../secondary-source/source-type!='internal-clock' and source-type!='internal-clock') and
             (../secondary-source/source-type!= source-type or
              ((../secondary-source/source-type='interface' and source-type='interface') and
               (../secondary-source/interface/name != interface/name or ../secondary-source/interface/type != interface/type)
              ))
            ) or
            not(../secondary-source/source-type) or not(source-type) or
            ../secondary-source/source-type='none' or ../secondary-source/source-type='internal-clock' or
            source-type='none' or source-type='internal-clock'" {
          error-message "2zzz2 secondary-source and tertiary-source are not none/internal-clock then could not be equals";
        }
*/
        // Check that tertiary and primary if not internal-clock must be different
        must "((../primary-source/source-type!='internal-clock' and source-type!='internal-clock') and
             (../primary-source/source-type!= source-type or
              ((../primary-source/source-type='interface' and source-type='interface') and
               (../primary-source/interface/name != interface/name or ../primary-source/interface/type != interface/type)
              ))
            ) or
            not(../primary-source/source-type) or not(source-type) or
            ../primary-source/source-type='internal-clock' or
            source-type='internal-clock'" {
          error-message "ne-reference: primary-source and tertiary-source are not internal-clock then could not be equals";
        }
/*
        must "((../primary-source/source-type!='none' and source-type!='none' and ../primary-source/source-type!='internal-clock' and source-type!='internal-clock') and
             (../primary-source/source-type!= source-type or
              ((../primary-source/source-type='interface' and source-type='interface') and
               (../primary-source/interface/name != interface/name or ../primary-source/interface/type != interface/type)
              ))
            ) or
            not(../primary-source/source-type) or not(source-type) or
            ../primary-source/source-type='none' or ../primary-source/source-type='internal-clock' or
            source-type='none' or source-type='internal-clock'" {
          error-message "2zz3 primary-source and tertiary-source are not none/internal-clock then could not be equals";
        }
*/
      }
    }

    grouping sync-refs-ne-grp {
      description "Timing - sources grouping for ne section";
      uses primary-ne-grp;
      uses secondary-ne-grp;
      uses tertiary-ne-grp;
    }

    grouping ne-reference-grp {
      description "Timing - Sync Ne Reference grouping";
      
      container ne-reference {
        description "Timing - Sync Ne Reference conatiner";
        uses sync-refs-ne-grp;
        must "((../../sync-config/timing-mode='external' or not(../../sync-config/timing-mode)) and
               (not(primary-source/source-type) or primary-source/source-type='internal-clock' or primary-source/source-type='bits-1-in' or primary-source/source-type='bits-2-in') and
               (not(secondary-source/source-type) or secondary-source/source-type='internal-clock' or secondary-source/source-type='bits-1-in' or secondary-source/source-type='bits-2-in') and
               (not(tertiary-source/source-type) or tertiary-source/source-type='internal-clock' or tertiary-source/source-type='bits-1-in' or tertiary-source/source-type='bits-2-in')) or
              (../../sync-config/timing-mode and ../../sync-config/timing-mode!='external')" {
          error-message "ne-reference synch with timing-mode external could be only internal-clock, bits-1-in, bits-2-in";
        }

        must "((../../sync-config/timing-mode='line') and
               (not(primary-source/source-type) or primary-source/source-type='internal-clock' or primary-source/source-type='interface') and
               (not(secondary-source/source-type) or secondary-source/source-type='internal-clock' or secondary-source/source-type='interface') and
               (not(tertiary-source/source-type) or tertiary-source/source-type='internal-clock' or tertiary-source/source-type='interface')) or
              (../../sync-config/timing-mode!='line' or not(../../sync-config/timing-mode))" {
          error-message "ne-reference synch with timing-mode line could be only internal-clock, interface";
        }

        must "((../../sync-config/timing-mode='mixed') and
               (not(primary-source/source-type) or (primary-source/source-type!='none' and primary-source/source-type!='ne-reference')) and
               (not(secondary-source/source-type) or (secondary-source/source-type!='none' and secondary-source/source-type!='ne-reference')) and
               (not(tertiary-source/source-type) or (tertiary-source/source-type!='none' and tertiary-source/source-type!='ne-reference'))) or
              (../../sync-config/timing-mode!='mixed' or not(../../sync-config/timing-mode))" {
          error-message "ne-reference synch with timing-mode mixed could be only internal-clock, bits-1-in, bits-2-in, interface";
        }

        must "((primary-source/source-type='internal-clock' or not(primary-source/source-type)) and 
               (secondary-source/source-type='internal-clock' or not(secondary-source/source-type)) and 
               (tertiary-source/source-type='internal-clock' or not(tertiary-source/source-type))) or
              (primary-source/source-type and primary-source/source-type!='internal-clock')" {
          error-message "when primary-source is internal-clock also secondary-source and tertiary-source must be internal-clock";
        }

        must "((not(secondary-source/source-type) or secondary-source/source-type='internal-clock') and 
               (not(tertiary-source/source-type) or tertiary-source/source-type='internal-clock')) or
              (secondary-source/source-type and secondary-source/source-type!='internal-clock')" {
          error-message "when secondary-source is internal-clock also  tertiary-source must be internal-clock";
        }
      }
    }

    grouping bits-1-out-grp {
        description "Timing - Sync Bits 1 Out grouping";
      
      container bits-1-out {
        description "Timing - Sync Bits 1 Out container";
        uses sync-refs-bits-grp;

        must "((not(../../sync-config/timing-mode) or ../../sync-config/timing-mode!='line') and
               (not(primary-source/source-type) or primary-source/source-type='none' or primary-source/source-type='interface') and
               (not(secondary-source/source-type) or secondary-source/source-type='none' or secondary-source/source-type='interface') and
               (not(tertiary-source/source-type) or tertiary-source/source-type='none' or tertiary-source/source-type='interface')) or
               (../../sync-config/timing-mode='line')" {
          error-message "bits-1-out synch with timing-mode different from line could be only none, interface";
        }

        must "((../../sync-config/timing-mode='line') and
               (not(primary-source/source-type) or primary-source/source-type='none' or primary-source/source-type='interface' or primary-source/source-type='ne-reference') and
               (not(secondary-source/source-type) or secondary-source/source-type='none' or secondary-source/source-type='interface' or secondary-source/source-type='ne-reference') and
               (not(tertiary-source/source-type) or tertiary-source/source-type='none' or tertiary-source/source-type='interface' or tertiary-source/source-type='ne-reference')) or
               (not(../../sync-config/timing-mode) or ../../sync-config/timing-mode!='line')" {
          error-message "bits-1-out synch with timing-mode different from line could be only none, interface, ne-reference";
        }

        must "((primary-source/source-type='none' or not(primary-source/source-type)) and 
               (secondary-source/source-type='none' or not(secondary-source/source-type)) and 
               (tertiary-source/source-type='none' or not(tertiary-source/source-type))) or
              (primary-source/source-type and primary-source/source-type!='none')" {
          error-message "bits-1-out when primary-source is none also secondary-source and tertiary-source must be none";
        }

        must "((not(secondary-source/source-type) or secondary-source/source-type='none') and 
               (not(tertiary-source/source-type) or tertiary-source/source-type='none')) or
              (secondary-source/source-type and secondary-source/source-type!='none')" {
          error-message "bits-1-out when secondary-source is none also tertiary-source must be none";
        }
      }
    }

    grouping bits-2-out-grp {
      description "Timing - Sync Bits 2 Out grouping";
      
      container bits-2-out {
        description "Timing - Sync Bits 2 Out container";
        uses sync-refs-bits-grp;

        must "((not(../../sync-config/timing-mode) or ../../sync-config/timing-mode!='line') and
               (not(primary-source/source-type) or primary-source/source-type='none' or primary-source/source-type='interface') and
               (not(secondary-source/source-type) or secondary-source/source-type='none' or secondary-source/source-type='interface') and
               (not(tertiary-source/source-type) or tertiary-source/source-type='none' or tertiary-source/source-type='interface')) or
               (../../sync-config/timing-mode='line')" {
          error-message "bits-2-out synch with timing-mode different from line could be only none, interface";
        }

        must "((../../sync-config/timing-mode='line') and
               (not(primary-source/source-type) or primary-source/source-type='none' or primary-source/source-type='interface' or primary-source/source-type='ne-reference') and
               (not(secondary-source/source-type) or secondary-source/source-type='none' or secondary-source/source-type='interface' or secondary-source/source-type='ne-reference') and
               (not(tertiary-source/source-type) or tertiary-source/source-type='none' or tertiary-source/source-type='interface' or tertiary-source/source-type='ne-reference')) or
               (not(../../sync-config/timing-mode) or ../../sync-config/timing-mode!='line')" {
          error-message "bits-2-out synch with timing-mode different from line could be only none, interface, ne-reference";
        }

        must "((primary-source/source-type='none' or not(primary-source/source-type)) and 
               (secondary-source/source-type='none' or not(secondary-source/source-type)) and 
               (tertiary-source/source-type='none' or not(tertiary-source/source-type))) or
              (primary-source/source-type and primary-source/source-type!='none')" {
          error-message "bits-2-out when primary-source is none also secondary-source and tertiary-source must be none";
        }

        must "((not(secondary-source/source-type) or secondary-source/source-type='none') and 
               (not(tertiary-source/source-type) or tertiary-source/source-type='none')) or
              (secondary-source/source-type and secondary-source/source-type!='none')" {
          error-message "bits-2-out when secondary-source is none also tertiary-source must be none";
        }
      }
    }

    grouping refs-grp {
      description "Timing - refs grouping";
      container timing-references {
        description "Timing - refs container";
        uses ne-reference-grp;
        uses bits-1-out-grp;
        uses bits-2-out-grp;
      }
    }

    grouping timing-general-grp {      
      description "Timing General grouping";
      container general {
        description "Timing General";
        uses timing-standard-grp  {
          when "../../chassis-type = 'cet:NCS2015-ANSI' or ../../chassis-type = 'cet:NCS2006-ANSI'";
        }
        uses sync-config-grp;
        uses refs-grp;
      }
    }

    grouping synch-reference-source-grp {
      description "Synch Reference source grouping";
      leaf source-type {
        type synct:synch-reference-source-t;
        mandatory true;
        description "Synch Reference source Type";
      }
      uses synch-reference-interface-grp  {
        when "source-type = 'interface'";
      }
    }

    grouping timing-actions-grp {
      description "Timing Action group";
      container commands {
        description "Timing Action commands container";

        action switch-reference-source {
          description "Action to set switch source mode of Clock reference";

          input {
            leaf reference-clock {
              type synct:reference-clock-t;
              mandatory true;
              description "Refence Clock Type (NE, Bits 1, Bits 2)";
            }

            leaf synch-switch-type {
              type synct:synch-switch-type-t;
              mandatory true;
              description "Synch Switch Type";
            }

            uses synch-reference-source-grp;

            must "source-type!='none'" {
              error-message "source-type cannot be none";
            }
            must "(source-type!='interface' and not(interface/name) and not(interface/type)) or source-type='interface'" {
              error-message "source-type not interface but interace name/type is provided";
            }
            must "(source-type='interface' and interface/name and interface/type) or source-type!='interface'" {
              error-message "source-type is interface but interace name/type not provided";
            }
            must "(reference-clock='ne' and source-type!='ne-reference') or reference-clock!='ne'" {
              error-message "source-type cannot be ne-reference for reference-clock ne";
            }
            must "(reference-clock!='ne' and source-type!='internal-clock') or reference-clock='ne'" {
              error-message "source-type cannot be internal-clock for reference-clock bits-1-out or bits-2-out";
            }
          }

          output {
            uses ccbog:rpc-status;
          }
        }

        action release-reference-source {
          description "Action to release switch source mode of Clock reference";

          input {
            leaf reference-clock {
              type synct:reference-clock-t;
              mandatory true;
              description "Refence Clock Type (NE, Bits 1, Bits 2)";
            }
          }

          output {
            uses ccbog:rpc-status;
          }
        }

        action on-demand-report {
            description "Action to acquire Synchronization Source Report";

            output {
              uses timing-report-response-grp;
            }
          }
      }
    }

    grouping reference-info-list-grp {
        description "Reference info list group";
        container reference-info-list {
            description "Reference info list container";
            list reference-info {
               description "Reference info list";
                leaf reference-number {
                    type uint16;
                    description "Reference number";
                }
                leaf admin-status {
                    type cct:admin-state-t;
                    description "Admin status";
                }
                leaf is-protect {
                    type boolean;
                    description "Is protect";
                }
                leaf stable-time {
                    type yang:date-and-time;
                    description "Stable time";
                }
                leaf current-selected {
                    type boolean;
                    description "Current selected";
                }
                leaf ssm-on {
                    type boolean;
                    description "Ssm on";
                }
                leaf ssm-quality {
                    type cct:clock-source-quality-level-t;
                    description "Ssm quality";
                }
                leaf reference-condition {
                    type synct:reference-condition-t;
                    description "Reference condition";
                }
                leaf is-ssm-valid {
                    type boolean;
                    description "Ssm validity";
                }
                leaf ssm-stable-time {
                    type yang:date-and-time;
                    description "Ssm stable time";
                }
                leaf timing-protocol {
                    type synct:timing-protocol-t;
                    description "Timing protocol";
                }
                uses synch-reference-source-grp;
            }
        }
    }

    grouping on-demand-report-list {
        description "Timing - On Demand report list group";
        container on-demand-reports {
           description "Timing - On Demand report list container";
            list on-demand-report {
                description "Timing - On Demand report list";
                leaf reference-clock {
                    type synct:reference-clock-t;
                    description "Reference Tyep (NE, Bits 1, Bits 2";
                }
                leaf timing-mode {
                    type synct:timing-mode-t;
                    description "Ting Mode";
                }
                leaf timing-state {
                    type synct:timing-state-t;
                    description "Timing State";
                }
                leaf ts-stable-time {
                    type yang:date-and-time;
                    description "Stable Time";
                }
                leaf switch-type {
                    type synct:synch-switch-type-t;
                    description "Switch type";
                }
                uses reference-info-list-grp;
            }
        }
    }

    grouping timing-report-response-grp {
      description "Timing - Report Response group";
      container timing-report-response {
        description "Timing - Report Response container";
        uses ccbog:rpc-status;
        uses on-demand-report-list;
      }
    }

    grouping facility-type-grp {
      description "Timing - Bits Facility Type grouping";
      
      leaf facility-type {
        type synct:bits-facility-t;
        config true;
        description "Bits Facility Type";
      }
    }

    grouping bit-state-grp {
      description "Timing - Bit State grouping";
      
      leaf bit-state {
        type cct:admin-state-t;
        config true;
        description "Bit State";
      }
    }

    grouping coding-grp {
      description "Timing - Coding grouping";
      
      leaf coding-type {
        type synct:line-coding-t;
        config true;
        description "Coding Type";
      }
    }

    grouping framing-grp {
      description "Timing - Framing grouping";
      
      leaf framing-type {
        type synct:line-type-t;
        config true;
        description "Framing Type";
      }
    }

    grouping bits-ssm-grp {
      description "Timing - Bits sync msg enabled / assumed quality grouping";
      
      leaf sync-messaging {
        type boolean;
        config true;
        description "Synch Message Enabled";
      }

      leaf admin-ssm-bits {
        type cct:clock-source-quality-level-t;
        config true;
        description "Assumed Quality";
      }
    }

    grouping ais-threshold-grp {
      description "Timing - Ais Threshold grouping";

      leaf ais-threshold {
        type cct:clock-source-quality-level-t;
        config true;
        description "AIS Threshold";
      }
    }

    grouping cable-type-grp {
      description "Timing - Cable Type grouping";
      
      leaf cable-type {
        type synct:cable-type-t;
        config true;
        description "Cable Type";
      }
    }

    grouping sa-bit-grp {
      description "Timing - Sa Bit grouping";
      
      leaf sa-bit {
        type synct:sa-bit-t;
        config true;
        description "Sa Bit";
      }
    }

    grouping bits-lbo-grp {
      description "Timing - Sa Bit grouping";
      
      leaf lbo {
        type synct:lbo-t;
        config true;
        description "Bits LBO";
      }
    }

    grouping facility-bits-common-grp {
      description "Timing - Facility Bits Common grouping";

      uses sa-bit-grp;
      uses cable-type-grp;
    }

    grouping facility-bits-in-grp {
      description "Timing - Facility Bits In grouping";

      container bits-in {
        description "Timing - Facility Bits In container";
        uses facility-type-grp;
        uses bit-state-grp;
        uses coding-grp;
        uses framing-grp;
        uses bits-ssm-grp;
      }
    }

    grouping facility-bits-out-grp {
      description "Timing - Facility Bits Out grouping";

      container bits-out {
        description "Timing - Facility Bits Out container";
        uses facility-type-grp;
        uses bit-state-grp;
        uses coding-grp;
        uses framing-grp;
        uses ais-threshold-grp;
        uses bits-lbo-grp {
          when "(../../../../chassis-type = 'cet:NCS2006-ANSI' or ../../../../chassis-type = 'cet:NCS2015-ANSI')
                and (../../../general/current-timing-standard = 'ccet:ansi' or not(../../../general/current-timing-standard))";
        }
      }
    }

    grouping timing-facility-bits-elem-grp {
      description "Timing - Facility Bits Elem grouping";

      uses facility-bits-common-grp {
        when "((../../../chassis-type = 'cet:NCS2006-ANSI' or ../../../chassis-type = 'cet:NCS2015-ANSI') and
               (../../general/current-timing-standard = 'ccet:etsi')
              ) or
              (../../../chassis-type = 'cet:NCS2006-ETSI' or ../../../chassis-type = 'cet:NCS2015-ETSI')";
      }
      uses facility-bits-in-grp;
      uses facility-bits-out-grp;
    }

    grouping timing-facility-bits-grp {
      description "Timing - Facility Bits grouping";

      container bits-facilities {
        description "Bits Facilities grouping";
        container bits-one {
          description "Bits One container";
          uses timing-facility-bits-elem-grp;
        }
        container bits-two {
          description "Bits Two container";
          uses timing-facility-bits-elem-grp;
        }
        must "(
              (bits-one/bits-in/coding-type = bits-one/bits-out/coding-type) and
              (bits-one/bits-in/framing-type = bits-one/bits-out/framing-type)
              ) or 
              (not(bits-one/bits-in/coding-type))" {
          error-message "bits 1 in/out must have the same coding and framing values";
        }
        must "(
              (bits-two/bits-in/coding-type = bits-two/bits-out/coding-type) and
              (bits-two/bits-in/framing-type = bits-two/bits-out/framing-type)
              ) or 
              (not(bits-two/bits-in/coding-type))" {
          error-message "bits 2 in/out must have the same coding and framing values";
        }
        must "(
              (bits-one/bits-in/facility-type = bits-one/bits-out/facility-type) and
              (bits-one/bits-out/facility-type = bits-two/bits-in/facility-type) and
              (bits-two/bits-in/facility-type = bits-two/bits-out/facility-type)
              ) or 
              (not(bits-one/bits-in/facility-type) and not(bits-one/bits-out/facility-type) and 
               not(bits-two/bits-in/facility-type) and not(bits-two/bits-out/facility-type))" {
          error-message "bits 1/2 in/out must have the same facility-type";
        }
        must "(
              (bits-one/bits-in/facility-type='BITS-FACILITY-64K') and
              (bits-one/bits-in/coding-type='AMI' and bits-one/bits-out/coding-type='AMI' and
               bits-two/bits-in/coding-type='AMI' and bits-two/bits-out/coding-type='AMI') and
              (bits-one/bits-in/framing-type='LINETYPE-NOT-APPLICABLE' and bits-one/bits-out/framing-type='LINETYPE-NOT-APPLICABLE' and
               bits-two/bits-in/framing-type='LINETYPE-NOT-APPLICABLE' and bits-two/bits-out/framing-type='LINETYPE-NOT-APPLICABLE') and
              (bits-one/bits-in/sync-messaging='false' and bits-two/bits-in/sync-messaging='false')
              ) or 
              (not( bits-one/bits-in/facility-type) or bits-one/bits-in/facility-type='BITS-FACILITY-2MHZ' or bits-one/bits-in/facility-type='BITS-FACILITY-T1' or bits-one/bits-in/facility-type='BITS-FACILITY-E1') or
              (../../chassis-type = 'cet:NCS2K-MF10-6RU' or ../../chassis-type = 'cet:NCS2K-MF-6RU')" {
          error-message "when facility-type is 64k then coding-type must be AMI, framing-type must be not applicable and sync-messaging must be false";
        }
        must "(
              (bits-one/bits-in/facility-type='BITS-FACILITY-2MHZ') and
              (bits-one/bits-in/coding-type='LINECODING-NOT-APPLICABLE' and bits-one/bits-out/coding-type='LINECODING-NOT-APPLICABLE' and
               bits-two/bits-in/coding-type='LINECODING-NOT-APPLICABLE' and bits-two/bits-out/coding-type='LINECODING-NOT-APPLICABLE') and
              (bits-one/bits-in/framing-type='LINETYPE-NOT-APPLICABLE' and bits-one/bits-out/framing-type='LINETYPE-NOT-APPLICABLE' and
               bits-two/bits-in/framing-type='LINETYPE-NOT-APPLICABLE' and bits-two/bits-out/framing-type='LINETYPE-NOT-APPLICABLE') and
              (bits-one/bits-in/sync-messaging='false' and bits-two/bits-in/sync-messaging='false')
              ) or 
              (not( bits-one/bits-in/facility-type) or bits-one/bits-in/facility-type='BITS-FACILITY-64K' or bits-one/bits-in/facility-type='BITS-FACILITY-T1' or bits-one/bits-in/facility-type='BITS-FACILITY-E1') or
              (../../chassis-type = 'cet:NCS2K-MF10-6RU' or ../../chassis-type = 'cet:NCS2K-MF-6RU')" {
          error-message "when facility-type is 2mhz then coding-type and framing-type must be not applicable and sync-messaging must be false";
        }
        must "(
              (bits-one/bits-in/facility-type='BITS-FACILITY-E1' or bits-one/bits-in/facility-type='BITS-FACILITY-T1') and
              (bits-one/bits-in/coding-type!='LINECODING-NOT-APPLICABLE' and bits-one/bits-out/coding-type!='LINECODING-NOT-APPLICABLE' and
               bits-two/bits-in/coding-type!='LINECODING-NOT-APPLICABLE' and bits-two/bits-out/coding-type!='LINECODING-NOT-APPLICABLE') and
              (bits-one/bits-in/framing-type!='LINETYPE-NOT-APPLICABLE' and bits-one/bits-out/framing-type!='LINETYPE-NOT-APPLICABLE' and
               bits-two/bits-in/framing-type!='LINETYPE-NOT-APPLICABLE' and bits-two/bits-out/framing-type!='LINETYPE-NOT-APPLICABLE')
              ) or 
              (not( bits-one/bits-in/facility-type)) or
              (bits-one/bits-in/facility-type='BITS-FACILITY-64K' or bits-one/bits-in/facility-type='BITS-FACILITY-2MHZ') or
              (../../chassis-type = 'cet:NCS2K-MF10-6RU' or ../../chassis-type = 'cet:NCS2K-MF-6RU')" {
          error-message "when facility-type is e1 or t1 then coding-type and framing-type must different from not applicable";
        }
        must "(
              (bits-one/bits-in/facility-type='BITS-FACILITY-64K' or bits-one/bits-in/facility-type='BITS-FACILITY-2MHZ') and
              (bits-one/sa-bit='SA-none' and bits-two/sa-bit='SA-none')
              ) or 
              (not( bits-one/bits-in/facility-type) or bits-one/bits-in/facility-type='BITS-FACILITY-T1' or bits-one/bits-in/facility-type='BITS-FACILITY-E1') or
               (../../chassis-type = 'cet:NCS2K-MF10-6RU' or ../../chassis-type = 'cet:NCS2K-MF-6RU')" {
          error-message "when facility-type is 64k or 2mhz then sa-bit must be not applicable";
        }
      }
    }

    grouping timing-grp {
      description "Timing grouping";
      container timing {
        description "Timing";
        uses timing-general-grp;
        uses timing-facility-bits-grp;
        uses timing-actions-grp ;
      }
   }
}
