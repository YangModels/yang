module cisco-svo-building-grp {
  yang-version 1.1;
  namespace "http://cisco.com/yang/svo/building-grp";
  prefix svo-building-grp;

  import cisco-svo-common-equipment-types { prefix ccet; }


  organization
    "Cisco Systems, Inc.";

  contact
    "Cisco Systems, Inc.
     Customer Service

     Postal: 170 West Tasman Drive
     San Jose, CA 95134

     Tel: +1 800 553-NETS

     E-mail: cs-yang@cisco.com";

  description
    "Grouping YANG definition for SVO node building related information.";

    revision 2020-12-04 { 
       description "Model version for SVO Release 12.1.0 "; 
       reference cisco-svo-building-grp.yang; 
    }
 



  identity no-standard-rack {
    base ccet:tdm-terminology-type;
    description "ANSI system type";
  }


  grouping rack-width {
      leaf width {
        units "inches";
        type uint8;
        description "The width of the rack";
      }
  }

  grouping building-grp{
  container building-information{
    leaf building-name {
      type string;
      description "A human readable string that is the name of the building that contains the racks";
    }
    
    container building-address {
      leaf state {
        type string;
        description "The state where is the building";
      }
      leaf country {
        type string;
        description "The country where is the building";
      }
      leaf address {
        type string;
        description "The address where is the building";
      }
      leaf zip {
        type string;
        description "The zip code where is the building";
      }
    } 
    
    list racks {
      key rack-number;
      unique "svo-rack-id";
      
      leaf rack-number {
        type uint8;
        description "an unique number that refer the rack";
      }
      
      leaf rack-type {
        type identityref {
          base ccet:tdm-terminology-type;
        }
        description "System Type, ANSI or ETSI";
      }
 
      uses rack-width {      
        when "../../tdm-terminology-type = 'ccet:ansi'";
      }
 
      leaf number-of-ru {
        type uint8;
        description "how many rack unit, this define the height of the rack";
      }
      
      leaf svo-rack-id {
        type leafref {
          path "/svo/chassis/rack-id";
        }
        description "it refers to the svo rack-id if the rack is one of those are controlled by the system";
      }
      
      leaf description {
        type string;
        description "Human readable label that describe the rack";
      }
    } 
    
    container building-rooms {
      list rooms {
        key "room-name";
            description "The list of rooms in the building where a rack with, at least, one svo controlled device is present.";
       
        leaf room-name {
          type string;
          description "The name of the room.";
        }
        
        leaf floor {
          type string;
        description "The floor where there is the room that contains the list of racks";
        }
        
        leaf description {
          type string;
        description "Human readable label to describe the room";
        }          

        list rack-position {
          key "rack-number";
          unique "row position-in-row";
          description "Two rack cannot share the same position";

          leaf rack-number {
            type leafref {
              path "../../../../racks/rack-number";
            }
            description "refer to the specific rack has been configured";
          }
          leaf row {
            type uint16;
            mandatory true;
            description "The row number on where is present the rack";
          }          
          leaf position-in-row {
            type uint16;
            mandatory true;
            description "The position on the row";
          }
        }
      }
    }
  }
 }
}
