module cisco-svo-common-als-live-grp {

    yang-version 1.1;
    namespace "http://cisco.com/yang/svo/common-als-live-grp";
    prefix "ccalslg";

    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description " Cisco Common ALS Live Data grouping";

    revision 2020-12-04 { 
       description "Model version for SVO Release 12.1.0 "; 
       reference cisco-svo-common-als-live-grp.yang; 
    }
 

    grouping als-live-data {
    	description "ALS live data grouping";
        leaf status {
            type cct:als-status-t;
            config false;
            description "ALS Status";
        }
    }
}
