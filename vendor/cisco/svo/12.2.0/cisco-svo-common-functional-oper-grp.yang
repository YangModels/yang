module cisco-svo-common-functional-oper-grp {

    yang-version 1.1;
    namespace "http://cisco.com/yang/svo/common-functional-oper-grp";
    prefix "ccfunctog";

    import ietf-inet-types { prefix inet; }
    import ietf-yang-types {prefix yang; }
    import cisco-svo-common-types { prefix cct; }
    import cisco-svo-common-equipment-types { prefix ccet; }
    import cisco-svo-common-base-opt-oper-grp { prefix ccboog; }
    
    organization
        "Cisco Systems, Inc.";

    contact
        "Cisco Systems, Inc. Customer Service Postal: 170 West Tasman
        Drive San Jose, CA 95134 Tel: +1 800 553-NETS E-mail: cs-yang@cisco.com";

    description "Cisco Common Functional Operational group";

    revision 2020-12-04 { 
       description "Model version for SVO Release 12.1.0 "; 
       reference cisco-svo-common-functional-oper-grp.yang; 
    }
 

    grouping node-degrees-oper-data {
    	description "Degree opeartional data grouping";

        leaf remote-node {
            type inet:ip-address;
            config false;
            description "Remote neighbouring node IP address";
        }

        leaf remote-degree-uid {
            type uint32;
            config false;
            description "Remote neighbouring side Unique Id (0 means no side connected";
        }

        leaf remote-shelf {
            type inet:ip-address;
            config false;
            description "Remote neighbouring shelf IP address";
        }

        list degree-interface {
          key interface-name {
            // string type matching the interface name among interfaces on the node.
          }

          leaf interface-name {
            type ccet:port-name-t;
            config false;
          }

          config false;
          description "List of all Interfaces logically belonging to the degree; all optical signals
                  traversing any of those interfaces can only be originated transmitted through the
                  degree input and output interfaces";
        }

    }

    grouping OMS-link-oper {
    	description "OMS link operational data grouping";

        list link-nodes {
            key "position";

            leaf position {
                type uint32;
                config false;
                description "Ordinal of the node in the list";
            }

            leaf node-ip {
                type inet:ip-address;
                config false;
                description "IP address of the node";
            }

            leaf input-degree-uid {
            	type cct:degree-uid-t;
                config false;
                description "Unique ID of the input degree in the node";
            }

            leaf output-degree-uid {
            	type cct:degree-uid-t;
                config false;
                description "Unique ID of the output degree in the node";
            }

            config false;
            description "List of nodes included in the link and managed by this ROADM node link power control";
        }
    }

    grouping OMS-link-GN-performance-oper-data {
    	description "GN model operational data grouping";
        uses ccboog:GN-Performance-Data;
    }

	grouping OMS-link-regulated-elements {
		description "Lists of elements regulated by the Link Power Control";

	   	list regulated-transport-interface {
       		key "name";

       	    leaf name {
               	type ccet:port-name-t;
               	config false;
               	description "The name of the interface.";
           	}

           	leaf regulation-order {
               	type uint32;
               	config false;
               	description "Specify the sequence of regulation done by the Link Power Control";
           	}

           	config false;
           	description "Lists of interfaces regulated by the Link Power Control";
        }

       	list regulated-amplifier {
       		key "egress-if";

           	leaf ingress-if {
           		type ccet:port-name-t;
               	config false;
               	description "Identifier of the amplifier input interface";
           	}

           	leaf egress-if {
           		type ccet:port-name-t;
               	config false;
               	description "Identifier of the amplifier output interface";
           	}

            leaf regulation-order {
               	type uint32;
               	config false;
               	description "Specify the sequence of regulation done by the Link Power Control";
           	}

           	config false;
           	description "Lists of amplifiers regulated by the Link Power Control";
       	}
	}

    grouping OMS-link-power-control-oper {
    	description "OMS link power control operational data grouping";

        leaf service-status {
            type cct:Pwr-Ctrl-status-t;
            config false;
            description "Current Status of Link Power Control; notifies whether Link Power Control can run on the link and,
				in case it cannot, what is the reason prevening Power Control from running";
        }

        leaf progress-status {
            type cct:Pwr-Ctrl-progress-status-t;
            config false;
            description "Current Progress Status of Link Power Control";
        }

        container path1 {
			uses OMS-link-regulated-elements;
            config false;
            description "List of regulated elements along optical path";
        }

        container path2 {
			uses OMS-link-regulated-elements;
            config false;
            description "List of regulated elements along optical path";
        }
    }

    grouping span-loss-oper-data {
        description "Span loss operational data grouping";

        list span-loss-measure {
            key "measured-by";

            leaf measured-by {
                type cct:span-loss-measure-ch-t;
                config false;
                description "Measurement channel type used for the span loss analysis";
            }

            leaf measured-span-loss {
                type cct:db-oper-t;
                config false;
                description "Span loss value";
            }

            leaf measured-span-loss-accuracy {
                type cct:db-oper-t;
                config false;
                description "Span loss accuracy";
            }

            leaf measure-time {
              type yang:date-and-time;
              description
                "The last time the value of the span loss has been measured by the device";
            }

            config false;
            description "List of Span loss measured on the span";
        }
    }

    grouping srg-oper-data {
      description "list of oper data for Shared Risk Group";

      leaf omni-directional {
        type boolean;
        config false;
        description "True : services created on this SRG can be routed on any degree; false : services can be routed only through the degree with the same degree UID";
      }

      list add-drop-interface {
        key interface-name {
          // string type matching the interface name among interfaces on the node.
        }

        leaf interface-name {
          type ccet:port-name-t;
          config false;
        }

        config false;
        description "List of Add-Drop Interfaces belonging to the shared risk group";
      }
      container add-path {
        uses ccboog:GN-Performance-Data;
      }
      container drop-path {
        uses ccboog:GN-Performance-Data;
      }
    }
}
