module cisco-svo-if-otn-otu {
    yang-version 1.1;
    namespace "http://cisco.com/yang/svo/otn-otu";
    prefix svo-otn-otu;

    import cisco-svo-common-interface-grp { prefix ccig;}
    import cisco-svo-common-otn-grp { prefix ccotng; }
    import cisco-svo-common-otn-otu-grp {prefix cotu;}
    import cisco-svo-common-otn-oper-grp { prefix ccotnog; }
    import cisco-svo-common-otn-otu-oper-grp {prefix cotuog;}
    import cisco-svo-common-otn-live-grp { prefix ccotnlg; }

    organization
        "Cisco Systems, Inc.";

    contact
        "Cisco Systems, Inc. Customer Service Postal: 170 West Tasman
        Drive San Jose, CA 95134 Tel: +1 800 553-NETS E-mail: cs-yang@cisco.com";

    description
        "YANG definition for device interfaces";

   revision 2021-04-16 { 
      description "Model version for SVO Release 12.2.0 "; 
      reference cisco-svo-if-otn-otu.yang; 
   }
 

    revision 2020-12-04 { 
       description "Model version for SVO Release 12.1.0 "; 
       reference cisco-svo-if-otn-otu.yang; 
    }
 

	grouping otn-otu-group {
		uses ccotnog:otu-attributes;

		uses cotu:hd-fec-grp;

		container proactive-protection {
			uses cotuog:proactive-protection-oper-grp;
			uses cotu:proactive-protection-cfg-grp;
		}

		container optical-transport-unit {
			container tti {
				uses ccotng:tti-cfg-grp;
				uses ccotnog:tti-oper-grp;
			}
			container legacy-tti {
				uses ccotng:legacy-tti-cfg-grp;
				uses ccotnog:tti-oper-grp;
			}

			uses ccotnlg:tti-live-grp;
			uses ccotnlg:legacy-tti-live-grp;
			
			
			container synchronization {
				uses ccotnog:sync-oper-grp;
				uses ccotng:sync-cfg-grp;
			}

                        uses cotu:odu-transparency-grp;
		}
	}
	
    grouping otn-otu-grp {
    	description "OTN OTU grouping";
        container otn-otu {
            description "Specific otn-otu Data";

            uses otn-otu-group;
            uses ccig:maintenance-loopback;
        }
    }
}
