module cisco-svo-common-otn-live-grp {

  yang-version 1.1;
  namespace "http://cisco.com/yang/svo/common-otn-live-grp";
  prefix ccotnlg;

  import cisco-svo-common-otn-types { prefix ccotnt; }
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO OTN common Live Data.";

    revision 2020-12-04 { 
       description "Model version for SVO Release 12.1.0 "; 
       reference cisco-svo-common-otn-live-grp.yang; 
    }
 


  grouping prbs-live-grp {
    container prbs-live {
      leaf detected-pattern {
        type ccotnt:prbs-pattern;
        config false;
        description "Detected prbs pattern";
      }
      leaf sync-status {
        type ccotnt:prbs-pattern-status;
        config false;
        description "Status of prbs pattern matching";
      }
      leaf error-counter {
        type uint32;
        config false;
        description "Counter of prbs errors";
      }
    }
  }
  
  grouping tti-live-grp {
    container tti-live {
      leaf accepted-sapi {
        type string;
        config false;
        description
        "The accepted SAPI recovered from the received multi-frame TTI field.
        Received SAPI contains the receive data, minus the sapi[0] and any 0x00 padding at the end";
      }
      leaf accepted-dapi {
        type string;
        config false;
        description
        "The accepted DAPI recovered from the received multi-frame TTI field
        Received DAPI contains the receive data, minus the dapi[0] and any 0x00 padding at the end";
      }
      leaf accepted-operator {
        type string;
        config false;
        description
        "The accepted Operator Specific field recovered from the received multi-frame TTI field";
      }
    }
  }
  
  grouping legacy-tti-live-grp {
    description "Optical Transport Network (OTN) old G.709 TTI live data management";
    container legacy-tti-live {
      leaf accepted-tti {
        type string;
        config false;
        description
        "The accepted TTI recovered from the received multi-frame TTI field.
        Received TTI is a 0..64 char string";
      }
    }
  }
}
