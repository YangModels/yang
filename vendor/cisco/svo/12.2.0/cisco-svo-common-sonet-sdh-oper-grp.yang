module cisco-svo-common-sonet-sdh-oper-grp {
  yang-version 1.1;
  namespace "http://cisco.com/yang/svo/common-sonet-sdh-oper-grp";
  prefix cossdhog;

  import cisco-svo-common-sonet-sdh-types { prefix ccssdht; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the SONET/SDH interface Operational Data.";

   revision 2021-04-16 { 
      description "Model version for SVO Release 12.2.0 "; 
      reference cisco-svo-common-sonet-sdh-oper-grp.yang; 
   }
 

    revision 2020-12-04 { 
       description "Model version for SVO Release 12.1.0 "; 
       reference cisco-svo-common-sonet-sdh-oper-grp.yang; 
    }
 

  grouping sonet-oper-base-parameter-group {
    leaf sonet-rate {
      type ccssdht:sonet-rate-t;
      config false;
      description "SONET Interface Rate";
    }
  }

  grouping sdh-oper-base-parameter-group {
    leaf sdh-rate {
      type ccssdht:sdh-rate-t;
      config false;
      description "SDH Interface Rate";
    }
  }

  grouping sonet-sdh-oper-synchronization-parameter-group {
      leaf provides-Sync {
       type boolean;
       config false;
       description "providesSyncFromCard - is used to indicate that this facility is the one providing the clock.";
    }
  }
  
  grouping sonet-oper-group {
    uses sonet-oper-base-parameter-group;
    container synchronization-oper {
      description "sonet synchronization oper data";
      uses sonet-sdh-oper-synchronization-parameter-group;
    }    
  }

  grouping sdh-oper-group {
    uses sdh-oper-base-parameter-group;
    container synchronization-oper {
      description "sdh synchronization oper data";
      uses sonet-sdh-oper-synchronization-parameter-group;
    }
  }
}
