module cisco-svo-common-amplifier-live-grp {

    yang-version 1.1;
    namespace "http://cisco.com/yang/svo/common-amplifier-live-grp";
    prefix "ccalg";

    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description " CISCO Common Amplifier Live Data grouping";

   revision 2021-04-16 { 
      description "Model version for SVO Release 12.2.0 "; 
      reference cisco-svo-common-amplifier-live-grp.yang; 
   }
 

    revision 2020-12-04 { 
       description "Model version for SVO Release 12.1.0 "; 
       reference cisco-svo-common-amplifier-live-grp.yang; 
    }
 
    
    grouping ampli-live-data {
    	description "Amplifier live data grouping";
    	
    	 leaf total-output-power {
             type cct:dbm-oper-t;
             config false;
             description "Amplifier total output power";
         }
         
         leaf active-services {
             type uint32;
             config false;
             description "Number of active services";
         }

         leaf actual-gain {
             type cct:db-oper-t;
             config false;
             description "Actual power gain value";
         }

         leaf target-gain {
             type cct:db-oper-t;
             config false;
             description "Power gain value requested to the device";
         }

         leaf status {
             type cct:amplifierStatus-t;
             config false;
             description "Current status of Amplifier";
         }

         leaf psd-optimized {
           type cct:psd-oper-t;
           config false;
           description "Current Spectral Density setpoint resulting from internal optimization";
       }
    }
    
    grouping rmn-ampli-live-data {
    	description "Raman amplifier live data grouping";

        list pumps-power {
        	key "pump-id";       	
        	config false;
        	description "List of single Raman pump power";

			leaf pump-id {
                type cct:pump-id-t;
                config false;
                description "Ordinal id of the Raman pump";
            }

            leaf pump-power {
                type cct:mw-oper-t;
                config false;
                description "Single pump power";
            }
        }

        leaf status {
             type cct:amplifierStatus-t;
             config false;
             description "Current status of Amplifier";
         }

    }
    
    
}
