module cisco-svo-common-node-functionalities-grp {
    yang-version 1.1;
    namespace "http://cisco.com/yang/svo/common-node-functionalities-grp";
    prefix "ccnfg";

    import ietf-yang-types {
        prefix ietf;
    }
    import tailf-common {
        prefix tailfs;
    }
    import ietf-inet-types {
        prefix inet;
    }

    organization
      "Cisco Systems, Inc.";

    contact
      "Cisco Systems, Inc. Customer Service Postal: 170 West Tasman
       Drive San Jose, CA 95134 Tel: +1 800 553-NETS E-mail: cs-yang@cisco.com";

    description
      " Cisco Common Node functionalities gruping";

    revision 2020-12-04 { 
       description "Model version for SVO Release 12.1.0 "; 
       reference cisco-svo-common-node-functionalities-grp.yang; 
    }
 

    typedef file-transfer-status {
        type enumeration {

            enum "transfer-in-progress" {
                description
                  "backup zip file transfer in progress";
            }
            enum "transfer-completed" {
                description
                  "backup zip file transfer completed";
            }
            enum "transfer-failed" {
                description
                  "backup zip file transfer failed";
            }
        }
    }

    typedef file-transfer-type {
        type enumeration {

            enum "upload" {
                description
                  "upload towards a remote server";
            }
            enum "download" {
                description
                  "download from remote server";
            }
        }
    }

    typedef protocol-type {
        description
          "Defines the supported protocols for download of package";
        type enumeration {
            enum "sftp" {
                value 1;
            }
        }
    }

    grouping log-status-msg {
        leaf current-log-status-time {
            type ietf:date-and-time;
            description
              "return data and time of the diagnostic log status.";
        }

        leaf log-message {
            type string;
            description
              "Message of the diagnostic status.";
        }
    }

    grouping upload-input-param {
        leaf protocol {
            type protocol-type;
            description
              "Protocol to be used to download the package";
        }
        choice credential {
            case user-password {
                leaf user {
                    type string;
                    description
                      "user name to be used to download the package";
                }
                leaf password {
                    type string;
                    tailfs:suppress-echo true;
                    description
                      "password to be used to download the package";
                }
            }
            case authgroup {
                leaf group-name {
                    type string;
                    description
                      "authorization group configured for download";
                }
            }
        }
    }

    grouping transfer-grouping {
        list file-transfer-status {
            description
              "Progress status related to the upload and download of backup zip file";

            key transfer-type;
            config false;

            leaf transfer-type {
                type file-transfer-type;
                description
                  "upload or download operation";
            }
            leaf transfer-result {
                type file-transfer-status;
                description
                  "description on what the debug does";
            }
            leaf transfer-time {
                type ietf:date-and-time;
                description
                  "data and time of transfer operation";
            }
            leaf message {
                type string;
                description
                  "message describing the result";
            }
        }
    }

    grouping remote-file-path {
        leaf remote-file-path {
            type inet:uri;
            description
              "Remote file path. A URI for the remote file path. Format:sftp://user[:password]@host[:port]/path.
               Ex: sftp://test:verify@[2001:db8:0:1::10]:22/home/user/sample";
            tailfs:info "Remote file path. A URI for the remote file path. Format:sftp://user[:password]@host[:port]/path.
                        Ex: sftp://test:verify@[2001:db8:0:1::10]:22/home/user/sample";
            config true;
        }
    }
}
