module cisco-svo-functional-model {
    yang-version 1.1;
    namespace "http://cisco.com/yang/svo/functional-model";
    prefix svo-functional;

    import cisco-svo-common-types { prefix cct; }
    import cisco-svo-common-base-opt-grp { prefix ccbog; }
    import cisco-svo-common-action-param-grp { prefix ccapg; }
    import cisco-svo-common-equipment-types { prefix ccet; }
    import cisco-svo-common-functional-grp { prefix ccfunctg; }
    import org-openroadm-common-link-types { prefix org-openroadm-common-link-types; revision-date 2018-03-30; }
    
    import cisco-svo-common-functional-oper-grp { prefix ccfunctog; }

    organization
        "Cisco Systems, Inc.";

    contact
        "Cisco Systems, Inc. Customer Service Postal: 170 West Tasman
       Drive San Jose, CA 95134 Tel: +1 800 553-NETS E-mail: cs-yang@cisco.com";

    description
        "YANG definition for node building blocks, from functional point of view";

   revision 2021-04-16 { 
      description "Model version for SVO Release 12.2.0 "; 
      reference cisco-svo-functional-model.yang; 
   }
 

    revision 2020-12-04 { 
       description "Model version for SVO Release 12.1.0 "; 
       reference cisco-svo-functional-model.yang; 
    }
 

    grouping OMS-Links {
    	description "Optical Multiplexing Section Links grouping";
        list oms-links {
            key "roadm-degree-uid";
            description "List of Optical Multiplexing Section Links";

            leaf roadm-degree-uid {
                type cct:degree-uid-t;
                description "Unique Id of parent Degree";
            }

            uses ccfunctog:OMS-link-oper;

            container link-power-control {
            	description "OMS link power control algorithm";
                uses ccfunctg:OMS-link-power-control-conf;
                uses ccfunctog:OMS-link-power-control-oper;

                action run-link-power-control {
                    description "Trigger a manual run of the link power control";
                    output {
                        uses ccbog:rpc-status;
                    }
                }

                action force-power-correction {
                    description "Override an \" \" alarm and allow to correct an excessive discrepancy between target power and actual power ";
                    output {
                        uses ccbog:rpc-status;
                    }
                }
            }

            uses ccfunctg:OMS-link-GN-performance-config-data;
            uses ccfunctog:OMS-link-GN-performance-oper-data;
        }
    }

    grouping span-loss-grp {
      description "Grouping for Span Loss informantion";

      container span-loss {
        description "Span Loss definitions";
        action measure-span-loss {
            description "Command triggering manual span-loss values measurement";
            output {
                uses ccbog:rpc-status;
            }
        }
        uses ccfunctg:span-loss-config-data;
        uses ccfunctog:span-loss-oper-data;
      }
    }

    grouping node-degrees {
    	description "Node Degrees grouping";
        list degrees {
            key "degree-uid";
			      description "List of Degrees defined on the node";

            leaf degree-uid {
                type cct:degree-uid-t;
                mandatory true;
                description "Side unique identifier";
            }

            leaf input-interface {
                type ccet:port-name-t;
                mandatory true;
                description "Interface of the port receiving from the optical fiber span";
            }

            leaf output-interface {
                type ccet:port-name-t;
            	mandatory true;
                description "Interface of the port sending into the optical fiber span";
            }

            uses ccfunctg:node-degrees-config-data;
            uses ccfunctog:node-degrees-oper-data;

            uses ccfunctg:optical-span-config-data;
            uses span-loss-grp;

            action get-tx-rx-raw-power-data {
                description "get the raw power data on the dereee TX and RX port; 
                if degree ports does not support that functionality, The closest port with such functionality
                will be used";
                output {
                  uses ccbog:rpc-status;
                  container rx {
            		uses ccapg:unidir-raw-power-data-grp;
        		  }
        
        		  container tx {
            		uses ccapg:unidir-raw-power-data-grp;
        		  }
                }
            }
        }
    }

    grouping srg-grp {
      description "Shared Risk grouping";
      list srg {
        key "group-uid";
        description "Shared Risk Group (SRG) for interfaces within the SVO optical node";
        config false;

        leaf group-uid {
          type cct:degree-uid-t;
          description "The identifier for the SRG, this is assigned by the node itself";
        }

        uses ccfunctog:srg-oper-data;
      }
    }

    grouping node-topopology-grp {
      description "Optical Node Internal Toplogy information";

      container node-topology {
        description
          "This containers hold all information related to the Optical Node Topology.
           Such information may vary according to line cards and internal liks composing the node.
           Mostly all data is operational as they are provided by the node itself.";

        uses srg-grp;
      }
    } // end-of-group


   grouping expected-input-power-grp {
	list expected-input-power {
		key "input-interface";

	leaf input-interface {
        	mandatory true;
                config true;
                type ccet:port-name-t;
        }

	choice expected-power-type {
		case total-power {
			description "Define expected power as total power";
			leaf total-power {
				type org-openroadm-common-link-types:power-dBm;
			}
		}
		case psd-power {
			description "Define expected power as channel psd";
			leaf psd-power {
				type cct:power-spectral-density-t;
				units "dBm/GHz";
			}
		}
	}
	}
   }

}
