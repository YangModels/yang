module cisco-svo-common-otn-oper-grp {

  yang-version 1.1;
  namespace "http://cisco.com/yang/svo/common-otn-oper-grp";
  prefix ccotnog;

  import org-openroadm-otn-common-types { prefix org-openroadm-otn-common-types; revision-date 2018-09-28; }
  import org-openroadm-interfaces { prefix or-if; revision-date 2018-09-28; }
  import cisco-svo-common-otn-types { prefix ccotnt; }
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO OTN common Operational Data.";

   revision 2021-04-16 { 
      description "Model version for SVO Release 12.2.0 "; 
      reference cisco-svo-common-otn-oper-grp.yang; 
   }
 

    revision 2020-12-04 { 
       description "Model version for SVO Release 12.1.0 "; 
       reference cisco-svo-common-otn-oper-grp.yang; 
    }
 

  grouping interface-ref {
    leaf type {
      type identityref {
        base or-if:interface-type;
      }
      description "Type of the interface.";
    }

    leaf name {
      type leafref {
        path "../../../../interface[type=current()/../type]/name";
      }
      description "reference to existing interface";
    }
  }


  grouping otu-attributes {
    description
    "OTU attributes";
    leaf otu-rate {
      type identityref {
        base org-openroadm-otn-common-types:otu-rate-identity;
      }
      config false;
      description
      "rate identity of the OTU. 'identityref' is used
      to allow to extend for future higher rates";
    }
    leaf otucn-n-rate {
      type uint16;
      config false;
      description
      "OTUCn rate";
    }
    leaf otucn-M-subrate {
      type uint16;
      config false;
      description
      "OTUCn subrate (OTUCn-M), value of M specifies the number of active
      5 Gbit/s OPUCn tributary slots (G.709 Annex H)";
    }
  }

  grouping odu-attributes {
    description
      "ODU attributes";
    leaf odu-rate {
      type identityref {
        base org-openroadm-otn-common-types:odu-rate-identity;
      }
      config false;
      description
        "rate identity of the ODU. 'identityref' is used
         to allow to extend for future higher rates";
    }

    leaf signal-type {
        type ccotnt:signal-type-type;
        config false;
        description
        "Payload framing types";
    } 

    leaf monitoring-mode {
      type enumeration {
        enum "not-terminated" {
          description
            "Not Terminated: no detection or generation.
             Overhead is passed through the interface transparently in receive direction";
        }
        enum "terminated" {
          description
            "Terminated: detection and generation enabled.
             Overhead is erased (replaced with all zeros) in receive direction";
        }
        enum "monitored" {
          description
            "Monitored: detection enabled.
             Overhead is passed through the interface transparently in receive direction";
        }
      }
      config false;
      description
        "Monitoring mode of the ODU Overhead";
    }

    leaf odu-function {
      type identityref {
        base org-openroadm-otn-common-types:odu-function-identity;
      }
      config false;
      description
        "ODUk interface function";
    }

    leaf no-oam-function {
      type empty;
      config false;
      description
        "No OAM functionality exists for this ODU interface, the entity exists in software only.
        This entity does not report alarms or PM and does not support TCM, TTI, delay measurement,
        loopbacks, test signal and other hardware-based functions.
        This is an optional parameter, it only needs to be present when no-oam-function is supported
        for this interface.";
    }
   
    container client-signal-interface {
      uses interface-ref;
      config false;
     description "Client Signal interface";
    }
  }

  
  grouping sync-oper-grp {
    description "Optical Transport Network (OTN) Parameters";
    
    leaf supports-sync {
      type boolean;
      config false;
      description "True if Sync configuration is supported";
    }
  }

  grouping gcc0-grp {
    description "OTN Reusable Container";
    
    container gcc0 {  
      leaf supported-gcc0 {
        type boolean;
        config false;
        description "supporting gcc0 based on hw capabilities";
      }

      leaf gcc0 {
        type boolean;
        default false;
        description "enable disable general comunication channel 0";
      }
    }
  }

  grouping tti-oper-grp {
    leaf supports-tti {
      type boolean;
      config false;
      default true;
      description "True if a TTI can be enabled on the ODU or OTU interface";
    }
  }
}
