module cisco-svo-common-optical-channel-oper-grp {

  yang-version 1.1;
  namespace "http://cisco.com/yang/svo/common-optical-channel-oper-grp";
  prefix cochog;

  import org-openroadm-common-optical-channel-types { prefix org-openroadm-common-optical-channel-types; revision-date 2018-05-30; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the OpticalChannel interface Operational Data.";

    revision 2020-12-04 { 
       description "Model version for SVO Release 12.1.0 "; 
       reference cisco-svo-common-optical-channel-oper-grp.yang; 
    }
 

  grouping optch-oper-group {
    leaf rate {
      type identityref {
        base org-openroadm-common-optical-channel-types:och-rate-identity;
      }
      config false;
      description "Rate";
    }

    leaf width {
      type org-openroadm-common-optical-channel-types:frequency-GHz;
      config false;
      description "Frequency width in GHz.";
    }

    leaf modulation-format {
      type org-openroadm-common-optical-channel-types:modulation-format;
      config false;
      description "Modulation format";
    }

    leaf role {
    	type enumeration {
        enum "Client" {
          description "Client role";
        }
        enum "Trunk" {
          description "Trunk role";
        }
      }
      config false;
      description "Interface role (Defines if the optical interface has a client or trunk role.)";
    }

    leaf supports-pm {
      type boolean;
      config false;
      description "True if Performance Monitoring is available for this optical-channel";
    }

    leaf supports-thresholds {
      type boolean;
      config false;
      description "True if Alarm Threhsolds settings are available for this optical-channel";
    }

    leaf is-otl-lane {
      type boolean;
      config false;
      description "True if OTL line. Common settings (reach, sd-fec etc) are not configurable for this optical-channel";
    }

  }
}
