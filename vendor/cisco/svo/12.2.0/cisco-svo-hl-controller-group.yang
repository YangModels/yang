module cisco-svo-hl-controller-group {
  namespace "http://cisco.com/yang/svo/hl-controller-group";
  prefix "svo-hl-ctrlg";

  import iana-crypt-hash { prefix ianach; }
  import tailf-common { prefix tailf; }
  import ietf-yang-types { prefix yang; }
  import tailf-xsd-types { prefix xs; }
  organization 
    "Cisco Systems, Inc.";

  contact 
    "Cisco Systems, Inc.
     Customer Service
     
     Postal: 170 West Tasman Drive
     San Jose, CA 95134
     
     Tel: +1 800 553-NETS
     
     E-mail: cs-yang@cisco.com";

  description 
    "This module defines the SVO card mgmt infos.";

    revision 2020-12-04 { 
       description "Model version for SVO Release 12.1.0 "; 
       reference cisco-svo-hl-controller-group.yang; 
    }
 

  typedef log-type-t {
    type enumeration {
      enum "tech-support" {
        value 0;
        description
          "tech support logs";
      }
      enum "obfl-log" {
        value 1;
        description
          "obfl logs";
      }

      enum "journald-log" {
        value 2;
        description
          "journald logs";
      }
    }
    description 
      "log collection type";
  }

  typedef card-led-status-t {
    type enumeration {
      enum "cs-off" {
        value 0;
        description
          "card status off";
      }
      enum "cs-green" {
        value 1;
        description
          "card status green";
      }
      enum "cs-amber" {
        value 2;
        description
          "card status amber";
      }
      enum "cs-red" {
        value 3;
        description
          "card status red";
      }
    }
    description 
      "card status LED";
  }

  typedef port-state-t {
    type enumeration {
      enum "OOS" {
        value 0;
        description
          "shut port state";
      }
      enum "IS" {
        value 1;
        description
          "no shut port state";
      }
    }
    description 
      "port state";
  }

  typedef port-number-t {
    type enumeration {
      enum "Port-1" {
        value 10;
        description
          "Port 3";
      }
      enum "Port-2" {
        value 8;
        description
          "Port 1";
      }
      enum "Port-3" {
        value 11;
        description
          "Port 4";
      }
      enum "Port-4" {
        value 9;
        description
          "Port 2";
      }
      enum "MGMT-1" {
        value 13;
        description
          "Mgmt port 2";
      }
      enum "CRAFT" {
        value 12;
        description
          "Mgmt port 1";
      }
      enum "Port-7" {
        value 2;
        description
          "Port 5";
      }
      enum "Port-8" {
        value 3;
        description
          "Port 6";
      }
      enum "Port-9" {
        value 4;
        description
          "Port 7";
      }
      enum "Port-10" {
        value 5;
        description
          "Port 8";
      }
    }
    description 
      "port number details";
  }

  typedef sensor-names-t {
    type enumeration {
     enum "0.6V_CPU_B" {
        value 0;
        description
          "0.6V_CPU_B sensor";
      }
      enum "1.2V_CPU" {
        value 1;
        description
          "1.2V_CPU sensor";
      }
      enum "1.5V_CPU" {
        value 2;
        description
          "1.5V_CPU sensor";
      }
      enum "1.7V_CPU" {
        value 3;
        description
          "1.7V_CPU sensor";
      }
      enum "3.3V_CPU" {
        value 4;
        description
          "3.3V_CPU sensor";
      }
      enum "1.05V_CPU" {
        value 5;
        description
          "1.05V_CPU sensor";
      }
      enum "1.82V_CPU" {
        value 6;
        description
          "1.82V_CPU sensor";
      }
      enum "1.3V_CPU" {
        value 7;
        description
          "1.3V_CPU sensor";
      }
      enum "0.6V_CPU_A" {
        value 8;
        description
          "0.6V_CPU_A sensor";
      }
      enum "5.0V_STBY" {
        value 9;
        description
          "5.0V_STBY sensor";
      }
      enum "3.3V_STBY" {
        value 10;
        description
          "3.3V_STBY sensor";
      }
      enum "3.3V" {
        value 11;
        description
          "3.3V sensor";
      }
      enum "2.5V" {
        value 12;
        description
          "2.5V sensor";
      }
      enum "1.8V" {
        value 13;
        description
          "1.8V sensor";
      }
      enum "1.2V" {
        value 14;
        description
          "1.2V sensor";
      }
      enum "1.0V_PHY" {
        value 15;
        description
          "1.0V_PHY sensor";
      }
      enum "1.0V" {
        value 16;
        description
          "1.0V sensor";
      }
      enum "BP_48V" {
        value 17;
        description
          "BP_48V sensor";
      }
      enum "Hotspot2" {
        value 18;
        description
          "Hotspot2 sensor";
      }
      enum "Hotspot1" {
        value 19;
        description
          "Hotspot1 sensor";
      }
      enum "Inlet_Air" {
        value 20;
        description
          "Inlet_Air sensor";
      }
      enum "Outlet_Air" {
        value 21;
        description
          "Outlet_Air sensor";
      }
      enum "Ethernet_Switch_Temp" {
        value 22;
        description
          "Ethernet_Switch_Temp sensor";
      }
      enum "CPU_Temp" {
        value 23;
        description
          "CPU_Temp sensor";
      }
      enum "DDR_Ch0_Temp" {
        value 24;
        description
          "DDR_Ch0_Temp sensor";
      }
      enum "DDR_Ch1_Temp" {
        value 25;
        description
          "DDR_Ch1_Temp sensor";
      }
      enum "BP_Current" {
        value 26;
        description
          "BP_Current sensor";
      }
      enum "Board_Power" {
        value 27;
        description
          "Board_Power sensor";
      }
    }
    description 
      "sensor names";
  }
   grouping idprom-entry-grp {
    description
      "IDPROM entry details";
        leaf idprom-eep-version {
          type xs:hexBinary;
          description
            "idprom eep version";
        }
        leaf idprom-compatibility-byte {
          type xs:hexBinary;
          description
             "idprom compatibility byte";
        }
        leaf idprom-pcb-partno {
          type string;
          description
            "pcb part number";
        }
        leaf idprom-pcb-revision {
          type string;
          description
            "pcb revision number";
        }
        leaf idprom-fab-version {
          type string;
          description
            "fab version";
        }
        leaf idprom-pcb-serial {
          type string;
          description
            "pcb serial number";
        }
        leaf idprom-hw-version {
          type string;
          description
            "hardware version";
        }
	leaf idprom-product-id {
          type string;
          description
            "product id";
        }
        leaf idprom-version-id {
          type string;
          description
            "version id";
        }
        leaf idprom-clei {
          type string;
          description
            "clei code";
        }
        leaf idprom-hw-type {
          type xs:hexBinary;
          description
            "hardware controller type";
        }
        leaf idprom-file-name {
          type string;
          description
            "file name";
        }
        leaf idprom-card-name {
          type string;
          description
            "card name";
        }
        leaf idprom-new-deviation {
          type string;
          description
            "new deviation number";
        }
	 leaf idprom-device-vals {
          type xs:hexBinary;
          description
            "platform features";
        }
        leaf idprom-rma-failcode {
          type xs:hexBinary;
          description
            "rma test history/failure code";
        }
        leaf idprom-rma-number {
          type string;
          description
            "rma number";
        }
        leaf idprom-rma-history {
          type uint8;
          description
            "rma history";
        }
        leaf idprom-field-diags {
          type string;
          description
            "field diagnostics results";
        }
        leaf idprom-mfg-test {
          type string;
          description
            "mfg test engineering field";
        }
        leaf idprom-macaddr-base {
          type yang:mac-address;
          description
            "base mac address";
        }
        leaf idprom-mac-blksize {
          type string;
          description
            "mac address block size";
        }
        leaf idprom-pca-partnbr {
          type string;
          description
            "pcb part number";
        }
        leaf idprom-eci-number {
          type string;
          description
            "eci number";
        }
  }
  grouping dom-info-grp {
    description
      "node optics-port dom info";
      leaf temp {
        type decimal64 {
          fraction-digits 3;
        }
      }
      leaf vcc {
        type decimal64 {
          fraction-digits 3;
        }
      }
      leaf tx-bias {
        type decimal64 {
          fraction-digits 3;
        }
      }
      leaf tx-power {
        type decimal64 {
          fraction-digits 3;
        }
      }
      leaf rx-power {
        type decimal64 {
          fraction-digits 3;
        }
      }
  }
  
   grouping sfp-vendor-info-grp {
    description
      "sfp vendor related details";
      leaf vendor-name {
        type string;
        description
          "vendor name";
      }
      leaf vendor-pn {
        type string;
        description
          "vendor part number";
      }
      leaf vendor-rev {
        type string;
        description
          "vendor revision level";
      }
      leaf vendor-serial {
        type string;
        description
          "serial number provided by vendor";
      }
      leaf cisco-clei {
        type string;
        description
          "cisco clei code";
      }
      leaf cisco-pn {
        type string;
        description
          "cisco part number";
      }
      leaf cisco-vid {
        type string;
        description
          "cisco Version ID";
      }
      leaf cisco-pid {
        type string;
        description
        "cisco Product ID";
      }
  }
typedef data-rates {
    type enumeration {
      enum "one-ge" {
        value 1;
        description
          "one ge";
      }
      enum "ten-ge" {
        value 2;
        description
          "ten ge";
      }
      enum "unknown" {
        value 3;
        description
          "unknown";
      }
    }
  }
   typedef sensor_alarm_type {
    type enumeration {
      enum "no_alarm" {
        value 0;
        description
          "no alarm present";
      }
      enum "not_applicable" {
        value 1;
        description
          "not applicable";
      }
      enum "threshold_crossed_low_critical" {
        value 2;
        description
          "threshold crossed low critical";
      }
      enum "threshold_crossed_low_major" {
        value 3;
        description
         "threshold_crossed_low_major";
      }
      enum "threshold_crossed_low_min" {
        value 4;
        description
          "threshold_crossed_low_min";
      }
      enum "threshold_crossed_high_min" {
        value 5;
        description
           "threshold_crossed_high_min";
      }
      enum "threshold_crossed_high_major" {
        value 6;
        description
          "threshold_crossed_high_major";
      }
      enum "threshold_crossed_high_critical" {
        value 7;
        description
          "threshold_crossed_high_critical";
      }
    }
  }
  grouping sensor-data-grp {
   leaf current-val {
      type decimal64 {
         fraction-digits 3;
      }
   }
   leaf low-critical {
      type decimal64 {
         fraction-digits 3;
      }
   }
   leaf low-major {
      type decimal64 {
         fraction-digits 3;
      }
   }
   leaf low-min {
      type decimal64 {
         fraction-digits 3;
      }
   }
   leaf high-min {
      type decimal64 {
         fraction-digits 3;
      }
   }
   leaf high-major {
      type decimal64 {
         fraction-digits 3;
      }
   }
   leaf high-critical {
      type decimal64 {
         fraction-digits 3;
      }
   }
   leaf sensor-alm {
        type sensor_alarm_type;
   }
  }

  typedef card-stat-t {
    type enumeration {
      enum "active" {
        value 0;
        description
          "card active";
      }
      enum "reset" {
        value 1;
        description
          "card reset";
      }
      enum "missing" {
        value 2;
        description
          "card missing";
      }
    }
    description 
      "card stat";
  }
  grouping port-counter-grp {
    description
      "ether counter values";
      leaf goodOctetsRcv {
        type uint64;
      }
      leaf badOctetsRcv {
        type uint64;
      }
      leaf macTransmitErr {
        type uint64;
      }
      leaf brdcPktsRcv {
        type uint64;
      }
      leaf mcPktsRcv {
        type uint64;
      }
      leaf pkts64Octets {
        type uint64;
      }
      leaf pkts65to127Octets {
        type uint64;
      }
      leaf pkts128to255Octets {
        type uint64;
      }
      leaf pkts256to511Octets {
        type uint64;
      }
      leaf pkts512to1023Octets {
        type uint64;
      }
      leaf pkts1024toMaxOctets {
        type uint64;
      }
      leaf goodOctetsSent {
        type uint64;
      }
      leaf excessiveCollisions {
        type uint64;
      }
      leaf mcPktsSent {
        type uint64;
      }
      leaf brdcPktsSent {
        type uint64;
      }
      leaf fcSent {
        type uint64;
      }
      leaf goodFcRcv {
        type uint64;
      }
      leaf dropEvents {
        type uint64;
      }
      leaf undersizePkts {
        type uint64;
      }
      leaf fragmentsPkts {
        type uint64;
      }
      leaf oversizePkts {
        type uint64;
      }
      leaf jabberPkts {
        type uint64;
      }
      leaf macRcvError {
        type uint64;
      }
      leaf badCrc {
        type uint64;
      }
      leaf collisions {
        type uint64;
      }
      leaf lateCollisions {
        type uint64;
      }
      leaf ucPktsSent {
        type uint64;
      }
  }

  grouping opt-thr-grp {
    description
      "node optics-port dom info";
      leaf laserbias {
        type decimal64 {
          fraction-digits 3;
          range "0..100";
        }
      }
      leaf rx-pwr-high {
        type decimal64 {
          fraction-digits 3;
          range "-40..30";
        }
	must "current() > ../rx-pwr-low";
      }
      leaf rx-pwr-low {
        type decimal64 {
          fraction-digits 3;
          range "-40..30";
        }
        must "current() < ../rx-pwr-high";
      }
      leaf tx-pwr-high {
        type decimal64 {
          fraction-digits 3;
          range "-40..30";
        }
        must "current() > ../tx-pwr-low";
      }
      leaf tx-pwr-low {
        type decimal64 {
          fraction-digits 3;
          range "-40..30";
        }
        must "current() < ../tx-pwr-high";
      }
  }

  typedef reach-t {
    type enumeration {
      enum "AutoProv" {
        value 0;
        description
          "Auto Prov";
      }
      enum "TEN_GE_SR" {
        value 1;
        description
          "TEN GE SR";
      }
      enum "TEN_GE_LR" {
        value 2;
        description
          "TEN GE LR";
      }
      enum "SX" {
        value 3;
        description
          "SX reach";
      }
      enum "LX" {
        value 4;
        description
          "LX reach";
      }
      enum "NA" {
        value 5;
        description
          "Not Applicable";
      }
    }
    description 
      "reach values";
  }

   grouping svo-controller-group {
    description
      "svo card management details";

    container card-information {
        leaf os-version {
            type string;
            config false;
            description "OS version of SVO card";
        }
        leaf sw-version {
            type string;
            config false;
            description "CONFD SW Version";
        }
    }
    container card-sensor {
        description
        "card sensor data";
         list sensor {
	   ordered-by user;
            key "name";
            leaf name {
              type sensor-names-t;
              description "sensor name";
            }
            container sensor-data {
                config false;
                uses sensor-data-grp;
            }
         }
    }

    container card-status {
      config false;
      description
        "status of card LED";
      leaf card-status-led {
        config false;
        type card-led-status-t;
        description
          "card status LED";
      }
    }
    container card-stats {
      config false;
      description
        "stat of card";
      leaf card-stat {
        config false;
        type card-stat-t;
        description
          "card stat";
      }
    }
    container idprom {
      description
        "idprom information";
        uses idprom-entry-grp;
    }
    list optics-pluggable {
      key "number";
      description
        "optics SFP/SFP+ details";
        leaf number {
          type uint32 {
            range "7..10";
          }
          description
            "portslot number";
        }
	leaf plugged-in {
          config false;
          type boolean;
          default "false";
	  description
	   "port plugged in";
        }
        leaf plugged-in-ever {
          type boolean;
          default "false";
          description
           "port plugged ever";
        }

        leaf data-rate {
          config false;
          type data-rates;
          description
               "data  rate";
        }
        leaf port-state {
          type port-state-t;
          default "IS";
          // below "must" is not supported in SVO 5.x
          // must "not((current()='OOS') and (current()/../sfp-vendor-info/cisco-pid = 'ONS-SE-ZE-EL        '))" {
          //    error-message "Provision of port state not supported for this pluggable!!!";
          // }
          description
            "port state enum";
        }

        container sfp-vendor-info {
          config false;
          description
            "sfp vendor specific infos";
            uses sfp-vendor-info-grp;
        }
        container dom-info {
          config false;
          description
            "port specific information";
          uses dom-info-grp;
        }
        list optics-thresholds {
          key "interval";
          leaf interval {
            type enumeration {
              enum "15MIN_TCA" {
                value 0;
                description
                "15 min TCA";
              }
              enum "1DAY_TCA" {
                value 1;
                description
                "1 day TCA";
              }
              enum "ALARM" {
                value 2;
                description
                "Alarm ";
              }
            }
          }
          uses opt-thr-grp;
          description
            "threshold information";
        }
        leaf reach {
          config false;
          type reach-t;
          description
            "reach value";
        }
    }
    list ether-counters {
        key "port";
        description
          "ether port counters details";
          leaf port {
            type port-number-t;
            description
              "ether port number";
          }
          container counter-info {
            config false;
            description 
              "ether port counter information";
            uses port-counter-grp;
          }
    }
  }
  grouping su {
    container super-user {
        config false;
        tailf:cdb-oper {
            tailf:persistent true;
        }
       leaf user-name {
            type string;
        }
        leaf password {
            type ianach:crypt-hash;
        }
	leaf old-password {
            type ianach:crypt-hash;
        }
    }
  }
  grouping svo-controller-actions-group {
    tailf:action retrieve-ether-counters {
        tailf:actionpoint refresh-counter;
        input {
            leaf port_num {
                mandatory true;
                type port-number-t;
            }
        }
        output {
        }
    }
    tailf:action clear-ether-per-port-counters {
        tailf:actionpoint clear-per-port-counter;
        input {
            leaf port_num {
                mandatory true;
                type port-number-t;
            }
        }
        output {
        }
    }
    tailf:action clear-ether-all-port-counters {
        tailf:actionpoint clear-all-port-counters;
        input {
        }
        output {
        }
    }
    tailf:action retrieve-ether-all-port-counters {
        tailf:actionpoint retrieve-all-port-counters;
        input {
        }
        output {
        }
    }
    tailf:action svo-hwreset {
        tailf:actionpoint reboot-card;
        input {
        }
        output {
        }
    }
    tailf:action reset-sfp-to-default {
        tailf:actionpoint rst-sfp-def;
        input {
          leaf port_num {
            mandatory true;
            type uint32 {
              range "7..10";
            }
          }
        }
        output {
        }
    }
    tailf:action super-user-change-password {
      tailf:actionpoint spu-change-pwd;
      input {
          leaf new-password {
              type ianach:crypt-hash;
              mandatory true;
          }
          leaf user-name {
              type string;
              mandatory true;
          }
      }
    }
    tailf:action rollback-su-pwd {
      tailf:actionpoint rb-su-pwd;
    }    
    tailf:action super-user-recreate {
      tailf:actionpoint spu-recreate;
      input {
          leaf password {
              type ianach:crypt-hash;
              mandatory true;
          }
          leaf user-name {
              type string;
              mandatory true;
          }
      }
    }
    tailf:action eth0 {
      tailf:actionpoint cfg-eth0;
      input {
         leaf ip {
           type string;
           mandatory true;
         }
         leaf subnet {
           type string;
           mandatory true;
         }
         leaf gateway {
           type string;
           mandatory true;
         }
      }
    }
    tailf:action collect-logs {
      tailf:actionpoint collect-log;
	input {
	  leaf log-type {
            type log-type-t;
            mandatory true;
            description
              "log type";
          }
        }
        output {
	  leaf result {
            type uint8;
            mandatory true;
            description
              "0-failure 1-success";
	  }
          leaf file-path {
            type string;
            mandatory true;
          }
        }
      }
      tailf:action os-upgrade {
        tailf:actionpoint os-upg;
        input {
          leaf path {
            type string;
            mandatory true;
          }
        }
        output {
	  leaf result {
            type uint8;
            mandatory true;
            description
                "0-succes 1-failure";
	  }
          leaf message {
             type string;
             mandatory true;
          }
        }
      }
      tailf:action ha-mgr-upgrade {
        tailf:actionpoint ha-mgr-upg;
          input {
            leaf image-name {
              type string;
              mandatory true;
            }
          }
          output {
	    leaf result {
              type uint8;
              mandatory true;
              description
                "0-succes 1-failure";
	  }
          leaf message {
            type string;
            mandatory true;
          }
      }
    }
  }
}
