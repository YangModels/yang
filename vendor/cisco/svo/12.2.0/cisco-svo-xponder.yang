module cisco-svo-xponder{
    yang-version 1.1;
    namespace "http://cisco.com/yang/svo/xponder";
    prefix svo-xpdr;

    import cisco-svo-common-equipment-types { prefix ccet; }
    import cisco-svo-common-types { prefix cct; }

    organization
        "Cisco Systems, Inc.";

    contact
        "Cisco Systems, Inc. Customer Service Postal: 170 West Tasman
        Drive San Jose, CA 95134 Tel: +1 800 553-NETS E-mail: cs-yang@cisco.com";

    description
        "YANG definition for svo xponder";

   revision 2021-04-16 { 
      description "Model version for SVO Release 12.2.0 "; 
      reference cisco-svo-xponder.yang; 
   }
 

    revision 2020-12-04 { 
       description "Model version for SVO Release 12.1.0 "; 
       reference cisco-svo-xponder.yang; 
    }
 

    grouping xponder-grp {
        list xponder {
            description "List of xponder";
            
            key "uid slot";         
            config false;
 
            leaf uid {
                type ccet:uid-t;
                description " the unique indentifier of chassis in svo across physical devices";  
            }

            leaf slot {
                type ccet:slot-t;
                description "Functional-module-group slot or card mode slot";
            }

            leaf fmg-slot {
                status deprecated;
                type ccet:slot-t;
                description "Functional-module-group primary slot, that could be module slot identifier 1:999 or ppmSlot identifier 1:999-1:99";
            }

            leaf xpdr-type {
                status deprecated;
                type identityref {
                    base cct:common-hw-identity;
                }
            }            

            choice connection-type {
               case client {
                  uses client-connection-grp; 
               }
               case bundle {
                uses bundle-connection-list-grp;
               }
               case regen {
                 uses regen-connection-list-grp;
               }
               case protected {
                 uses protected-connection-list-grp; 
               }
               case mixed-regen-client {
                 uses mixed-regen-client-list-grp; 
               }
            }
        }


    }

   grouping client-connection-grp {
     list client-connection {
       key "primary-module-id  primary-port-id";

       leaf primary-module-id {
         type ccet:slot-t;
       }

       leaf primary-port-id {
         type ccet:port-id-t;
       }

       container client-port {
         uses xponder-port-grp;
       }
      
       container trunk-port {
         uses xponder-port-grp;
       }
     }
   }

   grouping mixed-regen-client-list-grp {
     container mixed-regen-client {
         uses client-connection-grp;
         uses regen-connection-list-grp;
     }
   }

   grouping bundle-connection-grp {
     list bundle-connection {
       status deprecated;
       key "primary-module-id  primary-port-id";

       leaf primary-module-id {
         type ccet:slot-t;
       }

       leaf primary-port-id {
         type ccet:port-id-t;
       }
       container client-port {
         uses xponder-port-grp;
       }
       container bundle {
         container trunk-port-1 {
           uses xponder-port-grp;
         }
         container trunk-port-2 {
           uses xponder-port-grp;
         }
       }
     }
   }

   grouping bundle-connection-list-grp {
     list bundle-connection {
       key "primary-module-id  primary-port-id";

       leaf primary-module-id {
         type ccet:slot-t;
       }

       leaf primary-port-id {
         type ccet:port-id-t;
       }
       container client-port {
         uses xponder-port-grp;
       }
       list trunk-ports {
         key "port-id module-id";
         uses xponder-port-grp;
       }
     }
   }

  grouping regen-connection-list-grp {
      container regen-connection {
         list trunk-ports {
           key "port-id module-id";
           uses xponder-port-grp;
         }
      }
  }

  grouping protected-connection-list-grp {
      list protected-connection {
       key "primary-module-id  primary-port-id";

       leaf primary-module-id {
         type ccet:slot-t;
       }

       leaf primary-port-id {
         type ccet:port-id-t;
       }

        container client-port {
          uses xponder-port-grp;
        }
         list trunk-ports {
           key "port-id module-id";
           uses xponder-port-grp;
         }
      }
    }



 
   grouping regen-connection-grp {
      container regen-connection {
        status deprecated;
        container trunk-port-1 {
          uses xponder-port-grp;
        }
        container trunk-port-2 {
          uses xponder-port-grp;
        }
      }
    }

    grouping protected-connection-grp {
      container protected-connection {
        status deprecated;
        container client-port {
          uses xponder-port-grp;
        }
        container trunk-port-1 {
          uses xponder-port-grp;
        }
        container trunk-port-2 {
          uses xponder-port-grp;
        }
      }
    }
  
    grouping xponder-port-grp {
      leaf module-id {
        type ccet:slot-t;
      }
      leaf port-id {
        type ccet:port-id-t;
      }
      leaf port-name {
        type ccet:port-name-t;
      }
    }
}
