module cisco-svo-services {
    yang-version 1.1;
    namespace "http://cisco.com/yang/svo/services";
    prefix svo-services;

    import cisco-svo-xconnect-grp { prefix csxcg; }
    import ietf-netconf-notifications { prefix ncn; }
    
    organization
        "Cisco Systems, Inc.";

    contact
        "Cisco Systems, Inc.
       Customer Service
       
       Postal: 170 West Tasman Drive
       San Jose, CA 95134
       
       Tel: +1 800 553-NETS
       
       E-mail: cs-yang@cisco.com";

    description
        "YANG definition for SVO optical cross connections";

   revision 2021-04-16 { 
      description "Model version for SVO Release 12.2.0 "; 
      reference cisco-svo-services.yang; 
   }
 

    revision 2020-12-04 { 
       description "Model version for SVO Release 12.1.0 "; 
       reference cisco-svo-services.yang; 
    }
 

    container oxc-services {
    	description "Optical XConnect callpoint for hiding /ncs:services";

        list oxc {
			key "connection-name";
            description "cross connection list";

            uses csxcg:oxc-grp;
        }
        
        uses csxcg:oxc-state-behavior-grp;
        
    }
    
    augment /ncn:netconf-config-change/ncn:edit {
    	leaf value {
    		 type string;
    	}
    }
}
