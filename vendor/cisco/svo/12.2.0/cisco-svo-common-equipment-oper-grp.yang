module cisco-svo-common-equipment-oper-grp {

  yang-version 1.1;
  namespace "http://cisco.com/yang/svo/common-equipment-oper-grp";
  prefix cceqptog;

  import ietf-yang-types { prefix yang; }  
  import ietf-inet-types { prefix inet; }
  import cisco-svo-common-types { prefix cct; }
  import cisco-svo-common-equipment-types { prefix ccet; }
  import cisco-svo-common-base-opt-oper-grp { prefix ccboog; }
  import cisco-svo-common-mfg-oper-grp { prefix ccmog; }

  organization
    "Cisco Systems, Inc.";

  contact
    "Cisco Systems, Inc.
     Customer Service

     Postal: 170 West Tasman Drive
     San Jose, CA 95134

     Tel: +1 800 553-NETS

     E-mail: cs-yang@cisco.com";

  description
    "Cisco Common Equipment Types Operational Data Group";

   revision 2021-04-16 { 
      description "Model version for SVO Release 12.2.0 "; 
      reference cisco-svo-common-equipment-oper-grp.yang; 
   }
 

    revision 2020-12-04 { 
       description "Model version for SVO Release 12.1.0 "; 
       reference cisco-svo-common-equipment-oper-grp.yang; 
    }
 
  
  grouping ipv4-oper-grp {
    leaf ip-address {
      type inet:ipv4-address;
      config false;
      description "IP address";
    }
    leaf subnet-prefix-len {
      type uint8 {
        range "0..32";
      }
      config false;
      description "The length of the subnet prefix.";
    }
    leaf default-gateway {
      type inet:ipv4-address;
      config false;
      description "Default Gateway";
    }
  }

  grouping ipv6-oper-grp {
    leaf ip-address {
      type inet:ipv6-address;
      config false;
      description "IPv6 address";
    }
    leaf subnet-prefix-len {
      type uint8 {
        range "0..128";
      }
      config false;
      description "The length of the IPv6 subnet prefix.";
    }
    leaf default-gateway {
      type inet:ipv6-address;
      config false;
      description "Default IPv6 Gateway";
    }
  }
  
  grouping common-info-oper {
    description "Common device info.";

    container device-information {
      leaf vendor {
        type string;
        description "Device vendor name (or enterprise id)";
        config false;
      }
    
      leaf model {
        type string;
        description "Device model";
        config false;
      }
    
      leaf active-sw-version {
        type string;
        description "Node Active SW Version";
        config false;
      }
    
      leaf upgrade-status {
        type string;
        description "SW Upgrade status";
        config false;
      }
    }
  }

  grouping mpo-addressing {
    description "
      Leaf describing the MPO attributes, not needed to address the port, but
      useful to propertly display in graphics.";
    container mpo {
      presence "MPO Port. Useful to propertly group and display the MPO Ports
        in GUI";
      description "
        MPO Port. Useful to propertly group and display the MPO Ports in GUI";
      config false;
      leaf mpo-id {
        type uint8;
        description "MPO Index";
      }
      leaf port-position-in-mpo {
        type uint8;
        description "Port Position in MPO";
      }
    }
  }


  grouping equipment-state-oper-grp {
    container equipment-state {
      description "Cisco Equipment State";
      config false;

      leaf eqp-state {
      	status deprecated;
        type ccet:eqp-state-t;
        description "Equipment status";
      }

      leaf admin-state {
        type cct:admin-state-t;
        // admin-state is read-only for chassis, cards, passive units, ppm's, ancillary elements
        description "Admin State";
      }

      uses ccboog:oper-state-grp;
    }
  }

  grouping equipment-properties-oper {
    uses equipment-state-oper-grp;
    uses ccmog:equipment-manufacturing-data-oper-grp;
  }

  grouping device-sync {
    leaf device-sync-status {
      type ccet:device-sync-t;
      default 'sync-not-started';
      description "This leaf is used to known if the device is fully synched. It reports all the internal phases, from the add of devise till
            its complete sync.";
    }

    leaf current-status-sync-time {
      type yang:date-and-time;
      description "return data and time of the start phase of the new sync.";
    }

    leaf last-completed-sync-time {
      type yang:date-and-time;
      description "return data and time of the last successful sync.";
    }

    leaf last-sync-error-time {
      type yang:date-and-time;
      description "return data and time of the detected error.";
    }

    leaf sync-error-message {
      type string;
      description "Report the error that cause the sync to fail. At the end of the sync phase the error message is cleared if the phase succeed.";
    }
  }

  grouping object-change-saved {
    leaf object-change-queue-size {
      type uint16;
      description "Number of object change events, present in current queue, to be processed.";
    }
  }

  grouping node-info-oper {
    description "Node info.";

    container device-sync {
      config false;
      uses device-sync;
    }

    container object-change-saved {
      config false;
      uses object-change-saved;
    }

    container ipv4 {
      config false;
      uses cceqptog:ipv4-oper-grp;
    }

    container ipv6 {
      config false;
      uses cceqptog:ipv6-oper-grp;
    }

    leaf mac-address {
      config false;
      description "Node MAC address";
      type yang:mac-address;
    }

    leaf wson-sson-status {
      config false;
      type ccet:wson-sson-status-t;
      default 'cpstate-active';
    }


    leaf multi-shelf-mode {
      description "configuration parameter of the mode of chassis. This leaf define the configurability of the IPv4 parameters";
      config false;
      type ccet:multi-shelf-t;
    }

    uses cceqptog:common-info-oper;

    leaf standby-sw-version {
      type string;
      description "Node Standby SW Version";
      config false;
    }
  }

  grouping node-connection-verification-oper-grp {
    leaf running-status {
      type ccet:cv-running-status-t;
      description "Connection Verification running status";
      config false;
    }

    leaf next-run {
      type yang:date-and-time;
      description "Timestamp of next connection verification run";
      config false;
    }
  }

  grouping internal-link-connection-verification-grp {
    container connection-verification {
      config false;
      leaf connection-check-result {
        type ccet:internal-link-connection-result-t;
        description "Connection check result";
      }

      leaf last-connection-result-change {
        type yang:date-and-time;
        description "Timestamp of last Connection result change";
      }

      leaf insertion-loss-check-result {
        type ccet:internal-link-insertion-loss-result-t;
        description "Insertion loss check result";
      }

      leaf last-insertion-loss-result-change {
        type yang:date-and-time;
        description "Timestamp of last Connection result change";
      }

      leaf excess-insertion-loss {
        type union {
          type cct:db-oper-t;
          type string;
        }

        description "Excess loss of internallink versus its expected loss; 0 means insertion loss is within specification";
      }

      leaf latest-check {
        type yang:date-and-time;
        description "Timestamp of last Connection Verification check";
      }
      
      leaf is-reachable {
        type boolean;
        description "Internal link can be reached by the Connection Verification check";
      }

      leaf alarms-acknowledged {
        type boolean;
        description "The user has acknowledged the alarms as not fixable; custom thresholds have been automatically set";
      }
      
      leaf customized-loss-degrade-threshold {
        type cct:db-oper-t;
        description "Customized specific loss degrade threshold set as a consequence of user acknowledging alarms";
      }

      leaf customized-loss-fail-threshold {
        type cct:db-oper-t;
        description "Customized specific loss fail threshold set as a consequence of user acknowledging alarms";
      }

      leaf combined-loss {
        type boolean;
        description "Indicates if the excess loss result is a combined loss (involve a group of links)";
      }
    }
  }

  grouping internal-links-oper-grp {
    leaf internal-link-type {
      type ccet:internal-link-type-t;
      description "Type of internal link";
      status obsolete;
      config false;
    }

    uses cceqptog:internal-link-connection-verification-grp;
  }

  grouping lane-content-oper {
    leaf port-type {
      type identityref {
        base ccet:port-type;
      }
      mandatory true;
      config false;
      description "Port Type";
    }

    leaf port-name {
      type ccet:port-name-t;
      config false;
      description "Portname with syntax UId/[Slot-Id/]Port-Id.";
    }

    leaf port-number {
      type uint16;
      config false;
      description "Port number";
    }

    leaf direction {
      type cct:direction;
      config false;
      description "Port direction: RX, TX, BIDI";
    }
  }  

  grouping fpd-version-grp{
		list fpd-version{
      key fpd-name;
      config false;
      description "List of the firmware versions";

        leaf fpd-name {
        type string;
        description "Port number";
        }
        
        leaf curr-version {
        type string;
        description "Current FPD version";
        }

        leaf pkg-version {
        type string;
        description "Package FPD version";
        }
    }
  }
}
