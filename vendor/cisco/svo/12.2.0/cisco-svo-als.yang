module cisco-svo-als {
    yang-version 1.1;
    namespace "http://cisco.com/yang/svo/als";
    prefix svo-als;

    import cisco-svo-common-types { prefix cct; }
    import cisco-svo-common-base-opt-grp { prefix ccbog; }
    import cisco-svo-common-equipment-types { prefix ccet; }
    import cisco-svo-common-als-grp { prefix ccalsg; }
    
    import cisco-svo-common-als-live-grp { prefix ccalslg; }

    organization
        "Cisco Systems, Inc.";

    contact
        "Cisco Systems, Inc.
        Customer Service
        
        Postal: 170 West Tasman Drive
        San Jose, CA 95134
        
        Tel: +1 800 553-NETS
        
        E-mail: cs-yang@cisco.com";

    description
        "YANG definition for Automatic Laser Shutdown (ALS) device interfaces";

    revision 2020-12-04 { 
       description "Model version for SVO Release 12.1.0 "; 
       reference cisco-svo-als.yang; 
    }
 

    grouping als-grp {
        description "Safety Features of Interfaces grouping";
        list als {
            key "als-id";
            description "List of Safety Features defined on the interfaces";

            leaf als-id {
                type ccet:port-name-t;
                description "Identifier of the ALS.";
            }

            leaf uid {
                type leafref {
                    path "../../chassis/uid";
                }
                config false;
                description "Identifier of the linked chassis, same device the interface is based on";
            }

            leaf supported-safety {
                type cct:als-support-t;
                config false;
                description "Supported safety features";
            }

            container supporting-port {
                description "Reference to Equipment port";
                leaf module-id {
                    type leafref {
                        path "../../../chassis[uid=current()/../../uid]/module/slot";
                    }
                    config false;
                    description "Identifier of the linked module.";
                }

                leaf port-id {
                    type leafref {
                        path "../../../chassis[uid=current()/../../uid]/module[slot=current()/../module-id]/port/port-id";
                    }
                    config false;
                    description "Identifier of the linked port.";
                }

                leaf port-name {
                  type ccet:port-name-t;
                  config false;
                  description "The name of the interface.";
                }

            }

            uses ccalsg:als-optics-params;
            uses ccalsg:als-osri-params;
            uses ccalslg:als-live-data {
                when "supported-safety = 'ALS' or supported-safety = 'ALS-OSRI'";
            }

            action manual-restart {
                description "Trigger a manual restart of the amplifier safety.";
                output {
                    uses ccbog:rpc-status;
                }
            }
        }
    }
}
