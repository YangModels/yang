module cisco-svo-debug {
  yang-version 1.1;
  namespace "http://cisco.com/yang/svo/debug";
  prefix svo-debug;

  import tailf-common {
    prefix tailfs;
  }
  import tailf-ncs {
    prefix ncs;
  }
  import cisco-svo-common-types {
    prefix cct;
  }
  import tailf-common { prefix tailf; }
  import cisco-svo-common-base-opt-grp { prefix ccbog; }
  
  organization "Cisco Systems, Inc.";
  contact
    "Cisco Systems, Inc. Customer Service Postal: 170 West Tasman
     Drive San Jose, CA 95134 Tel: +1 800 553-NETS E-mail: cs-yang@cisco.com";
     
  description
    "Yang definition of all thsoe action are useful to debug the System";



  revision 2021-04-16 { 
       description "Model version for SVO Release 12.2.0         
       				added:
       	 				new action to create a json file starting from a specific sor file";
       	 
       reference cisco-svo-debug.yang;  
  }

  revision 2020-12-04 { 
       description "Model version for SVO Release 12.1.0 "; 
       reference cisco-svo-debug.yang; 
  }

  typedef memory-debug-t {
    type enumeration {
      enum "all" {
        description
          "return the percentage of the memory occupancy for container and ncs-java";
      }
      enum "container" {
        description
          "return the percentage of the memory occupancy for container ";
      }
      enum "ncs-java" {
        description
          "return the percentage of the memory occupancy for ncs-java";
      }
    }
  }

  grouping rpc-status {
    description
      "Response Status";
    leaf status {
      type identityref {
        base cct:rpc-response-status;
      }
      description
        "Status code";
    }
    leaf message {
      type string;
      description
        "Descriptive Error or Message";
    }
  }

  grouping eng-commands {
    container commands {
        uses cisco-support-grp;
    
	    container debug {
	      tailfs:action "debug-marker" {
	        tailfs:info "write the engineer marker in the ncs-java-vm.log file";
	        description
	          "write the engineer marker in the ncs-java-vm.log file";
	        tailfs:actionpoint "debug-marker";
	        input {
	          leaf printable-text {
	            description
	              "A printable marker that will be visible in the ncs-java-vm.log file.
	               The file is downloadeable by the  SVO diagnostics action";
	            type string;
	            default "DEFAULT DEBUG MARKER";
	          }
	        }
	        output {
	          uses rpc-status;
	        }
	      }
	      tailfs:action "debug-activation" {
	        tailfs:info "Activate the log of a specific section in the ncs-java-vm.log file";
	        description "Activate the log of a specific section in the ncs-java-vm.log file";
	        tailfs:actionpoint "debug-activation";
	        input {
	          leaf debug-level {
	            type ncs:log-level-type;
	            mandatory true;
	          }
	          leaf debug-area {
	            type leafref {
	              path "/svo-debug:svo-debug/svo-debug:engineer/svo-debug:svo-area-of-debug/svo-debug:debug-name";
	            }
	            mandatory true;
	          }
	        }
	        output {
	          uses rpc-status;
	        }
	      }
	      tailfs:action "debug-clear-all" {
	        tailfs:info "Remove all the debug level";
	        description "Remove all the debug level";
	        tailfs:actionpoint "debug-clear-all";
	        output {
	          uses rpc-status;
	        }
	      }
	    }
	    
	    container reset {
			tailfs:action "force-reset" {
			    tailfs:info "Reset the current status of backup&restore functionality put it to idle. Use it carefully";
			    description "Reset the current status of backup&restore functionality put it to idle. Use it carefully";
			    tailfs:actionpoint "force-reset";
			    
			    input {
				    leaf type {
		                type reset-type;
		                description "The reset type to perform";
		            }
			    }
			    
			    output {
			      uses rpc-status;
			    }
			}
	    }
    }
  }

	typedef reset-type {
        type enumeration {
            enum reset-backup-restore {
                value 0;
                description "reset backup restore";
            }
        }
        description "Available reset types";
    }

  grouping mem-commands {
    container commands {
      
      tailfs:action "activate-process-memory" {
        tailfs:info " (Cisco Support) Activate the debug monitoring feature";
        description " (Cisco Support) Activate the debug monitoring feature";
        tailfs:actionpoint "activate-process-memory";
        input {
          leaf activate {
            default true;
            type boolean;
          }
        }
        output {
          uses rpc-status;
        }
      }
      
      tailfs:action "debug-memory-occupation" {
        tailfs:info "return the memory occupation percentage";
        description "return the memory occupation percentage";
        tailfs:actionpoint "debug-memory-occupation";
        input {
          leaf memory {
            type memory-debug-t;
            description
              "choose which time of memory occupancy need to be evaluated.";
          }
        }
        output {
          uses rpc-status;
        }
      }
      
      tailfs:action "get-process-memory" {
        tailfs:info "return a list with the memory process information";
        description
          "return a list with the memory process information";
        tailfs:actionpoint "get-process-memory";
        input {
          choice filter {
            case pid {
              leaf id {
                type int32;
              }
            }
            case process {
              leaf name {
                type string;
              }
            }
            case all-process {
              leaf active {
                type boolean;
              }
              description "return the whole list of process, if boolean is true only active are returned";
            }
          }
        }
        output {
          uses return-memory-process-data;
        }
      }
      
      tailfs:action "remove-process-memory" {
        tailfs:info "remove data of memory occupation of a specific process";
        description
          "remove data of memory occupation of a specific process";
        tailfs:actionpoint "remove-process-memory";
        input {
          choice filter {
            case pid {
              leaf id {
                type int32;
              }
            }
            case all-process {
              leaf active {
                type boolean;
              }
              description " clear the whole list of process.  With active equal to true only the active process are considered. With active equal to true only the NOT active process are considered.";
            }
          }
        }
        output {
          uses rpc-status;
        }
      }
      
      tailfs:action "clean-memory-data" {
        tailfs:info "clean data of memory occupation of all processes. Min and Max are reset to zero";
        description "clean data of memory occupation of all processes. Min and Max are reset to zero";
        tailfs:actionpoint "clean-memory-data";
        input {
          choice filter {
            case pid {
              leaf id {
                type int32;
              }
            }
            case all-process {
              leaf active {
                type boolean;
              }
              description " clear the whole list of process.  With active equal to true only the active process are considered. With active equal to true only the NOT active process are considered.";
            }
          }
        }
        output {
          uses rpc-status;
        }
      }
      
      tailfs:action "baseline" {
        tailfs:info "create a baseline of memory occupation of all processes";
        description "create a baseline of memory occupation of all processes";
        tailfs:actionpoint "baseline";
        output {
          uses rpc-status;
        }
      }
    }
  }

  grouping return-memory-process-data {
    list memory-information {
      key "pid";
      leaf pid {
        type int32;
      }
      leaf is-active {
        type boolean;
      }
      leaf process-name {
        type string;
      }
      leaf max-memory-used {
        type int32;
      }
      leaf min-memory-used {
        type int32;
      }
      leaf current-memory-used {
        type int32;
      }
      leaf baseline-diff {
        type int32;
      }
    }
  }

  grouping operational {
    list svo-area-of-debug {
      description
        "Progress status related to the retrieve of devices logs";
      config false;
      key "debug-name";
      leaf debug-name {
        type string;
        description
          "a mnemonic string that describe which area could be activate for  debugging";
      }
      leaf debug-area-description {
        type string;
        description
          "description on what the debug does";
      }
    }
  }
  
  typedef protocol-type {
        description "Defines the supported protocols for download of package";
        type enumeration {
            enum "sftp" {
                value 1;
            }
        }
  }
    
  grouping upload-download-input-param {
        leaf file-name {
            description "The sor filename to download on the system";
            type string;
        }
        
        leaf protocol {
            type protocol-type;
            description "Protocol to be used to download the sor";
        }
        
        choice credential {
            case user-password {
                leaf user {
                    type string;
                    description "user name to be used for the download";
                }
                leaf password {
                    type string;
                    tailf:suppress-echo true;
                    description "password to be used for the download";
                }
            }
            case authgroup {
                leaf group-name {
                    type string;
                    description "authorization group configured for download";
                }
            }
        }
  }

  grouping cisco-support-grp {
        tailf:action execute-otdr-ml {
            tailf:info  "run the otdr-ml json file creation over a specific SOR";
            description "run the otdr-ml json file creation over a specific SOR";
            tailf:actionpoint execute-otdr-ml;
            input {
                leaf sor-file-name {
                    description "SOR file that will be parsed by otdr-ml";
                    type string;
                    mandatory true;
                }
                leaf json-destination-file {
                    description "path and filename of the json file ";
                    type string;
                    mandatory true;
                }
            }

            output {
                uses ccbog:rpc-status;
            }
        }
  }
    
  container svo-debug {
    container engineer {
      uses operational;
      uses eng-commands;      
    }
    
    container memory {      
      uses mem-commands;
    }
  }
}
