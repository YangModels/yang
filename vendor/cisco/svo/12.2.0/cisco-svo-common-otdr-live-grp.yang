module cisco-svo-common-otdr-live-grp {

  yang-version 1.1;
  namespace "http://cisco.com/yang/svo/common-otdr-live-grp";
  prefix colg;
  
  organization 
  "Cisco Systems, Inc.";

  contact 
  "Cisco Systems, Inc.
  Customer Service
  
  Postal: 170 West Tasman Drive
  San Jose, CA 95134
  
  Tel: +1 800 553-NETS
  
  E-mail: cs-yang@cisco.com";

  description "YANG definition for SVO CV common Live Data.";

   revision 2021-04-16 { 
      description "Model version for SVO Release 12.2.0 "; 
      reference cisco-svo-common-otdr-live-grp.yang; 
   }
 

    revision 2020-12-04 { 
       description "Model version for SVO Release 12.1.0 "; 
       reference cisco-svo-common-cv-live-grp.yang; 
    }
 

    grouping orl-live {  
      description "live data for orl value on tx and rx direction.";                                
      leaf actual-value {
        config false;
        type decimal64 {
          fraction-digits 2;
        }
      }  
    }
  
}
