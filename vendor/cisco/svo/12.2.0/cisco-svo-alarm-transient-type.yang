module cisco-svo-alarm-transient-type {
  namespace "http://cisco.com/yang/svo/alarm-transient-type";
  prefix svo-al-tr-t;

  include cisco-svo-alarm-transient-type-def;
  include cisco-devices-alarm-transient-types;

  
  organization
    "Cisco Systems, Inc.";

  contact
    "Cisco Systems, Inc.
    Customer Service

    Postal: 170 West Tasman Drive
    San Jose, CA 95134

    Tel: +1 800 553-NETS

    E-mail: cs-yang@cisco.com";

  description
    "This module defines the root of svo alarms under the 
      alarm-type under the module tailf-ncs-alarms";

    revision 2020-12-04 { 
       description "Model version for SVO Release 12.1.0 "; 
       reference cisco-svo-alarm-transient-type.yang; 
    }
 
}
