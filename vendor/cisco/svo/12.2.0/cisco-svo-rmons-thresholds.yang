module cisco-svo-rmons-thresholds {
    yang-version 1.1;
    namespace "http://cisco.com/yang/svo/rmons-thresholds";
    prefix hlrthresholds;

    import cisco-svo-common-equipment-types { prefix ccet; }

    organization
        "Cisco Systems, Inc.";

    contact
        "Cisco Systems, Inc. Customer Service Postal: 170 West Tasman
        Drive San Jose, CA 95134 Tel: +1 800 553-NETS E-mail: cs-yang@cisco.com";

    description
        "YANG definition for RMONs Thresholds";

    revision 2020-12-04 { 
       description "Model version for SVO Release 12.1.0 "; 
       reference cisco-svo-rmons-thresholds.yang; 
    }
 

    typedef stats-id-enum {
        type enumeration {
            enum "UNKNOWN" {
                value 1;
                description "UNKNOWN";
            }
            enum "IfInOctets" {
                value 2;
                description "IfInOctets";
            }
            enum "IfInUcastPkts" {
                value 3;
                description "IfInUcastPkts";
            }
            enum "IfInMulticastPkts" {
                value 4;
                description "IfInMulticastPkts";
            }
            enum "IfInBroadcastPkts" {
                value 5;
                description "IfInBroadcastPkts";
            }
            enum "IfInDiscards" {
                value 6;
                description "IfInDiscards";
            }
            enum "IfInErrors" {
                value 7;
                description "IfInErrors";
            }
            enum "IfOutOctets" {
                value 8;
                description "IfOutOctets";
            }
            enum "IfOutUcastPkts" {
                value 9;
                description "IfOutUcastPkts";
            }
            enum "IfOutMulticastPkts" {
                value 10;
                description "IfOutMulticastPkts";
            }
            enum "IfOutBroadcastPkts" {
                value 11;
                description "IfOutBroadcastPkts";
            }
            enum "IfOutDiscards" {
                value 12;
                description "IfOutDiscards";
            }
            enum "Dot3StatsAlignmentErrors" {
                value 13;
                description "Dot3StatsAlignmentErrors";
            }
            enum "Dot3StatsFCSErrors" {
                value 14;
                description "Dot3StatsFCSErrors";
            }
            enum "Dot3StatsSingleCollisionFrames" {
                value 15;
                description "Dot3StatsSingleCollisionFrames";
            }
            enum "Dot3StatsMultipleCollisionFrames" {
                value 16;
                description "Dot3StatsMultipleCollisionFrames";
            }
            enum "Dot3StatsDeferredTransmissions" {
                value 17;
                description "Dot3StatsDeferredTransmissions";
            }
            enum "Dot3StatsLateCollisions" {
                value 18;
                description "Dot3StatsLateCollisions";
            }
            enum "Dot3StatsExcessiveCollisions" {
                value 19;
                description "Dot3StatsExcessiveCollisions";
            }
            enum "Dot3StatsFrameTooLong" {
                value 20;
                description "Dot3StatsFrameTooLong";
            }
            enum "Dot3StatsCarrierSenseErrors" {
                value 21;
                description "Dot3StatsCarrierSenseErrors";
            }
            enum "Dot3StatsSQETestErrors" {
                value 22;
                description "Dot3StatsSQETestErrors";
            }
            enum "EtherStatsUndersizePkts" {
                value 23;
                description "EtherStatsUndersizePkts";
            }
            enum "EtherStatsFragments" {
                value 24;
                description "EtherStatsFragments";
            }
            enum "EtherStatsPkts64Octets" {
                value 25;
                description "EtherStatsPkts64Octets";
            }
            enum "EtherStatsPkts65to127Octets" {
                value 26;
                description "EtherStatsPkts65to127Octets";
            }
            enum "EtherStatsPkts128to255Octets" {
                value 27;
                description "EtherStatsPkts128to255Octets";
            }
            enum "EtherStatsPkts256to511Octets" {
                value 28;
                description "EtherStatsPkts256to511Octets";
            }
            enum "EtherStatsPkts512to1023Octets" {
                value 29;
                description "EtherStatsPkts512to1023Octets";
            }
            enum "EtherStatsPkts1024to1518Octets" {
                value 30;
                description "EtherStatsPkts1024to1518Octets";
            }
            enum "EtherStatsBroadcastPkts" {
                value 31;
                description "EtherStatsBroadcastPkts";
            }
            enum "EtherStatsMulticastPkts" {
                value 32;
                description "EtherStatsMulticastPkts";
            }
            enum "EtherStatsOversizePkts" {
                value 33;
                description "EtherStatsOversizePkts";
            }
            enum "EtherStatsJabbers" {
                value 34;
                description "EtherStatsJabbers";
            }
            enum "EtherStatsOctets" {
                value 35;
                description "EtherStatsOctets";
            }
            enum "EtherStatsCollisions" {
                value 36;
                description "EtherStatsCollisions";
            }
            enum "EtherStatsCollisionFrames" {
                value 37;
                description "EtherStatsCollisionFrames";
            }
            enum "EtherStatsCRCAlignErrors" {
                value 38;
                description "EtherStatsCRCAlignErrors";
            }
            enum "EtherStatsDropEvents" {
                value 39;
                description "EtherStatsDropEvents";
            }
            enum "ReceivePauseFrames" {
                value 40;
                description "ReceivePauseFrames";
            }
            enum "TransmitPauseFrames" {
                value 41;
                description "TransmitPauseFrames";
            }
            enum "ReceivePktsDroppedInternalCongestion" {
                value 42;
                description "ReceivePktsDroppedInternalCongestion";
            }
            enum "TransmitPktsDroppedInternalCongestion" {
                value 43;
                description "TransmitPktsDroppedInternalCongestion";
            }
            enum "TxTotalPkts" {
                value 44;
                description "txTotalPkts";
            }
            enum "RxTotalPkts" {
                value 45;
                description "rxTotalPkts";
            }
            enum "hdlcPktDrops" {
                value 46;
                description "hdlcPktDrops";
            }
            enum "ReceiveControlFrames" {
                value 47;
                description "ReceiveControlFrames";
            }
            enum "ReceiveUnknownOpcodeFrames" {
                value 48;
                description "ReceiveUnknownOpcodeFrames";
            }
            enum "IfInErrorBytePkts" {
                value 49;
                description "IfInErrorBytePkts";
            }
            enum "IfInFramingErrorPkts" {
                value 50;
                description "IfInFramingErrorPkts";
            }
            enum "IfInJunkInterPkts" {
                value 51;
                description "IfInJunkInterPkts";
            }
            enum "IfOutErrors" {
                value 52;
                description "IfOutErrors";
            }
            enum "GfpStatsRxSBitErrors" {
                value 53;
                description "GfpStatsRxSBitErrors";
            }
            enum "GfpStatsRxMBitErrors" {
                value 54;
                description "GfpStatsRxMBitErrors";
            }
            enum "GfpStatsRxTypeInvalid" {
                value 55;
                description "GfpStatsRxTypeInvalid";
            }
            enum "GfpStatsRxCRCErrors" {
                value 56;
                description "GfpStatsRxCRCErrors";
            }
            enum "GfpStatsRxCIDInvalid" {
                value 57;
                description "GfpStatsRxCIDInvalid";
            }
            enum "GfpStatsLFDRaised" {
                value 58;
                description "GfpStatsLFDRaised";
            }
            enum "GfpStatsCSFRaised" {
                value 59;
                description "GfpStatsCSFRaised";
            }
            enum "GfpStatsRxFrame" {
                value 60;
                description "GfpStatsRxFrame";
            }
            enum "GfpStatsTxFrame" {
                value 61;
                description "GfpStatsTxFrame";
            }
            enum "GfpStatsRxOctets" {
                value 62;
                description "GfpStatsRxOctets";
            }
            enum "GfpStatsTxOctets" {
                value 63;
                description "GfpStatsTxOctets";
            }
            enum "GfpStatsRoundTripLatency" {
                value 64;
                description "GfpStatsRoundTripLatency";
            }
            enum "MediaIndStatsRxFramesTruncated" {
                value 65;
                description "MediaIndStatsRxFramesTruncated";
            }
            enum "MediaIndStatsRxFramesTooLong" {
                value 66;
                description "MediaIndStatsRxFramesTooLong";
            }
            enum "MediaIndStatsRxFramesBadCRC" {
                value 67;
                description "MediaIndStatsRxFramesBadCRC";
            }
            enum "MediaIndStatsTxFramesBadCRC" {
                value 68;
                description "MediaIndStatsTxFramesBadCRC";
            }
            enum "GfpStatsRxDistanceExtBuffers" {
                value 69;
                description "GfpStatsRxDistanceExtBuffers";
            }
            enum "GfpStatsTxDistanceExtBuffers" {
                value 70;
                description "GfpStatsTxDistanceExtBuffers";
            }
            enum "FibreStatsLinkRecoveries" {
                value 71;
                description "FibreStatsLinkRecoveries";
            }
            enum "FibreStatsRXCredits" {
                value 72;
                description "FibreStatsRXCredits";
            }
            enum "FibreStatsTXCredits" {
                value 73;
                description "FibreStatsTXCredits";
            }
            enum "FibreStatsZeroTxCredits" {
                value 74;
                description "FibreStatsZeroTxCredits";
            }
            enum "8b10bInvalidOrderedSets" {
                value 75;
                description "8b10bInvalidOrderedSets";
            }
            enum "8b10bStatsEncodingDispErrors" {
                value 76;
                description "8b10bStatsEncodingDispErrors";
            }
            enum "8b10bIdleOrderedSets" {
                value 77;
                description "8b10bIdleOrderedSets";
            }
            enum "8b10bNonIdleOrderedSets" {
                value 78;
                description "8b10bNonIdleOrderedSets";
            }
            enum "8b10bDataOrderedSets" {
                value 79;
                description "8b10bDataOrderedSets";
            }
            enum "8b10bLossOfSync" {
                value 80;
                description "8b10bLossOfSync";
            }
            enum "hdlcInOctets" {
                value 81;
                description "hdlcInOctets";
            }
            enum "hdlcRxAborts" {
                value 82;
                description "hdlcRxAborts";
            }
            enum "hdlcOutOctets" {
                value 83;
                description "hdlcOutOctets";
            }
            enum "MediaIndStatsRxShortPkts" {
                value 84;
                description "MediaIndStatsRxShortPkts";
            }
            enum "MediaIndStatsOversizeDropped" {
                value 85;
                description "MediaIndStatsOversizeDropped";
            }
            enum "EtherStatsPkts" {
                value 86;
                description "EtherStatsPkts";
            }
            enum "Dot3StatsInternalMacTxErrors" {
                value 87;
                description "Dot3StatsInternalMacTxErrors";
            }
            enum "Dot3StatsInternalMacRxErrors" {
                value 88;
                description "Dot3StatsInternalMacRxErrors";
            }
            enum "Dot3StatsSymbolErrors" {
                value 89;
                description "Dot3StatsSymbolErrors";
            }
            enum "IfOutOversizePkts" {
                value 90;
                description "IfOutOversizePkts";
            }
            enum "GfpStatsRxSblkCRCErrors" {
                value 91;
                description "GfpStatsRxSblkCRCErrors";
            }
            enum "MediaIndStatsTxFramesTooLong" {
                value 92;
                description "MediaIndStatsTxFramesTooLong";
            }
            enum "IfInPayloadCrcErrors" {
                value 93;
                description "IfInPayloadCrcErrors";
            }
            enum "IfOutPayloadCrcErrors" {
                value 94;
                description "IfOutPayloadCrcErrors";
            }
            enum "FibreStatsRxRecvrReady" {
                value 95;
                description "FibreStatsRxRecvrReady";
            }
            enum "FibreStatsTxRecvrReady" {
                value 96;
                description "FibreStatsTxRecvrReady";
            }
            enum "8b10bInvalidOrderedSetsDispErrorsSum" {
                value 97;
                description "8b10bInvalidOrderedSetsDispErrorsSum";
            }
            enum "rprIfStatsInOctets" {
                value 98;
                description "rprIfStatsInOctets";
            }
            enum "rprIfStatsInFrames" {
                value 99;
                description "rprIfStatsInFrames";
            }
            enum "rprIfStatsOutOctets" {
                value 100;
                description "rprIfStatsOutOctets";
            }
            enum "rprIfStatsOutFrames" {
                value 101;
                description "rprIfStatsOutFrames";
            }
            enum "rprPortCounterError" {
                value 102;
                description "rprPortCounterError";
            }
            enum "rprSpanStatsInUcastClassCFrames" {
                value 103;
                description "rprSpanStatsInUcastClassCFrames";
            }
            enum "rprSpanStatsOutUcastClassCFrames" {
                value 104;
                description "rprSpanStatsOutUcastClassCFrames";
            }
            enum "rprSpanStatsInUcastClassCOctets" {
                value 105;
                description "rprSpanStatsInUcastClassCOctets";
            }
            enum "rprSpanStatsOutUcastClassCOctets" {
                value 106;
                description "rprSpanStatsOutUcastClassCOctets";
            }
            enum "rprSpanStatsInMcastClassCFrames" {
                value 107;
                description "rprSpanStatsInMcastClassCFrames";
            }
            enum "rprSpanStatsOutMcastClassCFrames" {
                value 108;
                description "rprSpanStatsOutMcastClassCFrames";
            }
            enum "rprSpanStatsInMcastClassCOctets" {
                value 109;
                description "rprSpanStatsInMcastClassCOctets";
            }
            enum "rprSpanStatsOutMcastClassCOctets" {
                value 110;
                description "rprSpanStatsOutMcastClassCOctets";
            }
            enum "rprSpanStatsInUcastClassBEirFrames" {
                value 111;
                description "rprSpanStatsInUcastClassBEirFrames";
            }
            enum "rprSpanStatsOutUcastClassBEirFrames" {
                value 112;
                description "rprSpanStatsOutUcastClassBEirFrames";
            }
            enum "rprSpanStatsInUcastClassBEirOctets" {
                value 113;
                description "rprSpanStatsInUcastClassBEirOctets";
            }
            enum "rprSpanStatsOutUcastClassBEirOctets" {
                value 114;
                description "rprSpanStatsOutUcastClassBEirOctets";
            }
            enum "rprSpanStatsInMcastClassBEirFrames" {
                value 115;
                description "rprSpanStatsInMcastClassBEirFrames";
            }
            enum "rprSpanStatsOutMcastClassBEirFrames" {
                value 116;
                description "rprSpanStatsOutMcastClassBEirFrames";
            }
            enum "rprSpanStatsInMcastClassBEirOctets" {
                value 117;
                description "rprSpanStatsInMcastClassBEirOctets";
            }
            enum "rprSpanStatsOutMcastClassBEirOctets" {
                value 118;
                description "rprSpanStatsOutMcastClassBEirOctets";
            }
            enum "rprSpanStatsInUcastClassBCirFrames" {
                value 119;
                description "rprSpanStatsInUcastClassBCirFrames";
            }
            enum "rprSpanStatsOutUcastClassBCirFrames" {
                value 120;
                description "rprSpanStatsOutUcastClassBCirFrames";
            }
            enum "rprSpanStatsInUcastClassBCirOctets" {
                value 121;
                description "rprSpanStatsInUcastClassBCirOctets";
            }
            enum "rprSpanStatsOutUcastClassBCirOctets" {
                value 122;
                description "rprSpanStatsOutUcastClassBCirOctets";
            }
            enum "rprSpanStatsInMcastClassBCirFrames" {
                value 123;
                description "rprSpanStatsInMcastClassBCirFrames";
            }
            enum "rprSpanStatsOutMcastClassBCirFrames" {
                value 124;
                description "rprSpanStatsOutMcastClassBCirFrames";
            }
            enum "rprSpanStatsInMcastClassBCirOctets" {
                value 125;
                description "rprSpanStatsInMcastClassBCirOctets";
            }
            enum "rprSpanStatsOutMcastClassBCirOctets" {
                value 126;
                description "rprSpanStatsOutMcastClassBCirOctets";
            }
            enum "rprSpanStatsInUcastClassAFrames" {
                value 127;
                description "rprSpanStatsInUcastClassAFrames";
            }
            enum "rprSpanStatsOutUcastClassAFrames" {
                value 128;
                description "rprSpanStatsOutUcastClassAFrames";
            }
            enum "rprSpanStatsInUcastClassAOctets" {
                value 129;
                description "rprSpanStatsInUcastClassAOctets";
            }
            enum "rprSpanStatsOutUcastClassAOctets" {
                value 130;
                description "rprSpanStatsOutUcastClassAOctets";
            }
            enum "rprSpanStatsInMcastClassAFrames" {
                value 131;
                description "rprSpanStatsInMcastClassAFrames";
            }
            enum "rprSpanStatsOutMcastClassAFrames" {
                value 132;
                description "rprSpanStatsOutMcastClassAFrames";
            }
            enum "rprSpanStatsInMcastClassAOctets" {
                value 133;
                description "rprSpanStatsInMcastClassAOctets";
            }
            enum "rprSpanStatsOutMcastClassAOctets" {
                value 134;
                description "rprSpanStatsOutMcastClassAOctets";
            }
            enum "rprSpanStatsInCtrlFrames" {
                value 135;
                description "rprSpanStatsInCtrlFrames";
            }
            enum "rprSpanStatsOutCtrlFrames" {
                value 136;
                description "rprSpanStatsOutCtrlFrames";
            }
            enum "rprSpanStatsInOamEchoFrames" {
                value 137;
                description "rprSpanStatsInOamEchoFrames";
            }
            enum "rprSpanStatsOutOamEchoFrames" {
                value 138;
                description "rprSpanStatsOutOamEchoFrames";
            }
            enum "rprSpanStatsInOamFlushFrames" {
                value 139;
                description "rprSpanStatsInOamFlushFrames";
            }
            enum "rprSpanStatsOutOamFlushFrames" {
                value 140;
                description "rprSpanStatsOutOamFlushFrames";
            }
            enum "rprSpanStatsInOamOrgFrames" {
                value 141;
                description "rprSpanStatsInOamOrgFrames";
            }
            enum "rprSpanStatsOutOamOrgFrames" {
                value 142;
                description "rprSpanStatsOutOamOrgFrames";
            }
            enum "rprSpanStatsInTopoAtdFrames" {
                value 143;
                description "rprSpanStatsInTopoAtdFrames";
            }
            enum "rprSpanStatsOutTopoAtdFrames" {
                value 144;
                description "rprSpanStatsOutTopoAtdFrames";
            }
            enum "rprSpanStatsInTopoChkSumFrames" {
                value 145;
                description "rprSpanStatsInTopoChkSumFrames";
            }
            enum "rprSpanStatsOutTopoChkSumFrames" {
                value 146;
                description "rprSpanStatsOutTopoChkSumFrames";
            }
            enum "rprSpanStatsInTopoTpFrames" {
                value 147;
                description "rprSpanStatsInTopoTpFrames";
            }
            enum "rprSpanStatsOutTopoTpFrames" {
                value 148;
                description "rprSpanStatsOutTopoTpFrames";
            }
            enum "rprClientStatsInUcastClassCFrames" {
                value 149;
                description "rprClientStatsInUcastClassCFrames";
            }
            enum "rprClientStatsOutUcastClassCFrames" {
                value 150;
                description "rprClientStatsOutUcastClassCFrames";
            }
            enum "rprClientStatsInUcastClassCOctets" {
                value 151;
                description "rprClientStatsInUcastClassCOctets";
            }
            enum "rprClientStatsOutUcastClassCOctets" {
                value 152;
                description "rprClientStatsOutUcastClassCOctets";
            }
            enum "rprClientStatsInMcastClassCFrames" {
                value 153;
                description "rprClientStatsInMcastClassCFrames";
            }
            enum "rprClientStatsOutMcastClassCFrames" {
                value 154;
                description "rprClientStatsOutMcastClassCFrames";
            }
            enum "rprClientStatsInMcastClassCOctets" {
                value 155;
                description "rprClientStatsInMcastClassCOctets";
            }
            enum "rprClientStatsOutMcastClassCOctets" {
                value 156;
                description "rprClientStatsOutMcastClassCOctets";
            }
            enum "rprClientStatsInUcastClassBEirFrames" {
                value 157;
                description "rprClientStatsInUcastClassBEirFrames";
            }
            enum "rprClientStatsOutUcastClassBEirFrames" {
                value 158;
                description "rprClientStatsOutUcastClassBEirFrames";
            }
            enum "rprClientStatsInUcastClassBEirOctets" {
                value 159;
                description "rprClientStatsInUcastClassBEirOctets";
            }
            enum "rprClientStatsOutUcastClassBEirOctets" {
                value 160;
                description "rprClientStatsOutUcastClassBEirOctets";
            }
            enum "rprClientStatsInMcastClassBEirFrames" {
                value 161;
                description "rprClientStatsInMcastClassBEirFrames";
            }
            enum "rprClientStatsOutMcastClassBEirFrames" {
                value 162;
                description "rprClientStatsOutMcastClassBEirFrames";
            }
            enum "rprClientStatsInMcastClassBEirOctets" {
                value 163;
                description "rprClientStatsInMcastClassBEirOctets";
            }
            enum "rprClientStatsOutMcastClassBEirOctets" {
                value 164;
                description "rprClientStatsOutMcastClassBEirOctets";
            }
            enum "rprClientStatsInUcastClassBCirFrames" {
                value 165;
                description "rprClientStatsInUcastClassBCirFrames";
            }
            enum "rprClientStatsOutUcastClassBCirFrames" {
                value 166;
                description "rprClientStatsOutUcastClassBCirFrames";
            }
            enum "rprClientStatsInUcastClassBCirOctets" {
                value 167;
                description "rprClientStatsInUcastClassBCirOctets";
            }
            enum "rprClientStatsOutUcastClassBCirOctets" {
                value 168;
                description "rprClientStatsOutUcastClassBCirOctets";
            }
            enum "rprClientStatsInMcastClassBCirFrames" {
                value 169;
                description "rprClientStatsInMcastClassBCirFrames";
            }
            enum "rprClientStatsOutMcastClassBCirFrames" {
                value 170;
                description "rprClientStatsOutMcastClassBCirFrames";
            }
            enum "rprClientStatsInMcastClassBCirOctets" {
                value 171;
                description "rprClientStatsInMcastClassBCirOctets";
            }
            enum "rprClientStatsOutMcastClassBCirOctets" {
                value 172;
                description "rprClientStatsOutMcastClassBCirOctets";
            }
            enum "rprClientStatsInUcastClassAFrames" {
                value 173;
                description "rprClientStatsInUcastClassAFrames";
            }
            enum "rprClientStatsOutUcastClassAFrames" {
                value 174;
                description "rprClientStatsOutUcastClassAFrames";
            }
            enum "rprClientStatsInUcastClassAOctets" {
                value 175;
                description "rprClientStatsInUcastClassAOctets";
            }
            enum "rprClientStatsOutUcastClassAOctets" {
                value 176;
                description "rprClientStatsOutUcastClassAOctets";
            }
            enum "rprClientStatsInMcastClassAFrames" {
                value 177;
                description "rprClientStatsInMcastClassAFrames";
            }
            enum "rprClientStatsOutMcastClassAFrames" {
                value 178;
                description "rprClientStatsOutMcastClassAFrames";
            }
            enum "rprClientStatsInMcastClassAOctets" {
                value 179;
                description "rprClientStatsInMcastClassAOctets";
            }
            enum "rprClientStatsOutMcastClassAOctets" {
                value 180;
                description "rprClientStatsOutMcastClassAOctets";
            }
            enum "rprClientStatsInBcastFrames" {
                value 181;
                description "rprClientStatsInBcastFrames";
            }
            enum "rprClientStatsOutBcastFrames" {
                value 182;
                description "rprClientStatsOutBcastFrames";
            }
            enum "rprErrorStatsBadParityFrames" {
                value 183;
                description "rprErrorStatsBadParityFrames";
            }
            enum "rprErrorStatsBadHecFrames" {
                value 184;
                description "rprErrorStatsBadHecFrames";
            }
            enum "rprErrorStatsTtlExpFrames" {
                value 185;
                description "rprErrorStatsTtlExpFrames";
            }
            enum "rprErrorStatsTooLongFrames" {
                value 186;
                description "rprErrorStatsTooLongFrames";
            }
            enum "rprErrorStatsTooShortFrames" {
                value 187;
                description "rprErrorStatsTooShortFrames";
            }
            enum "rprErrorStatsBadFcsFrames" {
                value 188;
                description "rprErrorStatsBadFcsFrames";
            }
            enum "rprErrorStatsSelfSrcUcastFrames" {
                value 189;
                description "rprErrorStatsSelfSrcUcastFrames";
            }
            enum "rprErrorStatsPmdAbortFrames" {
                value 190;
                description "rprErrorStatsPmdAbortFrames";
            }
            enum "rprErrorStatsBadAddrFrames" {
                value 191;
                description "rprErrorStatsBadAddrFrames";
            }
            enum "rprErrorStatsContainedFrames" {
                value 192;
                description "rprErrorStatsContainedFrames";
            }
            enum "rprErrorStatsScffErrors" {
                value 193;
                description "rprErrorStatsScffErrors";
            }
            enum "Dot3StatsControlInUnknownOpCodes" {
                value 194;
                description "Dot3StatsControlInUnknownOpCodes";
            }
            enum "Dot3StatsInPauseFrames" {
                value 195;
                description "Dot3StatsInPauseFrames";
            }
            enum "Dot3StatsOutPauseFrames" {
                value 196;
                description "Dot3StatsOutPauseFrames";
            }
            enum "EtherStatsPkts1519to1522Octets" {
                value 197;
                description "EtherStatsPkts1519to1522Octets";
            }
            enum "rprErrorOversizeFrames" {
                value 198;
                description "rprErrorOversizeFrames";
            }
            enum "EtherStatsTxFifoOverflowEvents" {
                value 199;
                description "EtherStatsTxFifoOverflowEvents";
            }
            enum "ifHCInOctets" {
                value 200;
                description "ifHCInOctets";
            }
            enum "ifHCInUcastPkts" {
                value 201;
                description "ifHCInUcastPkts";
            }
            enum "ifHCInMulticastPkts" {
                value 202;
                description "ifHCInMulticastPkts";
            }
            enum "ifHCInBroadcastPkts" {
                value 203;
                description "ifHCInBroadcastPkts";
            }
            enum "ifHCOutOctets" {
                value 204;
                description "ifHCOutOctets";
            }
            enum "ifHCOutMulticastPkts" {
                value 205;
                description "ifHCOutMulticastPkts";
            }
            enum "ifHCOutBroadcastPkts" {
                value 206;
                description "ifHCOutBroadcastPkts";
            }
            enum "etherStatsHighCapacityPkts" {
                value 207;
                description "etherStatsHighCapacityPkts";
            }
            enum "etherStatsHighCapacityOctets" {
                value 208;
                description "etherStatsHighCapacityOctets";
            }
            enum "etherStatsHighCapacityPkts64Octets" {
                value 209;
                description "etherStatsHighCapacityPkts64Octets";
            }
            enum "etherStatsHighCapacityPkts65to127Octets" {
                value 210;
                description "etherStatsHighCapacityPkts65to127Octets";
            }
            enum "etherStatsHighCapacityPkts128to255Octets" {
                value 211;
                description "etherStatsHighCapacityPkts128to255Octets";
            }
            enum "etherStatsHighCapacityPkts256to511Octets" {
                value 212;
                description "etherStatsHighCapacityPkts256to511Octets";
            }
            enum "etherStatsHighCapacityPkts512to1023Octets" {
                value 213;
                description "etherStatsHighCapacityPkts512to1023Octets";
            }
            enum "etherStatsHighCapacityPkts1024to1518Octets" {
                value 214;
                description "etherStatsHighCapacityPkts1024to1518Octets";
            }
            enum "cisRxReports" {
                value 215;
                description "cisRxReports";
            }
            enum "cisRxLeaves" {
                value 216;
                description "cisRxLeaves";
            }
            enum "cisTxReports" {
                value 217;
                description "cisTxReports";
            }
            enum "cisTxLeaves" {
                value 218;
                description "cisTxLeaves";
            }
            enum "cisTxGeneralQueries" {
                value 219;
                description "cisTxGeneralQueries";
            }
            enum "cisTxGroupSpecificQueries" {
                value 220;
                description "cisTxGroupSpecificQueries";
            }
            enum "cisRxGeneralQueries" {
                value 221;
                description "cisRxGeneralQueries";
            }
            enum "cisRxGroupSpecificQueries" {
                value 222;
                description "cisRxGroupSpecificQueries";
            }
            enum "cisRxValidPackets" {
                value 223;
                description "cisRxValidPackets";
            }
            enum "cisRxInvalidPackets" {
                value 224;
                description "cisRxInvalidPackets";
            }
            enum "dot3adAggPortStatsLACPDUsRx" {
                value 225;
                description "dot3adAggPortStatsLACPDUsRx";
            }
            enum "dot3adAggPortStatsLACPDUsTx" {
                value 226;
                description "dot3adAggPortStatsLACPDUsTx";
            }
            enum "crepHflRxPdus" {
                value 227;
                description "crepHflRxPdus";
            }
            enum "crepHflTxPdus" {
                value 228;
                description "crepHflTxPdus";
            }
            enum "crepLslRxPdus" {
                value 229;
                description "crepLslRxPdus";
            }
            enum "crepLslTxPdus" {
                value 230;
                description "crepLslTxPdus";
            }
            enum "MediaIndStatsTxFramesTruncated" {
                value 231;
                description "MediaIndStatsTxFramesTruncated";
            }
            enum "GfpRxCmfFrame" {
                value 232;
                description "GfpRxCmfFrame";
            }
            enum "GfpTxCmfFrame" {
                value 233;
                description "GfpTxCmfFrame";
            }
            enum "EtherStatsPkts1519toMaxOctets" {
                value 234;
                description "EtherStatsPkts1519toMaxOctets";
            }
            enum "MediaIndStatsTxShortPkts" {
                value 235;
                description "MediaIndStatsTxShortPkts";
            }
            enum "MediaIndStatsRxLcvErrors" {
                value 236;
                description "MediaIndStatsRxLcvErrors";
            }
            enum "MediaIndStatsTxLcvErrors" {
                value 237;
                description "MediaIndStatsTxLcvErrors";
            }
            enum "Dot3StatsLcvErrors" {
                value 238;
                description "Dot3StatsLcvErrors";
            }
            enum "Dot3StatsLayer1Errors" {
                value 239;
                description "Dot3StatsLayer1Errors";
            }
            enum "GfpStatsCHecRxMBitErrors" {
                value 240;
                description "GfpStatsCHecRxMBitErrors";
            }
            enum "GfpStatsTHecRxMBitErrors" {
                value 241;
                description "GfpStatsTHecRxMBitErrors";
            }
            enum "Rx8b10bWords" {
                value 242;
                description "Rx8b10bWords";
            }
            enum "Tx8b10bWords" {
                value 243;
                description "Tx8b10bWords";
            }
            enum "Pcs49RxErrBer" {
                value 244;
                description "Pcs49RxErrBer";
            }
            enum "Pcs49RxErrDec" {
                value 245;
                description "Pcs49RxErrDec";
            }
            enum "PcsErrCount" {
                value 246;
                description "PcsErrCount";
            }
            enum "PcsErrCount2" {
                value 247;
                description "PcsErrCount2";
            }
            enum "PcsEgRxErrFrames" {
                value 248;
                description "PcsEgRxErrFrames";
            }
            enum "NUM_ID" {
                value 249;
                description "NUM_STATS_ID";
            }
        }
    }

    typedef alarm-type-enum {
        type enumeration {
            enum "Unknown" {
                value 1;
                description
                "Unknown";
            }

            enum "Rising" {
                value 2;
                description
                "Rising alarm";
            }

            enum "Falling" {
                value 3;
                description
                "Falling alarm";
            }

            enum "Rising_Or_Falling" {
                value 4;
                description
                "Rising or Falling alarm";
            }
        }
    }

    typedef sample-type-enum {
        type enumeration {
            enum "Unknown" {
                value 1;
                description
                "Unknown";
            }

            enum "Absolute" {
                value 2;
                description
                "Absolute Sampling";
            }

            enum "Relative" {
                value 3;
                description
                "Relative Sampling";
            }
        }
    }

    grouping rmon-threshold {
        leaf id {
            type string;
            mandatory true;
        }

        leaf alarm-index {
            type uint32;
            description "Ether Rmon Threshold alarm index. used to map with the alarms rised.";
        }
        
        leaf interface-name {
            type string;
        }

        leaf uid {
            type ccet:uid-t;
        }

        leaf slot-id {
            type string;
        }

        leaf stats-id {
            type stats-id-enum;
        }

        leaf alarm-type {
            type alarm-type-enum;
        }

        leaf sample-type {
            type sample-type-enum;
        }

        leaf sample-period {
            type uint64;
            mandatory true;
        }

        leaf rising-threshold {
            type uint64;
            mandatory true;
        }

        leaf falling-threshold {
            type uint64;
            mandatory true;
        }
    }

    grouping rmon-threshold-group {
        list rmon-thresholds-list {
            key "id";
            uses rmon-threshold;
        }
    }
}
