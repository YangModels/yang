module cisco-svo-common-optical-channel-grp {
  yang-version 1.1;
  namespace "http://cisco.com/yang/svo/common-optical-channel-grp";
  prefix coch;

  import org-openroadm-common-optical-channel-types { prefix org-openroadm-common-optical-channel-types; revision-date 2018-05-30; }
  import org-openroadm-common-link-types { prefix org-openroadm-common-link-types; revision-date 2018-03-30; }
  import cisco-svo-common-types { prefix cct; }
  import cisco-svo-common-base-opt-grp { prefix ccbog; }

  organization 
    "Cisco Systems, Inc.";

  contact 
    "Cisco Systems, Inc.
     Customer Service
     
     Postal: 170 West Tasman Drive
     San Jose, CA 95134
     
     Tel: +1 800 553-NETS
     
     E-mail: cs-yang@cisco.com";

  description "
    This module defines the Optical Channel interface Config group";

   revision 2021-04-16 { 
      description "Model version for SVO Release 12.2.0 "; 
      reference cisco-svo-common-optical-channel-grp.yang; 
   }
 

    revision 2020-12-04 { 
       description "Model version for SVO Release 12.1.0 "; 
       reference cisco-svo-common-optical-channel-grp.yang; 
    }
 

  typedef psm-info-t {
    type enumeration {
      enum "NA" {
        description "Not Available";
      }
      enum "Disable" {
        description "Disable Psm mode";
      }
      enum "Enable" {
        description "Enable Psm mode";
      }
    }
    description "When enabled on a trunk port with PSM, consequent actions will not be inserted toward clients, allowing a faster switching on some cards.";
  }

  grouping optch-config-group {
    leaf reach {
      type cct:reach-t;
      description "Reach";
    }

    leaf sd-fec {
      type identityref {
        base cct:sd-fec-type;
      }
      description "permitted fec states";
    }

    leaf frequency {
      type org-openroadm-common-optical-channel-types:frequency-THz;
      description
      "Center Frequency in THz.";
    }

    leaf transmit-power {
      type org-openroadm-common-link-types:power-dBm;
      description
      "The target transmit power for this channel. When set, the xponder will work to ensure that port-current-power reaches this level. Applicable only to channel on top of xpdr-network port";
    }

    container cd-range {
      description "Configures the CD lookup interval";
      uses ccbog:cd-range-grp;
    }

    leaf psm-info {
      type coch:psm-info-t;
      description "Configures the channel as operating with a connected PSM";
    }

    leaf tx-shutdown {
      type boolean;
      description "Enable maximum output attenuation, shutting down the channel (the laser is not turned off)";
    }

    leaf otn-enabled {
      type boolean;
      description "Enable ITU-T G.709 OTN";
    }

    container threshold-parameters {
      description "Available threshold parameters";
      
      container rx-power {
        description "Received optical power thresholds";
        uses ccbog:och-power-thresholds-grp;
      }
      
      container tx-power {
        description "Transmitted optical power thresholds";
        uses ccbog:och-power-thresholds-grp;
      }

      container cd {
        description "Chromatic Dispersion thresholds";
        uses ccbog:cd-range-grp;
      }

      container laser-bias {
        description "Laser bias thresholds";
        uses ccbog:laser-bias-high-threshold-grp;
      }
    }
  }

}
