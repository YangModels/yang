module cisco-svo-common-equipment-grp {
    yang-version 1.1;
    namespace "http://cisco.com/yang/svo/common-equipment-grp";
    prefix cceqptg;

    import ietf-inet-types { prefix inet; }
    import cisco-svo-common-equipment-types { prefix ccet; }

    organization
        "Cisco Systems, Inc.";

    contact
        "Cisco Systems, Inc. Customer Service Postal: 170 West Tasman
        Drive San Jose, CA 95134 Tel: +1 800 553-NETS E-mail: cs-yang@cisco.com";

    description " Cisco Common Equipment Types Config Data Group";

    revision 2020-12-04 { 
       description "Model version for SVO Release 12.1.0 "; 
       reference cisco-svo-common-equipment-grp.yang; 
    }
 


    grouping position-in-rack {
      description "Definition of position in rack for chassis, passive chassis and passive units";
      leaf rack-id {
        type ccet:rack-id-t;
        description "Rack ID";
        mandatory true;
      }

      leaf ru-position {
        type ccet:ru-position-t;
        mandatory true;
        description "Rack Unit (RU) Position";
      }
    }

    grouping usb-port-association-info-grp {

        container usb-port-association-info {
            leaf usb-uts-id {
                type ccet:usb-uts-id-t;
                description "Usb uts identifier";
            }

            leaf port-id {
                type ccet:usb-port-id-t;
                description "Port identifier";
            }
        }
    }

    grouping ipv4-grp {
      leaf ip-address {
        type inet:ipv4-address;
        mandatory true;
        description "IP address";
      }
      leaf subnet-prefix-len {
        type uint8 {
          range "0..32";
        }
        description "The length of the subnet prefix.";
      }
      leaf default-gateway {
        type inet:ipv4-address;
        mandatory true;
        description "Default Gateway";
      }
    }

    grouping ipv6-grp {
      leaf ip-address {
        type inet:ipv6-address;
        mandatory true;
        description "IP address";
      }
      leaf subnet-prefix-len {
        type uint8 {
          range "0..128";
        }
        description "The length of the subnet prefix.";
      }
      leaf default-gateway {
        type inet:ipv6-address;
        mandatory true;
        description "Default Gateway";
      }
    }

    grouping cfg-event-stats-grp {
      leaf to-file {
        type boolean;
        default false;
        description "print configuration event statistics to default file";
      }

      leaf filtered {
        type boolean;
        default false;
        description "print configuration event statistics for processed events only";
      }

      leaf avg-rate-th {
        type uint8;
        default 0;
        description "print configuration event statistics if avg rate value equals or is greater than threshold";
      }
    }

}
