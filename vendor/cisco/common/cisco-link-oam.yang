module cisco-link-oam {

  /*** NAMESPACE / PREFIX DEFINITION ***/

  namespace "urn:cisco:params:xml:ns:yang:cisco-link-oam";

  prefix "cisco-link-oam";

  /*** LINKAGE (IMPORTS / INCLUDES) ***/
  
  import ietf-interfaces { prefix "if"; }

  import ethernet { prefix "eth"; }

  import ethernet-link-oam { prefix "link-oam"; }

  import Cisco-IOS-XR-types { prefix "xr"; }

  /*** META INFORMATION ***/

  organization
    "Cisco Systems, Inc.
     Customer Service

     Postal: 170 W Tasman Drive
     San Jose, CA 95134

     Tel: +1 1800 553-NETS
     
     E-mail: cs-yang@cisco.com";

  contact
    "Richard Furness - rfurness@cisco.com";

  description 
    "This module contains a collection of YANG definitions
     for managing the IEEE 802.3 Ethernet Link OAM feature on Cisco
     devices.

     This YANG module augments the 'ethernet-link-oam' module with
     various features specific to Cisco devices such as:
     - Configuration profiles
     - Link monitoring high thresholds and corresponding actions
     - Configuration to specify the support required of the peer
     - Configurable hello interval and connection timeout
     - Mis-wiring detection

     Copyright (c) 2015 by Cisco Systems, Inc.
     All rights reserved.";

  revision "2015-10-29" {
    description
      "Initial version";
    reference
      "IEEE 802.3 2012";
  }

  typedef hello-interval-enum {
    type enumeration {
      enum 1s {
        value 0;
        description "1 s OAM hello interval";
      }
      enum 100ms {
        value 1;
        description "100 ms OAM hello interval";
      }
    }
    description "Ethernet Link OAM interface hello interval enum";
  }
  typedef require-mode-enum {
    type enumeration {
      enum passive {
        value 0;
        description "Ethernet Link OAM Passive mode";
      }
      enum active {
        value 1;
        description "Ethernet Link OAM Active mode";
      }
      enum either {
        value 2;
        description "Ethernet Link OAM mode not required";
      }
    }
    description "Possible modes required of the peer";
  }

  typedef action-enum {
    type enumeration {
      enum no-action {
        value 1;
        description "Disabled (do nothing)";
      }
      enum error-disable {
        value 2;
        description "Error-Disable the interface";
      }
      enum log {
        value 3;
        description "Log the event and do nothing else";
      }
      enum efd {
        value 4;
        description "EFD the interface";
      }
    }
    description "Actions supported by an OAM interface";
  }

  grouping cisco-intf-config {
    description
      "Cisco-specific Link OAM configuration items";

    container action {
      description "Configure action parameters";
      leaf dying-gasp {
        type action-enum;
        default log;
        must ". != 'efd'";
        description
          "Action to perform when a dying gasp is received";
      }
      leaf link-fault {
        type action-enum;
        default log;
        description
          "Action to perform when a uni-directional link fault
           notification is received from the peer";
      }
      leaf capabilities-conflict {
        type action-enum;
        default log;
        description
          "Action to perform when a capabilities conflict occurs";
      }
      leaf session-up {
        type action-enum;
        default log;
        must ". != 'efd' and . != 'error-disable'";
        description
          "Action to perform when a session comes up";
      }
      leaf critical-event {
        type action-enum;
        default log;
        must ". != 'efd'";
        description
          "Action to perform when a critical event is received from
           the peer";
      }
      leaf remote-loopback {
        type action-enum;
        if-feature link-oam:remote-loopback;
        default log;
        must ". != 'efd' and . != 'error-disable'";
        description
          "Action to perform when the device enters loopback mode
           as requested by the peer";
      }
      leaf wiring-conflict {
        type action-enum;
        default error-disable;
        description
          "Action to perform when a wiring conflict is detected";
      }
      leaf high-threshold {
        if-feature link-oam:link-monitoring;
        default no-action;
        type action-enum;
        must ". != 'efd'";
        description
          "Action to perform when a link monitoring event (either
           local or remote) crosses the configured high threshold.
           By default no action is performed.";
      }
      leaf discovery-timeout {
        type action-enum;
        default log;
        description
          "Action to perform when discovery timeout occurs";
      }
      leaf session-down {
        type action-enum;
        default log;
        description
          "Action to perform when a session goes down";
      }
    }

    container require-remote {
      description "Configure remote requirement parameters";
      leaf mode {
        type require-mode-enum;
        default either;
        description
          "The Link OAM required of the peer (if any)";
      }
      leaf mib-retrieval {
        type boolean;
        if-feature link-oam:remote-mib-retrieval;
        default false;
        description
          "If True, do not bring up a session unless the peer
           supports MIB retrieval";
      }
      leaf remote-loopback {
        type boolean;
        if-feature link-oam:remote-loopback;
        default false;
        description
          "If True, do not bring up a session unless the peer
           supports remote loopback";
      }
      leaf link-monitoring {
        type boolean;
        if-feature link-oam:link-monitoring;
        default false;
        description
          "If True, do not bring up a session unless the peer
           supports link monitoring";
      }
    }
    leaf timeout {
      type uint32 {
        range "2..30";
      }
      default 5;
      description
        "Connection timeout period in number of lost heartbeats";
    }
    leaf hello-interval {
      type hello-interval-enum;
      default 1s;
      description "Possible Ethernet Link OAM hello intervals";
    }
  }

  /*
   * Augmentation to support Cisco units and high-threshold
   * configuration
   */
  grouping link-monitoring-config {
    description
      "Link monitoring configuration shared between interface,
       profile and running configuration";

    leaf threshold-high {
      if-feature link-oam:link-monitoring;
      type uint64 {
        range "1..max";
      }
      description
        "The threshold value to use when determining whether to
         take the configured action for this particular theshold
         event type. The units, and upper and lower bounds are the
         same as for 'threshold' in the base model.

         If not configured, no high threshold action will be taken.

         The high threshold must be greater than (or equal to) the
         regular threshold.";
      must ". >= ../threshold";
    }

    container cisco {
      description
        "A set of leaves for configuring Link Monitoring using 'Cisco
         units'.";
      presence
        "If present (which must be the case if any of the three
         leaves is set for a particular event type) then the values
         of both 'window' and 'threshold' (from the standard model)
         are ignored, and are overriden by the 'window-cisco' and
         'threshold-cisco' leaves defined here.
         In such cases, even if a particular leaf (say
         'window-cisco') is not set, this distinction is relevant as
         the default value is as defined by 'window-cisco' rather
         than the standard 'window'.";

      leaf window {
        type uint64;
        units milliseconds;
        description
          "An alternative means to configure the size of the window
           to use when monitoring for this threshold event. The units
           are milliseconds, differing from those in the standard
           model in order to better support interfaces of varying
           speeds.

           If the parent 'cisco' container is present, this leaf
           overrides the 'window' leaf in the standard model.

           The default and upper and lower bounds depend on the
           threshold type as follows:

           Symbol Period:
             Default: 1 second
             Min: 1 second
             Max: 1 minute
           Frame:
             Default: 1 second
             Min: 1 second
             Max: 1 minute
           Frame Period:
             Def: 1 second
             Min: 1 second
             Max: 1 minute
           Frame Seconds:
             Default: 60 seconds
             Min: 10 seconds
             Max: 900 seconds
           ";
      }

      leaf threshold {
        type uint64 {
          range "1..12000000";
        }
        description
          "An alternative means to configure the threshold value to
           use when determining whether to generate an event given
           the number of errors that occurred in a given window. The
           units differ from those in the standard model in order
           to better support interfaces of varying speeds.

           If the parent 'cisco' container is present, this leaf
           overrides the 'threshold' leaf in the standard model.

           The units, default and upper and lower bounds are depend
           on the threshold type as follows:

           Symbol Period:
             Units: errors per million symbols
             Default: 1
             Min: 1
             Max: 1000000
           Frame:
             Units: number of errored frames
             Default: 1
             Min: 1
             Max: 12000000
           Frame Period:
             Units: errors per million frames
             Default: 1
             Min: 1
             Max: 1000000
           Frame Seconds:
             Units: number of errored frame-seconds
             Default: 1
             Min: 1
             Max: 900
           ";
      }

      leaf threshold-high {
        if-feature link-oam:link-monitoring;
        type uint64 {
          range "1..12000000";
        }
        description
          "The threshold value to use when determining whether to
           take the configured action for this particular theshold
           event type. The units, and upper and lower bounds are the
           same as for the Cisco-specific 'threshold' above.

           If the parent 'cisco' container is present, this leaf
           overrides the 'threshold' leaf in the standard model.

           If not configured, no high threshold action will be taken.

           The high threshold must be greater than (or equal to) the
           regular threshold.";
        must ". >= ../threshold";
      }
    }
  }
  augment "/if:interfaces/if:interface/eth:ethernet" +
          "/link-oam:link-oam/link-oam:link-monitor" +
          "/link-oam:event-type" {
    description
      "Augmentation to support Cisco units and high-threshold
       configuration";
    uses link-monitoring-config;
  }

  /*
   * Augmentation to support other Cisco-specific per-interface
   * configuration
   */

  augment "/if:interfaces/if:interface/eth:ethernet" +
          "/link-oam:link-oam" {
    description
      "This augment extends the per-interface Ethernet Link OAM
       configuration data model with items specific to Cisco
       devices";

    leaf profile-name {
      type leafref {
        path "/ethernet-link-oam/profiles/profile/name";
      }
      description "Set the profile to use on the interface";
    }

    uses cisco-intf-config;
  }

  /*
   * New nodes to support Cisco-specific global Link OAM config
   */

  container ethernet-link-oam {
    description "Ethernet Link OAM global configuration";

    container profiles {
      description "List of Ethernet Link OAM configuration profiles";

      list profile {
        key "name";
        description "List of Link OAM configuration profiles";

        leaf name {
          type string {
            length "1..32";
          }
          description "Name of the profile";
        }

        /*
         * Reuse the per-interface configuration groupings (standard
         * and Cisco-specific).
         */
        uses link-oam:intf-config {
          augment "link-monitor/event-type" {
            description
              "Augmentation to support Cisco units and high-threshold
               configuration";
            uses link-monitoring-config;
          }
        }

        uses cisco-intf-config;
      }
    }
  }

  /*
   * Augmentations to support Cisco-specific per-interface
   * operational data
   */

  augment "/if:interfaces-state/if:interface/eth:ethernet" +
          "/link-oam:link-oam/link-oam:event-log" +
          "/link-oam:event-log-entry" {
    description
      "Augmentation to add Cisco-specific items to the event log";
    leaf local-high-threshold {
      type uint64;
      description
        "Size of the local high threshold (If applicable). For remote
         threshold events this is scaled for comparison with the
         Breaching Value. This is to account for different local and
         remote window sizes.";
    }
    leaf action-taken {
      type action-enum;
      description "Local action taken (If applicable)";
    }
  }

  augment "/if:interfaces-state/if:interface/eth:ethernet" +
          "/link-oam:link-oam/link-oam:discovery-info" {
    description
      "Augments per-interface discovery information with Cisco-
       specific items";
    leaf miswired {
      type boolean;
      description "Has the interface been mis-wired?";
    }
  }

  augment "/if:interfaces-state/if:interface/eth:ethernet" +
          "/link-oam:link-oam/link-oam:statistics" {
    description
      "Augments per-interface statistics with Cisco-specific items";
    leaf fixed-frames-rx {
      type uint32;
      description
        "Number of RX frames 'fixed' by Link OAM. This counts the
         number of received packets that could still be processed
         despite being in some way invalid (e.g. having
         unexpected TLVs present).";
    }
  }

  augment "/if:interfaces-state/if:interface/eth:ethernet" +
          "/link-oam:link-oam" {
    description
      "This augment extends the per-interface Ethernet Link OAM
       operational data model with items specific to Cisco devices";

    container efd-triggers {
      description
        "Triggers currently causing the interface to be
        brought down using EFD";
      leaf link-fault-received {
        type empty;
        description "Link-fault messages being received";
      }
      leaf discovery-timed-out {
        type empty;
        description "The discovery process has timed out";
      }
      leaf capabilities-conflict {
        type empty;
        description "A capabilities conflict has been detected";
      }
      leaf wiring-conflict {
        type empty;
        description "A wiring conflict has been detected";
      }
      leaf session-down {
        type empty;
        description "The 802.3 OAM session is down";
      }
    }

    leaf local-mwd-key {
      type uint32;
      description "The local mis-wiring-detection key";
    }
    leaf remote-mwd-key {
      type uint32;
      description "The remote mis-wiring-detection key";
    }

    container running-config {
      description
        "The configuration currently running on an interface, based
         on both per-interface and profile configuration (if
         present).";
      /*
       * Reuse the per-interface configuration groupings (standard
       * and Cisco-specific).
       */
      uses link-oam:intf-config {
        augment "link-monitor/event-type" {
          description
            "Augmentation to support Cisco units and high-threshold
             configuration";
          uses link-monitoring-config;
        }
      }

      uses cisco-intf-config;
    }
  }

  /*
   * New nodes to support Cisco-specific global Link OAM state data
   */

  container ethernet-link-oam-state {
    description "Ethernet Link OAM global operational state";
    config false;

    container nodes {
      description "Node table for node-specific operational data";

      list node {
        key "node-name";
        description "Node-specific data for a particular node";
        leaf node-name {
          type xr:Node-id;
          description "Node";
        }
        container summary {
          description
            "Ethernet Link OAM Summary information for the entire
             node";
          leaf interfaces {
            type uint32;
            mandatory true;
            description
              "The number of interfaces with 802.3 OAM configured";
          }
          leaf port-down {
            type uint32;
            mandatory true;
            description
              "The number of interfaces in 'Port Down' state";
          }
          leaf passive-wait {
            type uint32;
            mandatory true;
            description
              "The number of interfaces in 'Passive Wait' state";
          }
          leaf active-send {
            type uint32;
            mandatory true;
            description
              "The number of interfaces in 'Active Send' state";
          }
          leaf evaluating {
            type uint32;
            mandatory true;
            description
              "The number of interfaces in 'Evaluating' state";
          }
          leaf local-accept {
            type uint32;
            mandatory true;
            description
              "The number of interfaces in 'Local Accept' state";
          }
          leaf local-reject {
            type uint32;
            mandatory true;
            description
              "The number of interfaces in 'Local Reject' state";
          }
          leaf remote-reject {
            type uint32;
            mandatory true;
            description
              "The number of interfaces in 'Remote Reject' state";
          }
          leaf operational {
            type uint32;
            mandatory true;
            description
              "The number of interfaces in 'Operational' state";
          }
          leaf loopback-mode {
            if-feature link-oam:remote-loopback;
            type uint32;
            mandatory true;
            description
              "The number of interfaces in loopback mode";
          }
          leaf miswired-connections {
            type uint32;
            mandatory true;
            description
              "The number of miswired connections";
          }
          leaf events {
            type uint64;
            mandatory true;
            description
              "The number of events recorded (including threshold
               events)";
          }
          leaf local-events {
            type uint64;
            mandatory true;
            description "The number of local events recorded";
          }
          leaf local-symbol-period {
            if-feature link-oam:link-monitoring;
            type uint64;
            mandatory true;
            description
              "The number of local symbol period events recorded";
          }
          leaf local-frame {
            if-feature link-oam:link-monitoring;
            type uint64;
            mandatory true;
            description
              "The mumber of local frame error events recorded";
          }
          leaf local-frame-period {
            if-feature link-oam:link-monitoring;
            type uint64;
            mandatory true;
            description
              "The number of local frame period events recorded";
          }
          leaf local-frame-seconds {
            if-feature link-oam:link-monitoring;
            type uint64;
            mandatory true;
            description
              "The number of local frame second events recoded";
          }
          leaf remote-events {
            type uint64;
            mandatory true;
            description
              "The number of remote events recorded";
          }
          leaf remote-symbol-period {
            if-feature link-oam:link-monitoring;
            type uint64;
            mandatory true;
            description
              "The number of remote symbol period events recorded";
          }
          leaf remote-frame {
            if-feature link-oam:link-monitoring;
            type uint64;
            mandatory true;
            description
              "The mumber of remote frame error events recorded";
          }
          leaf remote-frame-period {
            if-feature link-oam:link-monitoring;
            type uint64;
            mandatory true;
            description
              "The number of remote frame period events recorded";
          }
          leaf remote-frame-seconds {
            if-feature link-oam:link-monitoring;
            type uint64;
            mandatory true;
            description
              "The number of remote frame second events recoded";
          }
        }
      }
    }
  }

  /*
   * RPCs for fetching Link OAM related MIB variables from the peer
   */

  rpc get-remote-stats {
    if-feature link-oam:remote-mib-retrieval;
    description
      "Retrieve Link OAM statistics from the peer for the specified
       interface.";
    input {
      leaf interface {
        type if:interface-ref;
        mandatory true;
        description
          "The interface to query statistics for.";
      }
    }
    output {
      uses link-oam:statistics-common;
    }
  }
  rpc get-remote-discovery-info {
    if-feature link-oam:remote-mib-retrieval;
    description
      "Retrieve Link OAM discovery information from the peer for the
       specified interface.";
    input {
      leaf interface {
        type if:interface-ref;
        mandatory true;
        description
          "The interface to query discovery information for.";
      }
    }
    output {
      uses link-oam:discovery-info;
    }
  }
}
