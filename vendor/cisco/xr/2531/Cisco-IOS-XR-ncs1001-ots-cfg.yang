module Cisco-IOS-XR-ncs1001-ots-cfg {
  namespace "http://cisco.com/ns/yang/Cisco-IOS-XR-ncs1001-ots-cfg";
  prefix ncs1001-ots-cfg;

  import ietf-inet-types {
    prefix inet;
  }
  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots package configuration.
     
     This YANG module augments the
       Cisco-IOS-XR-config-mda-cfg
     module with configuration data.
     
     Copyright (c) 2013-2023 by Cisco Systems, Inc.
     All rights reserved.";

  revision 2023-04-03 {
    description
      "added Cisco-IOS-XR-config-mda-cfg
       2023-03-24
         IPv6 MDA schema datatype to match CLI datatype
       2022-12-01
         additional configs to support IPv6";
    semver:module-version "3.0.0";
  }
  revision 2020-01-31 {
    description
      "added refractive index ad back scattering OTDR parameters";
    semver:module-version "2.1.0";
  }
  revision 2019-05-28 {
    description
      "added OTDR periodic scan and event triggered auto scan";
    semver:module-version "2.0.0";
  }
  revision 2019-04-05 {
    description
      "Establish semantic version baseline.";
    semver:module-version "2.0.0";
  }
  revision 2018-03-20 {
    description
      "added Otdr management.";
  }
  revision 2015-11-09 {
    description
      "IOS XR 6.0 revision.";
  }

  typedef Ots-amplifier-node {
    type enumeration {
      enum "term" {
        value 0;
        description
          "Nodetype TERM";
      }
      enum "ila" {
        value 1;
        description
          "Nodetype InLine Amplifier";
      }
      enum "roadm" {
        value 2;
        description
          "Nodetype ROADM";
      }
    }
    description
      "Ots amplifier node";
  }

  typedef Ots-amplifier-grid-mode {
    type enumeration {
      enum "100g-hz" {
        value 0;
        description
          "100GHz mode";
      }
      enum "50g-hz" {
        value 1;
        description
          "50GHz mode";
      }
      enum "gr-idle-ss" {
        value 2;
        description
          "Gridless mode";
      }
      enum "75ghz" {
        value 3;
        description
          "75GHz mode";
      }
    }
    description
      "Ots amplifier grid mode";
  }

  typedef Ots-otdr-scan {
    type enumeration {
      enum "auto" {
        value 0;
        description
          "Auto";
      }
    }
    description
      "Ots otdr scan";
  }

  typedef Ots-otdr-direction {
    type enumeration {
      enum "tx" {
        value 0;
        description
          "Tx";
      }
      enum "rx" {
        value 1;
        description
          "Rx";
      }
    }
    description
      "Ots otdr direction";
  }

  typedef Ots-psm-primary-path {
    type enumeration {
      enum "working" {
        value 1;
        description
          "Working port";
      }
      enum "protected" {
        value 2;
        description
          "Protected port";
      }
    }
    description
      "Ots psm primary path";
  }

  typedef Ots-psm-lockout-from {
    type enumeration {
      enum "working" {
        value 1;
        description
          "Working port";
      }
      enum "protected" {
        value 2;
        description
          "Protected port";
      }
    }
    description
      "Ots psm lockout from";
  }

  grouping NODE-CFG {
    description
      "active/preconfigured nodes configuration";
    list slot {
      key "slot-id";
      description
        "Slot Id";
      container otdr-auto-scans {
        description
          "Otdr Auto Scan";
        list otdr-auto-scan {
          key "port";
          description
            "Otdr Auto Scan";
          container auto-scan-ipv6 {
            presence "Indicates a auto-scan-ipv6 node is configured.";
            description
              "OTDR Event Triggered Automatic Scan
               Configuration IPv6";
            leaf otdr-ip-address {
              type inet:ipv6-address-no-zone;
              mandatory true;
              description
                "IPv6 address of OTDR module host";
            }
            leaf otdr-farend-ip-address {
              type inet:ipv6-address-no-zone;
              mandatory true;
              description
                "IPv6 address of OTDR far-end host";
            }
            leaf otdr-far-end-slot-id {
              type uint32 {
                range "1..3";
              }
              mandatory true;
              description
                "Set OTDR far-end Slot Number";
            }
            leaf scan-type {
              type Ots-otdr-scan;
              mandatory true;
              description
                "Scan Type AUTO";
            }
          }
          container auto-scan {
            presence "Indicates a auto-scan node is configured.";
            description
              "OTDR Event Triggered Automatic Scan
               Configuration";
            leaf otdr-ip-address {
              type inet:ip-address-no-zone;
              mandatory true;
              description
                "IP address of OTDR module host";
            }
            leaf otdr-farend-ip-address {
              type inet:ip-address-no-zone;
              mandatory true;
              description
                "IP address of OTDR far-end host";
            }
            leaf otdr-far-end-slot-id {
              type uint32 {
                range "1..3";
              }
              mandatory true;
              description
                "Set OTDR far-end Slot Number";
            }
            leaf scan-type {
              type Ots-otdr-scan;
              mandatory true;
              description
                "Scan Type AUTO";
            }
          }
          leaf port {
            type uint32;
            description
              "Port Id";
          }
        }
      }
      container otdrs {
        description
          "OTDR Configs";
        list otdr {
          key "port direction";
          description
            "Otdr Id";
          container periodic-scan {
            description
              "Periodic Scan";
            leaf minutes {
              type uint32 {
                range "30..600000";
              }
              units "minute";
              description
                "Periodicity in minutes (min value supported
                 30 min)";
            }
          }
          container mode-auto {
            description
              "Mode Auto";
            leaf loss-rel-threshold {
              type uint32 {
                range "1..300";
              }
              description
                "relative Loss Threshold, supported values [1
                 ,300] in units of 0.1dB";
            }
            leaf loss-sensitivity {
              type uint32 {
                range "4..50";
              }
              description
                "Otdr Loss Sensitivity, supported values [4
                 ,50] in units of 0.1dB";
            }
            leaf reflection-rel-threshold {
              type uint32 {
                range "1..300";
              }
              description
                "Relative Reflection Threshold, supported
                 values [1,300] in units of 0.1dB";
            }
            leaf reflection-sensitivity {
              type int32 {
                range "-400..-140";
              }
              description
                "Otdr Reflection Sensitivity, supported
                 values [-400,-140] in units of 0.1dB";
            }
          }
          container mode-expert {
            description
              "Mode Expert";
            leaf fiber-resolution {
              type uint32 {
                range "0..100";
              }
              description
                "Fiber Resolution in meters, supported values
                 [0,100]";
            }
            leaf capture-length {
              type uint32 {
                range "1..150";
              }
              description
                "Capture Length in Km, supported values [1
                 ,150]";
            }
            leaf loss-rel-threshold {
              type uint32 {
                range "1..300";
              }
              description
                "relative Loss Threshold, supported values [1
                 ,300] in units of 0.1dB";
            }
            leaf pulse-width {
              type uint32 {
                range "8..100000";
              }
              units "nanosecond";
              description
                "Pulse Width in nanoseconds, supported values
                 [8,100000]";
            }
            leaf measure-time {
              type uint32 {
                range "1..360";
              }
              units "second";
              description
                "Measure time in seconds, supported values [1
                 ,360]";
            }
            leaf loss-sensitivity {
              type uint32 {
                range "4..50";
              }
              description
                "Otdr Loss Sensitivity, supported values [4
                 ,50] in units of 0.1dB";
            }
            leaf reflection-rel-threshold {
              type uint32 {
                range "1..300";
              }
              description
                "Relative Reflection Threshold, supported
                 values [1,300] in units of 0.1dB";
            }
            leaf capture-offset {
              type uint32 {
                range "0..150";
              }
              description
                "Capture Offset in Km, supported values [0
                 ,150]";
            }
            leaf span-length {
              type uint32 {
                range "1..150";
              }
              description
                "Span Length in Km, supported values [1,150]";
            }
            leaf reflection-sensitivity {
              type int32 {
                range "-400..-140";
              }
              description
                "Otdr Reflection Sensitivity, supported
                 values [-400,-140] in units of 0.1dB";
            }
          }
          leaf ml-enabled {
            type uint32 {
              range "0..1";
            }
            description
              "Otdr enable machine learning event detection";
          }
          leaf total-loss {
            type uint32 {
              range "0..500";
            }
            description
              "Otdr Insertion Loss, supported values [0,500]
               in units of 0.1dB";
          }
          leaf back-scattering {
            type int32 {
              range "-1000..0";
            }
            description
              "Otdr back scattering (BC), supported values
               [-1000,0] in units of 0.1dB";
          }
          leaf refractive-index {
            type uint32 {
              range "1000000..2000000";
            }
            description
              "Otdr refracive index (GI), supported values
               [1000000,2000000] ";
          }
          leaf port {
            type uint32 {
              range "1..2";
            }
            description
              "Port Id";
          }
          leaf direction {
            type Ots-otdr-direction;
            description
              "Direction Id";
          }
        }
      }
      container otdr-thresholds {
        description
          "Otdr Threshold";
        list otdr-threshold {
          key "port";
          description
            "Otdr Threshold";
          leaf loss-abs-threshold {
            type uint32 {
              range "1..300";
            }
            description
              "Absolute Loss Threshold, supported values [1
               ,300] in units of 0.1dB";
          }
          leaf reflection-abs-threshold {
            type int32 {
              range "-500..0";
            }
            description
              "Absolute Reflection Threshold, supported
               values [-500,0] in units of 0.1dB";
          }
          leaf orl-abs-threshold {
            type uint32 {
              range "140..400";
            }
            description
              "Absolute Orl Threshold, supported values [140
               ,400] in units of 0.1dB";
          }
          leaf port {
            type uint32;
            description
              "Port Id";
          }
        }
      }
      container amplifier {
        description
          "Amplifier Configs";
        container remote-node-ipv6 {
          presence "Indicates a remote-node-ipv6 node is configured.";
          description
            "RemoteNode Configuration IPv6";
          leaf local-ip-address {
            type inet:ipv6-address-no-zone;
            mandatory true;
            description
              "IPv6 address of local host";
          }
          leaf remote-ip-address {
            type inet:ipv6-address-no-zone;
            mandatory true;
            description
              "IPv6 address of remote host";
          }
          leaf remote-slot-id {
            type uint32 {
              range "1..3";
            }
            mandatory true;
            description
              "Set remote Slot";
          }
        }
        container otdr-auto-scan {
          presence "Indicates a otdr-auto-scan node is configured.";
          description
            "OTDR Event Triggered Automatic Scan
             Configuration";
          leaf otdr-ip-address {
            type inet:ip-address-no-zone;
            mandatory true;
            description
              "IP address of OTDR module host";
          }
          leaf otdr-slot-id {
            type uint32 {
              range "1..3";
            }
            mandatory true;
            description
              "Set OTDR Slot Number";
          }
          leaf otdr-port-id {
            type uint32 {
              range "1..2";
            }
            mandatory true;
            description
              "Set OTDR Port Number";
          }
          leaf ampli-farend-ip-address {
            type inet:ip-address-no-zone;
            mandatory true;
            description
              "IP address of amplifier far-end host";
          }
          leaf ampli-far-end-slot-id {
            type uint32 {
              range "1..3";
            }
            mandatory true;
            description
              "Set amplifier far-end Slot Number ";
          }
          leaf scan-type {
            type Ots-otdr-scan;
            mandatory true;
            description
              "Scan Type AUTO";
          }
        }
        container flex-channel-identifiers {
          description
            "Amplifier Flex Channel Config";
          list flex-channel-identifier {
            key "channel-id";
            description
              "Flex Channel Identifier";
            container flex-channel-frequencies {
              description
                "Channel Frequency";
              list flex-channel-frequency {
                key "channel-freq";
                description
                  "Channel Frequency configuration in units of
                   0.1GHz";
                leaf flex-channel-width {
                  type uint32 {
                    range "500..8000";
                  }
                  description
                    "Set Channel Width in units of 0.1GHz,
                     allowed values in step of 125";
                }
                leaf channel-freq {
                  type uint32 {
                    range "1913500..1961000";
                  }
                  description
                    "Set Channel Frequency in units of 0.1GHz";
                }
              }
            }
            leaf channel-id {
              type uint32 {
                range "1..96";
              }
              description
                "Channel Identifier";
            }
          }
        }
        container remote-node {
          presence "Indicates a remote-node node is configured.";
          description
            "RemoteNode Configuration";
          leaf local-ip-address {
            type inet:ip-address-no-zone;
            mandatory true;
            description
              "IP address of local host";
          }
          leaf remote-ip-address {
            type inet:ip-address-no-zone;
            mandatory true;
            description
              "IP address of remote host";
          }
          leaf remote-slot-id {
            type uint32 {
              range "1..3";
            }
            mandatory true;
            description
              "Set remote Slot";
          }
        }
        container otdr-auto-scan-ipv6 {
          presence "Indicates a otdr-auto-scan-ipv6 node is configured.";
          description
            "OTDR Event Triggered Automatic Scan
             Configuration IPv6 ";
          leaf otdr-ip-address {
            type inet:ipv6-address-no-zone;
            mandatory true;
            description
              "IPv6 address of OTDR module host";
          }
          leaf otdr-slot-id {
            type uint32 {
              range "1..3";
            }
            mandatory true;
            description
              "Set OTDR Slot Number";
          }
          leaf otdr-port-id {
            type uint32 {
              range "1..2";
            }
            mandatory true;
            description
              "Set OTDR Port Number";
          }
          leaf ampli-farend-ip-address {
            type inet:ipv6-address-no-zone;
            mandatory true;
            description
              "IPv6 address of amplifier far-end host";
          }
          leaf ampli-far-end-slot-id {
            type uint32 {
              range "1..3";
            }
            mandatory true;
            description
              "Set amplifier far-end Slot Number";
          }
          leaf scan-type {
            type Ots-otdr-scan;
            mandatory true;
            description
              "Scan Type AUTO";
          }
        }
        container span-loss {
          description
            "SpanLoss configuration";
          leaf enable {
            type boolean;
            description
              "Span Loss enabled";
          }
          leaf delta {
            type uint32 {
              range "0..500";
            }
            description
              "Set Span Loss change delta value";
          }
        }
        container channel-widths {
          description
            "Amplifier Channel Width Configs";
          list channel-width {
            key "channel-id";
            description
              "Channel Identifier";
            leaf channel-width {
              type uint32 {
                range "1000..8000";
              }
              description
                "Set Channel Width in units of 0.1GHz,
                 allowed values in step of 250";
            }
            leaf channel-id {
              type uint32 {
                range "1..96";
              }
              description
                "Channel Identifier";
            }
          }
        }
        leaf flex-mode {
          type boolean;
          description
            "FlexMode configuration";
        }
        leaf node-type {
          type Ots-amplifier-node;
          description
            "Define the type of node in which the amplifier
             is set to work";
        }
        leaf auto-threshold {
          type boolean;
          description
            "Amplifier automatic rx-low threshold set
             enabled";
        }
        leaf grid-mode {
          type Ots-amplifier-grid-mode;
          description
            "Define the working mode for the optical module";
        }
        leaf udc-vlan {
          type uint32 {
            range "2..4080";
          }
          description
            "Define the VLAN ID in range <2-4080>";
        }
      }
      container psm {
        description
          "PSM Configs";
        container auto-threshold {
          description
            "Psm Automatic Threshold Setting";
          leaf enable {
            type boolean;
            description
              "PSM revertive enabled";
          }
          leaf delta {
            type uint32 {
              range "0..800";
            }
            description
              "Set auto threshold delta";
          }
        }
        container relative-switch-threshold {
          description
            "Psm Relative Switch Threshold";
          leaf psm-relative-switch-threshold {
            type uint32 {
              range "0..800";
            }
            description
              "Set Psm Relative Switch Threshold";
          }
          leaf psm-relative-switch-threshold-offset {
            type int32 {
              range "-300..300";
            }
            description
              "Set Psm Relative Switch Threshold Offset";
          }
        }
        container revertive {
          description
            "PSM Revertive Configuration";
          leaf enable {
            type boolean;
            description
              "PSM revertive enabled";
          }
          leaf wtr {
            type uint32 {
              range "0..4294967295";
            }
            units "second";
            description
              "Set wait time to restore in seconds";
          }
        }
        leaf mono-dir {
          type boolean;
          description
            "Psm Uni directional configuration";
        }
        leaf primary-path {
          type Ots-psm-primary-path;
          description
            "Select Psm Primary Path";
        }
        leaf path-protection {
          type boolean;
          description
            "Psm path protection configuration";
        }
        leaf section-protection {
          type boolean;
          description
            "Psm section protection configuration";
        }
        leaf lockout-from {
          type Ots-psm-lockout-from;
          description
            "Exclude selected port from protection";
        }
      }
      leaf slot-id {
        type uint32 {
          range "1..3";
        }
        description
          "Set Slot";
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
