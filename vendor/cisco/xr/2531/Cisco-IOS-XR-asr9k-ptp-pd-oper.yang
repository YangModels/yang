module Cisco-IOS-XR-asr9k-ptp-pd-oper {
  namespace "http://cisco.com/ns/yang/Cisco-IOS-XR-asr9k-ptp-pd-oper";
  prefix asr9k-ptp-pd-oper;

  import cisco-semver {
    prefix semver;
  }
  import Cisco-IOS-XR-ptp-oper {
    prefix a1;
  }
  include Cisco-IOS-XR-asr9k-ptp-pd-oper-sub1 {
    revision-date 2020-06-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-ptp-pd package operational data.
     
     This YANG module augments the
       Cisco-IOS-XR-ptp-oper
     module with state data.
     
     Copyright (c) 2013-2020 by Cisco Systems, Inc.
     All rights reserved.";

  revision 2020-06-03 {
    description
      "IOS-XR 7.3.1 revision.";
    semver:module-version "1.0.0";
  }
  revision 2019-04-05 {
    description
      "Establish semantic version baseline.";
  }
  revision 2015-11-09 {
    description
      "IOS XR 6.0 revision.";
  }

  augment "/a1:ptp" {
    description
      "This augment extends the operational data of
       'Cisco-IOS-XR-ptp-oper'";
    container platform {
      description
        "PTP platform specific data";
      container servo {
        description
          "PTP servo related parameters";
        uses PTP-PD-SERVO-INFO;
      }
    }
  }
}
