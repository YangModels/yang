module Cisco-IOS-XR-um-8000-udf-cfg {
  namespace "http://cisco.com/ns/yang/Cisco-IOS-XR-um-8000-udf-cfg";
  prefix um-8000-udf-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-udf package configuration.
     
     This YANG module augments the
     modules with configuration data.
     
     Copyright (c) 2020-2025 by Cisco Systems, Inc., and/or its affiliates.
     All rights reserved.";

  revision 2020-12-07 {
    description
      "Initial release";
    semver:module-version "1.0.0";
  }

  container udfs {
    description
      "UDF configuration";
    list udf {
      key "udf-name";
      description
        "UDF configuration";
      leaf udf-name {
        type xr:Cisco-ios-xr-string {
          length "1..16" {
            description
              "UDF name - maximum 16 characters";
          }
          pattern "[a-z0-9A-Z][-_.:a-z0-9A-Z]*";
        }
        description
          "UDF configuration";
      }
      container header {
        description
          "Header for UDF";
        leaf header-type {
          type enumeration {
            enum "inner" {
              value 0;
              description
                "Inner header for UDF";
            }
            enum "outer" {
              value 1;
              description
                "Outer header for UDF";
            }
          }
          mandatory true;
          description
            "Header for UDF";
        }
        leaf udf-layer {
          type enumeration {
            enum "l2" {
              value 0;
              description
                "L2 layer for UDF";
            }
            enum "l3" {
              value 1;
              description
                "L3 layer for UDF";
            }
            enum "l4" {
              value 2;
              description
                "L4 layer for UDF";
            }
          }
          mandatory true;
          description
            "configure this node";
        }
        leaf offset {
          type uint32 {
            range "0..65535" {
              description
                "Configure the offset value (bytes)";
            }
          }
          mandatory true;
          description
            "Configure the offset (bytes) in the header";
        }
        leaf length {
          type uint32 {
            range "0..65535" {
              description
                "Configure the length (bytes)";
            }
          }
          mandatory true;
          description
            "Configure the length (bytes) in the header";
        }
      }
    }
  }
}
