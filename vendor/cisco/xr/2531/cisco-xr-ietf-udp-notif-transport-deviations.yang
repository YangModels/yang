module cisco-xr-ietf-udp-notif-transport-deviations {
  namespace "http://cisco.com/ns/yang/cisco-xr-ietf-udp-notif-transport-deviations";
  prefix xr-unt-d;

  import ietf-udp-notif-transport {
    prefix unt;
  }

  import ietf-subscribed-notifications {
    prefix sn;
  }

  import ietf-subscribed-notif-receivers {
    prefix snr;
  }

  import ietf-inet-types {
    prefix inet;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations of:

        ietf-udp-notif-transport@2024-10-17

     on Cisco IOS-XR devices.

     Copyright (c) 2025 by Cisco Systems, Inc., and/or its affiliates.
     All rights reserved.";


  revision 2025-01-20 {
    description
      "Initial version.";
  }

  /*
   * If in the future this deviations file only contains RPC or notification
   * nodes, it will stop appearing in Yang Library or capabilities/hello
   * output.
   * See CSCwn84289 for more details. This comment can be removed once the
   * issue is resolved.
   */

  // "Not-supported" deviations.

  // Remove receiver UDP dtls support.
  deviation /sn:subscriptions/snr:receiver-instances/snr:receiver-instance/snr:transport-type/unt:udp-notif/unt:udp-notif-receiver/unt:dtls {
    deviate not-supported;
  }

  // Remove receiver UDP local-address and local-port support.
  deviation /sn:subscriptions/snr:receiver-instances/snr:receiver-instance/snr:transport-type/unt:udp-notif/unt:udp-notif-receiver/unt:local-address {
    deviate not-supported;
  }
  deviation /sn:subscriptions/snr:receiver-instances/snr:receiver-instance/snr:transport-type/unt:udp-notif/unt:udp-notif-receiver/unt:local-port {
    deviate not-supported;
  }

  // Type deviations.

  deviation /sn:subscriptions/snr:receiver-instances/snr:receiver-instance/snr:transport-type/unt:udp-notif/unt:udp-notif-receiver/unt:remote-address {
    deviate replace {
        type "inet:ip-address-no-zone";
    }
  }
}
