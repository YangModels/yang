module Cisco-IOS-XR-um-stats-resource-cfg {
  namespace "http://cisco.com/ns/yang/Cisco-IOS-XR-um-stats-resource-cfg";
  prefix um-stats-resource-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR stats-resource package configuration.
     
     This YANG module augments the
     modules with configuration data.
     
     Copyright (c) 2024-2025 by Cisco Systems, Inc., and/or its affiliates.
     All rights reserved.";

  revision 2025-02-06 {
    description
      "description added for LOCATION-BODY and its augments";
    semver:module-version "1.0.0";
  }
  revision 2024-09-09 {
    description
      "Initial release";
  }

  grouping LOCATION-BODY {
    description
      "Group stats-infra";
    container stats-resource {
      description
        "Counter engine configuration commands";
      container reassign {
        presence "Indicates a reassign node is configured.";
        description
          "reassign engine configuration commands";
        container internal {
          description
            "Internal stats hardware resources";
          container feature {
            description
              "Internal stats feature type";
            container trap {
              description
                "Trap feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container lpts-pbr {
              description
                "LPTS and PBR feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container aclrx-mcrouterx {
              description
                "Ingress ACL feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container acltx {
              description
                "Egress ACL feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container qosrx {
              description
                "Ingress qos feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container voq {
              description
                "VOQ feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container l3rx {
              description
                "Ingress L3 Interface feature";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container mplsrx {
              description
                "SR Rx feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container l2rx {
              description
                "Ingress L2 Interface feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container l3tx {
              description
                "Egress L3 Interface feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container l2tx-mctx {
              description
                "Egress L2 Interface feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
            container tetx {
              description
                "MPLS Te Tx feature ";
              container eng-idses {
                description
                  "Engine id(s) to be allocated to feature";
                leaf-list eng-ids {
                  type uint32 {
                    range "0..4294967295" {
                      description
                        "Enter engine ID : 1 2 3...21";
                    }
                  }
                  max-elements "22";
                  description
                    "Engine id(s) to be allocated to feature";
                }
              }
            }
          }
        }
      }
    }
  }

  augment "/location:locations/location:location" {
    description
      "augment1 for group stats-infra";
    uses LOCATION-BODY;
  }
  augment "/location:locations/location:preconfigured-location" {
    description
      "augment2 for group stats-infra";
    uses LOCATION-BODY;
  }
}
