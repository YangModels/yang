module cisco-xr-ietf-netconf-monitoring-deviations {

  /*** NAMESPACE / PREFIX DEFINITION ***/

  namespace "http://cisco.com/ns/yang/cisco-xr-ietf-netconf-monitoring-deviations";

  prefix "cisco-xr-ietf-ncm-devs";

  /*** LINKAGE (IMPORTS / INCLUDES) ***/
  import ietf-netconf-monitoring { prefix ncm; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a set of deviations of IETF netconf monitoring data
     model set for Cisco IOS-XR.

     Copyright (c) 2016-2025 by Cisco Systems, Inc., and/or its affiliates.
     All rights reserved.";

  revision "2024-07-24" {
    description
      "Migrate manual model edits to be represented as deviations";
  }

  revision "2018-04-09" {
    description
      "We now support sessions and statistics and these have been removed 
       from the deviations";
  }

  revision "2016-02-16" {
    description
      "Initial revision applicable to IOS-XR 6.0.1 and older releases";
  }

  /*
   * If in the future this deviations file only contains RPC or notification
   * nodes, it will stop appearing in Yang Library or capabilities/hello
   * output.
   * See CSCwn84289 for more details. This comment can be removed once the
   * issue is resolved.
   */

  deviation /ncm:netconf-state/ncm:capabilities {
    deviate not-supported;
  }

  deviation /ncm:netconf-state/ncm:datastores {
    deviate not-supported;
  }

  deviation /ncm:get-schema {
    deviate not-supported;
  }

  deviation /ncm:netconf-state/ncm:schemas/ncm:schema/ncm:format {
    deviate replace {
      type string;
    }
  }

  deviation /ncm:netconf-state/ncm:schemas/ncm:schema/ncm:location {
    deviate replace {
      type string;
    }
  }

  deviation /ncm:netconf-state/ncm:sessions/ncm:session/ncm:session-id {
    deviate replace {
      type uint32;
    }
  }

  deviation /ncm:netconf-state/ncm:sessions/ncm:session/ncm:transport {
    deviate replace {
      type string;
    }
  }
}
