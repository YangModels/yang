module Cisco-IOS-XR-um-track-cfg {
  namespace "http://cisco.com/ns/yang/Cisco-IOS-XR-um-track-cfg";
  prefix um-track-cfg;

  import Cisco-IOS-XR-types {
    prefix xr;
  }
  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR track package configuration.
     
     This YANG module augments the
     modules with configuration data.
     
     Copyright (c) 2021-2025 by Cisco Systems, Inc., and/or its affiliates.
     All rights reserved.";

  revision 2023-01-20 {
    description
      "changed /action/track-(down(or)up)/auto-recover to container
       2023-01-08
         changed leaf type from xr-string to string
       to match with cli behaviour
       2022-07-11
         Added missing description statement to nodes
       2022-01-25
         Added track-name leaf under tracks container";
    semver:module-version "2.0.0";
  }
  revision 2021-05-10 {
    description
      "Initial release";
    semver:module-version "1.0.0";
  }

  grouping IF-BODY {
    description
      "Grouping for interface";
    container line-protocol {
      description
        "Line-protocol state tracks another object";
      leaf track {
        type xr:Cisco-ios-xr-string {
          length "1..32" {
            description
              "Track name";
          }
        }
        description
          "Object track";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container tracks {
    description
      "Configure Track";
    list track {
      key "track-name";
      description
        "track name";
      leaf track-name {
        type xr:String-identifier {
          length "1..32" {
            description
              "track name";
          }
        }
        description
          "track name";
      }
      container delay {
        description
          "Set track notification delay";
        leaf up {
          type uint32 {
            range "1..3600" {
              description
                "Up time delay in seconds";
            }
          }
          description
            "Up time";
        }
        leaf down {
          type uint32 {
            range "1..3600" {
              description
                "Down time delay in seconds";
            }
          }
          description
            "Down time";
        }
      }
      container type {
        description
          "Set track type";
        container route {
          description
            "track type ipv4 route";
          container reachability {
            presence "Indicates a reachability node is configured.";
            description
              "track type ipv4 route reachability";
            container route {
              description
                "Set track route";
              container ipv4 {
                must "not(../address-prefix)";
                presence "Indicates a ipv4 node is configured.";
                description
                  "IP Address";
                leaf address {
                  type inet:ipv4-address-no-zone;
                  mandatory true;
                  description
                    "Network address";
                }
                leaf mask {
                  type inet:ipv4-address-no-zone;
                  mandatory true;
                  description
                    "Network mask";
                }
              }
              leaf address-prefix {
                type inet:ip-address-no-zone;
                must "not(../ipv4)";
                description
                  "Network address";
              }
              leaf address-prefix-length {
                type uint32 {
                  range "1..128";
                }
                must "../address-prefix";
                description
                  "Masklength";
              }
            }
            leaf vrf {
              type xr:Cisco-ios-xr-string {
                length "1..32" {
                  description
                    "VRF tag";
                }
              }
              description
                "specify vrf";
            }
          }
        }
        container line-protocol {
          description
            "track type line-protocol";
          container state {
            presence "Indicates a state node is configured.";
            description
              "track type line-protocol state";
            leaf interface {
              type xr:Interface-name;
              description
                "Set track interface";
            }
          }
        }
        container boolean {
          description
            "track type boolean expression";
          container expression {
            presence "Indicates a expression node is configured.";
            description
              "track type boolean expression";
            leaf string {
              type string {
                length "1..127" {
                  description
                    "defines boolean relationship among objects";
                }
                pattern "\".*.\"";
              }
              description
                "defines boolean relationship among objects";
            }
          }
        }
        leaf rtr {
          type uint32 {
            range "1..2048" {
              description
                " ipsla operation number";
            }
          }
          description
            "track type ipsla";
        }
        container list {
          description
            "track type list";
          container boolean {
            description
              "List of tracks (of any type) with boolean logic";
            container and {
              presence "Indicates a and node is configured.";
              description
                "track type list boolean and";
              container objects {
                description
                  "Set track object";
                list object {
                  key "object-name";
                  description
                    "Set track object";
                  leaf object-name {
                    type xr:Cisco-ios-xr-string {
                      length "1..127" {
                        description
                          "object name";
                      }
                    }
                    description
                      "Set track object";
                  }
                  container not {
                    presence "Indicates a not node is configured.";
                    description
                      "boolean not";
                  }
                }
              }
            }
            container or {
              presence "Indicates a or node is configured.";
              description
                "track type list boolean or";
              container objects {
                description
                  "Set track object";
                list object {
                  key "object-name";
                  description
                    "Set track object";
                  leaf object-name {
                    type xr:Cisco-ios-xr-string {
                      length "1..127" {
                        description
                          "object name";
                      }
                    }
                    description
                      "Set track object";
                  }
                  container not {
                    presence "Indicates a not node is configured.";
                    description
                      "boolean not";
                  }
                }
              }
            }
          }
          container threshold {
            description
              "List of tracks (of any type) with threshold logic";
            container weight {
              presence "Indicates a weight node is configured.";
              description
                "threshold based on weighted sum.";
              container objects {
                description
                  "Set track object";
                list object {
                  key "object-name";
                  description
                    "Set track object";
                  leaf object-name {
                    type xr:Cisco-ios-xr-string {
                      length "1..127" {
                        description
                          "object name";
                      }
                    }
                    description
                      "Set track object";
                  }
                  leaf weight {
                    type uint32 {
                      range "0..4294967295" {
                        description
                          "weight <number>";
                      }
                    }
                    description
                      "Weight to be assigned for this object";
                  }
                }
              }
              container threshold {
                description
                  "Threshold value";
                container weight {
                  description
                    "Threshold values based on weight";
                  leaf up {
                    type uint32 {
                      range "0..4294967295" {
                        description
                          "weight <number>";
                      }
                    }
                    must "../down";
                    description
                      "Threshold limit at which track is set to UP state";
                  }
                  leaf down {
                    type uint32 {
                      range "0..4294967295" {
                        description
                          "weight <number>";
                      }
                    }
                    must "../up";
                    description
                      "Threshold limit at which track is set to DOWN state";
                  }
                }
              }
            }
            container percentage {
              presence "Indicates a percentage node is configured.";
              description
                "threshold based on percentage of objects.";
              container objects {
                description
                  "Set track object";
                list object {
                  key "object-name";
                  description
                    "Set track object";
                  leaf object-name {
                    type xr:Cisco-ios-xr-string {
                      length "1..127" {
                        description
                          "object name";
                      }
                    }
                    description
                      "Set track object";
                  }
                  leaf weight {
                    type uint32 {
                      range "0..4294967295" {
                        description
                          "weight <number>";
                      }
                    }
                    description
                      "Weight to be assigned for this object";
                  }
                }
              }
              container threshold {
                description
                  "Threshold value";
                container percentage {
                  description
                    "Threshold values based on percentage";
                  leaf up {
                    type uint32 {
                      range "1..100" {
                        description
                          "percentage <1 - 100>";
                      }
                    }
                    must "../down";
                    description
                      "Threshold limit at which track is set to UP state";
                  }
                  leaf down {
                    type uint32 {
                      range "1..100" {
                        description
                          "percentage <1 - 100>";
                      }
                    }
                    must "../up";
                    description
                      "Threshold limit at which track is set to DOWN state";
                  }
                }
              }
            }
          }
          container line-protocol {
            description
              "List of line-protocol tracks";
            container state {
              description
                "List of line-protocol state tracks";
              container threshold {
                description
                  "List of tracks (of any type) with threshold logic";
                container weight {
                  presence "Indicates a weight node is configured.";
                  description
                    "threshold based on weighted sum.";
                  container threshold {
                    description
                      "Threshold value";
                    container weight {
                      description
                        "Threshold values based on weight";
                      leaf up {
                        type uint32 {
                          range "0..4294967295" {
                            description
                              "weight <number>";
                          }
                        }
                        must "../down";
                        description
                          "Threshold limit at which track is set to UP state";
                      }
                      leaf down {
                        type uint32 {
                          range "0..4294967295" {
                            description
                              "weight <number>";
                          }
                        }
                        must "../up";
                        description
                          "Threshold limit at which track is set to DOWN state";
                      }
                    }
                  }
                  container interfaces {
                    description
                      "List member interface";
                    list interface {
                      key "interface-name";
                      description
                        "List member interface";
                      leaf interface-name {
                        type xr:Interface-name;
                        description
                          "interface name";
                      }
                      leaf weight {
                        type uint32 {
                          range "0..4294967295" {
                            description
                              "weight <number>";
                          }
                        }
                        description
                          "Weight to be assigned for this object";
                      }
                    }
                  }
                }
                container percentage {
                  presence "Indicates a percentage node is configured.";
                  description
                    "threshold based on percentage of objects.";
                  container interfaces {
                    description
                      "List member interface";
                    list interface {
                      key "interface-name";
                      description
                        "List member interface";
                      leaf interface-name {
                        type xr:Interface-name;
                        description
                          "interface name";
                      }
                    }
                  }
                  container threshold {
                    description
                      "Threshold value";
                    container percentage {
                      description
                        "Threshold values based on percentage";
                      leaf up {
                        type uint32 {
                          range "1..100" {
                            description
                              "percentage <1 - 100>";
                          }
                        }
                        must "../down";
                        description
                          "Threshold limit at which track is set to UP state";
                      }
                      leaf down {
                        type uint32 {
                          range "1..100" {
                            description
                              "percentage <1 - 100>";
                          }
                        }
                        must "../up";
                        description
                          "Threshold limit at which track is set to DOWN state";
                      }
                    }
                  }
                }
              }
              container boolean {
                description
                  "Track state based on boolean logic";
                container and {
                  presence "Indicates a and node is configured.";
                  description
                    "Boolean and logic";
                  container interfaces {
                    description
                      "List member interface";
                    list interface {
                      key "interface-name";
                      description
                        "List member interface";
                      leaf interface-name {
                        type xr:Interface-name;
                        description
                          "interface name";
                      }
                    }
                  }
                }
                container or {
                  presence "Indicates a or node is configured.";
                  description
                    "Boolean or logic";
                  container interfaces {
                    description
                      "List member interface";
                    list interface {
                      key "interface-name";
                      description
                        "List member interface";
                      leaf interface-name {
                        type xr:Interface-name;
                        description
                          "interface name";
                      }
                    }
                  }
                }
              }
            }
          }
        }
        container bfdrtr {
          presence "Indicates a bfdrtr node is configured.";
          description
            "track type bfd rtr";
          leaf rate {
            type uint32 {
              range "1..5000" {
                description
                  "time interval ms";
              }
            }
            must "../debounce";
            mandatory true;
            description
              "Tx interval in ms";
          }
          leaf debounce {
            type uint32 {
              range "1..10" {
                description
                  "numeric counter";
              }
            }
            must "../rate and ../interface";
            mandatory true;
            description
              "Debounce count";
          }
          leaf interface {
            type xr:Interface-name;
            must "../debounce and ../destaddress";
            mandatory true;
            description
              "The link on rc to be used to track";
          }
          leaf destaddress {
            type inet:ipv4-address-no-zone;
            must "../interface";
            mandatory true;
            description
              "Destination Ip Address to track via bfd";
          }
        }
        container bgp {
          description
            "track type bgp";
          container instances {
            description
              "Instance name";
            list instance {
              key "instance-name";
              description
                "Instance name";
              leaf instance-name {
                type xr:Cisco-ios-xr-string {
                  length "1..32" {
                    description
                      "Instance name";
                  }
                }
                description
                  "Instance name";
              }
              container neighbor {
                description
                  "track type bgp neighbor";
                container address-family {
                  description
                    "track type bgp neighbor address-family";
                  container state {
                    presence "Indicates a state node is configured.";
                    description
                      "track type bgp neighbor address-family state";
                    container address-family {
                      description
                        "Address Family";
                      container ipv4 {
                        description
                          "IPv4 Address Family";
                        container flowspec {
                          presence "Indicates a flowspec node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container labeled-unicast {
                          presence "Indicates a labeled-unicast node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container mdt {
                          presence "Indicates a mdt node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container multicast {
                          presence "Indicates a multicast node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container mvpn {
                          presence "Indicates a mvpn node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container rt-filter {
                          presence "Indicates a rt-filter node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container sr-policy {
                          presence "Indicates a sr-policy node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container tunnel {
                          presence "Indicates a tunnel node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container unicast {
                          presence "Indicates a unicast node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                      }
                      container ipv6 {
                        description
                          "IPv6 Address Family";
                        container flowspec {
                          presence "Indicates a flowspec node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container labeled-unicast {
                          presence "Indicates a labeled-unicast node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container multicast {
                          presence "Indicates a multicast node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container mvpn {
                          presence "Indicates a mvpn node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container sr-policy {
                          presence "Indicates a sr-policy node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                        container unicast {
                          presence "Indicates a unicast node is configured.";
                          description
                            "Address Family modifier";
                          leaf neighbor {
                            type inet:ip-address-no-zone;
                            mandatory true;
                            description
                              "Neighbor address";
                          }
                          leaf vrf {
                            type xr:Cisco-ios-xr-string {
                              length "1..32" {
                                description
                                  "Vrf name";
                              }
                            }
                            must "../neighbor";
                            description
                              "Vrf name";
                          }
                          container disable {
                            description
                              "Disable fib check";
                            container fib-check {
                              presence "Indicates a fib-check node is configured.";
                              description
                                "Disable Fib chcking";
                            }
                          }
                        }
                      }
                      container l2vpn {
                        description
                          "L2vpn Address Family";
                        container evpn {
                          presence "Indicates a evpn node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container mspw {
                          presence "Indicates a mspw node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container vpls-vpws {
                          presence "Indicates a vpls-vpws node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                      }
                      container link-state {
                        description
                          "Link-state Address Family";
                        container link-state {
                          presence "Indicates a link-state node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                      }
                      container vpnv4 {
                        description
                          "Vpnv4 Address Family";
                        container flowspec {
                          presence "Indicates a flowspec node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container multicast {
                          presence "Indicates a multicast node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container unicast {
                          presence "Indicates a unicast node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                      }
                      container vpnv6 {
                        description
                          "Vpnv6 Address Family";
                        container flowspec {
                          presence "Indicates a flowspec node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container multicast {
                          presence "Indicates a multicast node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                        container unicast {
                          presence "Indicates a unicast node is configured.";
                          description
                            "Address Family modifier";
                          leaf neighbor {
                            type inet:ip-address-no-zone;
                            mandatory true;
                            description
                              "Neighbor address";
                          }
                          container disable {
                            description
                              "Disable fib check";
                            container fib-check {
                              presence "Indicates a fib-check node is configured.";
                              description
                                "Disable Fib chcking";
                            }
                          }
                        }
                      }
                    }
                  }
                }
              }
            }
          }
          container neighbor {
            description
              "track type bgp neighbor";
            container address-family {
              description
                "track type bgp neighbor address-family";
              container state {
                presence "Indicates a state node is configured.";
                description
                  "track type bgp neighbor address-family state";
                container address-family {
                  description
                    "Address Family";
                  container ipv4 {
                    description
                      "IPv4 Address Family";
                    container flowspec {
                      presence "Indicates a flowspec node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container labeled-unicast {
                      presence "Indicates a labeled-unicast node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container mdt {
                      presence "Indicates a mdt node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container multicast {
                      presence "Indicates a multicast node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container mvpn {
                      presence "Indicates a mvpn node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container rt-filter {
                      presence "Indicates a rt-filter node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container sr-policy {
                      presence "Indicates a sr-policy node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container tunnel {
                      presence "Indicates a tunnel node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container unicast {
                      presence "Indicates a unicast node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                  }
                  container ipv6 {
                    description
                      "IPv6 Address Family";
                    container flowspec {
                      presence "Indicates a flowspec node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container labeled-unicast {
                      presence "Indicates a labeled-unicast node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container multicast {
                      presence "Indicates a multicast node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container mvpn {
                      presence "Indicates a mvpn node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container sr-policy {
                      presence "Indicates a sr-policy node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                    container unicast {
                      presence "Indicates a unicast node is configured.";
                      description
                        "Address Family modifier";
                      leaf neighbor {
                        type inet:ip-address-no-zone;
                        mandatory true;
                        description
                          "Neighbor address";
                      }
                      leaf vrf {
                        type xr:Cisco-ios-xr-string {
                          length "1..32" {
                            description
                              "Vrf name";
                          }
                        }
                        must "../neighbor";
                        description
                          "Vrf name";
                      }
                      container disable {
                        description
                          "Disable fib check";
                        container fib-check {
                          presence "Indicates a fib-check node is configured.";
                          description
                            "Disable Fib chcking";
                        }
                      }
                    }
                  }
                  container l2vpn {
                    description
                      "L2vpn Address Family";
                    container evpn {
                      presence "Indicates a evpn node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container mspw {
                      presence "Indicates a mspw node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container vpls-vpws {
                      presence "Indicates a vpls-vpws node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                  }
                  container link-state {
                    description
                      "Link-state Address Family";
                    container link-state {
                      presence "Indicates a link-state node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                  }
                  container vpnv4 {
                    description
                      "Vpnv4 Address Family";
                    container flowspec {
                      presence "Indicates a flowspec node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container multicast {
                      presence "Indicates a multicast node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container unicast {
                      presence "Indicates a unicast node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                  }
                  container vpnv6 {
                    description
                      "Vpnv6 Address Family";
                    container flowspec {
                      presence "Indicates a flowspec node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container multicast {
                      presence "Indicates a multicast node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                    container unicast {
                      presence "Indicates a unicast node is configured.";
                      description
                        "Address Family modifier";
                      leaf neighbor {
                        type inet:ip-address-no-zone;
                        mandatory true;
                        description
                          "Neighbor address";
                      }
                      container disable {
                        description
                          "Disable fib check";
                        container fib-check {
                          presence "Indicates a fib-check node is configured.";
                          description
                            "Disable Fib chcking";
                        }
                      }
                    }
                  }
                }
              }
            }
          }
        }
      }
      container action {
        description
          "Actions to be taken when the state of the track changes";
        container track-down {
          description
            "Action will be performed when track goes Down";
          container error-disable {
            description
              "Disable specified interface when track state changes";
            container interfaces {
              description
                "Interface to be disabled";
              list interface {
                key "interface-name";
                description
                  "Interface to be disabled";
                leaf interface-name {
                  type xr:Interface-name;
                  description
                    "Interface to be disabled";
                }
                container auto-recover {
                  presence "Indicates a auto-recover node is configured.";
                  description
                    "Auto-recover the interface state when the track returns to pre-error-disable state";
                }
              }
            }
          }
        }
        container track-up {
          description
            "Action will be performed when track goes Up";
          container error-disable {
            description
              "Disable specified interface when track state changes";
            container interfaces {
              description
                "Interface to be disabled";
              list interface {
                key "interface-name";
                description
                  "Interface to be disabled";
                leaf interface-name {
                  type xr:Interface-name;
                  description
                    "Interface to be disabled";
                }
                container auto-recover {
                  presence "Indicates a auto-recover node is configured.";
                  description
                    "Auto-recover the interface state when the track returns to pre-error-disable state";
                }
              }
            }
          }
        }
      }
    }
  }
}
