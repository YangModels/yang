module Cisco-IOS-XR-ztp-cfg {
  namespace "http://cisco.com/ns/yang/Cisco-IOS-XR-ztp-cfg";
  prefix ztp-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ztp package configuration.
     
     This module contains definitions
     for the following management objects:
       ztp: ZTP configuration data
     
     Copyright (c) 2013-2024 by Cisco Systems, Inc.
     All rights reserved.";

  revision 2024-05-16 {
    description
      "Added bootz vrf cli.
       2024-02-05
         Added bootz server config cli.";
    semver:module-version "1.1.0";
  }
  revision 2019-04-05 {
    description
      "Establish semantic version baseline.";
    semver:module-version "1.0.0";
  }
  revision 2015-11-09 {
    description
      "IOS XR 6.0 revision.";
  }

  container ztp {
    description
      "ZTP configuration data";
    container bootz-server {
      presence "Indicates a bootz-server node is configured.";
      description
        "Configure Bootz server";
      leaf address {
        type string;
        mandatory true;
        description
          "IPv4/v6 address or hostname";
      }
      leaf port {
        type xr:Cisco-ios-xr-port-number;
        mandatory true;
        description
          "Port number";
      }
      leaf trust-anchor {
        type string;
        description
          "Trust Anchor path";
      }
      leaf action {
        type uint32 {
          range "0..1";
        }
        description
          "None or Shutdown";
      }
    }
    container bootz {
      presence "Indicates a bootz node is configured.";
      description
        "Configure Bootz settings";
      leaf bootz-interface {
        type xr:Interface-name;
        description
          "Configure Bootz interface";
      }
      leaf bootz-vrf {
        type xr:Cisco-ios-xr-string {
          length "1..32";
        }
        mandatory true;
        description
          "Configure Bootz vrf";
      }
    }
    leaf usb-boot {
      type empty;
      description
        "Enable ZTP USB boot";
    }
  }
}
