submodule Cisco-IOS-XR-man-ems-oper-sub1 {
  belongs-to Cisco-IOS-XR-man-ems-oper {
    prefix Cisco-IOS-XR-man-ems-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR man-ems package operational data.
     
     Copyright (c) 2013-2025 by Cisco Systems, Inc.
     All rights reserved.";

  revision 2025-04-28 {
    description
      "Removed status container under grpc.
       2024-08-28
         Added yang support for show grpc services
       2024-07-16
         Added support to view tls versions
       2024-03-03
         Added SRTE session list
       2023-12-18
         Added 'key' statement to list node 'destination'.
       2023-11-28
         Added support to view max-concurrent-streams.
       2023-09-01
         Added support to view certificate used by gRPC server for TLS authentication.
       2023-07-27
         Added gNMI, P4RT, and gRIBI service ports to grpc state.
       2023-06-01
         Added support for certificate common name.
       2023-04-26
         Added support for EMSd-Go soft memory limit.
       2023-04-21
         Added server name, keepalive time, timeout, enforcement to grpc state
       2023-03-22
         Added nodes server-keepalive-timeout and server-keepalive-time.
       2023-02-05
         Added gRPC tunnel virtual IP and listen address.
       2022-12-07
         Added support for gRPC listen addresses
       2022-07-20
         Added support for gRPC TLS version 1.0 flag
       2022-04-26
         Added support for gRPC server name
       2021-10-22
         Added certificate bundle statistics
       2021-10-20
         Added counters for load bundle
       2021-09-13
         Added status string to reflect unavailable port state.";
    semver:module-version "2.0.0";
  }
  revision 2021-06-10 {
    description
      "Added gRPC tunnel.";
    semver:module-version "1.2.0";
  }
  revision 2021-03-22 {
    description
      "Added keep alive commands.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  typedef Local-conn-state {
    type enumeration {
      enum "disabled" {
        value 0;
        description
          "Local connection is disabled";
      }
      enum "enabled" {
        value 1;
        description
          "Local connection is enabled";
      }
    }
    description
      "Local conn state";
  }

  typedef Tls-version {
    type enumeration {
      enum "tls-1-0" {
        value 0;
        description
          "TLS version is TLS 1.0";
      }
      enum "tls-1-1" {
        value 1;
        description
          "TLS version is TLS 1.1";
      }
      enum "tls-1-2" {
        value 2;
        description
          "TLS version is TLS 1.2";
      }
      enum "tls-1-3" {
        value 3;
        description
          "TLS version is TLS 1.3";
      }
    }
    description
      "Tls version";
  }

  typedef Grpc-tls-cipher-default {
    type enumeration {
      enum "none" {
        value 0;
        description
          "Not configured";
      }
      enum "disable" {
        value 1;
        description
          "Disable all ciphers";
      }
      enum "enable" {
        value 2;
        description
          "Enable all ciphers";
      }
    }
    description
      "Grpc tls cipher default";
  }

  typedef Tlsv1-0-state {
    type enumeration {
      enum "disabled" {
        value 0;
        description
          "TLS version 1.0 is disabled";
      }
      enum "enabled" {
        value 1;
        description
          "TLS version 1.0 is enabled";
      }
    }
    description
      "Tlsv1 0 state";
  }

  typedef Certauth-state {
    type enumeration {
      enum "disabled" {
        value 0;
        description
          "Certificate authentication is disabled";
      }
      enum "enabled" {
        value 1;
        description
          "Certificate authentication is enabled";
      }
    }
    description
      "Certauth state";
  }

  typedef Tls-mutual-state {
    type enumeration {
      enum "disabled" {
        value 0;
        description
          "TLS mutual is disabled";
      }
      enum "enabled" {
        value 1;
        description
          "TLS mutual is enabled";
      }
    }
    description
      "Tls mutual state";
  }

  typedef Tls-state {
    type enumeration {
      enum "disabled" {
        value 0;
        description
          "TLS is disabled";
      }
      enum "enabled" {
        value 1;
        description
          "TLS is enabled";
      }
    }
    description
      "Tls state";
  }

  typedef Af {
    type enumeration {
      enum "ipv4" {
        value 0;
        description
          "IPv4";
      }
      enum "ipv6" {
        value 1;
        description
          "IPv6";
      }
      enum "dual" {
        value 2;
        description
          "Dual";
      }
    }
    description
      "Af";
  }

  typedef Grpc-tunnel-status {
    type enumeration {
      enum "not-connected" {
        value 0;
        description
          "Not connected";
      }
      enum "connected" {
        value 1;
        description
          "Tunnel session is connected";
      }
    }
    description
      "Grpc tunnel status";
  }

  grouping GRPC-STATISTICS-INFO-B {
    description
      "gRPC statistics";
    leaf ct-show-cmd-txt-req-recv {
      type uint64;
      description
        "CounterShowCmdTxtReqRecv";
    }
    leaf ct-show-cmd-txt-res-sent {
      type uint64;
      description
        "CounterShowCmdTxtResSent";
    }
    leaf ct-get-config-req-recv {
      type uint64;
      description
        "CounterGetConfigReqRecv";
    }
    leaf ct-get-config-res-sent {
      type uint64;
      description
        "CounterGetConfigResSent";
    }
    leaf ct-cli-config-req-recv {
      type uint64;
      description
        "CounterCliConfigReqRecv";
    }
    leaf ct-cli-config-res-sent {
      type uint64;
      description
        "CounterCliConfigResSent";
    }
    leaf ct-merge-config-req-recv {
      type uint64;
      description
        "CounterMergeConfigReq";
    }
    leaf ct-merge-config-res-sent {
      type uint64;
      description
        "CounterMergeConfigRes";
    }
    leaf ct-commit-replace-req-recv {
      type uint64;
      description
        "CounterCommitReplaceReq";
    }
    leaf ct-commit-replace-res-sent {
      type uint64;
      description
        "CounterCommitReplaceRes";
    }
    leaf ct-delete-config-req-recv {
      type uint64;
      description
        "CounterDeleteConfigReq";
    }
    leaf ct-delete-config-res-sent {
      type uint64;
      description
        "CounterDeleteConfigRes";
    }
    leaf ct-remove-config-req-recv {
      type uint64;
      description
        "CounterRemoveConfigReq";
    }
    leaf ct-remove-config-res-sent {
      type uint64;
      description
        "CounterRemoveConfigRes";
    }
    leaf ct-replace-config-req-recv {
      type uint64;
      description
        "CounterReplaceConfigReq";
    }
    leaf ct-replace-config-res-sent {
      type uint64;
      description
        "CounterReplaceConfigSent";
    }
    leaf ct-get-oper-req-recv {
      type uint64;
      description
        "CounterGetOperReqRecv";
    }
    leaf ct-get-oper-res-sent {
      type uint64;
      description
        "CounterGetOperResSent";
    }
    leaf ct-get-current-session {
      type uint32;
      description
        "CounterGetCurrentSession";
    }
    leaf ct-commit-config-req-recv {
      type uint64;
      description
        "CounterForHowManyCommitConfigRequests";
    }
    leaf ct-commit-config-res-sent {
      type uint64;
      description
        "CounterForHowManyCommitConfigResponses";
    }
    leaf ct-action-json-req-recv {
      type uint64;
      description
        "CounterForHowManyActionJsonRequests";
    }
    leaf ct-action-json-res-sent {
      type uint64;
      description
        "CounterForHowManyActionJsonResponses";
    }
  }

  grouping GRPC-TUNNEL-SESSIONS {
    description
      "gRPC tunnel session";
    leaf address-xr {
      type string;
      description
        "Destination address";
    }
    leaf status {
      type Grpc-tunnel-status;
      description
        "Session status";
    }
    leaf status-str {
      type string;
      description
        "Status string in case of error";
    }
    leaf source-interface {
      type string;
      description
        "Source interface";
    }
    leaf source-ip {
      type string;
      description
        "Source interface IP";
    }
    leaf source-vrf {
      type string;
      description
        "Source interface vrf";
    }
    leaf vrf {
      type string;
      description
        "Configured VRF";
    }
    leaf target {
      type string;
      description
        "Target name";
    }
    leaf last-connected-timestamp {
      type uint64;
      description
        "Timestamp when session got connected";
    }
    leaf last-attempted-timestamp {
      type uint64;
      description
        "Timestamp when connection attempt was done";
    }
    leaf virtual-ip-status {
      type string;
      description
        "Virtual IP status, can be active or inactive";
    }
    leaf virtual-ip-enabled {
      type boolean;
      description
        "When set to true, tunnel uses virtual IP as the
         source address";
    }
    leaf address-family {
      type string;
      description
        "Address family (ipv4/ipv6) of domain addresses";
    }
    leaf listen-address {
      type string;
      description
        "Established tunnel listen address";
    }
  }

  grouping GRPC-VERSIONS-INFO-B {
    description
      "gRPC Services";
    leaf version {
      type string;
      description
        "Service Version";
    }
  }

  grouping LADDR-STR {
    description
      "LADDR STR";
    leaf laddr {
      type string {
        length "0..40";
      }
      description
        "laddr";
    }
  }

  grouping GRPC-STATE {
    description
      "gRPC state";
    leaf address-family {
      type Af;
      description
        "gRPC address family";
    }
    leaf port {
      type uint32;
      description
        "gRPC port";
    }
    leaf gnmi-port {
      type uint16;
      description
        "gNMI port";
    }
    leaf p4rt-port {
      type uint16;
      description
        "p4RT port";
    }
    leaf gribi-port {
      type uint16;
      description
        "gRIBI port";
    }
    leaf listen-address-count {
      type uint8;
      description
        "gRPC number of listen addresses";
    }
    leaf vrf {
      type string;
      description
        "gRPC VRF";
    }
    leaf tls {
      type Tls-state;
      description
        "gRPC TLS state";
    }
    leaf tls-mutual {
      type Tls-mutual-state;
      description
        "gRPC TLS mutual";
    }
    leaf trustpoint {
      type string;
      description
        "gRPC trustpoint";
    }
    leaf common-name {
      type string;
      description
        "Common name when generate certificates";
    }
    leaf cert-auth {
      type Certauth-state;
      description
        "gRPC Certificate Authentication";
    }
    leaf tlsv1-0 {
      type Tlsv1-0-state;
      description
        "gRPC TLS v1.0";
    }
    leaf max-requests {
      type uint32;
      description
        "Maximum number of requests";
    }
    leaf max-requests-per-user {
      type uint32;
      description
        "Maximum number of requests per user";
    }
    leaf max-streams {
      type uint32;
      description
        "Maximum number of streaming gRPCs";
    }
    leaf max-streams-per-user {
      type uint32;
      description
        "Maximum number of streaming gRPCs per user";
    }
    leaf memory-limit {
      type uint16;
      description
        "EMSd-Go soft memory limit (MB)";
    }
    leaf dscp {
      type uint8;
      description
        "QoS marking DSCP on transmitted gRPC";
    }
    leaf cipher-default {
      type Grpc-tls-cipher-default;
      description
        "Default of all ciphers";
    }
    leaf cipher-enable {
      type string;
      description
        "Comma separated list of enable ciphers, if
         cipher-default is disabled'";
    }
    leaf cipher-disable {
      type string;
      description
        "Comma separated list of disable ciphers, if
         cipher-default is enabled'";
    }
    leaf oper-cipher-enable {
      type string;
      description
        "Comma separated list of enable ciphers based on
         cipher default, disable, and enable";
    }
    leaf oper-cipher-disable {
      type string;
      description
        "Comma separated list of disable ciphers based on
         cipher default, disable, and enable";
    }
    leaf server {
      type uint32;
      description
        "Server SHUT state";
    }
    leaf server-disable-reason {
      type uint32;
      description
        "Server SHUT reason";
    }
    leaf ttl {
      type uint8;
      description
        "TTL settings for transmitted gRPC";
    }
    leaf server-name {
      type string;
      description
        "gRPC server name";
    }
    leaf keepalive-enforcement-min-time {
      type uint32;
      units "second";
      description
        "gRPC server keepalive enforcement minimum time
         in seconds";
    }
    leaf keepalive-timeout {
      type uint32;
      units "second";
      description
        "gRPC server keepalive timeout in seconds";
    }
    leaf keepalive-time {
      type uint32;
      units "second";
      description
        "gRPC server keepalive time in seconds";
    }
    leaf max-concurrent-streams {
      type uint32;
      description
        "gRPC maximum concurrent streams per connection";
    }
    leaf min-tls-version {
      type Tls-version;
      description
        "gRPC minimum TLS version";
    }
    leaf max-tls-version {
      type Tls-version;
      description
        "gRPC maximum TLS version";
    }
    leaf latest-connection-id {
      type uint64;
      description
        "gRPC latest connection Id in connection manager";
    }
    leaf local-connection {
      type Local-conn-state;
      description
        "gRPC Server Unix socket";
    }
    list laddr {
      max-elements "32";
      description
        "gRPC listen address list";
      uses LADDR-STR;
    }
  }

  grouping CERTIFICATE {
    description
      "gRPC Certificate";
    leaf certificate {
      type string;
      description
        "Certificate in PEM";
    }
  }
}
