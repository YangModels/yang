module Cisco-IOS-XR-um-asr9k-if-ethernet-cfg {
  namespace "http://cisco.com/ns/yang/Cisco-IOS-XR-um-asr9k-if-ethernet-cfg";
  prefix um-asr9k-if-ethernet-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-if-ethernet package configuration.
     
     This YANG module augments the
     modules with configuration data.
     
     Copyright (c) 2021-2025 by Cisco Systems, Inc., and/or its affiliates.
     All rights reserved.";

  revision 2022-07-11 {
    description
      "Added missing description statement to nodes";
    semver:module-version "1.1.0";
  }
  revision 2021-03-03 {
    description
      "Initial release";
    semver:module-version "1.0.0";
  }

  grouping IF-BODY {
    description
      "Grouping for interface";
    container transport-mode {
      when "../a1:interface-name[starts-with(text(),'GigabitEthernet')] or ../a1:interface-name[starts-with(text(),'TenGigE')] or ../a1:interface-name[starts-with(text(),'FortyGigE')] or ../a1:interface-name[starts-with(text(),'FiftyGigE')] or ../a1:interface-name[starts-with(text(),'HundredGigE')] or ../a1:interface-name[starts-with(text(),'FourHundredGigE')]" {
        tailf:dependency "../a1:interface-name";
      }
      description
        "Set the transport mode on an interface";
      container wan {
        when "../../a1:interface-name[starts-with(text(),'TenGigE')]" {
          tailf:dependency "../../a1:interface-name";
        }
        must
          "not(../rx-only or ../tx-only
           or ../signal-degrade)";
        presence "Indicates a wan node is configured.";
        description
          "10GBASE-W WAN SONET/SDH (9.95328Gb/s)";
      }
      container otn {
        when "../../a1:interface-name[starts-with(text(),'TenGigE')]" {
          tailf:dependency "../../a1:interface-name";
        }
        description
          "10GE over Optical Transport Network (G.709)";
        container bit-transparent {
          description
            "10GBASE-R transparently mapped into OTU-2";
          container opu1e {
            must "not(../opu2e)";
            presence "Indicates a opu1e node is configured.";
            description
              "10GBASE-R over OPU1e without fixed stuffing (11.0491Gb/s)";
          }
          container opu2e {
            must "not(../opu1e)";
            presence "Indicates a opu2e node is configured.";
            description
              "10GBASE-R over OPU2e with fixed stuffing (11.0957Gb/s)";
          }
        }
      }
      container rx-only {
        must
          "not(../wan or ../tx-only
           or ../signal-degrade)";
        presence "Indicates a rx-only node is configured.";
        description
          "10GE UDE Mode, Receive Only";
      }
      container tx-only {
        must
          "not(../wan or ../rx-only
           or ../signal-degrade)";
        presence "Indicates a tx-only node is configured.";
        description
          "10GE UDE Mode, Transmit Only";
      }
      container signal-degrade {
        when "../../a1:interface-name[starts-with(text(),'GigabitEthernet')]" {
          tailf:dependency "../../a1:interface-name";
        }
        must
          "not(../wan or ../rx-only
           or ../tx-only)";
        presence "Indicates a signal-degrade node is configured.";
        description
          "Enable port for signal degrade detection, 1GE Only";
      }
    }
    container transceiver {
      when "../a1:interface-name[starts-with(text(),'GigabitEthernet')] or ../a1:interface-name[starts-with(text(),'TenGigE')] or ../a1:interface-name[starts-with(text(),'FortyGigE')] or ../a1:interface-name[starts-with(text(),'FiftyGigE')] or ../a1:interface-name[starts-with(text(),'HundredGigE')] or ../a1:interface-name[starts-with(text(),'FourHundredGigE')]" {
        tailf:dependency "../a1:interface-name";
      }
      description
        "transceiver commands";
      container permit {
        description
          "permit";
        container pid {
          description
            "Permit pluggable pid (Product ID) all";
          container all {
            presence "Indicates a all node is configured.";
            description
              "all";
          }
        }
        container type {
          description
            "Permit pluggable type all";
          container all {
            presence "Indicates a all node is configured.";
            description
              "all";
          }
        }
      }
    }
    container small-frame-padding {
      presence "Indicates a small-frame-padding node is configured.";
      description
        "Pad small frames to 68 bytes";
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
}
