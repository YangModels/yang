module Cisco-IOS-XR-um-asr9k-hw-module-subslot-cfg {
  namespace "http://cisco.com/ns/yang/Cisco-IOS-XR-um-asr9k-hw-module-subslot-cfg";
  prefix um-asr9k-hw-module-subslot-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-subslot package configuration.
     
     This YANG module augments the
     modules with configuration data.
     
     Copyright (c) 2020-2025 by Cisco Systems, Inc., and/or its affiliates.
     All rights reserved.";

  revision 2020-09-02 {
    description
      "Initial release";
    semver:module-version "1.0.0";
  }

  container hw-module {
    description
      "Configure h/w module";
    container subslots {
      description
        "Configure subslot h/w module";
      list subslot {
        must "shutdown or cardtype or mode";
        key "subslot-name";
        description
          "Configure subslot h/w module";
        leaf subslot-name {
          type xr:Node-id;
          description
            "Configure subslot h/w module";
        }
        leaf shutdown {
          type enumeration {
            enum "unpowered" {
              value 1;
              description
                "Keep the shutdown module unpowered";
            }
            enum "powered" {
              value 2;
              description
                "Keep the shutdown module powered (default)";
            }
          }
          description
            "Shutdown a subslot h/w module";
        }
        leaf cardtype {
          type enumeration {
            enum "t3" {
              value 1;
              description
                "T3 interface type(default)";
            }
            enum "e3" {
              value 2;
              description
                "E3 interface type";
            }
            enum "t1" {
              value 3;
              description
                "T1 interface type";
            }
            enum "e1" {
              value 4;
              description
                "E1 interface type";
            }
            enum "sonet" {
              value 5;
              description
                "Sonet interface type";
            }
            enum "sdh" {
              value 6;
              description
                "SDH interface type";
            }
          }
          description
            "Configure the SPA physical interface type";
        }
        leaf mode {
          type enumeration {
            enum "CEM" {
              value 1;
              description
                "Circuit Emulation mode";
            }
          }
          description
            "Configure the SPA mode";
        }
      }
    }
  }
}
