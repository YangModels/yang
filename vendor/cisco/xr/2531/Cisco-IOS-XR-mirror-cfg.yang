module Cisco-IOS-XR-mirror-cfg {
  namespace "http://cisco.com/ns/yang/Cisco-IOS-XR-mirror-cfg";
  prefix mirror-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mirror package configuration.
     
     This module contains definitions
     for the following management objects:
       mirror-cfg: mirror directory configuration commands
     
     Copyright (c) 2013-2019 by Cisco Systems, Inc.
     All rights reserved.";

  revision 2019-11-08 {
    description
      "IOS XR 7.2.1 revision";
    semver:module-version "1.0.0";
  }
  revision 2019-04-05 {
    description
      "Establish semantic version baseline.";
  }
  revision 2015-11-09 {
    description
      "IOS XR 6.0 revision.";
  }

  container mirror-cfg {
    description
      "mirror directory configuration commands";
    leaf mirror-cfg-checksum {
      type empty;
      description
        "rsync will use --checksum option for determining
         if file is in sync";
    }
    leaf mirror-cfg-enable {
      type empty;
      description
        "Enable mirror directory syncing to standby RP";
    }
  }
}
