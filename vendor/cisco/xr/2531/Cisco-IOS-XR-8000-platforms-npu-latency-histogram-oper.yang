module Cisco-IOS-XR-8000-platforms-npu-latency-histogram-oper {
  namespace "http://cisco.com/ns/yang/Cisco-IOS-XR-8000-platforms-npu-latency-histogram-oper";
  prefix xr-8000-platforms-npu-latency-histogram-oper;

  import Cisco-IOS-XR-types {
    prefix xr;
  }
  import cisco-semver {
    prefix semver;
  }
  include Cisco-IOS-XR-8000-platforms-npu-latency-histogram-oper-sub1 {
    revision-date 2025-03-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-latency-histogram package operational data.
     
     This module contains definitions
     for the following management objects:
       traffic-class-latency: Packet latency histogram bins per
         traffic-class
     
     Copyright (c) 2013-2025 by Cisco Systems, Inc.
     All rights reserved.";

  revision 2025-03-12 {
    description
      "Create the initial npu-latency-histogram oper yang model.";
    semver:module-version "1.0.0";
  }
  revision 2019-04-05 {
    description
      "Establish semantic version baseline.";
  }
  revision 2015-11-09 {
    description
      "IOS XR 6.0 revision.";
  }

  container traffic-class-latency {
    config false;
    description
      "Packet latency histogram bins per traffic-class";
    container nodes {
      description
        "Available nodes on the system";
      list node {
        key "node-name";
        description
          "Histogram data for a particular node";
        leaf node-name {
          type xr:Node-id;
          description
            "Node ID";
        }
        list npu-id {
          key "npu-id";
          description
            "NPU ID to dump histogram latency bins";
          leaf npu-id {
            type uint32;
            description
              "Npu number";
          }
          list option {
            key "opt-num";
            description
              "Display Option <0 - 4> to dump histogram
               latency bins";
            leaf opt-num {
              type uint32;
              description
                "Option number";
            }
            list slice {
              key "slice-id";
              description
                "Slice number <0-5> to dump histogram latency
                 bins for all IFGs on this slice for all TCs";
              leaf slice-id {
                type uint32;
                description
                  "Slice number";
              }
              list ifg {
                key "ifg-id";
                description
                  "IFG number <0-1> to dump histogram latency
                   bins for all TCs";
                leaf ifg-id {
                  type uint32;
                  description
                    "Ifg number";
                }
                list traffic-class {
                  key "tc-num";
                  description
                    "Traffic-class <0-7> to dump histogram
                     latency bins";
                  leaf tc-num {
                    type uint32;
                    description
                      "Tc number";
                  }
                  uses OFA-TCLATENCYHISTOGRAM-BINS-ARRAY-ST;
                }
              }
            }
          }
        }
      }
    }
  }
}
