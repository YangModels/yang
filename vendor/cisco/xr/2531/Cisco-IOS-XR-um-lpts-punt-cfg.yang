module Cisco-IOS-XR-um-lpts-punt-cfg {
  namespace "http://cisco.com/ns/yang/Cisco-IOS-XR-um-lpts-punt-cfg";
  prefix um-lpts-punt-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-punt package configuration.
     
     This YANG module augments the
     modules with configuration data.
     
     Copyright (c) 2021-2025 by Cisco Systems, Inc., and/or its affiliates.
     All rights reserved.";

  revision 2022-07-11 {
    description
      "Added missing description statement to nodes";
    semver:module-version "1.1.0";
  }
  revision 2021-10-04 {
    description
      "Initial release";
    semver:module-version "1.0.0";
  }

  feature pifib_punt_policer_config_check {
    description
      "pifib punt policer config check";
  }

  feature pifib_local_punt_policer_config_check {
    description
      "pifib local punt policer config check";
  }

  feature pifib_punt_policer_bcast_config_check {
    description
      "pifib punt policer bcast config check";
  }

  feature pifib_domains_config_check {
    description
      "pifib domains config check";
  }

  feature pifib_policer_node_check {
    description
      "pifib policer node check";
  }

  grouping LOCATION-BODY {
    description
      "Grouping for location";
    container lpts {
      description
        "lpts configuration commands";
      container punt {
        description
          "punt configuration commands";
        container police {
          presence "Indicates a protocol node is configured.";
          description
            "ingress policers configuration command";
          container protocol {
            description
              "Protocol packets";
            container arp {
              description
                "ARP Packets";
              leaf rate {
                type uint32 {
                  range "0..4294967295" {
                    description
                      "Packets Per Second (actual Min and Max range depends on platform)";
                  }
                }
                description
                  "Rate in PPS";
              }
            }
            container cdp {
              description
                "CDP Packets";
              leaf rate {
                type uint32 {
                  range "0..4294967295" {
                    description
                      "Packets Per Second (actual Min and Max range depends on platform)";
                  }
                }
                description
                  "Rate in PPS";
              }
            }
            container lacp {
              description
                "LACP Packets";
              leaf rate {
                type uint32 {
                  range "0..4294967295" {
                    description
                      "Packets Per Second (actual Min and Max range depends on platform)";
                  }
                }
                description
                  "Rate in PPS";
              }
            }
            container lldp {
              description
                "LLDP Packets";
              leaf rate {
                type uint32 {
                  range "0..4294967295" {
                    description
                      "Packets Per Second (actual Min and Max range depends on platform)";
                  }
                }
                description
                  "Rate in PPS";
              }
            }
            container ssfp {
              description
                "Smart SFP Mgmt Packets";
              leaf rate {
                type uint32 {
                  range "0..4294967295" {
                    description
                      "Packets Per Second (actual Min and Max range depends on platform)";
                  }
                }
                description
                  "Rate in PPS";
              }
            }
            container ipv6-nd-proxy {
              description
                "IPv6-ND-proxy Packets";
              leaf rate {
                type uint32 {
                  range "0..4294967295" {
                    description
                      "Packets Per Second (actual Min and Max range depends on platform)";
                  }
                }
                description
                  "Rate in PPS";
              }
            }
            container cfm {
              description
                "Connectivity Fault Management Protocol packets";
              container cc {
                description
                  "Continuity Check packets";
                container rsp {
                  description
                    "CC packets for RSP";
                  leaf rate {
                    type uint32 {
                      range "0..4294967295" {
                        description
                          "Packets Per Second";
                      }
                    }
                    description
                      "Rate in PPS";
                  }
                }
              }
            }
            container rsvp {
              description
                "Resource Reservation Protocol packets";
              container options {
                description
                  "Rsvp options packets";
                leaf rate {
                  type uint32 {
                    range "0..4294967295" {
                      description
                        "Packets Per Second";
                    }
                  }
                  description
                    "Rate in PPS";
                }
              }
            }
            container pim {
              description
                "Pim Protocol packets";
              container options {
                description
                  "PIM options packets";
                container punt {
                  description
                    "PIM SM Snoop/Trap packets";
                  leaf rate {
                    type uint32 {
                      range "0..4294967295" {
                        description
                          "Packets Per Second";
                      }
                    }
                    description
                      "Rate in PPS";
                  }
                }
              }
            }
            container igmp {
              description
                "igmp Protocol packets";
              container options {
                description
                  "IGMP options packets";
                leaf rate {
                  type uint32 {
                    range "0..4294967295" {
                      description
                        "Packets Per Second";
                    }
                  }
                  description
                    "Rate in PPS";
                }
              }
            }
            container dhcp {
              description
                "Dynamic Host Configuration Protocol";
              leaf rate {
                type uint32 {
                  range "0..4294967295" {
                    description
                      "Packets Per Second";
                  }
                }
                description
                  "Rate in PPS";
              }
            }
            container ipv4 {
              description
                "IPv4 packets";
              container options {
                description
                  "IPv4 packets with options";
                leaf rate {
                  type uint32 {
                    range "0..4294967295" {
                      description
                        "Packets Per Second";
                    }
                  }
                  description
                    "Rate in PPS";
                }
              }
            }
            container bfd {
              description
                "Bidirectional Forwarding Detection packets";
              leaf rate {
                type uint32 {
                  range "0..4294967295" {
                    description
                      "Packets Per Second";
                  }
                }
                description
                  "Rate in PPS";
              }
            }
            container mpls {
              description
                "MPLS punt packets";
              container fib {
                description
                  "MPLS fib punt packets";
                leaf rate {
                  type uint32 {
                    range "0..4294967295" {
                      description
                        "Packets Per Second";
                    }
                  }
                  description
                    "Rate in PPS";
                }
              }
            }
            container ipv6 {
              description
                "IPv6 packets";
              container multicast {
                description
                  "IPv6 multicast punt packets";
                container forward {
                  description
                    "IPv6 multicast punt and forward packets";
                  leaf rate {
                    type uint32 {
                      range "0..4294967295" {
                        description
                          "Packets Per Second";
                      }
                    }
                    description
                      "Rate in PPS";
                  }
                }
              }
              container hop-by-hop {
                description
                  "IPv6 EXT header hop-by-hop packets";
                leaf rate {
                  type uint32 {
                    range "0..4294967295" {
                      description
                        "Packets Per Second";
                    }
                  }
                  description
                    "Rate in PPS";
                }
              }
            }
            container ptp {
              description
                "PTP (1588) Protocol packets";
              leaf rate {
                type uint32 {
                  range "0..4294967295" {
                    description
                      "Packets Per Second";
                  }
                }
                description
                  "Rate in PPS";
              }
            }
          }
          container domains {
            description
              "LPTS Domain";
            list domain {
              key "domain-name";
              description
                "LPTS Domain";
              leaf domain-name {
                type xr:Cisco-ios-xr-string {
                  length "1..32" {
                    description
                      "Domain name";
                  }
                  pattern "[a-z0-9A-Z][-_.:a-z0-9A-Z]*";
                }
                description
                  "LPTS Domain";
              }
              container protocol {
                description
                  "Protocol packets";
                container arp {
                  description
                    "ARP Packets";
                  leaf rate {
                    type uint32 {
                      range "0..4294967295" {
                        description
                          "Packets Per Second (actual Min and Max range depends on platform)";
                      }
                    }
                    description
                      "Rate in PPS";
                  }
                }
                container cdp {
                  description
                    "CDP Packets";
                  leaf rate {
                    type uint32 {
                      range "0..4294967295" {
                        description
                          "Packets Per Second (actual Min and Max range depends on platform)";
                      }
                    }
                    description
                      "Rate in PPS";
                  }
                }
                container lacp {
                  description
                    "LACP Packets";
                  leaf rate {
                    type uint32 {
                      range "0..4294967295" {
                        description
                          "Packets Per Second (actual Min and Max range depends on platform)";
                      }
                    }
                    description
                      "Rate in PPS";
                  }
                }
                container lldp {
                  description
                    "LLDP Packets";
                  leaf rate {
                    type uint32 {
                      range "0..4294967295" {
                        description
                          "Packets Per Second (actual Min and Max range depends on platform)";
                      }
                    }
                    description
                      "Rate in PPS";
                  }
                }
                container ssfp {
                  description
                    "Smart SFP Mgmt Packets";
                  leaf rate {
                    type uint32 {
                      range "0..4294967295" {
                        description
                          "Packets Per Second (actual Min and Max range depends on platform)";
                      }
                    }
                    description
                      "Rate in PPS";
                  }
                }
                container ipv6-nd-proxy {
                  description
                    "IPv6-ND-proxy Packets";
                  leaf rate {
                    type uint32 {
                      range "0..4294967295" {
                        description
                          "Packets Per Second (actual Min and Max range depends on platform)";
                      }
                    }
                    description
                      "Rate in PPS";
                  }
                }
              }
            }
          }
          container exception {
            description
              "Exception packets";
            container ipv4 {
              description
                "IPV4 exception packets";
              container ttl-error {
                description
                  "IPV4 TTL Error packets";
                leaf rate {
                  type uint32 {
                    range "0..4294967295" {
                      description
                        "Packets Per Second";
                    }
                  }
                  description
                    "Rate in PPS";
                }
              }
              container fragment {
                description
                  "Fragmentation needed packets";
                leaf rate {
                  type uint32 {
                    range "0..4294967295" {
                      description
                        "Packets Per Second";
                    }
                  }
                  description
                    "Rate in PPS";
                }
              }
            }
            container tunnel-term-fragment {
              description
                "TunnelTermination And Fragmented";
              leaf rate {
                type uint32 {
                  range "0..4294967295" {
                    description
                      "Packets Per Second";
                  }
                }
                description
                  "Rate in PPS";
              }
            }
            container fib-drop {
              description
                "pkt drop due no fib match";
              leaf rate {
                type uint32 {
                  range "0..4294967295" {
                    description
                      "Packets Per Second";
                  }
                }
                description
                  "Rate in PPS";
              }
            }
            container acl-log {
              description
                "acl log packets";
              leaf rate {
                type uint32 {
                  range "0..4294967295" {
                    description
                      "Packets Per Second";
                  }
                }
                description
                  "Rate in PPS";
              }
            }
            container recycle {
              description
                "For recycle packets";
              leaf rate {
                type uint32 {
                  range "0..4294967295" {
                    description
                      "Packets Per Second";
                  }
                }
                description
                  "Rate in PPS";
              }
            }
            container netflow {
              description
                "For netflow packets";
              leaf rate {
                type uint32 {
                  range "0..4294967295" {
                    description
                      "Packets Per Second";
                  }
                }
                description
                  "Rate in PPS";
              }
            }
            container mpls {
              description
                "MPLS exception packets";
              container icmp-gen {
                description
                  "MPLS ICMP generation packets";
                leaf rate {
                  type uint32 {
                    range "0..4294967295" {
                      description
                        "Packets Per Second";
                    }
                  }
                  description
                    "Rate in PPS";
                }
              }
              container ttl-error {
                description
                  "MPLS TTL Error packets";
                leaf rate {
                  type uint32 {
                    range "0..4294967295" {
                      description
                        "Packets Per Second";
                    }
                  }
                  description
                    "Rate in PPS";
                }
              }
            }
            container adjacency {
              description
                "Glean Adjacency resolution packets";
              leaf rate {
                type uint32 {
                  range "0..4294967295" {
                    description
                      "Packets Per Second";
                  }
                }
                description
                  "Rate in PPS";
              }
            }
            container ipv6 {
              description
                "IPv6 packets";
              container ttl-error {
                description
                  "IPV6 TTL error packets";
                leaf rate {
                  type uint32 {
                    range "0..4294967295" {
                      description
                        "Packets Per Second";
                    }
                  }
                  description
                    "Rate in PPS";
                }
              }
              container fragment {
                description
                  "IPV6 Too Big packets";
                leaf rate {
                  type uint32 {
                    range "0..4294967295" {
                      description
                        "Packets Per Second";
                    }
                  }
                  description
                    "Rate in PPS";
                }
              }
            }
            container urpf {
              description
                "urpf exception packets";
              leaf rate {
                type uint32 {
                  range "0..4294967295" {
                    description
                      "Packets Per Second";
                  }
                }
                description
                  "Rate in PPS";
              }
            }
          }
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
  container lpts {
    if-feature "pifib_punt_policer_config_check";
    if-feature "pifib_local_punt_policer_config_check";
    description
      "lpts configuration commands";
    container punt {
      description
        "punt configuration commands";
      container police {
        presence "Indicates a police node is configured.";
        description
          "ingress policers configuration command";
        container mcast {
          description
            "Multicast Packets";
          leaf rate {
            type uint32 {
              range "0..4294967295" {
                description
                  "Packets Per Second (actual Min and Max range depends on platform)";
              }
            }
            description
              "Rate in PPS";
          }
        }
        container bcast {
          if-feature "pifib_punt_policer_bcast_config_check";
          description
            "Broadcast Packets";
          leaf rate {
            type uint32 {
              range "0..4294967295" {
                description
                  "Packets Per Second (actual Min and Max range depends on platform)";
              }
            }
            description
              "Rate in PPS";
          }
        }
        container protocol {
          description
            "Protocol packets";
          container arp {
            description
              "ARP Packets";
            leaf rate {
              type uint32 {
                range "0..4294967295" {
                  description
                    "Packets Per Second (actual Min and Max range depends on platform)";
                }
              }
              description
                "Rate in PPS";
            }
          }
          container cdp {
            description
              "CDP Packets";
            leaf rate {
              type uint32 {
                range "0..4294967295" {
                  description
                    "Packets Per Second (actual Min and Max range depends on platform)";
                }
              }
              description
                "Rate in PPS";
            }
          }
          container lacp {
            description
              "LACP Packets";
            leaf rate {
              type uint32 {
                range "0..4294967295" {
                  description
                    "Packets Per Second (actual Min and Max range depends on platform)";
                }
              }
              description
                "Rate in PPS";
            }
          }
          container lldp {
            description
              "LLDP Packets";
            leaf rate {
              type uint32 {
                range "0..4294967295" {
                  description
                    "Packets Per Second (actual Min and Max range depends on platform)";
                }
              }
              description
                "Rate in PPS";
            }
          }
          container ssfp {
            description
              "Smart SFP Mgmt Packets";
            leaf rate {
              type uint32 {
                range "0..4294967295" {
                  description
                    "Packets Per Second (actual Min and Max range depends on platform)";
                }
              }
              description
                "Rate in PPS";
            }
          }
          container ipv6-nd-proxy {
            description
              "IPv6-ND-proxy Packets";
            leaf rate {
              type uint32 {
                range "0..4294967295" {
                  description
                    "Packets Per Second (actual Min and Max range depends on platform)";
                }
              }
              description
                "Rate in PPS";
            }
          }
        }
        container domains {
          description
            "LPTS Domain";
          list domain {
            key "domain-name";
            description
              "LPTS Domain";
            leaf domain-name {
              type xr:Cisco-ios-xr-string {
                length "1..32" {
                  description
                    "Domain name";
                }
                pattern "[a-z0-9A-Z][-_.:a-z0-9A-Z]*";
              }
              description
                "LPTS Domain";
            }
            container mcast {
              description
                "Multicast Packets";
              leaf rate {
                type uint32 {
                  range "0..4294967295" {
                    description
                      "Packets Per Second (actual Min and Max range depends on platform)";
                  }
                }
                description
                  "Rate in PPS";
              }
            }
            container bcast {
              if-feature "pifib_punt_policer_bcast_config_check";
              description
                "Broadcast Packets";
              leaf rate {
                type uint32 {
                  range "0..4294967295" {
                    description
                      "Packets Per Second (actual Min and Max range depends on platform)";
                  }
                }
                description
                  "Rate in PPS";
              }
            }
            container protocol {
              description
                "Protocol packets";
              container arp {
                description
                  "ARP Packets";
                leaf rate {
                  type uint32 {
                    range "0..4294967295" {
                      description
                        "Packets Per Second (actual Min and Max range depends on platform)";
                    }
                  }
                  description
                    "Rate in PPS";
                }
              }
              container cdp {
                description
                  "CDP Packets";
                leaf rate {
                  type uint32 {
                    range "0..4294967295" {
                      description
                        "Packets Per Second (actual Min and Max range depends on platform)";
                    }
                  }
                  description
                    "Rate in PPS";
                }
              }
              container lacp {
                description
                  "LACP Packets";
                leaf rate {
                  type uint32 {
                    range "0..4294967295" {
                      description
                        "Packets Per Second (actual Min and Max range depends on platform)";
                    }
                  }
                  description
                    "Rate in PPS";
                }
              }
              container lldp {
                description
                  "LLDP Packets";
                leaf rate {
                  type uint32 {
                    range "0..4294967295" {
                      description
                        "Packets Per Second (actual Min and Max range depends on platform)";
                    }
                  }
                  description
                    "Rate in PPS";
                }
              }
              container ssfp {
                description
                  "Smart SFP Mgmt Packets";
                leaf rate {
                  type uint32 {
                    range "0..4294967295" {
                      description
                        "Packets Per Second (actual Min and Max range depends on platform)";
                    }
                  }
                  description
                    "Rate in PPS";
                }
              }
              container ipv6-nd-proxy {
                description
                  "IPv6-ND-proxy Packets";
                leaf rate {
                  type uint32 {
                    range "0..4294967295" {
                      description
                        "Packets Per Second (actual Min and Max range depends on platform)";
                    }
                  }
                  description
                    "Rate in PPS";
                }
              }
            }
          }
        }
        container interfaces {
          description
            "Per interface level policer configuration";
          list interface {
            key "interface-name";
            description
              "Per interface level policer configuration";
            leaf interface-name {
              type xr:Interface-name;
              description
                "Per interface level policer configuration";
            }
            container mcast {
              description
                "Multicast Packets";
              leaf rate {
                type uint32 {
                  range "0..4294967295" {
                    description
                      "Packets Per Second (actual Min and Max range depends on platform)";
                  }
                }
                must "not(../disabled)";
                description
                  "Rate in PPS";
              }
              container disabled {
                must "not(../rate)";
                presence "Indicates a disabled node is configured.";
                description
                  "disable punt policer";
              }
            }
            container bcast {
              if-feature "pifib_punt_policer_bcast_config_check";
              description
                "Broadcast Packets";
              leaf rate {
                type uint32 {
                  range "0..4294967295" {
                    description
                      "Packets Per Second (actual Min and Max range depends on platform)";
                  }
                }
                must "not(../disabled)";
                description
                  "Rate in PPS";
              }
              container disabled {
                must "not(../rate)";
                presence "Indicates a disabled node is configured.";
                description
                  "disable punt policer";
              }
            }
          }
        }
      }
    }
  }
}
