module Cisco-IOS-XR-attestation-agent-oper {
  namespace "http://cisco.com/ns/yang/Cisco-IOS-XR-attestation-agent-oper";
  prefix attestation-agent-oper;

  import Cisco-IOS-XR-types {
    prefix xr;
  }
  import cisco-semver {
    prefix semver;
  }
  include Cisco-IOS-XR-attestation-agent-oper-sub1 {
    revision-date 2022-10-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR attestation-agent package operational data.
     
     This module contains definitions
     for the following management objects:
       attestation-agent: Oper data for attestation-agent
     
     Copyright (c) 2013-2022 by Cisco Systems, Inc.
     All rights reserved.";

  revision 2022-10-10 {
    description
      "Added support for AIK and SUDI certificates.";
    semver:module-version "1.0.0";
  }
  revision 2022-06-03 {
    description
      "Added new oper model for attestation entities.";
  }
  revision 2019-04-05 {
    description
      "Establish semantic version baseline.";
  }
  revision 2015-11-09 {
    description
      "IOS XR 6.0 revision.";
  }

  container attestation-agent {
    config false;
    description
      "Oper data for attestation-agent";
    container nodes {
      description
        "Node-specific attestation agent operational data";
      list node {
        key "node-name";
        description
          "attestation agent operational data for a
           particular node";
        container cert-details {
          description
            "System certificates from nodes running
             attestation-agent";
          list cert-detail {
            key "certificate-identifier";
            description
              "Certificate data in PEM format";
            leaf certificate-identifier {
              type xr:Cisco-ios-xr-string;
              description
                "Certificate Identifer(CiscoSUDI or CiscoAIK
                 or CiscoHASUDI)";
            }
            uses SYSTEM-CERTS;
          }
        }
        container challenge-cert-details {
          description
            "System certificates from nodes running
             attestation-agent with challenge response to
             prove identity";
          list challenge-cert-detail {
            key "certificate-identifier nonce";
            description
              "Certificate data in PEM format with signature";
            leaf certificate-identifier {
              type xr:Cisco-ios-xr-string;
              description
                "Certificate Identifer(CiscoSUDI or CiscoAIK
                 or CiscoHASUDI)";
            }
            leaf nonce {
              type xr:Cisco-ios-xr-string;
              description
                "Nonce as non-zero hex string of even length,
                 length range: <02-128>";
            }
            uses SYSTEM-CERTS-CHALLENGE;
          }
        }
        container node-secure-boot-status {
          description
            "Secure boot status from different nodes
             running attestation-agent";
          uses SECURE-BOOT-STATUS;
        }
        leaf node-name {
          type xr:Node-id;
          description
            "The node name";
        }
      }
    }
  }
}
