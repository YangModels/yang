module Cisco-IOS-XR-8000-platforms-npu-latency-histogram-act {
  namespace "http://cisco.com/ns/yang/Cisco-IOS-XR-8000-platforms-npu-latency-histogram-act";
  prefix platforms-npu-latency-histogram-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco-IOS-XR-8000-platforms-npu-latency-histogram package actions.
     
     This module contains definitions
     for the following management objects:
       8000-platforms-npu-latency-histogram : TC LATENCY HISTOGRAM DATA
     
     Copyright (c) 2024-2025 by Cisco Systems, Inc., and/or its affiliates.
     All rights reserved.";

  revision 2024-06-24 {
    description
      "HW stores packet-latency data in the form bins (aka intervals). There are
       a total of 8 bins for each traffic-class and the delay range for these bins
       is configurable. Latency Histogram is the graphical representation of this
       latency data which helps analyze which port and traffic-class consumes
       more time in scheduling and queuing.
       
       This is the action yang model for clearing the packet-latency histogram bin
       data with the clear-npu-latency-histogram action";
    semver:module-version "1.0.0";
  }

  rpc clear-npu-latency-histogram {
    description
      "Clear NPU Latency Histogram Bins";
    input {
      leaf node-name {
        type xr:Node-id;
        mandatory true;
        description
          "Location of interfaces to be cleared";
      }
      leaf npu-id {
        type uint8 {
          range "0..7";
        }
        mandatory true;
        description
          "ASIC UNIT of the Line Card Location";
      }
      leaf slice {
        type uint8 {
          range "0..5";
        }
        description
          "Slice on this UNIT to be cleared";
      }
      leaf ifg {
        type uint8 {
          range "0..1";
        }
        description
          "Interface-grouping (IFG) on this Slice to be cleared";
      }
      leaf traffic-class {
        type uint8 {
          range "0..7";
        }
        description
          "Traffic class to be cleared, default is all traffic classes";
      }
    }
  }
}
