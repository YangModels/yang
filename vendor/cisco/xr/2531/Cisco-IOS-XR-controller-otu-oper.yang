module Cisco-IOS-XR-controller-otu-oper {
  namespace "http://cisco.com/ns/yang/Cisco-IOS-XR-controller-otu-oper";
  prefix controller-otu-oper;

  import Cisco-IOS-XR-types {
    prefix xr;
  }
  import cisco-semver {
    prefix semver;
  }
  include Cisco-IOS-XR-controller-otu-oper-sub1 {
    revision-date 2025-04-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-otu package operational data.
     
     This module contains definitions
     for the following management objects:
       otu: OTU operational data
     
     Copyright (c) 2013-2025 by Cisco Systems, Inc.
     All rights reserved.";

  revision 2025-04-04 {
    description
      "Added support for FEC Support Under CoherentDSP controllers with ThirdPartySD parameters.
       2024-10-24
         Added support for client network mapping under show controller coherentdsp.
       2024-10-15
         Added state transition count and link flap fields
       2024-03-20
         Added support for PRBS Lock lost time
       2024-03-08
         Added support for Cumulative PRBS stats
       2021-12-01
         Added LED State
       2021-09-01
         Added support for PRBS direction and error-inject";
    semver:module-version "4.0.0";
  }
  revision 2020-05-12 {
    description
      "Added flexo oper";
    semver:module-version "3.1.0";
  }
  revision 2019-12-19 {
    description
      "Added new values in OTU_G709FECMode
       2019-09-18
         Added new parameters, q-margin, q-factor, bandwidth to reflect under show controller coherentdsp.";
    semver:module-version "3.0.0";
  }
  revision 2019-04-05 {
    description
      "Establish semantic version baseline.";
    semver:module-version "2.0.0";
  }
  revision 2017-05-01 {
    description
      "Fixing backward compatibility error in module.";
  }
  revision 2017-03-13 {
    description
      "PRBS Info added";
  }
  revision 2015-11-09 {
    description
      "IOS XR 6.0 revision.";
  }

  container otu {
    config false;
    description
      "OTU operational data";
    container controllers {
      description
        "All OTU Port operational data";
      list controller {
        key "controller-name";
        description
          "OTU Port operational data";
        container prbs {
          description
            "OTU port PRBS operational data";
          uses OTU-PRBS-INFO;
        }
        container info {
          description
            "OTU port operational data";
          uses OTU-PER-PORT-INFO;
        }
        leaf controller-name {
          type xr:Interface-name;
          description
            "Port name";
        }
      }
    }
  }
}
