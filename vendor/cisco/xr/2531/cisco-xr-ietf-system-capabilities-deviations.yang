module cisco-xr-ietf-system-capabilities-deviations {
  namespace "http://cisco.com/ns/yang/cisco-xr-ietf-system-capabilities-deviations";
  prefix xr-sysc-d;

  import ietf-system-capabilities {
    prefix sysc;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of 'not-supported' deviations of:

        ietf-system-capabilities@2022-02-17

     on Cisco IOS-XR devices.

     Copyright (c) 2025 by Cisco Systems, Inc., and/or its affiliates.
     All rights reserved.";


  revision 2025-01-20 {
    description
      "Initial version.";
  }

  /*
   * If in the future this deviations file only contains RPC or notification
   * nodes, it will stop appearing in Yang Library or capabilities/hello
   * output.
   * See CSCwn84289 for more details. This comment can be removed once the
   * issue is resolved.
   */

  // DATA MODEL DEVIATIONS


  // Remove support for per-node capabilities.
  deviation /sysc:system-capabilities/sysc:datastore-capabilities {
    deviate not-supported;
  }

}
