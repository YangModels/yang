module Cisco-IOS-XR-openconfig-npu-resources-oper-ext {
  yang-version 1;
  namespace "http://cisco.com/ns/yang/Cisco-IOS-XR-openconfig-npu-resources-oper-ext";
  prefix cisco-res;

  import openconfig-types {
    prefix oc-types;
  }
  import openconfig-extensions {
    prefix oc-ext;
  }
  import openconfig-platform {
    prefix oc-platform;
  }

  organization
    "Cisco Systems, Inc";
  contact
    "Cisco Systems
     Customer Service
     Postal: 170 West Tasman Drive
     San Jose, CA 95134
     Tel: +1 800 553-NETS
     E-mail: cs-yang@cisco.com";
  description
    "Adding augments to oc-res yang for providing vendor based counters.";

  revision 2024-10-10 {
    description
      "Updated resource oor state enum";
  }
  revision 2024-05-31 {
    description
      "Add augment vendor groupings";
    reference "0.1.0";
  }

  typedef oor-state {
    type enumeration {
      enum "green" {
        description
          "OOR threshold green";
      }
      enum "yellow" {
        description
          "OOR threshold yellow";
      }
      enum "red" {
        description
          "OOR threshold red";
      }
    }
    description
      "OOR threshold color type";
  }

  grouping cisco-oor-threshold {
    description
      "OOR threshold leaf grouping";
    leaf oor-red-threshold-percentage {
      type oc-types:percentage;
      description
        "Percentage at which Yellow to Red OOR limit is hit";
    }
    leaf oor-yellow-threshold-percentage {
      type oc-types:percentage;
      description
        "Percentage at which Green to Yellow OOR limit is hit";
    }
    leaf resource-oor-state {
      type oor-state;
      description
        "Resource OOR state to indicate Red, Yellow or Green threshold";
    }
    leaf last-resource-oor-change {
      type oc-types:timeticks64;
      description
        "Timestamp at which Resource Threshold state change occured";
    }
  }

  augment "/oc-platform:components/oc-platform:component/oc-platform:integrated-circuit/oc-platform:utilization/oc-platform:resources/oc-platform:resource/oc-platform:state" {
    description
      "Add vendor container for exporting vendor based leafs that contains 00R related info";
    container cisco {
      description
        "Cisco specific NPU resource container";
      uses cisco-oor-threshold;
    }
  }
  oc-ext:openconfig-version "0.1.0";
  oc-ext:catalog-organization "openconfig";
  oc-ext:origin "openconfig";
}
