module Cisco-IOS-XR-osa-linesystem-cfg {
  namespace "http://cisco.com/ns/yang/Cisco-IOS-XR-osa-linesystem-cfg";
  prefix osa-linesystem-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa-linesystem package configuration.
     
     This YANG module augments the
       Cisco-IOS-XR-config-mda-cfg
     module with configuration data.
     
     Copyright (c) 2013-2025 by Cisco Systems, Inc.
     All rights reserved.";

  revision 2025-03-05 {
    description
      "Adding support for SLTE";
    semver:module-version "1.0.0";
  }
  revision 2023-10-13 {
    description
      "Adding support for ASE Loading Disable config";
  }
  revision 2020-03-30 {
    description
      "Initial Revision.";
  }
  revision 2019-04-05 {
    description
      "Establish semantic version baseline.";
  }
  revision 2015-11-09 {
    description
      "IOS XR 6.0 revision.";
  }

  grouping NODE-CFG {
    description
      "active/preconfigured nodes configuration";
    container inline-amplifier {
      description
        "Inline Amplifier Configuration";
      container ila-grid-mode {
        description
          "Grid Mode Type";
        container ila-channel-identifiers {
          description
            "Flex Grid";
          list ila-channel-identifier {
            key "channel-number";
            description
              "Channel Identifier";
            leaf channel-number {
              type uint32;
              description
                "Channel Number";
            }
            leaf centre-frequency {
              type string {
                length "1..11";
              }
              description
                "Centre Frequency in THz (Max Length 11,
                 resolution 1 MHz)";
            }
            leaf channel-width {
              type string {
                length "1..9";
              }
              description
                "Channel Width in GHz (Max Length 9,
                 resolution 1 MHz)";
            }
          }
        }
      }
    }
    container terminal-amplifier {
      description
        "Terminal Amplifier Configuration";
      container olt-grid-mode {
        description
          "Grid Mode Type";
        container olt-channel-identifier-tables {
          description
            "Flex Grid";
          list olt-channel-identifier-table {
            key "channel-number";
            description
              "Channel Identifier";
            container olt-channel-definition {
              description
                "Channel Definition";
              leaf centre-frequency {
                type string {
                  length "1..11";
                }
                description
                  "Centre Frequency in THz (Max Length 11,
                   resolution 1 MHz)";
              }
              leaf channel-width {
                type string {
                  length "1..9";
                }
                description
                  "Channel Width in GHz (Max Length 9,
                   resolution 1 MHz)";
              }
            }
            leaf olt-channel-force-ase-loading {
              type empty;
              description
                "Force the ASE Loading per channel";
            }
            leaf olt-channel-ase-loading-disable {
              type empty;
              description
                "Disable the ASE Loading per channel";
            }
            leaf channel-number {
              type uint32;
              description
                "Channel Number";
            }
          }
        }
      }
      leaf olt-module-ase-guard-band-width {
        type string {
          length "1..7";
        }
        description
          "ASE Guard Band Width in GHz";
      }
      leaf olt-module-ase-loading-disable {
        type empty;
        description
          "Disable the ASE Loading on Module level";
      }
      leaf olt-module-channel-hold-off-time {
        type uint32 {
          range "1..600";
        }
        units "second";
        description
          "Channel Restoration Hold Off Timer between 1
           and 600 seconds, NO default";
      }
      leaf olt-static-ase-disable {
        type empty;
        description
          "Disable the Static ASE";
      }
      leaf olt-module-ase-tx-voa {
        type uint32 {
          range "0..200";
        }
        description
          "ASE TX Voa Attenuation Setpoint";
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
