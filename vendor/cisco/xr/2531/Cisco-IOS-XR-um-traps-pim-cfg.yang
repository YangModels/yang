module Cisco-IOS-XR-um-traps-pim-cfg {
  namespace "http://cisco.com/ns/yang/Cisco-IOS-XR-um-traps-pim-cfg";
  prefix um-traps-pim-cfg;

  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps-pim package configuration.
     
     This YANG module augments the
     modules with configuration data.
     
     Copyright (c) 2020-2025 by Cisco Systems, Inc., and/or its affiliates.
     All rights reserved.";

  revision 2022-07-11 {
    description
      "Added missing description statement to nodes";
    semver:module-version "1.0.0";
  }
  revision 2020-12-03 {
    description
      "Initial release";
    semver:module-version "1.0.0";
  }

  augment "/a1:snmp-server/a1:traps" {
    description
      "This augment extends snmp-server traps nodes
       configuration";
    container pim {
      description
        "Enable SNMP PIM traps";
      container neighbor-change {
        presence "Indicates a neighbor-change node is configured.";
        description
          "Enable neighbor change trap";
      }
      container interface-state-change {
        presence "Indicates a interface-state-change node is configured.";
        description
          "Enable interface state change trap";
      }
      container invalid-message-received {
        presence "Indicates a invalid-message-received node is configured.";
        description
          "Enable invalid message received trap";
      }
      container rp-mapping-change {
        presence "Indicates a rp-mapping-change node is configured.";
        description
          "Enable rp mapping change trap";
      }
    }
  }
}
