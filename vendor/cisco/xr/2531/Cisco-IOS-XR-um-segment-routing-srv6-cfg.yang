module Cisco-IOS-XR-um-segment-routing-srv6-cfg {
  namespace "http://cisco.com/ns/yang/Cisco-IOS-XR-um-segment-routing-srv6-cfg";
  prefix um-segment-routing-srv6-cfg;

  import Cisco-IOS-XR-types {
    prefix xr;
  }
  import ietf-inet-types {
    prefix inet;
  }
  import Cisco-IOS-XR-um-segment-routing-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-srv6 package configuration.
     
     This YANG module augments the
     modules with configuration data.
     
     Copyright (c) 2021-2025 by Cisco Systems, Inc., and/or its affiliates.
     All rights reserved.";

  revision 2022-05-31 {
    description
      "Model Deprecated";
    semver:module-version "1.1.0";
  }
  revision 2021-01-25 {
    description
      "Initial release";
    semver:module-version "1.0.0";
  }

  augment "/a1:segment-routing" {
    container srv6 {
      presence "Indicates a srv6 node is configured.";
      status deprecated;
      description
        "Segment Routing with IPv6 dataplane";
      container logging {
        description
          "Enable logging";
        container locator {
          description
            "Configure logging for locator events";
          container status {
            presence "Indicates a status node is configured.";
            description
              "Enable logging for locator status changes";
          }
        }
      }
      container sid {
        description
          "Configure SID parameters";
        leaf holdtime {
          type uint32 {
            range "0..60" {
              description
                "Time (in minutes)";
            }
          }
          description
            "Configure SID holdtime for a stale/freed SID";
        }
      }
      container encapsulation {
        description
          "Configure encapsulation parameters";
        leaf source-address {
          type inet:ipv6-address-no-zone;
          description
            "Specify Source address";
        }
        leaf hop-limit {
          type uint32 {
            range "1..255" {
              description
                "Specify the count for hop-limit";
            }
          }
          must "not(../propagate-hop-limit)";
          description
            "Control Hop-limit field setting on IPv6 header";
        }
        container propagate-hop-limit {
          must "not(../hop-limit)";
          presence "Indicates a propagate-hop-limit node is configured.";
          description
            "Propagate IP TTL/Hop-limit";
        }
        leaf traffic-class {
          type uint32 {
            range "0..255" {
              description
                "Specify the value (as 2 hexadecimal nibbbles) for traffic class";
            }
          }
          must "not(../propagate-traffic-class)";
          description
            "Control traffic-class field setting on IPv6 header";
        }
        container propagate-traffic-class {
          must "not(../traffic-class)";
          presence "Indicates a propagate-traffic-class node is configured.";
          description
            "Set traffic class value by propagation (from incoming packet/frame)";
        }
        container evpn {
          description
            "Control EVPN related SRv6 encapsulation parameters";
          leaf next-header {
            type enumeration {
              enum "59" {
                value 59;
                description
                  "Protocol number 59 (deprecated)";
              }
            }
            description
              "Specify protocol number to use in the Next-header field of IPv6 or SRH header";
          }
        }
      }
      container locators {
        description
          "Configure Locators";
        list locator {
          key "locator-name";
          description
            "Configure a Locator";
          leaf locator-name {
            type xr:Cisco-ios-xr-string {
              length "1..58" {
                description
                  "Specify locator name";
              }
              pattern "[a-z0-9A-Z][a-z0-9A-Z_.:]*";
            }
            description
              "Configure a Locator";
          }
          container micro-segment {
            description
              "Configure micro-segments (uSID) related parameters";
            container behavior {
              description
                "Specify Locator's behavior";
              container unode {
                description
                  "uNode type";
                container shift-only {
                  must "not(../psp-usd)";
                  presence "Indicates a shift-only node is configured.";
                  description
                    "uNode (shift only)";
                }
                container psp-usd {
                  must "not(../shift-only)";
                  presence "Indicates a psp-usd node is configured.";
                  description
                    "uNode PSP/USD variant";
                }
              }
            }
          }
          container prefix {
            description
              "Configure locator's prefix value";
            leaf address {
              type inet:ipv6-address-no-zone;
              must "../length";
              description
                "Configure locator's prefix value";
            }
            leaf length {
              type uint32 {
                range "32..112";
              }
              must "../address";
              description
                "Configure locator's prefix value";
            }
          }
          leaf algorithm {
            type uint32 {
              range "128..255" {
                description
                  "Algorithm ID";
              }
            }
            description
              "Algorithm associated with the locator";
          }
          container anycast {
            presence "Indicates a anycast node is configured.";
            description
              "Specify locator as an anycast type";
          }
        }
      }
      container micro-segment {
        description
          "Configure micro-segment parameters";
        container merge-overlay-underlay-sids {
          presence "Indicates a merge-overlay-underlay-sids node is configured.";
          description
            "Enable merge mode for SIDs from overlay and underlay";
        }
      }
    }
  }
}
