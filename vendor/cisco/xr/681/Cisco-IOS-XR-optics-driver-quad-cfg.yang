module Cisco-IOS-XR-optics-driver-quad-cfg {
  namespace "http://cisco.com/ns/yang/Cisco-IOS-XR-optics-driver-quad-cfg";
  prefix optics-driver-quad-cfg;

  import cisco-semver {
    prefix semver;
  }
  import Cisco-IOS-XR-config-mda-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-driver-quad package configuration.
     
     This YANG module augments the
       Cisco-IOS-XR-config-mda-cfg
     module with configuration data.
     
     Copyright (c) 2013-2021 by Cisco Systems, Inc.
     All rights reserved.";

  revision 2021-03-02 {
    description
      "Augment MDA schema
       2020-06-17
         Changed type of NodeName from String to StringNodeID, added pathformat of quad as decimal in schema file";
    semver:module-version "2.0.0";
  }
  revision 2019-04-05 {
    description
      "Establish semantic version baseline.";
    semver:module-version "1.0.1";
  }
  revision 2018-07-21 {
    description
      "Schema added.";
  }
  revision 2015-11-09 {
    description
      "IOS XR 6.0 revision.";
  }

  grouping QUAD-CONFIG-TABLE {
    description
      "Common node of active-node, preconfigured-node";
    container quad-configs {
      description
        "quad configuration";
      list quad-config {
        key "id1";
        description
          "none";
        container mode {
          description
            "select mode 10g or 25g for a quad(group of 4
             ports).";
          leaf speed {
            type string;
            description
              "speed 10g or 25g";
          }
        }
        leaf id1 {
          type uint32;
          description
            "none";
        }
      }
    }
  }

  augment "/a1:preconfigured-nodes/a1:preconfigured-node" {
    description
      "This augment extends the configuration data of
       'Cisco-IOS-XR-config-mda-cfg'";
    uses QUAD-CONFIG-TABLE;
  }
  augment "/a1:active-nodes/a1:active-node" {
    description
      "This augment extends the configuration data of
       'Cisco-IOS-XR-config-mda-cfg'";
    uses QUAD-CONFIG-TABLE;
  }
}
