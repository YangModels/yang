module Cisco-IOS-XR-plat-chas-invmgr-oper {
  namespace "http://cisco.com/ns/yang/Cisco-IOS-XR-plat-chas-invmgr-oper";
  prefix plat-chas-invmgr-oper;

  import Cisco-IOS-XR-types {
    prefix xr;
  }
  import cisco-semver {
    prefix semver;
  }
  include Cisco-IOS-XR-plat-chas-invmgr-oper-sub2 {
    revision-date 2019-08-14;
  }
  include Cisco-IOS-XR-plat-chas-invmgr-oper-sub1 {
    revision-date 2019-08-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR plat-chas-invmgr package operational data.
     
     This module contains definitions
     for the following management objects:
       platform: Platform information
       platform-inventory: Inventory operational data
     
     Copyright (c) 2013-2019 by Cisco Systems, Inc.
     All rights reserved.";

  revision 2019-08-14 {
    description
      "Added node-name leaf in platform.bag.";
    semver:module-version "1.0.0";
  }
  revision 2019-04-05 {
    description
      "Establish semantic version baseline.";
  }
  revision 2018-01-22 {
    description
      "Fixing incorrect spelling for node-description in module.";
  }
  revision 2015-01-07 {
    description
      "IOS XR 5.3.1 revision.";
  }

  grouping STATE {
    description
      "Common node of instance, slot";
    container state {
      description
        "State information";
      uses PLATFORM-INFO;
    }
  }

  grouping PORT-SLOT-TABLE {
    description
      "Common node of card, module";
    container port-slots {
      description
        "Table of port slots";
      list port-slot {
        key "name";
        description
          "Port slot number";
        container port {
          description
            "Port";
          uses INVENTORY-COMMON-ATTRIBUTES;
        }
        leaf name {
          type xr:Cisco-ios-xr-string;
          description
            "Port slot name";
        }
        uses INVENTORY-COMMON-SENSOR-TABLE;
        uses INVENTORY-COMMON-ATTRIBUTES;
      }
    }
  }

  grouping SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses INV-PROCESSOR;
              }
              container motherboard-information {
                description
                  "MotherboardInformation";
                uses INV-XML-MOTHERBOARD-INFO;
              }
              container bootflash-information {
                description
                  "BootflashInformation";
                uses INV-BOOTFLASH;
              }
              container disk-information {
                description
                  "DiskInformation";
                uses INV-XML-DISK-INFO;
              }
            }
            container sub-slots {
              description
                "Table of subslots";
              list sub-slot {
                key "name";
                description
                  "Subslot number";
                container module {
                  description
                    "Module of a subslot";
                  uses PORT-SLOT-TABLE;
                  uses INVENTORY-COMMON-SENSOR-TABLE;
                  uses INVENTORY-COMMON-ATTRIBUTES;
                }
                leaf name {
                  type xr:Cisco-ios-xr-string;
                  description
                    "Subslot name";
                }
                uses INVENTORY-COMMON-ATTRIBUTES;
              }
            }
            container hw-components {
              description
                "Table of  HW components ";
              list hw-component {
                key "name";
                description
                  "HW component number";
                leaf name {
                  type xr:Cisco-ios-xr-string;
                  description
                    "HW component name";
                }
                uses INVENTORY-COMMON-SENSOR-TABLE;
                uses INVENTORY-COMMON-ATTRIBUTES;
              }
            }
            container modules {
              description
                "Table of modules";
              list module {
                key "module-name";
                description
                  "A module";
                container sub-modules {
                  description
                    "Table of Sub Module components ";
                  list sub-module {
                    key "name";
                    description
                      "Sub Module component number";
                    container sub-module-l2s {
                      description
                        "Table of Sub Module components ";
                      list sub-module-l2 {
                        key "name";
                        description
                          "Sub Module component number";
                        container sub-module-l3s {
                          description
                            "Table of Sub Module components ";
                          list sub-module-l3 {
                            key "name";
                            description
                              "Sub Module component number";
                            container sub-module-l4s {
                              description
                                "Table of Sub Module components ";
                              list sub-module-l4 {
                                key "name";
                                description
                                  "Sub Module component number";
                                container sub-module-l5s {
                                  description
                                    "Table of Sub Module components ";
                                  list sub-module-l5 {
                                    key "name";
                                    description
                                      "Sub Module component number";
                                    leaf name {
                                      type xr:Cisco-ios-xr-string;
                                      description
                                        "HW component name";
                                    }
                                    uses INVENTORY-EXT2-OPER-SENSOR-TABLE;
                                    uses INVENTORY-EXT2-OPER-ATTRIBUTES;
                                    uses INVENTORY-EXT2-OPER-HW-COMPONENT-TABLE;
                                  }
                                }
                                leaf name {
                                  type xr:Cisco-ios-xr-string;
                                  description
                                    "HW component name";
                                }
                                uses INVENTORY-EXT2-OPER-SENSOR-TABLE;
                                uses INVENTORY-EXT2-OPER-ATTRIBUTES;
                                uses INVENTORY-EXT2-OPER-HW-COMPONENT-TABLE;
                              }
                            }
                            container ports {
                              description
                                "Table of spirit port slots";
                              list port {
                                key "name";
                                description
                                  "Port number";
                                leaf name {
                                  type xr:Cisco-ios-xr-string;
                                  description
                                    "Port name";
                                }
                                uses INVENTORY-EXT2-OPER-ATTRIBUTES;
                              }
                            }
                            leaf name {
                              type xr:Cisco-ios-xr-string;
                              description
                                "HW component name";
                            }
                            uses INVENTORY-EXT2-OPER-SENSOR-TABLE;
                            uses INVENTORY-EXT2-OPER-ATTRIBUTES;
                            uses INVENTORY-EXT2-OPER-HW-COMPONENT-TABLE;
                          }
                        }
                        leaf name {
                          type xr:Cisco-ios-xr-string;
                          description
                            "HW component name";
                        }
                        uses INVENTORY-EXT2-OPER-SENSOR-TABLE;
                        uses INVENTORY-EXT2-OPER-ATTRIBUTES;
                        uses INVENTORY-EXT2-OPER-HW-COMPONENT-TABLE;
                      }
                    }
                    container ports {
                      description
                        "Table of spirit port slots";
                      list port {
                        key "name";
                        description
                          "Port number";
                        container port-modules {
                          description
                            "Table of Module components ";
                          list port-module {
                            key "name";
                            description
                              "POrt Module component number";
                            leaf name {
                              type xr:Cisco-ios-xr-string;
                              description
                                "module name";
                            }
                            uses ATTRIBUTES;
                          }
                        }
                        leaf name {
                          type xr:Cisco-ios-xr-string;
                          description
                            "Port name";
                        }
                        uses ATTRIBUTES;
                        uses HW-COMPONENT-TABLE;
                      }
                    }
                    leaf name {
                      type xr:Cisco-ios-xr-string;
                      description
                        "HW component name";
                    }
                    uses SENSOR-TABLE;
                    uses ATTRIBUTES;
                    uses HW-COMPONENT-TABLE;
                  }
                }
                leaf module-name {
                  type xr:Cisco-ios-xr-string;
                  description
                    "Module name";
                }
                uses SENSOR-TABLE;
                uses ATTRIBUTES;
                uses HW-COMPONENT-TABLE;
              }
            }
            leaf name {
              type xr:Cisco-ios-xr-string;
              description
                "Card name";
            }
            uses PORT-SLOT-TABLE;
            uses INVENTORY-COMMON-SENSOR-TABLE;
            uses INVENTORY-COMMON-ATTRIBUTES;
          }
        }
        leaf name {
          type xr:Cisco-ios-xr-string;
          description
            "Slot name";
        }
        uses INVENTORY-COMMON-ATTRIBUTES;
      }
    }
  }

  grouping PLATFORM-COMMON-SLOT-TABLE {
    description
      "Common node of rack, rackCommon node of rack,
       rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses STATE;
          }
        }
        container vm {
          description
            "VM information";
          uses VM-INFO;
        }
        leaf slot-name {
          type xr:Cisco-ios-xr-string;
          description
            "Slot name";
        }
        uses STATE;
      }
    }
  }

  grouping SENSOR-TABLE {
    description
      "Common node of module, sub-module, hw-component";
    container sensors {
      description
        "Table of sensors";
      list sensor {
        key "name";
        description
          "Sensor number";
        leaf name {
          type xr:Cisco-ios-xr-string;
          description
            "Sensor name";
        }
        uses ATTRIBUTES;
      }
    }
  }

  grouping INVENTORY-EXT2-OPER-SENSOR-TABLE {
    description
      "Common node of module, sub-module,
       hw-componentCommon node of hw-component,
       sub-module-l2, sub-module-l3, sub-module-l4,
       sub-module-l5";
    container sensors {
      description
        "Table of sensors";
      list sensor {
        key "name";
        description
          "Sensor number";
        leaf name {
          type xr:Cisco-ios-xr-string;
          description
            "Sensor name";
        }
        uses INVENTORY-EXT2-OPER-ATTRIBUTES;
      }
    }
  }

  grouping INVENTORY-COMMON-SENSOR-TABLE {
    description
      "Common node of module, sub-module,
       hw-componentCommon node of hw-component,
       sub-module-l2, sub-module-l3, sub-module-l4,
       sub-module-l5Common node of card, module,
       hw-component, port-slot";
    container sensors {
      description
        "Table of sensors";
      list sensor {
        key "name";
        description
          "Sensor number";
        leaf name {
          type xr:Cisco-ios-xr-string;
          description
            "Sensor name";
        }
        uses INVENTORY-COMMON-ATTRIBUTES;
      }
    }
  }

  grouping HW-COMPONENT-TABLE {
    description
      "Common node of module, sub-module, port";
    container hw-components {
      description
        "Table of HW components ";
      list hw-component {
        key "name";
        description
          "HW component number";
        leaf name {
          type xr:Cisco-ios-xr-string;
          description
            "HW component name";
        }
        uses SENSOR-TABLE;
        uses ATTRIBUTES;
      }
    }
  }

  grouping INVENTORY-EXT2-OPER-HW-COMPONENT-TABLE {
    description
      "Common node of module, sub-module, portCommon
       node of sub-module-l2, sub-module-l3,
       sub-module-l4, sub-module-l5";
    container hw-components {
      description
        "Table of HW components ";
      list hw-component {
        key "name";
        description
          "HW component number";
        leaf name {
          type xr:Cisco-ios-xr-string;
          description
            "HW component name";
        }
        uses INVENTORY-EXT2-OPER-SENSOR-TABLE;
        uses INVENTORY-EXT2-OPER-ATTRIBUTES;
      }
    }
  }

  grouping INVENTORY-EXT3-OPER-HW-COMPONENT-TABLE {
    description
      "Common node of module, sub-module, portCommon
       node of sub-module-l2, sub-module-l3,
       sub-module-l4, sub-module-l5Common node of
       backplane, module";
    container hw-components {
      description
        "Table of  HW components ";
      list hw-component {
        key "name";
        description
          "HW component number";
        leaf name {
          type xr:Cisco-ios-xr-string;
          description
            "HW component name";
        }
        uses INVENTORY-EXT3-OPER-ATTRIBUTES;
      }
    }
  }

  grouping ATTRIBUTES {
    description
      "Common node of module, sub-module, sensor,
       hw-component, port, port-module";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-EXT2-OPER-ATTRIBUTES {
    description
      "Common node of module, sub-module, sensor,
       hw-component, port, port-moduleCommon node of
       sub-module-l2, sub-module-l3, sub-module-l4,
       sub-module-l5, sensor, hw-component, port";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-EXT3-OPER-ATTRIBUTES {
    description
      "Common node of module, sub-module, sensor,
       hw-component, port, port-moduleCommon node of
       sub-module-l2, sub-module-l3, sub-module-l4,
       sub-module-l5, sensor, hw-component, portCommon
       node of backplane, module, hw-component";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-COMMON-ATTRIBUTES {
    description
      "Common node of module, sub-module, sensor,
       hw-component, port, port-moduleCommon node of
       sub-module-l2, sub-module-l3, sub-module-l4,
       sub-module-l5, sensor, hw-component, portCommon
       node of backplane, module, hw-componentCommon
       node of rack, rack, slot, card, sub-slot, module,
       port-slot, hw-component, sensor, port";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping BACKPLANE-TABLE {
    description
      "Common node of rack, rack";
    container backplanes {
      description
        "Table of backplane";
      list backplane {
        key "name";
        description
          "Backplane name";
        container modules {
          description
            "Table of modules";
          list module {
            key "module-name";
            description
              "A module";
            leaf module-name {
              type xr:Cisco-ios-xr-string;
              description
                "Module name";
            }
            uses INVENTORY-EXT3-OPER-ATTRIBUTES;
            uses INVENTORY-EXT3-OPER-HW-COMPONENT-TABLE;
          }
        }
        leaf name {
          type xr:Cisco-ios-xr-string;
          description
            "Backplane name";
        }
        uses INVENTORY-EXT3-OPER-ATTRIBUTES;
        uses INVENTORY-EXT3-OPER-HW-COMPONENT-TABLE;
      }
    }
  }

  container platform {
    config false;
    description
      "Platform information";
    container racks {
      description
        "Table of racks";
      list rack {
        key "rack-name";
        description
          "Rack name";
        leaf rack-name {
          type xr:Cisco-ios-xr-string;
          description
            "Rack name";
        }
        uses PLATFORM-COMMON-SLOT-TABLE;
      }
    }
  }
  container platform-inventory {
    config false;
    description
      "Inventory operational data";
    container racks {
      description
        "Table of racks";
      list rack {
        key "name";
        description
          "Rack name";
        leaf name {
          type xr:Cisco-ios-xr-string;
          description
            "Rack name";
        }
        uses SLOT-TABLE;
        uses INVENTORY-COMMON-ATTRIBUTES;
        uses BACKPLANE-TABLE;
      }
    }
  }
}
