module Cisco-IOS-XR-ncs5k-fea-pfilter-nonatomic-cfg {
  namespace "http://cisco.com/ns/yang/Cisco-IOS-XR-ncs5k-fea-pfilter-nonatomic-cfg";
  prefix ncs5k-fea-pfilter-nonatomic-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs5k-fea-pfilter-nonatomic package configuration.
     
     This module contains definitions
     for the following management objects:
       hardware: Hardware
     
     Copyright (c) 2013-2019 by Cisco Systems, Inc.
     All rights reserved.";

  revision 2019-04-05 {
    description
      "Establish semantic version baseline.";
    semver:module-version "1.0.0";
  }
  revision 2016-09-01 {
    description
      "Implementing Conf Yang Model for Non-Atomic ACL";
  }
  revision 2015-11-09 {
    description
      "IOS XR 6.0 revision.";
  }

  typedef Atomic-disable-dflt-actn {
    type enumeration {
      enum "default-action-deny" {
        value 1;
        description
          "Drops traffic during modification";
      }
      enum "default-action-permit" {
        value 2;
        description
          "Forward traffic during modification";
      }
    }
    description
      "Atomic disable dflt actn";
  }

  container hardware {
    description
      "Hardware";
    container access-list {
      description
        "Access-list option";
      leaf atomic-disable {
        type Atomic-disable-dflt-actn;
        description
          "Specify Option for Atomic disable";
      }
    }
  }
}
