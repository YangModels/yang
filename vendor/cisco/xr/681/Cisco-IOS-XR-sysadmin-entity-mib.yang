module Cisco-IOS-XR-sysadmin-entity-mib {
  namespace "http://www.cisco.com/ns/yang/Cisco-IOS-XR-sysadmin-entity-mib";
  prefix ENTITY_MIB;

  import ietf-yang-types {
    prefix yang;
  }
  import tailf-common {
    prefix tailf;
  }
  import SNMPv2-TC {
    prefix SNMPv2-TC;
  }
  import SNMP-FRAMEWORK-MIB {
    prefix SNMP-FRAMEWORK-MIB;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2015-2020 by Cisco Systems, Inc.
     All rights reserved.";

  revision 2019-04-15 {
    description
      "Establish semantic version baseline.";
    semver:module-version "1.0.0";
  }
  revision 2017-04-12 {
    description
      "Changed namespace and module name";
  }
  revision 1999-12-07 {
    description
      "";
  }

  typedef PhysicalIndex {
    type int32 {
      range "1 .. 2147483647";
    }
  }

  typedef PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef SnmpEngineIdOrNone {
    type tailf:hex-list;
  }

  typedef entPhysicalContainedInType {
    type int32 {
      range "0 .. 2147483647";
    }
  }

  typedef entPhysicalParentRelPosType {
    type int32 {
      range "-1 .. 2147483647";
    }
  }

  typedef entPhysicalSerialNumType {
    type string {
      length "min .. 32";
    }
  }

  typedef entPhysicalAliasType {
    type string {
      length "min .. 32";
    }
  }

  typedef entPhysicalAssetIDType {
    type string {
      length "min .. 32";
    }
  }

  typedef entLogicalIndexType {
    type int32 {
      range "1 .. 2147483647";
    }
  }

  typedef entLogicalCommunityType {
    type tailf:hex-list;
  }

  typedef entAliasLogicalIndexOrZeroType {
    type int32 {
      range "0 .. 2147483647";
    }
  }
  tailf:id "http://tail-f.com/ns/mibs/ENTITY-MIB/199912070000Z";
  tailf:snmp-mib-module-name "ENTITY-MIB";

  container ENTITY-MIB {
    container entityGeneral {
      config false;
      tailf:snmp-oid "1.3.6.1.2.1.47.1.4";
      leaf entLastChangeTime {
        type yang:timestamp;
        config false;
        tailf:snmp-oid "1.3.6.1.2.1.47.1.4.1";
      }
    }
    container entPhysicalTable {
      config false;
      list entPhysicalEntry {
        key "entPhysicalIndex";
        config false;
        tailf:sort-order "snmp";
        tailf:snmp-oid "1.3.6.1.2.1.47.1.1.1";
        leaf entPhysicalIndex {
          type PhysicalIndex;
          tailf:snmp-oid "1.3.6.1.2.1.47.1.1.1.1.1";
        }
        leaf entPhysicalDescr {
          type SNMP-FRAMEWORK-MIB:SnmpAdminString;
          config false;
          tailf:snmp-oid "1.3.6.1.2.1.47.1.1.1.1.2";
        }
        leaf entPhysicalVendorType {
          type SNMPv2-TC:AutonomousType;
          config false;
          tailf:snmp-oid "1.3.6.1.2.1.47.1.1.1.1.3";
        }
        leaf entPhysicalContainedIn {
          type entPhysicalContainedInType;
          config false;
          tailf:snmp-oid "1.3.6.1.2.1.47.1.1.1.1.4";
        }
        leaf entPhysicalClass {
          type PhysicalClass;
          config false;
          tailf:snmp-oid "1.3.6.1.2.1.47.1.1.1.1.5";
        }
        leaf entPhysicalParentRelPos {
          type entPhysicalParentRelPosType;
          config false;
          tailf:snmp-oid "1.3.6.1.2.1.47.1.1.1.1.6";
        }
        leaf entPhysicalName {
          type SNMP-FRAMEWORK-MIB:SnmpAdminString;
          config false;
          tailf:snmp-oid "1.3.6.1.2.1.47.1.1.1.1.7";
        }
        leaf entPhysicalHardwareRev {
          type SNMP-FRAMEWORK-MIB:SnmpAdminString;
          config false;
          tailf:snmp-oid "1.3.6.1.2.1.47.1.1.1.1.8";
        }
        leaf entPhysicalFirmwareRev {
          type SNMP-FRAMEWORK-MIB:SnmpAdminString;
          config false;
          tailf:snmp-oid "1.3.6.1.2.1.47.1.1.1.1.9";
        }
        leaf entPhysicalSoftwareRev {
          type SNMP-FRAMEWORK-MIB:SnmpAdminString;
          config false;
          tailf:snmp-oid "1.3.6.1.2.1.47.1.1.1.1.10";
        }
        leaf entPhysicalSerialNum {
          type entPhysicalSerialNumType;
          config false;
          tailf:snmp-oid "1.3.6.1.2.1.47.1.1.1.1.11";
        }
        leaf entPhysicalMfgName {
          type SNMP-FRAMEWORK-MIB:SnmpAdminString;
          config false;
          tailf:snmp-oid "1.3.6.1.2.1.47.1.1.1.1.12";
        }
        leaf entPhysicalModelName {
          type SNMP-FRAMEWORK-MIB:SnmpAdminString;
          config false;
          tailf:snmp-oid "1.3.6.1.2.1.47.1.1.1.1.13";
        }
        leaf entPhysicalAlias {
          type entPhysicalAliasType;
          config false;
          tailf:snmp-oid "1.3.6.1.2.1.47.1.1.1.1.14";
        }
        leaf entPhysicalAssetID {
          type entPhysicalAssetIDType;
          config false;
          tailf:snmp-oid "1.3.6.1.2.1.47.1.1.1.1.15";
        }
        leaf entPhysicalIsFRU {
          type SNMPv2-TC:TruthValue;
          config false;
          tailf:snmp-oid "1.3.6.1.2.1.47.1.1.1.1.16";
        }
      }
    }
    container entLogicalTable {
      config false;
      list entLogicalEntry {
        key "entLogicalIndex";
        config false;
        tailf:sort-order "snmp";
        tailf:snmp-oid "1.3.6.1.2.1.47.1.2.1";
        leaf entLogicalIndex {
          type entLogicalIndexType;
          tailf:snmp-oid "1.3.6.1.2.1.47.1.2.1.1.1";
        }
        leaf entLogicalDescr {
          type SNMP-FRAMEWORK-MIB:SnmpAdminString;
          config false;
          tailf:snmp-oid "1.3.6.1.2.1.47.1.2.1.1.2";
        }
        leaf entLogicalType {
          type SNMPv2-TC:AutonomousType;
          config false;
          tailf:snmp-oid "1.3.6.1.2.1.47.1.2.1.1.3";
        }
        leaf entLogicalCommunity {
          type entLogicalCommunityType;
          config false;
          tailf:snmp-oid "1.3.6.1.2.1.47.1.2.1.1.4";
        }
        leaf entLogicalTAddress {
          type SNMPv2-TC:TAddress;
          config false;
          tailf:snmp-oid "1.3.6.1.2.1.47.1.2.1.1.5";
        }
        leaf entLogicalTDomain {
          type SNMPv2-TC:TDomain;
          config false;
          tailf:snmp-oid "1.3.6.1.2.1.47.1.2.1.1.6";
        }
        leaf entLogicalContextEngineID {
          type SnmpEngineIdOrNone;
          config false;
          tailf:snmp-oid "1.3.6.1.2.1.47.1.2.1.1.7";
        }
        leaf entLogicalContextName {
          type SNMP-FRAMEWORK-MIB:SnmpAdminString;
          config false;
          tailf:snmp-oid "1.3.6.1.2.1.47.1.2.1.1.8";
        }
      }
    }
    container entLPMappingTable {
      config false;
      list entLPMappingEntry {
        key "entLogicalIndex entLPPhysicalIndex";
        config false;
        tailf:sort-order "snmp";
        tailf:snmp-oid "1.3.6.1.2.1.47.1.3.1";
        leaf entLogicalIndex {
          type entLogicalIndexType;
          tailf:snmp-oid "1.3.6.1.2.1.47.1.2.1.1.1";
        }
        leaf entLPPhysicalIndex {
          type PhysicalIndex;
          tailf:snmp-oid "1.3.6.1.2.1.47.1.3.1.1.1";
        }
      }
    }
    container entAliasMappingTable {
      config false;
      list entAliasMappingEntry {
        key "entPhysicalIndex entAliasLogicalIndexOrZero";
        config false;
        tailf:sort-order "snmp";
        tailf:snmp-oid "1.3.6.1.2.1.47.1.3.2";
        leaf entPhysicalIndex {
          type PhysicalIndex;
          tailf:snmp-oid "1.3.6.1.2.1.47.1.1.1.1.1";
        }
        leaf entAliasLogicalIndexOrZero {
          type entAliasLogicalIndexOrZeroType;
          tailf:snmp-oid "1.3.6.1.2.1.47.1.3.2.1.1";
        }
        leaf entAliasMappingIdentifier {
          type SNMPv2-TC:RowPointer;
          config false;
          tailf:snmp-oid "1.3.6.1.2.1.47.1.3.2.1.2";
        }
      }
    }
    container entPhysicalContainsTable {
      config false;
      list entPhysicalContainsEntry {
        key "entPhysicalIndex entPhysicalChildIndex";
        config false;
        tailf:sort-order "snmp";
        tailf:snmp-oid "1.3.6.1.2.1.47.1.3.3";
        leaf entPhysicalIndex {
          type PhysicalIndex;
          tailf:snmp-oid "1.3.6.1.2.1.47.1.1.1.1.1";
        }
        leaf entPhysicalChildIndex {
          type PhysicalIndex;
          tailf:snmp-oid "1.3.6.1.2.1.47.1.3.3.1.1";
        }
      }
    }
  }
}
