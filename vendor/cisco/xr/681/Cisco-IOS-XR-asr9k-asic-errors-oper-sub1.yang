submodule Cisco-IOS-XR-asr9k-asic-errors-oper-sub1 {
  belongs-to Cisco-IOS-XR-asr9k-asic-errors-oper {
    prefix Cisco-IOS-XR-asr9k-asic-errors-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-asic-errors package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping HFR-SUMMARY-DATA {
    description
      "HFR SUMMARY DATA";
    leaf instance {
      type uint32;
      description
        "instance";
    }
    leaf num-nodes {
      type uint32;
      description
        "num nodes";
    }
    leaf crc-err-count {
      type uint32;
      description
        "crc err count";
    }
    leaf sbe-err-count {
      type uint32;
      description
        "sbe err count";
    }
    leaf mbe-err-count {
      type uint32;
      description
        "mbe err count";
    }
    leaf par-err-count {
      type uint32;
      description
        "par err count";
    }
    leaf gen-err-count {
      type uint32;
      description
        "gen err count";
    }
    leaf reset-err-count {
      type uint32;
      description
        "reset err count";
    }
    leaf-list node-key {
      type uint32;
      description
        "node key";
    }
  }

  grouping HFR-ASIC-SUMMARY {
    description
      "HFR ASIC SUMMARY";
    list sum-data {
      description
        "sum data";
      uses HFR-SUMMARY-DATA;
    }
  }
}
