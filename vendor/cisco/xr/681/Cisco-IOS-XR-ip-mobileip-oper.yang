module Cisco-IOS-XR-ip-mobileip-oper {
  namespace "http://cisco.com/ns/yang/Cisco-IOS-XR-ip-mobileip-oper";
  prefix ip-mobileip-oper;

  import ietf-inet-types {
    prefix inet;
  }
  import Cisco-IOS-XR-types {
    prefix xr;
  }
  import cisco-semver {
    prefix semver;
  }
  include Cisco-IOS-XR-ip-mobileip-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-mobileip package operational data.
     
     This module contains definitions
     for the following management objects:
       pmipv6: Proxy Mobile IPv6
     
     Copyright (c) 2013-2019 by Cisco Systems, Inc.
     All rights reserved.";

  revision 2019-04-05 {
    description
      "Establish semantic version baseline.";
    semver:module-version "1.0.1";
  }
  revision 2016-03-10 {
    description
      "Initial version";
  }
  revision 2015-11-09 {
    description
      "IOS XR 6.0 revision.";
  }

  container pmipv6 {
    config false;
    description
      "Proxy Mobile IPv6";
    container lma {
      description
        "None";
      container statistics {
        description
          "None";
        container customer-statistics {
          description
            "Table of CustomerStatistics";
          list customer-statistic {
            key "customer-name";
            description
              "Customer statistics";
            leaf customer-name {
              type xr:Cisco-ios-xr-string;
              description
                "Customer Name";
            }
            uses PMIPV6-SHOW-LMA-CUST-STATS-BD;
          }
        }
        container license {
          description
            "LMA License Statistics";
          uses PMIPV6-SHOW-LMA-LICENSE-STATS-BD;
        }
        container global {
          description
            "Global Statistics";
          uses PMIPV6-SHOW-LMA-STATS-BD;
        }
        container mag-statistics {
          description
            "Table of MAGStatistics";
          list mag-statistic {
            key "mag-name";
            description
              "Peer MAG statistics";
            leaf mag-name {
              type xr:Cisco-ios-xr-string;
              description
                "Peer MAG Name";
            }
            uses PMIPV6-SHOW-LMA-PEER-STATS-BD;
          }
        }
      }
      container bindings {
        description
          "Table of Binding";
        list binding {
          description
            "Binding Parameters";
          leaf mag-name {
            type xr:Cisco-ios-xr-string;
            description
              "Peer MAG ID";
          }
          leaf nai-string {
            type xr:Cisco-ios-xr-string;
            description
              "NAI String";
          }
          leaf imsi-string {
            type xr:Cisco-ios-xr-string;
            description
              "IMSI String";
          }
          leaf customer-name {
            type xr:Cisco-ios-xr-string;
            description
              "Customer String";
          }
          uses PMIPV6-SHOW-BINDING-BD;
        }
      }
      container heartbeats {
        description
          "Table of Heartbeat";
        list heartbeat {
          key "peer-addr";
          description
            "Heartbeat information";
          leaf peer-addr {
            type inet:ip-address-no-zone;
            description
              "IPv4 or IPv6 address";
          }
          uses PMIPV6-SHOW-HB-PATH-BD;
        }
      }
      container config-variables {
        description
          "Global Configuration Variables";
        container customer-variables {
          description
            "Table of CustomerVariables";
          list customer-variable {
            key "customer-name";
            description
              "Customer name string";
            leaf customer-name {
              type xr:Cisco-ios-xr-string;
              description
                "Customer name";
            }
            uses PMIPV6-SHOW-CUST-GLOBALS-BD;
          }
        }
        container global-variables {
          description
            "Global Configuration Variables";
          uses PMIPV6-SHOW-GLOBALS-BD;
        }
      }
    }
  }
}
