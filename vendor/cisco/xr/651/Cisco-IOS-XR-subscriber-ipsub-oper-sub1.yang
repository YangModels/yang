submodule Cisco-IOS-XR-subscriber-ipsub-oper-sub1 {
  belongs-to Cisco-IOS-XR-subscriber-ipsub-oper {
    prefix Cisco-IOS-XR-subscriber-ipsub-oper;
  }

  import ietf-inet-types {
    prefix inet;
  }
  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-ipsub package operational data.
     
     Copyright (c) 2013-2018 by Cisco Systems, Inc.
     All rights reserved.";

  revision 2015-11-09 {
    description
      "IOS XR 6.0 revision.";
  }

  typedef Ipsub-ma-parent-intf-vlan {
    type enumeration {
      enum "plain" {
        description
          "Plain";
      }
      enum "ambiguous" {
        description
          "Ambiguous";
      }
    }
    description
      "Access interface VLAN type";
  }

  typedef Ipsub-ma-parent-intf-state-data {
    type enumeration {
      enum "deleted" {
        description
          "Interface being deleted";
      }
      enum "down" {
        description
          "Interface operationally down";
      }
      enum "up" {
        description
          "Interface up";
      }
    }
    description
      "Parent interface state";
  }

  typedef Ipsub-ma-intf-state-data {
    type enumeration {
      enum "invalid" {
        value 0;
        description
          "Invalid state";
      }
      enum "initialized" {
        value 1;
        description
          "Initial state";
      }
      enum "session-creation-started" {
        value 2;
        description
          "Interface creation started";
      }
      enum "control-policy-executing" {
        value 3;
        description
          "Interface created in IM, AAA session start
           called";
      }
      enum "control-policy-executed" {
        value 4;
        description
          "AAA session created";
      }
      enum "session-features-applied" {
        value 5;
        description
          "Interface config activated";
      }
      enum "vrf-configured" {
        value 6;
        description
          "Interface address and VRF information received
           from IPv4";
      }
      enum "adding-adjacency" {
        value 7;
        description
          "VRF configuration received and interface config
           activated";
      }
      enum "adjacency-added" {
        value 8;
        description
          "Subscriber AIB adjacency added";
      }
      enum "up" {
        value 9;
        description
          "Session up";
      }
      enum "down" {
        value 10;
        description
          "Session down";
      }
      enum "address-family-down" {
        value 11;
        description
          "Session down in progress";
      }
      enum "address-family-down-complete" {
        value 12;
        description
          "Session down complete";
      }
      enum "disconnecting" {
        value 13;
        description
          "Session teardown in progress";
      }
      enum "disconnected" {
        value 14;
        description
          "Session disconnected";
      }
      enum "error" {
        value 15;
        description
          "Session in error state";
      }
    }
    description
      "Interface states";
  }

  typedef Ipsub-ma-intf-initiator-data {
    type enumeration {
      enum "dhcp" {
        value 0;
        description
          "Session creation via DHCP discover packet";
      }
      enum "packet-trigger" {
        value 1;
        description
          "Session creation via unclassified IPv4 packet";
      }
      enum "invalid-trigger" {
        value 2;
        description
          "Invalid Trigger";
      }
    }
    description
      "Ipsub ma intf initiator data";
  }

  grouping TOTAL-SOURCE {
    description
      "Session limits for all categories of all packet
       sources";
    leaf per-vlan {
      type uint32;
      description
        "Per-VLAN limit category";
    }
  }

  grouping UNCLASSIFIED-SOURCE {
    description
      "Session limits for all categories for
       unclassified-source packets";
    leaf per-vlan {
      type uint32;
      description
        "Per-VLAN limit category";
    }
  }

  grouping IPSUB-MA-PARENT-INTF-SESSION-LIMIT-DATA {
    description
      "Session limits for various categories by packet
       source";
    container unclassified-source {
      description
        "Unclassified source session limits";
      uses UNCLASSIFIED-SOURCE;
    }
    container total {
      description
        "All sources session limits";
      uses TOTAL-SOURCE;
    }
  }

  grouping IPSUB-MA-PARENT-INTF-INITIATOR-DATA {
    description
      "IPSUB MA PARENT INTF INITIATOR DATA";
    leaf is-configured {
      type boolean;
      description
        "Ture if the initiator is configred";
    }
    leaf unique-ip-check {
      type boolean;
      description
        "True if check for subscriber address
         uniquenessduring first sign of life is enabled";
    }
    leaf sessions {
      type uint32;
      description
        "Number of sessions currently up for each
         initiator";
    }
    leaf fsol-packets {
      type uint32;
      description
        "Number of first sign of life packets received
         for initiating protocol on this interface";
    }
    leaf fsol-bytes {
      type uint32;
      units "byte";
      description
        "Number of first sign of life bytes received for
         initiating protocol on this interface";
    }
    leaf fsol-dropped-packets {
      type uint32;
      description
        "Number of first sign of life packets received
         for initiating protocol on this interface that
         were dropped";
    }
    leaf fsol-dropped-bytes {
      type uint32;
      units "byte";
      description
        "Number of first sign of life bytes received for
         initiating protocol on this interface that were
         dropped";
    }
    leaf fsol-dropped-packets-flow {
      type uint32;
      description
        "Number of first sign of life packets received
         for initiating protocol on this interface that
         were dropped due to exceeding creation rate";
    }
    leaf fsol-dropped-packets-session-limit {
      type uint32;
      description
        "Number of first sign of life packets received
         for initiating protocol on this interface that
         were dropped due to exceeding one or more of the
         configured session limits";
    }
    leaf fsol-dropped-packets-dup-addr {
      type uint32;
      description
        "Number of first sign of life packets received
         for initiating protocol on this interface that
         were dropped due to duplicate source address";
    }
  }

  grouping IPSUB-MA-PARENT-INTF-INITIATORS {
    description
      "Initiator protocol details";
    container dhcp {
      description
        "DHCP information";
      uses IPSUB-MA-PARENT-INTF-INITIATOR-DATA;
    }
    container packet-trigger {
      description
        "packet trigger information";
      uses IPSUB-MA-PARENT-INTF-INITIATOR-DATA;
    }
  }

  grouping IPSUB-MA-PARENT-INTF-DATA {
    description
      "Parent interface data";
    container initiators {
      description
        "Configurational state-statistics for each
         initiating protocol enabled on this parent
         interface";
      uses IPSUB-MA-PARENT-INTF-INITIATORS;
    }
    container ipv6-initiators {
      description
        "Configurational state-statistics for each
         initiating protocol enabled on this parent
         interface for IPv6 session";
      uses IPSUB-MA-PARENT-INTF-INITIATORS;
    }
    container session-limit {
      description
        "Configuration session limits for each session
         limit source and type";
      uses IPSUB-MA-PARENT-INTF-SESSION-LIMIT-DATA;
    }
    leaf interface-creation-time {
      type string;
      description
        "Interface creation time in Month Date HH:MM:SS
         format";
    }
    leaf age {
      type string;
      description
        "Age in HH:MM:SS format";
    }
    leaf interface-type {
      type string;
      description
        "Interface Type";
    }
    leaf state {
      type Ipsub-ma-parent-intf-state-data;
      description
        "Operational state of this interface";
    }
    leaf ipv6-state {
      type Ipsub-ma-parent-intf-state-data;
      description
        "Operational ipv6 state of this interface";
    }
    leaf vlan-type {
      type Ipsub-ma-parent-intf-vlan;
      description
        "The VLAN type on the access interface";
    }
  }

  grouping VRF-DATA {
    description
      "VRF details";
    leaf vrf-name {
      type string;
      description
        "VRF name";
    }
    leaf table-name {
      type string;
      description
        "Table";
    }
  }

  grouping IPSUB-MA-INTF-DATA {
    description
      "Interface details";
    container vrf {
      description
        "IPv4 VRF details";
      uses VRF-DATA;
    }
    container ipv6vrf {
      description
        "IPv6 VRF details";
      uses VRF-DATA;
    }
    leaf access-interface {
      type xr:Interface-name;
      description
        "Access interface through which this subscriber
         is accessible";
    }
    leaf subscriber-ipv4-address {
      type inet:ipv4-address;
      description
        "IPv4 Address of the subscriber";
    }
    leaf subscriber-ipv6-address {
      type string;
      description
        "IPv6 Address of the subscriber";
    }
    leaf subscriber-mac-addres {
      type yang:mac-address;
      description
        "MAC address of the subscriber";
    }
    leaf subscriber-label {
      type uint32;
      description
        "Subscriber label for this subscriber interface";
    }
    leaf interface-creation-time {
      type string;
      description
        "Interface creation time in month day hh:mm:ss
         format";
    }
    leaf age {
      type string;
      description
        "Age in hh:mm:ss format";
    }
    leaf initiator {
      type Ipsub-ma-intf-initiator-data;
      description
        "Protocol trigger for creation of this subscriber
         session";
    }
    leaf state {
      type Ipsub-ma-intf-state-data;
      description
        "State of the subscriber session";
    }
    leaf old-state {
      type Ipsub-ma-intf-state-data;
      description
        "Previous state of the subscriber session";
    }
    leaf last-state-change-time {
      type string;
      description
        "Interface's last state change time in month day
         hh:mm:ss format";
    }
    leaf current-change-age {
      type string;
      description
        "Current change age in hh:mm:ss format";
    }
    leaf ipv6-initiator {
      type Ipsub-ma-intf-initiator-data;
      description
        "Protocol trigger for creation of this
         subscriber's IPv6 session";
    }
    leaf ipv6-state {
      type Ipsub-ma-intf-state-data;
      description
        "State of the subscriber's IPv6 session";
    }
    leaf ipv6-old-state {
      type Ipsub-ma-intf-state-data;
      description
        "Previous state of the subscriber's IPv6 session";
    }
    leaf ipv6-last-state-change-time {
      type string;
      description
        "Interface's IPV6 last state change time in month
         day hh:mm:ss format";
    }
    leaf ipv6-current-change-age {
      type string;
      description
        "IPV6 Current change age in hh:mm:ss format";
    }
    leaf is-l2-connected {
      type boolean;
      description
        "True if L2 connected";
    }
    leaf session-type {
      type string;
      description
        "Session Type";
    }
  }

  grouping IPSUB-MA-INTF-VRF-SUMMARY-DATA {
    description
      "IPSUB MA INTF VRF SUMMARY DATA";
    leaf vrf-name {
      type string;
      description
        "IPv4 VRF";
    }
    leaf ipv6vrf-name {
      type string;
      description
        "IPv6 VRF";
    }
    leaf interfaces {
      type uint64;
      description
        "Number of IP subscriber interfaces in the VRF
         table";
    }
    leaf ipv6-interfaces {
      type uint64;
      description
        "Number of IPv6 subscriber interfaces in the VRF
         table";
    }
  }

  grouping INTERFACE-COUNTS {
    description
      "Interface state values";
    leaf invalid {
      type uint32;
      description
        "Invalid";
    }
    leaf initialized {
      type uint32;
      description
        "Initialized";
    }
    leaf session-creation-started {
      type uint32;
      description
        "Session creation started";
    }
    leaf control-policy-executing {
      type uint32;
      description
        "Control policy executing";
    }
    leaf control-policy-executed {
      type uint32;
      description
        "Control policy executed";
    }
    leaf session-features-applied {
      type uint32;
      description
        "Session features applied";
    }
    leaf vrf-configured {
      type uint32;
      description
        "VRF configured";
    }
    leaf adding-adjacency {
      type uint32;
      description
        "Adding adjacency";
    }
    leaf adjacency-added {
      type uint32;
      description
        "Adjacency added";
    }
    leaf up {
      type uint32;
      description
        "Up";
    }
    leaf down {
      type uint32;
      description
        "Down";
    }
    leaf disconnecting {
      type uint32;
      description
        "Disconnecting";
    }
    leaf disconnected {
      type uint32;
      description
        "Disconnected";
    }
    leaf error {
      type uint32;
      description
        "Error";
    }
    leaf total-interfaces {
      type uint32;
      description
        "Total number of interfaces in all states";
    }
  }

  grouping INTF-INITIATOR-STATS {
    description
      "Initiator statistics";
    container dhcp {
      description
        "DHCP";
      uses INTERFACE-COUNTS;
    }
    container packet-trigger {
      description
        "Packet trigger";
      uses INTERFACE-COUNTS;
    }
  }

  grouping INTF-INTITIATORS {
    description
      "Initiators";
    container initiators {
      description
        "Initiators";
      uses INTF-INITIATOR-STATS;
    }
    container ipv6-initiators {
      description
        "IPv6 Initiators";
      uses INTF-INITIATOR-STATS;
    }
  }

  grouping IPSUB-MA-PARENT-INTF-SUMMARY-INITIATOR-DATA {
    description
      "IPSUB MA PARENT INTF SUMMARY INITIATOR DATA";
    leaf fsol-packets {
      type uint32;
      description
        "Number of first sign of life packets received
         for initiating protocol";
    }
    leaf fsol-bytes {
      type uint32;
      units "byte";
      description
        "Number of first sign of life bytes received for
         initiating protocol";
    }
  }

  grouping IPSUB-MA-INITITATORS {
    description
      "Initiators";
    container dhcp {
      description
        "DHCP summary statistics";
      uses IPSUB-MA-PARENT-INTF-SUMMARY-INITIATOR-DATA;
    }
    container packet-trigger {
      description
        "Packet trigger summary statistics";
      uses IPSUB-MA-PARENT-INTF-SUMMARY-INITIATOR-DATA;
    }
  }

  grouping IPSUB-MA-PARENT-INTF-SUMMARY {
    description
      "Access interface summary statistics";
    container initiators {
      description
        "Summary counts per initiator";
      uses IPSUB-MA-INITITATORS;
    }
    container ipv6-initiators {
      description
        "Summary counts per initiator for ipv6 session";
      uses IPSUB-MA-INITITATORS;
    }
    leaf interfaces {
      type uint32;
      description
        "Number of interfaces with subscriber
         configuration";
    }
  }

  grouping IPSUB-MA-INTF-SUMMARY-DATA {
    description
      "Interface summary statistics";
    container access-interface-summary {
      description
        "Access interface summary statistics";
      uses IPSUB-MA-PARENT-INTF-SUMMARY;
    }
    container interface-counts {
      description
        "Initiator interface counts";
      uses INTF-INTITIATORS;
    }
    list vrf {
      description
        "Array of VRFs with IPSUB interfaces";
      uses IPSUB-MA-INTF-VRF-SUMMARY-DATA;
    }
  }
}
