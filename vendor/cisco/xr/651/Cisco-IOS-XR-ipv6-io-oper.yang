module Cisco-IOS-XR-ipv6-io-oper {
  namespace "http://cisco.com/ns/yang/Cisco-IOS-XR-ipv6-io-oper";
  prefix ipv6-io-oper;

  import Cisco-IOS-XR-types {
    prefix xr;
  }
  include Cisco-IOS-XR-ipv6-io-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-io package operational data.
     
     This module contains definitions
     for the following management objects:
       ipv6-io: IPv6 IO Operational Data
     
     Copyright (c) 2013-2018 by Cisco Systems, Inc.
     All rights reserved.";

  revision 2015-11-09 {
    description
      "IOS XR 6.0 revision.";
  }
  revision 2015-08-27 {
    description
      "IOS XR 6.0.0 revision.";
  }

  container ipv6-io {
    config false;
    description
      "IPv6 IO Operational Data";
    container nodes {
      description
        "Node-specific IPv6 IO operational data";
      list node {
        key "node-name";
        description
          "IPv6 network operational data for a particular
           node";
        container statistics {
          description
            "Statistical IPv6 network operational data for
             a node";
          container traffic {
            description
              "Traffic statistics for a node";
            uses IPV6-TRAFFIC;
          }
        }
        leaf node-name {
          type xr:Node-id;
          description
            "Node name";
        }
      }
    }
  }
}
