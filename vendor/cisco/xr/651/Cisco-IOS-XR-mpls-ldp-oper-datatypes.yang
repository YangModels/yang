module Cisco-IOS-XR-mpls-ldp-oper-datatypes {
  namespace "http://cisco.com/ns/yang/Cisco-IOS-XR-mpls-ldp-oper-datatypes";
  prefix mpls-ldp-oper-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-ldp-oper-data package operational data.
     
     Copyright (c) 2013-2018 by Cisco Systems, Inc.
     All rights reserved.";

  revision 2015-11-09 {
    description
      "IOS XR 6.0 revision.";
  }

  typedef Mpls-ldp-oper-af-name {
    type enumeration {
      enum "ipv4" {
        value 1;
        description
          "IPv4";
      }
      enum "ipv6" {
        value 2;
        description
          "IPv6";
      }
      enum "all" {
        value 65535;
        description
          "All";
      }
    }
    description
      "Mpls ldp oper af name";
  }
}
