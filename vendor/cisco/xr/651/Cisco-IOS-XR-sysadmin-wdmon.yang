module Cisco-IOS-XR-sysadmin-wdmon {
  namespace "http://www.cisco.com/ns/yang/Cisco-IOS-XR-sysadmin-wdmon";
  prefix wdmonh;

  import tailf-common {
    prefix tailf;
  }
  import tailf-xsd-types {
    prefix xs;
  }
  import Cisco-IOS-XR-sysadmin-show-trace {
    prefix show_trace;
  }

  revision 2017-05-01 {
    description
      "Namespace change to comply with Cisco guidelines on namespace";
  }
  tailf:id "http://cisco.com/calvados/wdmon";

  container wdmon {
    config false;
    tailf:cli-incomplete-show-path;
    uses show_trace:traceable;
  }
  container wdmon-info {
    config false;
    tailf:callpoint "wdmon_info_show_location";
    tailf:hidden "internal-command";
    list all-locations {
      key "location";
      tailf:cli-drop-node-name;
      tailf:cli-show-template
        "----------------------------------------------------------------------
         node\\\\:      $(location)
         ----------------------------------------------------------------------
                                  Start Time\\\\: $(start-timestamp)
                            Hushd connection\\\\: $(hushd-capi-up|dict:true=Up:false=Down)
          Hushd last connection Up timestamp\\\\: $(hushd-capi-up-timestamp)
                      Hushd pending response\\\\: $(hushd-pending-resp|dict:true=Y:false=N)
                      Hushd last HB response\\\\: $(hushd-last-hb-resp|floatformat:-3) sec ago
           wdmon/Calv/Hushd liveness timeout\\\\: $(hushd-timeout|floatformat:-3) sec
                 Calvados restart WD timeout\\\\: $(calv-restart-timeout) sec
                Hushd watchdog expire action\\\\: $(hushd-wd-action-disable|dict:true=Disabled:false=Enabled)
                 Hushd last action timestamp\\\\: $(hushd-wd-action-timestamp)
             Wdmon stopped punching Hushd HB\\\\: $(hushd-stop-punching|dict:true=Y:false=N)
                       Num of Hushd connects\\\\: $(hushd-num-capi-connects)
                     Wdmon client connection\\\\: $(wds-client-up|dict:true=Up:false=Down)
              Wdmon last client Up timestamp\\\\: $(wds-client-up-timestamp)
                            Wdmon client PID\\\\: $(wds-client-pid)
                        Wdmon client last HB\\\\: $(wds-client-last-hb|floatformat:-3) sec ago
             Status reported by wdmon client\\\\: $(wds-client-reported-status)
                Num of wdmon client connects\\\\: $(wds-client-num-connects)
                 Wdmon client timeout action\\\\: $(wds-action-disable|dict:true=Disabled:false=Enabled)
          Wdmon client last action timestamp\\\\: $(wds-action-timestamp)
            Wdmon client num restart timeout\\\\: $(wds-num-restart-timeout)
           Wdmon client num liveness timeout\\\\: $(wds-num-liveness-timeout)
                Wdmon client restart timeout\\\\: $(wds-restart-timeout) sec
               Wdmon client liveness timeout\\\\: $(wds-liveness-timeout) sec
        ";
      leaf location {
        type string;
        tailf:cli-allow-range;
        tailf:cli-expose-key-name;
      }
      leaf start-timestamp {
        type string;
        description
          "Last start date and time for wdmon";
      }
      leaf hushd-timeout {
        type xs:double;
        description
          "wdmon/Calv/Hushd liveness timeout";
      }
      leaf calv-restart-timeout {
        type uint32;
        description
          "Calvados restart timeout";
      }
      leaf hushd-wd-action-disable {
        type boolean;
        description
          "Hushd WD expire action disable or not";
      }
      leaf hushd-wd-action-timestamp {
        type string;
        description
          "Last Hushd WD expire action date and time";
      }
      leaf hushd-capi-up {
        type boolean;
        description
          "Hushd CAPI up or not";
      }
      leaf hushd-pending-resp {
        type boolean;
        description
          "Any pending response from Hushd";
      }
      leaf hushd-stop-punching {
        type boolean;
        description
          "Hushd HB punching stopped";
      }
      leaf hushd-capi-up-timestamp {
        type string;
        description
          "Last Hushd CAPI up date and time";
      }
      leaf hushd-last-hb-resp {
        type xs:double;
        description
          "How long ago was last HB response from Hushd";
      }
      leaf hushd-num-capi-connects {
        type uint32;
        description
          "Num of Hushd CAPI connects";
      }
      leaf wds-action-disable {
        type boolean;
        description
          "wdmon client timeout action disabled or not";
      }
      leaf wds-action-timestamp {
        type string;
        description
          "Last wdmon client timeout action date and time";
      }
      leaf wds-restart-timeout {
        type uint32;
        description
          "wdmon client restart timeout";
      }
      leaf wds-liveness-timeout {
        type uint32;
        description
          "wdmon client liveness timeout";
      }
      leaf wds-client-up {
        type boolean;
        description
          "wdmon client is up or not";
      }
      leaf wds-client-pid {
        type uint32;
        description
          "Process ID of the wdmon client";
      }
      leaf wds-client-up-timestamp {
        type string;
        description
          "Last wdmon client connect date and time";
      }
      leaf wds-client-last-hb {
        type xs:double;
        description
          "How long ago was last HB from wdmon client";
      }
      leaf wds-client-num-connects {
        type uint32;
        description
          "Total number of client connects";
      }
      leaf wds-num-liveness-timeout {
        type uint32;
        description
          "Total number of client liveness timeouts";
      }
      leaf wds-num-restart-timeout {
        type uint32;
        description
          "Total number of client restart timeouts";
      }
      leaf wds-client-reported-status {
        type string;
        description
          "Status reported by wdmon client";
      }
    }
  }
}
