module Cisco-IOS-XR-sysadmin-ethsw-esdma-trunk {
  namespace "http://www.cisco.com/ns/yang/Cisco-IOS-XR-sysadmin-ethsw-esdma-trunk";
  prefix esdma_trunk;

  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains the YANG definitions
     for the Cisco IOS-XR SysAdmin
     'show controller switch trunk' command.
     
     Copyright(c) 2011-2017 by Cisco Systems, Inc.
     All rights reserved.
     
     Copyright (c) 2012-2018 by Cisco Systems, Inc.
     All rights reserved.";

  revision 2017-05-01 {
    description
      "Namespace change to comply with Cisco guidelines on namespace";
  }

  grouping switch-trunk-group {
    container trunk {
      list location {
        key "rack card switch-id";
        leaf rack {
          type esdma_types:esdma-rack-num-enum;
          description
            "Rack to display the switch trunk group information for";
        }
        leaf card {
          type esdma_types:esdma-cpu;
          description
            "Card to display the switch trunk group information for";
        }
        leaf switch-id {
          type esdma_types:esdma-switch-type-enum;
          description
            "Switch type to display the switch trunk group information for";
        }
        leaf trunk-member-count {
          type uint32;
          description
            "Number of member ports in the trunk group";
        }
        leaf trunk-name {
          type string;
          description
            "Name of the trunk group";
        }
        list trunk-member-port-iter {
          key "trunk-member-port";
          leaf trunk-member-port {
            type uint32;
            description
              "Trunk Member Port";
          }
          leaf trunk-member-status {
            type esdma_types:esdma-trunk-member-status;
            description
              "Trunk Member Status";
          }
        }
      }
    }
  }
}
