module Cisco-IOS-XR-sysadmin-show-obfl {
  namespace "http://www.cisco.com/ns/yang/Cisco-IOS-XR-sysadmin-show-obfl";
  prefix shobfl;

  import tailf-common {
    prefix tailf;
  }

  organization
    "Cisco Systems Inc.";
  description
    "This module holds OBFL data.";

  revision 2017-10-09 {
    description
      "Added fia_asic_init_fail container";
  }
  revision 2017-07-31 {
    description
      "Changed namespace to follow Cisco guidelines on naming convention";
  }
  revision 2011-11-24 {
    description
      "Initial revision of show obfl related commands";
  }

  grouping obfl_data {
    container uptime {
      config false;
      tailf:info "OBFL Uptime Data information";
      tailf:callpoint "obfl_uptime_cp";
      list location {
        key "location";
        tailf:info "Select node location";
        tailf:cli-full-command;
        tailf:cli-no-match-completion;
        tailf:cli-suppress-table;
        tailf:cli-show-template-enter
          "
           OBFL Uptime Information For : $(location)
          ";
        tailf:cli-show-template "$(uptime|show)\n";
        leaf location {
          type string;
          tailf:display-column-name "Location";
        }
        container uptime {
          tailf:cli-drop-node-name;
          leaf-list uptime_values {
            type string;
            tailf:cli-drop-node-name;
            tailf:cli-list-syntax;
          }
        }
      }
    }
    container nvram {
      config false;
      tailf:info "Dump nvram contents";
      tailf:callpoint "obfl_nvram_cp";
      list location {
        key "location";
        tailf:info "Select node location";
        tailf:cli-full-command;
        tailf:cli-no-match-completion;
        tailf:cli-suppress-table;
        tailf:cli-show-template-enter
          "
           NVRAM Information for: $(location)
          ";
        tailf:cli-show-template "$(nvram|show)\n";
        leaf location {
          type string;
          tailf:display-column-name "Location";
        }
        container nvram {
          tailf:cli-drop-node-name;
          leaf-list nvram_values {
            type string;
            tailf:cli-drop-node-name;
            tailf:cli-list-syntax;
          }
        }
      }
    }
    container fia_asic_init_fail {
      config false;
      tailf:info "FIA ASIC initialization failure information";
      tailf:callpoint "obfl_fia_asic_init_fail_cp";
      list location {
        key "location";
        tailf:info "select node location";
        tailf:cli-full-command;
        tailf:cli-no-match-completion;
        tailf:cli-suppress-table;
        tailf:cli-show-template-enter
          "
           OBFL FIA ASIC initialization failure information For :$(location)
          ";
        tailf:cli-show-template "$(fia_asic_init_fail|show)\n";
        leaf location {
          type string;
          tailf:display-column-name "Location";
        }
        container fia_asic_init_fail {
          tailf:cli-drop-node-name;
          leaf-list fia_asic_init_fail_values {
            type string;
            tailf:cli-drop-node-name;
            tailf:cli-list-syntax;
          }
        }
      }
    }
    container inventory {
      config false;
      tailf:info "OBFL Inventory Data information";
      tailf:callpoint "obfl_inventory_cp";
      list location {
        key "location";
        tailf:info "Select node location";
        tailf:cli-full-command;
        tailf:cli-no-match-completion;
        tailf:cli-suppress-table;
        tailf:cli-show-template-enter
          "
           OBFL Inventory Information For : $(location)
          ";
        tailf:cli-show-template "$(inventory|show)\n";
        leaf location {
          type string;
          tailf:display-column-name "Location";
        }
        container inventory {
          tailf:cli-drop-node-name;
          leaf-list inventory_values {
            type string;
            tailf:cli-drop-node-name;
            tailf:cli-list-syntax;
          }
        }
      }
    }
    container temperature {
      config false;
      tailf:info "OBFL Temperature Data information";
      tailf:callpoint "obfl_temp_cp";
      list location {
        key "location";
        tailf:info "Select node location";
        tailf:cli-full-command;
        tailf:cli-no-match-completion;
        tailf:cli-suppress-table;
        tailf:cli-show-template-enter
          "
           OBFL Temperature Information For : $(location)
          ";
        tailf:cli-show-template "$(temperature|show)\n";
        leaf location {
          type string;
          tailf:display-column-name "Location";
        }
        container temperature {
          tailf:cli-drop-node-name;
          leaf-list temp_values {
            type string;
            tailf:cli-drop-node-name;
            tailf:cli-list-syntax;
          }
        }
      }
    }
    container voltage {
      config false;
      tailf:info "OBFL Voltage Data information";
      tailf:callpoint "obfl_volt_cp";
      list location {
        key "location";
        tailf:info "Select node location";
        tailf:cli-full-command;
        tailf:cli-no-match-completion;
        tailf:cli-suppress-table;
        tailf:cli-show-template-enter
          "
           OBFL Voltage Information For : $(location)
          ";
        tailf:cli-show-template "$(voltage|show)\n";
        leaf location {
          type string;
          tailf:display-column-name "Location";
        }
        container voltage {
          tailf:cli-drop-node-name;
          leaf-list volt_values {
            type string;
            tailf:cli-drop-node-name;
            tailf:cli-list-syntax;
          }
        }
      }
    }
    container fpd {
      config false;
      tailf:info "OBFL FPD Data information";
      tailf:callpoint "obfl_fpd_cp";
      list location {
        key "location";
        tailf:info "Select node location";
        tailf:cli-full-command;
        tailf:cli-no-match-completion;
        tailf:cli-suppress-table;
        tailf:cli-show-template-enter
          "
           OBFL FPD Information For : $(location)
          ";
        tailf:cli-show-template "$(fpd|show)\n";
        leaf location {
          type string;
          tailf:display-column-name "Location";
        }
        container fpd {
          tailf:cli-drop-node-name;
          leaf-list fpd_values {
            type string;
            tailf:cli-drop-node-name;
            tailf:cli-list-syntax;
          }
        }
      }
    }
    container diag_result {
      config false;
      tailf:info "OBFL Diag Test Results information";
      tailf:callpoint "obfl_diag_result_cp";
      list location {
        key "location";
        tailf:info "Select node location";
        tailf:cli-full-command;
        tailf:cli-no-match-completion;
        tailf:cli-suppress-table;
        tailf:cli-show-template-enter
          "
           OBFL Diag Test Result Information For : $(location)
          ";
        tailf:cli-show-template "$(diag_result|show)\n";
        leaf location {
          type string;
          tailf:display-column-name "Location";
        }
        container diag_result {
          tailf:cli-drop-node-name;
          leaf-list diag_result_values {
            type string;
            tailf:cli-drop-node-name;
            tailf:cli-list-syntax;
          }
        }
      }
    }
    container diag_log {
      config false;
      tailf:info "OBFL Diag Logs Data information";
      tailf:callpoint "obfl_diag_log_cp";
      list location {
        key "location";
        tailf:info "Select node location";
        tailf:cli-full-command;
        tailf:cli-no-match-completion;
        tailf:cli-suppress-table;
        tailf:cli-show-template-enter
          "
           OBFL Diag Logs Data Information For : $(location)
          ";
        tailf:cli-show-template "$(diag_log|show)\n";
        leaf location {
          type string;
          tailf:display-column-name "Location";
        }
        container diag_log {
          tailf:cli-drop-node-name;
          leaf-list diag_log_values {
            type string;
            tailf:cli-drop-node-name;
            tailf:cli-list-syntax;
          }
        }
      }
    }
    container fmea {
      config false;
      tailf:info "OBFL FMEA Data information";
      tailf:callpoint "obfl_fmea_cp";
      list location {
        key "location";
        tailf:info "Select node location";
        tailf:cli-full-command;
        tailf:cli-no-match-completion;
        tailf:cli-suppress-table;
        tailf:cli-show-template-enter
          "
           OBFL FMEA Information For : $(location)
          ";
        tailf:cli-show-template "$(fmea|show)\n";
        leaf location {
          type string;
          tailf:display-column-name "Location";
        }
        container fmea {
          tailf:cli-drop-node-name;
          leaf-list fmea_values {
            type string;
            tailf:cli-drop-node-name;
            tailf:cli-list-syntax;
          }
        }
      }
    }
    container fabric {
      config false;
      tailf:info "OBFL FABRIC Data information";
      tailf:callpoint "obfl_fabric_cp";
      list location {
        key "location";
        tailf:info "Select node location";
        tailf:cli-full-command;
        tailf:cli-no-match-completion;
        tailf:cli-suppress-table;
        tailf:cli-show-template-enter
          "
           OBFL FABRIC Information For : $(location)
          ";
        tailf:cli-show-template "$(fabric|show)\n";
        leaf location {
          type string;
          tailf:display-column-name "Location";
        }
        container fabric {
          tailf:cli-drop-node-name;
          leaf-list fabric_values {
            type string;
            tailf:cli-drop-node-name;
            tailf:cli-list-syntax;
          }
        }
      }
    }
    container prm {
      config false;
      tailf:info "OBFL new PRM Data information";
      tailf:callpoint "obfl_prm_cp";
      list location {
        key "location";
        tailf:info "Select node location";
        tailf:cli-full-command;
        tailf:cli-no-match-completion;
        tailf:cli-suppress-table;
        tailf:cli-show-template-enter
          "
           OBFL PRM Information For : $(location)
          ";
        tailf:cli-show-template "$(prm|show)\n";
        leaf location {
          type string;
          tailf:display-column-name "Location";
        }
        container prm {
          tailf:cli-drop-node-name;
          leaf-list prm_values {
            type string;
            tailf:cli-drop-node-name;
            tailf:cli-list-syntax;
          }
        }
      }
    }
  }

  grouping obfl-show-grp {
    container onboard {
      tailf:info "OBFL logging data";
      tailf:cli-incomplete-show-path;
      uses obfl_data;
    }
  }
  tailf:id "http://www.cisco.com/panini/calvados/shobfl";
}
