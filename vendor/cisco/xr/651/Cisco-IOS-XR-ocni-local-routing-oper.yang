module Cisco-IOS-XR-ocni-local-routing-oper {
  namespace "http://cisco.com/ns/yang/Cisco-IOS-XR-ocni-local-routing-oper";
  prefix ocni-local-routing-oper;

  include Cisco-IOS-XR-ocni-local-routing-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ocni-local-routing package operational data.
     
     This module contains definitions
     for the following management objects:
       ocni: An OpenConfig description of a network-instance. This
         may be a Layer 3 forwarding construct such as a virtual
         routing and forwarding (VRF) instance, or a Layer 2 instance
         such as a virtual switch instance (VSI). Mixed Layer 2 and
         Layer 3 instances are also supported.
     
     Copyright (c) 2013-2018 by Cisco Systems, Inc.
     All rights reserved.";

  revision 2015-11-09 {
    description
      "IOS XR 6.0 revision.";
  }

  grouping NETWORK-INSTANCES-TABLE {
    description
      "Common node of vrfipv4, vrfipv6";
    container network-instances {
      description
        "Network instances configured on the local system";
      list network-instance {
        key "name";
        description
          "Network instances configured on the local
           system";
        container protocols {
          description
            "A process (instance) of a routing protocol.
             Some systems may not support more than one
             instance of a particular routing protocol";
          list protocol {
            description
              "A process (instance) of a routing protocol.
               Some systems may not support more than one
               instance of a particular routing protocol";
            container state {
              description
                "State parameters relating to the routing
                 protocol instance";
              uses OVERLAY-OCNI-STATE;
            }
            container static-routes {
              description
                "List of locally configured static routes";
              list static-route {
                key "prefix";
                description
                  "List of locally configured static routes";
                container next-hops {
                  description
                    "A list of next-hops to be utilised for the
                     static route being specified.";
                  list next-hop {
                    key "index";
                    description
                      "A list of next-hops to be utilised for
                       the static route being specified.";
                    leaf index {
                      type string;
                      description
                        "A reference to the index of the current
                         next-hop. The index is intended to be a
                         user-specified value which can be used
                         to reference the next-hop in question,
                         without any other semantics being
                         assigned to it.";
                    }
                    uses OVERLAY-OCNI-NEXT-HOP;
                  }
                }
                container static-routes-state {
                  description
                    "Operational state data for static routes";
                  uses OVERLAY-OCNI-STATIC-STATE;
                }
                leaf prefix {
                  type string;
                  description
                    "Reference to the destination prefix list
                     key.";
                }
              }
            }
            leaf identifier {
              type string;
              description
                "The protocol name for the routing or
                 forwarding protocol to be instantiated";
            }
            leaf name {
              type string;
              description
                "An operator-assigned identifier for the
                 routing or forwarding protocol. For some
                 processes this leaf may be system defined.";
            }
          }
        }
        leaf name {
          type string;
          description
            "A unique name identifying the network instance";
        }
      }
    }
  }

  container ocni {
    config false;
    description
      "An OpenConfig description of a network-instance.
       This may be a Layer 3 forwarding construct such
       as a virtual routing and forwarding (VRF)
       instance, or a Layer 2 instance such as a virtual
       switch instance (VSI). Mixed Layer 2 and Layer 3
       instances are also supported.";
    container vrfipv4 {
      description
        "IPv4 static configuration";
      uses NETWORK-INSTANCES-TABLE;
    }
    container vrfipv6 {
      description
        "IPv6 static configuration";
      uses NETWORK-INSTANCES-TABLE;
    }
  }
}
