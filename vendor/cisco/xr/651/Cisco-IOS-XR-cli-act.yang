module Cisco-IOS-XR-cli-act {

    namespace "http://cisco.com/ns/yang/Cisco-IOS-XR-cli-act";
    
    prefix "cli-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2016 by Cisco Systems, Inc.
     All rights reserved.";
    
    revision "2016-09-22" {
        description
            "IOS XR 6.2.1 revision.";
    }

    rpc cli-command {
        description "Actions on certificate revocation lists";
        input {
            leaf command {
                description "CLI command string";
                type string;
                mandatory true;
            }
        }
        output {
            leaf response {
                description "CLI command output string";
                type string;
            }
        }
    }

}
