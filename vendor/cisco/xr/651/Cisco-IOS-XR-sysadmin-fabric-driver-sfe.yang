module Cisco-IOS-XR-sysadmin-fabric-driver-sfe {
  namespace "http://www.cisco.com/ns/yang/Cisco-IOS-XR-sysadmin-fabric-driver-sfe";
  prefix fabric_sfe;

  import tailf-common {
    prefix tailf;
  }
  import Cisco-IOS-XR-sysadmin-fabric-types {
    prefix fabric-types;
  }
  import Cisco-IOS-XR-sysadmin-show-trace {
    prefix show-trace;
  }

  revision 2017-05-01 {
    description
      "Namespace change to comply with Cisco guidelines on namespace";
  }

  grouping sfe_drvr_info {
    list drvr_info {
      key "idx";
      tailf:cli-suppress-table;
      tailf:cli-show-template-enter "";
      tailf:cli-show-template-legend
        "$(.legend_shown != true ?
         =========================================================================
         SFE Driver information
         =========================================================================
         )";
      tailf:cli-show-template
        "
         Driver Version: $(drv_version)   ($(coeff_major_rev).$(coeff_minor_rev))
         
         Functional role: $(func_role),   ISSU role: $(issu_role)
         Rack\\\\: $(rack_name), Type\\\\: $(rack_type), Number\\\\: $(rack_num), IP Address: $(ip_address)
         Startup time       : $(startup_time)
         Availability Masks :
              Card\\\\: 0x$(card_avail_mask|hex)       Asic\\\\: 0x$(asic_avail_mask|hex)       Exp Asic\\\\: 0x$(exp_asic_avail_mask|hex)
         Unicast/Multicast (ratio) \\\\: $(ucmc_ratio)
         +----------------------------------------------------------------+
         |Process  | Connection | Registration| Connection | DLL          |
         |/Lib     | status     | status      | requests   | registration |
         +----------------------------------------------------------------+
         | PM      | $($(pm_conn_active == true ? Active : Inactive)|ljust:11)| $( n/a|ljust:12)| $(num_pm_conn_reqs|rjust:11)| $( n/a|ljust:13)|
         | PL-LOCAL| $($(platform_local_conn_active == true ? Active : Inactive)|ljust:11)| $($(platform_local_reg_active == true ? Active : Inactive)|ljust:12)| $(num_platform_local_conn_reqs|rjust:11)| $( n/a|ljust:13)|
         | FSDB    | $($(fsdb_conn_active == true ? Active : Inactive)|ljust:11)| $($(fsdb_reg_active == true ? Active : Inactive)|ljust:12)| $(num_fsdb_conn_reqs|rjust:11)| $( n/a|ljust:13)|
         | FGID    | $($(fgid_conn_active == true ? Active : Inactive)|ljust:11)| $($(fgid_reg_active == true ? Active : Inactive)|ljust:12)| $(num_fgid_conn_reqs|rjust:11)| $( n/a|ljust:13)|
         | CM      | $($(cm_conn_active == true ? Active : Inactive)|ljust:11)| $($(cm_reg_active == true ? Active : Inactive)|ljust:12)| $(num_cm_conn_reqs|rjust:11)| $( n/a|ljust:13)|
         | CCC     | $($(ccc_conn_active == true ? Active : Inactive)|ljust:11)| $( n/a|ljust:12)| $(num_ccc_conn_reqs|rjust:11)| $( n/a|ljust:13)|
         | GASPP   | $( n/a|ljust:11)| $( n/a|ljust:12)| $( n/a|rjust:11)| $($(is_gaspp_registered == true ? Yes : No)|ljust:13)|
         | CIH     | $( n/a|ljust:11)| $( n/a|ljust:12)| $( n/a|rjust:11)| $($(is_cih_registered == true ? Yes : No)|ljust:13)|
         +----------------------------------------------------------------+
         
         Asics \\\\:
         HP - HotPlug event,  PON - Power ON reset,     WB - Warm Boot,  A - All
         HR - Hard Reset,     DC  - Disconnect signal,  DL - DownLoad
         +---------------------------------------------------------------------------+
         | Asic inst.|card|HP|Asic| Admin|plane| Fgid| Asic State |DC| Last  |PON|HR |
         |  (R/S/A\\\\)  |pwrd|  |type| /Oper|/grp | DL  |            |  | init  |(#\\\\)|(#\\\\)|
         +---------------------------------------------------------------------------+
         $(asic_list|show)+---------------------------------------------------------------------------+
        ";
      leaf idx {
        type int32;
      }
      leaf drv_version {
        type uint32;
        tailf:hidden "internal";
      }
      leaf coeff_major_rev {
        type uint32;
        tailf:hidden "internal";
      }
      leaf coeff_minor_rev {
        type uint32;
        tailf:hidden "internal";
      }
      leaf func_role {
        type string;
        tailf:hidden "internal";
      }
      leaf issu_role {
        type string;
        tailf:hidden "internal";
      }
      leaf rack_name {
        type string;
        tailf:hidden "internal";
      }
      leaf rack_type {
        type string;
        tailf:hidden "internal";
      }
      leaf rack_num {
        type string;
        tailf:hidden "internal";
      }
      leaf ip_address {
        type string;
        tailf:hidden "internal";
      }
      leaf card_avail_mask {
        type uint32;
        tailf:hidden "internal";
      }
      leaf asic_avail_mask {
        type uint64;
        tailf:hidden "internal";
      }
      leaf exp_asic_avail_mask {
        type uint64;
        tailf:hidden "internal";
      }
      leaf ucmc_ratio {
        type uint32;
        tailf:hidden "internal";
      }
      leaf pm_conn_active {
        type boolean;
        tailf:hidden "internal";
      }
      leaf platform_local_conn_active {
        type boolean;
        tailf:hidden "internal";
      }
      leaf fsdb_conn_active {
        type boolean;
        tailf:hidden "internal";
      }
      leaf fgid_conn_active {
        type boolean;
        tailf:hidden "internal";
      }
      leaf cm_conn_active {
        type boolean;
        tailf:hidden "internal";
      }
      leaf ccc_conn_active {
        type boolean;
        tailf:hidden "internal";
      }
      leaf issu_mgr_conn_active {
        type boolean;
        tailf:hidden "internal";
      }
      leaf peer_sfe_conn_active {
        type boolean;
        tailf:hidden "internal";
      }
      leaf cxp_conn_active {
        type boolean;
        tailf:hidden "internal";
      }
      leaf pm_reg_active {
        type boolean;
        tailf:hidden "internal";
      }
      leaf platform_local_reg_active {
        type boolean;
        tailf:hidden "internal";
      }
      leaf fsdb_reg_active {
        type boolean;
        tailf:hidden "internal";
      }
      leaf fgid_reg_active {
        type boolean;
        tailf:hidden "internal";
      }
      leaf cm_reg_active {
        type boolean;
        tailf:hidden "internal";
      }
      leaf issu_mgr_reg_active {
        type boolean;
        tailf:hidden "internal";
      }
      leaf peer_sfe_reg_active {
        type boolean;
        tailf:hidden "internal";
      }
      leaf cxp_reg_active {
        type boolean;
        tailf:hidden "internal";
      }
      leaf num_pm_conn_reqs {
        type uint8;
        tailf:hidden "internal";
      }
      leaf num_platform_local_conn_reqs {
        type uint8;
        tailf:hidden "internal";
      }
      leaf num_fsdb_conn_reqs {
        type uint8;
        tailf:hidden "internal";
      }
      leaf num_fgid_conn_reqs {
        type uint8;
        tailf:hidden "internal";
      }
      leaf num_fstats_conn_reqs {
        type uint8;
        tailf:hidden "internal";
      }
      leaf num_cm_conn_reqs {
        type uint8;
        tailf:hidden "internal";
      }
      leaf num_ccc_conn_reqs {
        type uint8;
        tailf:hidden "internal";
      }
      leaf num_issu_mgr_conn_reqs {
        type uint8;
        tailf:hidden "internal";
      }
      leaf num_peer_sfe_conn_reqs {
        type uint8;
        tailf:hidden "internal";
      }
      leaf num_cxp_conn_reqs {
        type uint8;
        tailf:hidden "internal";
      }
      leaf is_gaspp_registered {
        type boolean;
        tailf:hidden "internal";
      }
      leaf is_cih_registered {
        type boolean;
        tailf:hidden "internal";
      }
      leaf startup_time {
        type string;
        tailf:hidden "internal";
      }
      list asic_list {
        key "asic_idx";
        tailf:cli-suppress-table;
        tailf:cli-show-template-enter "";
        tailf:cli-show-template "| $(asic_instance|ljust:10)| $(card_powered|ljust:3)| $(hotplug_event|ljust:1)|$(asic_type|rjust:4)| $(admin-state|ljust:2)/$(oper_state|ljust:2)|$(fab_plane|rjust:2)/$(fab_group|ljust:2)|$(fgid_download|rjust:5)| $(asic_state|ljust:11)|$(asic_disconnect_signal|rjust:2)| $(last_init_cause|ljust:6)|$(num_pon_resets|rjust:3)|$(num_hard_resets|rjust:3)|\n";
        leaf asic_idx {
          type uint32;
        }
        leaf asic_instance {
          type string;
          tailf:hidden "internal";
        }
        leaf card_present {
          type string;
          tailf:hidden "internal";
        }
        leaf card_powered {
          type string;
          tailf:hidden "internal";
        }
        leaf hotplug_event {
          type uint32;
          tailf:hidden "internal";
        }
        leaf asic_type {
          type string;
          tailf:hidden "internal";
        }
        leaf admin-state {
          type string;
          tailf:hidden "internal";
        }
        leaf oper_state {
          type string;
          tailf:hidden "internal";
        }
        leaf fab_plane {
          type string;
          tailf:hidden "internal";
        }
        leaf fab_group {
          type string;
          tailf:hidden "internal";
        }
        leaf fgid_download {
          type string;
          tailf:hidden "internal";
        }
        leaf asic_state {
          type string;
          tailf:hidden "internal";
        }
        leaf asic_disconnect_signal {
          type string;
          tailf:hidden "internal";
        }
        leaf last_init_cause {
          type string;
          tailf:hidden "internal";
        }
        leaf num_pon_resets {
          type uint32;
          tailf:hidden "internal";
        }
        leaf num_hard_resets {
          type uint32;
          tailf:hidden "internal";
        }
      }
    }
  }

  grouping sfe_link_info_asic_instance {
    list instance {
      key "instance-id";
      tailf:cli-no-key-completion;
      tailf:cli-no-match-completion;
      tailf:cli-show-template-enter "";
      tailf:cli-suppress-table;
      tailf:cli-show-template
        "$(is_show == true ?$(.path ~= rx ? $(.path ~= topo ?
         --------------------------------------------------------------------------------
         Node ID\\\\: $(nodeid_str|ljust:12)  Instance\\\\: $(instance-id)
         
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         --------------------------------------------------------------------------------
         Link ID      Link  Asic  Plane  EN/    Flags        Far-End       Far-End          
                      Spd   Stg. /Group  Oper                Link (FSDB\\\\)   Link (HW\\\\)  
                     (Gbps\\\\)             Status                                    
         --------------------------------------------------------------------------------:$(.path ~= flap ? 
         --------------------------------------------------------------------------------
         Node ID\\\\: $(nodeid_str|ljust:12)  Instance\\\\: $(instance-id)
         $(.path ~= detail ?
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         )--------------------------------------------------------------------------------
         Link ID        Oper       Link       Admin
                        Status     Errors     Shuts
         --------------------------------------------------------------------------------:$(.path ~= stats ? 
         --------------------------------------------------------------------------------
         Node ID\\\\: $(nodeid_str|ljust:12)  Instance\\\\: $(instance-id)
         --------------------------------------------------------------------------------
         $(.path ~= all ?Link ID              Ctrl          Data          Data       Re-Xmit  Async    
                              cells         cells         bytes               FIFO Rate
         :$(.path ~= ctrl ?Link ID                Ctrl     Dropped    
                                cells    rexmit ctrl
         :Link ID              Data          Data        CRC              CE          UCE
                              cells         bytes       errors                          
         ))--------------------------------------------------------------------------------))):$(.path ~= stats ?
         --------------------------------------------------------------------------------
         Node ID\\\\: $(nodeid_str|ljust:12)  Instance\\\\: $(instance-id)
         --------------------------------------------------------------------------------
         $(.path ~= all ?Link ID              Ctrl          Data          Data       Re-Xmit  Async    
                              cells         cells         bytes               FIFO Rate
         :$(.path ~= ctrl ?Link ID                Ctrl 
                                cells
         :Link ID                Data            Data 
                                cells           bytes
         ))--------------------------------------------------------------------------------:
         --------------------------------------------------------------------------------
         Node ID\\\\: $(nodeid_str|ljust:12)  Instance\\\\: $(instance-id)
         $(.path ~= detail ?
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         )--------------------------------------------------------------------------------
         Link ID      Oper   Enable                    
                      Status Status                    
         --------------------------------------------------------------------------------))
         $(link_idx_list|show))";
      leaf instance-id {
        type fabric-types:sfe_instance_type;
      }
      leaf nodeid_str {
        type string;
        tailf:hidden "internal";
      }
      leaf is_show {
        type boolean;
        tailf:hidden "internal";
      }
      list link_idx_list {
        key "link_idx";
        tailf:cli-suppress-table;
        tailf:cli-show-template-enter "";
        tailf:cli-show-template "$(.path ~= rx ?$(.path ~= topo ?$(link_id_str|ljust:12) $(speed|rjust:5)  $(stage|ljust:4) $(fab_plane|rjust:2)/$(fab_group|ljust:3) $(admin-state|rjust:2)/$(oper_state|ljust:3) $(flags|ljust:12) $(far_end_link_fsdb|ljust:13) $(far_end_link_hw|ljust:13)$(.path ~= detail ?$(history|show)):$(.path ~= flap ?$(link_id_str|ljust:14) $(oper_state|ljust:8) $(flap_cnt|rjust:6)    $(num_admin_shuts|rjust:6)    $(fsm_state|rjust:40)$(.path ~= detail ?$(history|show)):$(.path ~= stats ?$(.path ~= all ?$(link_id_str|ljust:12) $(RX_Control_cells_counter|rjust:13) $(RX_Data_cell_counter|rjust:13) $(RX_Data_byte_counter|rjust:13) $(RX_BEC_retransmit|rjust:12) $(RX_Asyn_fifo_rate|rjust:10):$(.path ~= ctrl ?$(link_id_str|ljust:12) $(RX_Control_cells_counter|rjust:15)$(RX_dropped_retransmitted_control|rjust:15) :$(link_id_str|ljust:12) $(RX_Data_cell_counter|rjust:13) $(RX_Data_byte_counter|rjust:13) $(RX_CRC_errors_counter|rjust:12) $(RX_LFEC_FEC_correctable_error|rjust:12) $(RX_LFEC_FEC_uncorrectable_errors|rjust:12)))))):$(.path ~= stats ?$(.path ~= all ?$(link_id_str|ljust:12) $(TX_Control_cells_counter|rjust:13) $(TX_Data_cell_counter|rjust:13) $(TX_Data_byte_counter|rjust:13) $(TX_BEC_retransmit|rjust:12) $(TX_Asyn_fifo_rate|rjust:10):$(.path ~= ctrl ?$(link_id_str|ljust:12) $(TX_Control_cells_counter|rjust:15):$(link_id_str|ljust:12) $(TX_Data_cell_counter|rjust:15) $(TX_Data_byte_counter|rjust:15))):$(link_id_str|ljust:12) $(oper_state|rjust:4)   $(admin-state|rjust:4)     $(fsm_state|rjust:40)$(.path ~= detail ?$(history|show))))\n";
        leaf link_idx {
          type int64;
        }
        leaf link_id_str {
          type string;
          tailf:hidden "internal";
        }
        leaf speed {
          type string;
          tailf:hidden "internal";
        }
        leaf stage {
          type string;
          tailf:hidden "internal";
        }
        leaf fab_plane {
          type uint32;
          tailf:hidden "internal";
        }
        leaf fab_group {
          type uint32;
          tailf:hidden "internal";
        }
        leaf flap_cnt {
          type uint32;
          tailf:hidden "internal";
        }
        leaf num_admin_shuts {
          type uint32;
          tailf:hidden "internal";
        }
        leaf admin-state {
          type string;
          tailf:hidden "internal";
        }
        leaf oper_state {
          type string;
          tailf:hidden "internal";
        }
        leaf flags {
          type string;
          tailf:hidden "internal";
        }
        leaf far_end_link_fsdb {
          type string;
          tailf:hidden "internal";
        }
        leaf far_end_link_hw {
          type string;
          tailf:hidden "internal";
        }
        leaf coeff1 {
          type uint32;
          tailf:hidden "internal";
        }
        leaf coeff2 {
          type uint32;
          tailf:hidden "internal";
        }
        leaf TX_Control_cells_counter {
          type uint64;
          tailf:hidden "internal";
        }
        leaf TX_Data_cell_counter {
          type uint64;
          tailf:hidden "internal";
        }
        leaf TX_Data_byte_counter {
          type uint64;
          tailf:hidden "internal";
        }
        leaf TX_BEC_retransmit {
          type uint64;
          tailf:hidden "internal";
        }
        leaf TX_Asyn_fifo_rate {
          type uint64;
          tailf:hidden "internal";
        }
        leaf RX_Control_cells_counter {
          type uint64;
          tailf:hidden "internal";
        }
        leaf RX_Data_cell_counter {
          type uint64;
          tailf:hidden "internal";
        }
        leaf RX_Data_byte_counter {
          type uint64;
          tailf:hidden "internal";
        }
        leaf RX_BEC_retransmit {
          type uint64;
          tailf:hidden "internal";
        }
        leaf RX_Asyn_fifo_rate {
          type uint64;
          tailf:hidden "internal";
        }
        leaf RX_CRC_errors_counter {
          type uint64;
          tailf:hidden "internal";
        }
        leaf RX_LFEC_FEC_correctable_error {
          type uint64;
          tailf:hidden "internal";
        }
        leaf RX_LFEC_FEC_uncorrectable_errors {
          type uint64;
          tailf:hidden "internal";
        }
        leaf RX_dropped_retransmitted_control {
          type uint64;
          tailf:hidden "internal";
        }
        leaf fsm_state {
          type string;
          tailf:hidden "internal";
        }
        list history {
          key "history_idx";
          tailf:cli-show-template-legend
            "
             +-----------------------------------------------------------------------------+
             | Timestamp                            Event(s)             Down Reasons      |
             +-----------------------------------------------------------------------------+
            ";
          tailf:cli-show-template "$(time_stamp|ljust:27) $(admin-state|ljust:10)$(oper_state|ljust:10)$(error_state|ljust:10)  $(down_reasons|ljust:12)\n";
          tailf:cli-suppress-table;
          tailf:cli-show-template-enter "";
          leaf history_idx {
            type int32;
          }
          leaf time_stamp {
            type string;
            tailf:hidden "internal";
          }
          leaf admin-state {
            type string;
            tailf:hidden "internal";
          }
          leaf oper_state {
            type string;
            tailf:hidden "internal";
          }
          leaf error_state {
            type string;
            tailf:hidden "internal";
          }
          leaf down_reasons {
            type string;
            tailf:hidden "internal";
          }
        }
      }
    }
  }

  grouping sfe_link_info_stats_asic_instance {
    container stats {
      container data {
        uses sfe_link_info_asic_instance;
      }
      container ctrl {
        uses sfe_link_info_asic_instance;
      }
      container all {
        uses sfe_link_info_asic_instance;
      }
    }
  }

  grouping sfe_statistics_asic_instance {
    list instance {
      key "instance-id";
      tailf:cli-no-key-completion;
      tailf:cli-no-match-completion;
      tailf:cli-suppress-table;
      tailf:cli-show-template-legend
        "$(.legend_shown != true ?Device statistics\\\\:
         )";
      tailf:cli-show-template-enter
        "$(is_show == true ?$(.legend_shown != true ?Device statistics\\\\:
         )============================================================
         Node\\\\: $(rack_num)/$(slot_num), Instance\\\\: $(asic_instance)
         ============================================================
         $(show_CCS == true ?CCS statistics\\\\: 
         ---------------------------------
         CCS statistics\\\\: 
         ---------------------------------
         CCS0 UnreachableDestinationCellsCnt\\\\:  $(CCS0_UnreachableDestinationCellsCnt)$(CCS0_UnreachableDestinationCellsCnt_ovf == true ? \\\\(ovf\\\\))
         CCS1 UnreachableDestinationCellsCnt\\\\:  $(CCS1_UnreachableDestinationCellsCnt)$(CCS1_UnreachableDestinationCellsCnt_ovf == true ? \\\\(ovf\\\\))
         CCS0 CaptureFifoDiscardCnt\\\\:           $(CCS0_CaptureFifoDiscardCnt)$(CCS0_CaptureFifoDiscardCnt_ovf == true ? \\\\(ovf\\\\))
         CCS1 CaptureFifoDiscardCnt\\\\:           $(CCS1_CaptureFifoDiscardCnt)$(CCS1_CaptureFifoDiscardCnt_ovf == true ? \\\\(ovf\\\\))
         CCS0 CdmaLpCellsDiscardCnt\\\\:           $(CCS0_CdmaLpCellsDiscardCnt)$(CCS0_CdmaLpCellsDiscardCnt_ovf == true ? \\\\(ovf\\\\))
         CCS1 CdmaLpCellsDiscardCnt\\\\:           $(CCS1_CdmaLpCellsDiscardCnt)$(CCS1_CdmaLpCellsDiscardCnt_ovf == true ? \\\\(ovf\\\\))
         CCS0 CdmbLpCellsDiscardCnt\\\\:           $(CCS0_CdmbLpCellsDiscardCnt)$(CCS0_CdmbLpCellsDiscardCnt_ovf == true ? \\\\(ovf\\\\))
         CCS1 CdmbLpCellsDiscardCnt\\\\:           $(CCS1_CdmbLpCellsDiscardCnt)$(CCS1_CdmbLpCellsDiscardCnt_ovf == true ? \\\\(ovf\\\\))
         CCS0 CrpParityErrCnt\\\\:                 $(CCS0_CrpParityErrCnt)$(CCS0_CrpParityErrCnt_ovf == true ? \\\\(ovf\\\\))
         CCS1 CrpParityErrCnt\\\\:                 $(CCS1_CrpParityErrCnt)$(CCS1_CrpParityErrCnt_ovf == true ? \\\\(ovf\\\\))
         CCS0 Ecc1bErrCnt\\\\:                     $(CCS0_Ecc_1bErrCnt)$(CCS0_Ecc_1bErrCnt_ovf == true ? \\\\(ovf\\\\))
         CCS1 Ecc1bErrCnt\\\\:                     $(CCS1_Ecc_1bErrCnt)$(CCS1_Ecc_1bErrCnt_ovf == true ? \\\\(ovf\\\\))
         CCS0 Ecc2bErrCnt\\\\:                     $(CCS0_Ecc_2bErrCnt)$(CCS0_Ecc_2bErrCnt_ovf == true ? \\\\(ovf\\\\))
         CCS1 Ecc2bErrCnt\\\\:                     $(CCS1_Ecc_2bErrCnt)$(CCS1_Ecc_2bErrCnt_ovf == true ? \\\\(ovf\\\\))
         )$(show_DCH == true ?
         DCH statistics\\\\: 
         ---------------------------------
         DCH0 FifoDiscardCounterP\\\\:             $(DCH0_FifoDiscardCounterP)$(DCH0_FifoDiscardCounterP_ovf == true ? \\\\(ovf\\\\))
         DCH1 FifoDiscardCounterP\\\\:             $(DCH1_FifoDiscardCounterP)$(DCH1_FifoDiscardCounterP_ovf == true ? \\\\(ovf\\\\))
         DCH2 FifoDiscardCounterP\\\\:             $(DCH2_FifoDiscardCounterP)$(DCH2_FifoDiscardCounterP_ovf == true ? \\\\(ovf\\\\))
         DCH3 FifoDiscardCounterP\\\\:             $(DCH3_FifoDiscardCounterP)$(DCH3_FifoDiscardCounterP_ovf == true ? \\\\(ovf\\\\))
         DCH0 DCHReordDiscardCounterP\\\\:         $(DCH0_DCHReordDiscardCounterP)$(DCH0_DCHReordDiscardCounterP_ovf == true ? \\\\(ovf\\\\))
         DCH1 DCHReordDiscardCounterP\\\\:         $(DCH1_DCHReordDiscardCounterP)$(DCH1_DCHReordDiscardCounterP_ovf == true ? \\\\(ovf\\\\))
         DCH2 DCHReordDiscardCounterP\\\\:         $(DCH2_DCHReordDiscardCounterP)$(DCH2_DCHReordDiscardCounterP_ovf == true ? \\\\(ovf\\\\))
         DCH3 DCHReordDiscardCounterP\\\\:         $(DCH3_DCHReordDiscardCounterP)$(DCH3_DCHReordDiscardCounterP_ovf == true ? \\\\(ovf\\\\))
         DCH0 FifoDiscardCounterS\\\\:             $(DCH0_FifoDiscardCounterS)$(DCH0_FifoDiscardCounterS_ovf == true ? \\\\(ovf\\\\))
         DCH1 FifoDiscardCounterS\\\\:             $(DCH1_FifoDiscardCounterS)$(DCH1_FifoDiscardCounterS_ovf == true ? \\\\(ovf\\\\))
         DCH2 FifoDiscardCounterS\\\\:             $(DCH2_FifoDiscardCounterS)$(DCH2_FifoDiscardCounterS_ovf == true ? \\\\(ovf\\\\))
         DCH3 FifoDiscardCounterS\\\\:             $(DCH3_FifoDiscardCounterS)$(DCH3_FifoDiscardCounterS_ovf == true ? \\\\(ovf\\\\))
         DCH0 DCHReordDiscardCounterS\\\\:         $(DCH0_DCHReordDiscardCounterS)$(DCH0_DCHReordDiscardCounterS_ovf == true ? \\\\(ovf\\\\))
         DCH1 DCHReordDiscardCounterS\\\\:         $(DCH1_DCHReordDiscardCounterS)$(DCH1_DCHReordDiscardCounterS_ovf == true ? \\\\(ovf\\\\))
         DCH2 DCHReordDiscardCounterS\\\\:         $(DCH2_DCHReordDiscardCounterS)$(DCH2_DCHReordDiscardCounterS_ovf == true ? \\\\(ovf\\\\))
         DCH3 DCHReordDiscardCounterS\\\\:         $(DCH3_DCHReordDiscardCounterS)$(DCH3_DCHReordDiscardCounterS_ovf == true ? \\\\(ovf\\\\))
         DCH0 UnreachDestCntP\\\\:                 $(DCH0_UnreachDestCntP)$(DCH0_UnreachDestCntP_ovf == true ? \\\\(ovf\\\\))
         DCH1 UnreachDestCntP\\\\:                 $(DCH1_UnreachDestCntP)$(DCH1_UnreachDestCntP_ovf == true ? \\\\(ovf\\\\))
         DCH2 UnreachDestCntP\\\\:                 $(DCH2_UnreachDestCntP)$(DCH2_UnreachDestCntP_ovf == true ? \\\\(ovf\\\\))
         DCH3 UnreachDestCntP\\\\:                 $(DCH3_UnreachDestCntP)$(DCH3_UnreachDestCntP_ovf == true ? \\\\(ovf\\\\))
         DCH0 UnreachDestCntS\\\\:                 $(DCH0_UnreachDestCntS)$(DCH0_UnreachDestCntS_ovf == true ? \\\\(ovf\\\\))
         DCH1 UnreachDestCntS\\\\:                 $(DCH1_UnreachDestCntS)$(DCH1_UnreachDestCntS_ovf == true ? \\\\(ovf\\\\))
         DCH2 UnreachDestCntS\\\\:                 $(DCH2_UnreachDestCntS)$(DCH2_UnreachDestCntS_ovf == true ? \\\\(ovf\\\\))
         DCH3 UnreachDestCntS\\\\:                 $(DCH3_UnreachDestCntS)$(DCH3_UnreachDestCntS_ovf == true ? \\\\(ovf\\\\))
         DCH0 DchDroppedLowMulCntP\\\\:            $(DCH0_DchDroppedLowMulCntP)$(DCH0_DchDroppedLowMulCntP_ovf == true ? \\\\(ovf\\\\))
         DCH1 DchDroppedLowMulCntP\\\\:            $(DCH1_DchDroppedLowMulCntP)$(DCH1_DchDroppedLowMulCntP_ovf == true ? \\\\(ovf\\\\))
         DCH2 DchDroppedLowMulCntP\\\\:            $(DCH2_DchDroppedLowMulCntP)$(DCH2_DchDroppedLowMulCntP_ovf == true ? \\\\(ovf\\\\))
         DCH3 DchDroppedLowMulCntP\\\\:            $(DCH3_DchDroppedLowMulCntP)$(DCH3_DchDroppedLowMulCntP_ovf == true ? \\\\(ovf\\\\))
         DCH0 DchDroppedLowMulCntS\\\\:            $(DCH0_DchDroppedLowMulCntS)$(DCH0_DchDroppedLowMulCntS_ovf == true ? \\\\(ovf\\\\))
         DCH1 DchDroppedLowMulCntS\\\\:            $(DCH1_DchDroppedLowMulCntS)$(DCH1_DchDroppedLowMulCntS_ovf == true ? \\\\(ovf\\\\))
         DCH2 DchDroppedLowMulCntS\\\\:            $(DCH2_DchDroppedLowMulCntS)$(DCH2_DchDroppedLowMulCntS_ovf == true ? \\\\(ovf\\\\))
         DCH3 DchDroppedLowMulCntS\\\\:            $(DCH3_DchDroppedLowMulCntS)$(DCH3_DchDroppedLowMulCntS_ovf == true ? \\\\(ovf\\\\))
         DCH0 ErrorFilterCntAP\\\\:                $(DCH0_ErrorFilterCntAP)$(DCH0_ErrorFilterCntAP_ovf == true ? \\\\(ovf\\\\))
         DCH1 ErrorFilterCntAP\\\\:                $(DCH1_ErrorFilterCntAP)$(DCH1_ErrorFilterCntAP_ovf == true ? \\\\(ovf\\\\))
         DCH2 ErrorFilterCntAP\\\\:                $(DCH2_ErrorFilterCntAP)$(DCH2_ErrorFilterCntAP_ovf == true ? \\\\(ovf\\\\))
         DCH3 ErrorFilterCntAP\\\\:                $(DCH3_ErrorFilterCntAP)$(DCH3_ErrorFilterCntAP_ovf == true ? \\\\(ovf\\\\))
         DCH0 ErrorFilterCntBP\\\\:                $(DCH0_ErrorFilterCntBP)$(DCH0_ErrorFilterCntBP_ovf == true ? \\\\(ovf\\\\))
         DCH1 ErrorFilterCntBP\\\\:                $(DCH1_ErrorFilterCntBP)$(DCH1_ErrorFilterCntBP_ovf == true ? \\\\(ovf\\\\))
         DCH2 ErrorFilterCntBP\\\\:                $(DCH2_ErrorFilterCntBP)$(DCH2_ErrorFilterCntBP_ovf == true ? \\\\(ovf\\\\))
         DCH3 ErrorFilterCntBP\\\\:                $(DCH3_ErrorFilterCntBP)$(DCH3_ErrorFilterCntBP_ovf == true ? \\\\(ovf\\\\))
         DCH0 ErrorFilterCntAS\\\\:                $(DCH0_ErrorFilterCntAS)$(DCH0_ErrorFilterCntAS_ovf == true ? \\\\(ovf\\\\))
         DCH1 ErrorFilterCntAS\\\\:                $(DCH1_ErrorFilterCntAS)$(DCH1_ErrorFilterCntAS_ovf == true ? \\\\(ovf\\\\))
         DCH2 ErrorFilterCntAS\\\\:                $(DCH2_ErrorFilterCntAS)$(DCH2_ErrorFilterCntAS_ovf == true ? \\\\(ovf\\\\))
         DCH3 ErrorFilterCntAS\\\\:                $(DCH3_ErrorFilterCntAS)$(DCH3_ErrorFilterCntAS_ovf == true ? \\\\(ovf\\\\))
         DCH0 ErrorFilterCntBS\\\\:                $(DCH0_ErrorFilterCntBS)$(DCH0_ErrorFilterCntBS_ovf == true ? \\\\(ovf\\\\))
         DCH1 ErrorFilterCntBS\\\\:                $(DCH1_ErrorFilterCntBS)$(DCH1_ErrorFilterCntBS_ovf == true ? \\\\(ovf\\\\))
         DCH2 ErrorFilterCntBS\\\\:                $(DCH2_ErrorFilterCntBS)$(DCH2_ErrorFilterCntBS_ovf == true ? \\\\(ovf\\\\))
         DCH3 ErrorFilterCntBS\\\\:                $(DCH3_ErrorFilterCntBS)$(DCH3_ErrorFilterCntBS_ovf == true ? \\\\(ovf\\\\))
         DCH0 DropLowPriCntP\\\\:                  $(DCH0_DropLowPriCntP)$(DCH0_DropLowPriCntP_ovf == true ? \\\\(ovf\\\\))
         DCH1 DropLowPriCntP\\\\:                  $(DCH1_DropLowPriCntP)$(DCH1_DropLowPriCntP_ovf == true ? \\\\(ovf\\\\))
         DCH2 DropLowPriCntP\\\\:                  $(DCH2_DropLowPriCntP)$(DCH2_DropLowPriCntP_ovf == true ? \\\\(ovf\\\\))
         DCH3 DropLowPriCntP\\\\:                  $(DCH3_DropLowPriCntP)$(DCH3_DropLowPriCntP_ovf == true ? \\\\(ovf\\\\))
         DCH0 DropLowPriCntS\\\\:                  $(DCH0_DropLowPriCntS)$(DCH0_DropLowPriCntS_ovf == true ? \\\\(ovf\\\\))
         DCH1 DropLowPriCntS\\\\:                  $(DCH1_DropLowPriCntS)$(DCH1_DropLowPriCntS_ovf == true ? \\\\(ovf\\\\))
         DCH2 DropLowPriCntS\\\\:                  $(DCH2_DropLowPriCntS)$(DCH2_DropLowPriCntS_ovf == true ? \\\\(ovf\\\\))
         DCH3 DropLowPriCntS\\\\:                  $(DCH3_DropLowPriCntS)$(DCH3_DropLowPriCntS_ovf == true ? \\\\(ovf\\\\))
         DCH0 Ecc1bErrCnt\\\\:                     $(DCH0_Ecc_1bErrCnt)$(DCH0_Ecc_1bErrCnt_ovf == true ? \\\\(ovf\\\\))
         DCH1 Ecc1bErrCnt\\\\:                     $(DCH1_Ecc_1bErrCnt)$(DCH1_Ecc_1bErrCnt_ovf == true ? \\\\(ovf\\\\))
         DCH2 Ecc1bErrCnt\\\\:                     $(DCH2_Ecc_1bErrCnt)$(DCH2_Ecc_1bErrCnt_ovf == true ? \\\\(ovf\\\\))
         DCH3 Ecc1bErrCnt\\\\:                     $(DCH3_Ecc_1bErrCnt)$(DCH3_Ecc_1bErrCnt_ovf == true ? \\\\(ovf\\\\))
         DCH0 Ecc2bErrCnt\\\\:                     $(DCH0_Ecc_2bErrCnt)$(DCH0_Ecc_2bErrCnt_ovf == true ? \\\\(ovf\\\\))
         DCH1 Ecc2bErrCnt\\\\:                     $(DCH1_Ecc_2bErrCnt)$(DCH1_Ecc_2bErrCnt_ovf == true ? \\\\(ovf\\\\))
         DCH2 Ecc2bErrCnt\\\\:                     $(DCH2_Ecc_2bErrCnt)$(DCH2_Ecc_2bErrCnt_ovf == true ? \\\\(ovf\\\\))
         DCH3 Ecc2bErrCnt\\\\:                     $(DCH3_Ecc_2bErrCnt)$(DCH3_Ecc_2bErrCnt_ovf == true ? \\\\(ovf\\\\))
         DCH0 ParityErrCnt\\\\:                    $(DCH0_ParityErrCnt)$(DCH0_ParityErrCnt_ovf == true ? \\\\(ovf\\\\))
         DCH1 ParityErrCnt\\\\:                    $(DCH1_ParityErrCnt)$(DCH1_ParityErrCnt_ovf == true ? \\\\(ovf\\\\))
         DCH2 ParityErrCnt\\\\:                    $(DCH2_ParityErrCnt)$(DCH2_ParityErrCnt_ovf == true ? \\\\(ovf\\\\))
         DCH3 ParityErrCnt\\\\:                    $(DCH3_ParityErrCnt)$(DCH3_ParityErrCnt_ovf == true ? \\\\(ovf\\\\))
         )$(show_DCl == true ?
         DCl statistics\\\\: 
         ---------------------------------
         DCL0 DclDroppedP0CntP\\\\:                $(DCL0_DclDroppedP0CntP)$(DCL0_DclDroppedP0CntP_ovf == true ? \\\\(ovf\\\\))
         DCL1 DclDroppedP0CntP\\\\:                $(DCL1_DclDroppedP0CntP)$(DCL1_DclDroppedP0CntP_ovf == true ? \\\\(ovf\\\\))
         DCL2 DclDroppedP0CntP\\\\:                $(DCL2_DclDroppedP0CntP)$(DCL2_DclDroppedP0CntP_ovf == true ? \\\\(ovf\\\\))
         DCL3 DclDroppedP0CntP\\\\:                $(DCL3_DclDroppedP0CntP)$(DCL3_DclDroppedP0CntP_ovf == true ? \\\\(ovf\\\\))
         DCL0 DclDroppedP1CntP\\\\:                $(DCL0_DclDroppedP1CntP)$(DCL0_DclDroppedP1CntP_ovf == true ? \\\\(ovf\\\\))
         DCL1 DclDroppedP1CntP\\\\:                $(DCL1_DclDroppedP1CntP)$(DCL1_DclDroppedP1CntP_ovf == true ? \\\\(ovf\\\\))
         DCL2 DclDroppedP1CntP\\\\:                $(DCL2_DclDroppedP1CntP)$(DCL2_DclDroppedP1CntP_ovf == true ? \\\\(ovf\\\\))
         DCL3 DclDroppedP1CntP\\\\:                $(DCL3_DclDroppedP1CntP)$(DCL3_DclDroppedP1CntP_ovf == true ? \\\\(ovf\\\\))
         DCL0 DclDroppedP2CntP\\\\:                $(DCL0_DclDroppedP2CntP)$(DCL0_DclDroppedP2CntP_ovf == true ? \\\\(ovf\\\\))
         DCL1 DclDroppedP2CntP\\\\:                $(DCL1_DclDroppedP2CntP)$(DCL1_DclDroppedP2CntP_ovf == true ? \\\\(ovf\\\\))
         DCL2 DclDroppedP2CntP\\\\:                $(DCL2_DclDroppedP2CntP)$(DCL2_DclDroppedP2CntP_ovf == true ? \\\\(ovf\\\\))
         DCL3 DclDroppedP2CntP\\\\:                $(DCL3_DclDroppedP2CntP)$(DCL3_DclDroppedP2CntP_ovf == true ? \\\\(ovf\\\\))
         DCL0 DclDroppedP3CntP\\\\:                $(DCL0_DclDroppedP3CntP)$(DCL0_DclDroppedP3CntP_ovf == true ? \\\\(ovf\\\\))
         DCL1 DclDroppedP3CntP\\\\:                $(DCL1_DclDroppedP3CntP)$(DCL1_DclDroppedP3CntP_ovf == true ? \\\\(ovf\\\\))
         DCL2 DclDroppedP3CntP\\\\:                $(DCL2_DclDroppedP3CntP)$(DCL2_DclDroppedP3CntP_ovf == true ? \\\\(ovf\\\\))
         DCL3 DclDroppedP3CntP\\\\:                $(DCL3_DclDroppedP3CntP)$(DCL3_DclDroppedP3CntP_ovf == true ? \\\\(ovf\\\\))
         DCL0 DclDroppedP0CntS\\\\:                $(DCL0_DclDroppedP0CntS)$(DCL0_DclDroppedP0CntS_ovf == true ? \\\\(ovf\\\\))
         DCL1 DclDroppedP0CntS\\\\:                $(DCL1_DclDroppedP0CntS)$(DCL1_DclDroppedP0CntS_ovf == true ? \\\\(ovf\\\\))
         DCL2 DclDroppedP0CntS\\\\:                $(DCL2_DclDroppedP0CntS)$(DCL2_DclDroppedP0CntS_ovf == true ? \\\\(ovf\\\\))
         DCL3 DclDroppedP0CntS\\\\:                $(DCL3_DclDroppedP0CntS)$(DCL3_DclDroppedP0CntS_ovf == true ? \\\\(ovf\\\\))
         DCL0 DclDroppedP1CntS\\\\:                $(DCL0_DclDroppedP1CntS)$(DCL0_DclDroppedP1CntS_ovf == true ? \\\\(ovf\\\\))
         DCL1 DclDroppedP1CntS\\\\:                $(DCL1_DclDroppedP1CntS)$(DCL1_DclDroppedP1CntS_ovf == true ? \\\\(ovf\\\\))
         DCL2 DclDroppedP1CntS\\\\:                $(DCL2_DclDroppedP1CntS)$(DCL2_DclDroppedP1CntS_ovf == true ? \\\\(ovf\\\\))
         DCL3 DclDroppedP1CntS\\\\:                $(DCL3_DclDroppedP1CntS)$(DCL3_DclDroppedP1CntS_ovf == true ? \\\\(ovf\\\\))
         DCL0 DclDroppedP2CntS\\\\:                $(DCL0_DclDroppedP2CntS)$(DCL0_DclDroppedP2CntS_ovf == true ? \\\\(ovf\\\\))
         DCL1 DclDroppedP2CntS\\\\:                $(DCL1_DclDroppedP2CntS)$(DCL1_DclDroppedP2CntS_ovf == true ? \\\\(ovf\\\\))
         DCL2 DclDroppedP2CntS\\\\:                $(DCL2_DclDroppedP2CntS)$(DCL2_DclDroppedP2CntS_ovf == true ? \\\\(ovf\\\\))
         DCL3 DclDroppedP2CntS\\\\:                $(DCL3_DclDroppedP2CntS)$(DCL3_DclDroppedP2CntS_ovf == true ? \\\\(ovf\\\\))
         DCL0 DclDroppedP3CntS\\\\:                $(DCL0_DclDroppedP3CntS)$(DCL0_DclDroppedP3CntS_ovf == true ? \\\\(ovf\\\\))
         DCL1 DclDroppedP3CntS\\\\:                $(DCL1_DclDroppedP3CntS)$(DCL1_DclDroppedP3CntS_ovf == true ? \\\\(ovf\\\\))
         DCL2 DclDroppedP3CntS\\\\:                $(DCL2_DclDroppedP3CntS)$(DCL2_DclDroppedP3CntS_ovf == true ? \\\\(ovf\\\\))
         DCL2 DclDroppedP3CntS\\\\:                $(DCL3_DclDroppedP3CntS)$(DCL3_DclDroppedP3CntS_ovf == true ? \\\\(ovf\\\\))
         DCL0 CCP0CIfDscrdCnt\\\\:                 $(DCL0_CCP0CIfDscrdCnt)$(DCL0_CCP0CIfDscrdCnt_ovf == true ? \\\\(ovf\\\\))
         DCL1 CCP0CIfDscrdCnt\\\\:                 $(DCL1_CCP0CIfDscrdCnt)$(DCL1_CCP0CIfDscrdCnt_ovf == true ? \\\\(ovf\\\\))
         DCL2 CCP0CIfDscrdCnt\\\\:                 $(DCL2_CCP0CIfDscrdCnt)$(DCL2_CCP0CIfDscrdCnt_ovf == true ? \\\\(ovf\\\\))
         DCL3 CCP0CIfDscrdCnt\\\\:                 $(DCL3_CCP0CIfDscrdCnt)$(DCL3_CCP0CIfDscrdCnt_ovf == true ? \\\\(ovf\\\\))
         DCL0 CCP1CIfDscrdCnt\\\\:                 $(DCL0_CCP1CIfDscrdCnt)$(DCL0_CCP1CIfDscrdCnt_ovf == true ? \\\\(ovf\\\\))
         DCL1 CCP1CIfDscrdCnt\\\\:                 $(DCL1_CCP1CIfDscrdCnt)$(DCL1_CCP1CIfDscrdCnt_ovf == true ? \\\\(ovf\\\\))
         DCL2 CCP1CIfDscrdCnt\\\\:                 $(DCL2_CCP1CIfDscrdCnt)$(DCL2_CCP1CIfDscrdCnt_ovf == true ? \\\\(ovf\\\\))
         DCL3 CCP1CIfDscrdCnt\\\\:                 $(DCL3_CCP1CIfDscrdCnt)$(DCL3_CCP1CIfDscrdCnt_ovf == true ? \\\\(ovf\\\\))
         DCL0 Ecc1bErrCnt\\\\:                     $(DCL0_Ecc_1bErrCnt)$(DCL0_Ecc_1bErrCnt_ovf == true ? \\\\(ovf\\\\))
         DCL1 Ecc1bErrCnt\\\\:                     $(DCL1_Ecc_1bErrCnt)$(DCL1_Ecc_1bErrCnt_ovf == true ? \\\\(ovf\\\\))
         DCL2 Ecc1bErrCnt\\\\:                     $(DCL2_Ecc_1bErrCnt)$(DCL2_Ecc_1bErrCnt_ovf == true ? \\\\(ovf\\\\))
         DCL3 Ecc1bErrCnt\\\\:                     $(DCL3_Ecc_1bErrCnt)$(DCL3_Ecc_1bErrCnt_ovf == true ? \\\\(ovf\\\\))
         DCL0 Ecc2bErrCnt\\\\:                     $(DCL0_Ecc_2bErrCnt)$(DCL0_Ecc_2bErrCnt_ovf == true ? \\\\(ovf\\\\))
         DCL1 Ecc2bErrCnt\\\\:                     $(DCL1_Ecc_2bErrCnt)$(DCL1_Ecc_2bErrCnt_ovf == true ? \\\\(ovf\\\\))
         DCL2 Ecc2bErrCnt\\\\:                     $(DCL2_Ecc_2bErrCnt)$(DCL2_Ecc_2bErrCnt_ovf == true ? \\\\(ovf\\\\))
         DCL3 Ecc2bErrCnt\\\\:                     $(DCL3_Ecc_2bErrCnt)$(DCL3_Ecc_2bErrCnt_ovf == true ? \\\\(ovf\\\\))
         DCL0 ParityErrCnt\\\\:                    $(DCL0_ParityErrCnt)$(DCL0_ParityErrCnt_ovf == true ? \\\\(ovf\\\\))
         DCL1 ParityErrCnt\\\\:                    $(DCL1_ParityErrCnt)$(DCL1_ParityErrCnt_ovf == true ? \\\\(ovf\\\\))
         DCL2 ParityErrCnt\\\\:                    $(DCL2_ParityErrCnt)$(DCL2_ParityErrCnt_ovf == true ? \\\\(ovf\\\\))
         DCL3 ParityErrCnt\\\\:                    $(DCL3_ParityErrCnt)$(DCL3_ParityErrCnt_ovf == true ? \\\\(ovf\\\\))
         DCL0 TagParErrCnt\\\\:                    $(DCL0_TagParErrCnt)$(DCL0_TagParErrCnt_ovf == true ? \\\\(ovf\\\\))
         DCL1 TagParErrCnt\\\\:                    $(DCL1_TagParErrCnt)$(DCL1_TagParErrCnt_ovf == true ? \\\\(ovf\\\\))
         DCL2 TagParErrCnt\\\\:                    $(DCL2_TagParErrCnt)$(DCL2_TagParErrCnt_ovf == true ? \\\\(ovf\\\\))
         DCL3 TagParErrCnt\\\\:                    $(DCL3_TagParErrCnt)$(DCL3_TagParErrCnt_ovf == true ? \\\\(ovf\\\\))
         DCL0 DataCrcErrCnt\\\\:                   $(DCL0_DataCrcErrCnt)$(DCL0_DataCrcErrCnt_ovf == true ? \\\\(ovf\\\\))
         DCL1 DataCrcErrCnt\\\\:                   $(DCL1_DataCrcErrCnt)$(DCL1_DataCrcErrCnt_ovf == true ? \\\\(ovf\\\\))
         DCL2 DataCrcErrCnt\\\\:                   $(DCL2_DataCrcErrCnt)$(DCL2_DataCrcErrCnt_ovf == true ? \\\\(ovf\\\\))
         DCL3 DataCrcErrCnt\\\\:                   $(DCL3_DataCrcErrCnt)$(DCL3_DataCrcErrCnt_ovf == true ? \\\\(ovf\\\\))
         )$(show_DCMA == true ?
         DCMA statistics\\\\: 
         ---------------------------------
         DCMA0 DcmmDroppedIp0\\\\:                 $(DCMA0_DcmmDroppedIp0)$(DCMA0_DcmmDroppedIp0_ovf == true ? \\\\(ovf\\\\))
         DCMA1 DcmmDroppedIp0\\\\:                 $(DCMA1_DcmmDroppedIp0)$(DCMA1_DcmmDroppedIp0_ovf == true ? \\\\(ovf\\\\))
         DCMA0 DcmmDroppedIp1\\\\:                 $(DCMA0_DcmmDroppedIp1)$(DCMA0_DcmmDroppedIp1_ovf == true ? \\\\(ovf\\\\))
         DCMA1 DcmmDroppedIp1\\\\:                 $(DCMA1_DcmmDroppedIp1)$(DCMA1_DcmmDroppedIp1_ovf == true ? \\\\(ovf\\\\))
         DCMA0 DcmmDroppedIp2\\\\:                 $(DCMA0_DcmmDroppedIp2)$(DCMA0_DcmmDroppedIp2_ovf == true ? \\\\(ovf\\\\))
         DCMA1 DcmmDroppedIp2\\\\:                 $(DCMA1_DcmmDroppedIp2)$(DCMA1_DcmmDroppedIp2_ovf == true ? \\\\(ovf\\\\))
         DCMA0 DcmmDroppedIp3\\\\:                 $(DCMA0_DcmmDroppedIp3)$(DCMA0_DcmmDroppedIp3_ovf == true ? \\\\(ovf\\\\))
         DCMA1 DcmmDroppedIp3\\\\:                 $(DCMA1_DcmmDroppedIp3)$(DCMA1_DcmmDroppedIp3_ovf == true ? \\\\(ovf\\\\))
         DCMA0 DcmmDroppedTotalCnt\\\\:            $(DCMA0_DcmmDroppedTotalCnt)$(DCMA0_DcmmDroppedTotalCnt_ovf == true ? \\\\(ovf\\\\))
         DCMA1 DcmmDroppedTotalCnt\\\\:            $(DCMA1_DcmmDroppedTotalCnt)$(DCMA1_DcmmDroppedTotalCnt_ovf == true ? \\\\(ovf\\\\))
         DCMA0 DcmuDroppedIp0\\\\:                 $(DCMA0_DcmuDroppedIp0)$(DCMA0_DcmuDroppedIp0_ovf == true ? \\\\(ovf\\\\))
         DCMA1 DcmuDroppedIp0\\\\:                 $(DCMA1_DcmuDroppedIp0)$(DCMA1_DcmuDroppedIp0_ovf == true ? \\\\(ovf\\\\))
         DCMA0 DcmuDroppedIp1\\\\:                 $(DCMA0_DcmuDroppedIp1)$(DCMA0_DcmuDroppedIp1_ovf == true ? \\\\(ovf\\\\))
         DCMA1 DcmuDroppedIp1\\\\:                 $(DCMA1_DcmuDroppedIp1)$(DCMA1_DcmuDroppedIp1_ovf == true ? \\\\(ovf\\\\))
         DCMA0 DcmmDroppedIp2\\\\:                 $(DCMA0_DcmuDroppedIp2)$(DCMA0_DcmuDroppedIp2_ovf == true ? \\\\(ovf\\\\))
         DCMA1 DcmuDroppedIp2\\\\:                 $(DCMA1_DcmuDroppedIp2)$(DCMA1_DcmuDroppedIp2_ovf == true ? \\\\(ovf\\\\))
         DCMA0 DcmuDroppedIp3\\\\:                 $(DCMA0_DcmuDroppedIp3)$(DCMA0_DcmuDroppedIp3_ovf == true ? \\\\(ovf\\\\))
         DCMA1 DcmuDroppedIp3\\\\:                 $(DCMA1_DcmuDroppedIp3)$(DCMA1_DcmuDroppedIp3_ovf == true ? \\\\(ovf\\\\))
         DCMA0 DcmuDroppedTotalCnt\\\\:            $(DCMA0_DcmuDroppedTotalCnt)$(DCMA0_DcmuDroppedTotalCnt_ovf == true ? \\\\(ovf\\\\))
         DCMA1 DcmuDroppedTotalCnt\\\\:            $(DCMA1_DcmuDroppedTotalCnt)$(DCMA1_DcmuDroppedTotalCnt_ovf == true ? \\\\(ovf\\\\))
         DCMA0 Ecc1bErrCnt\\\\:                    $(DCMA0_Ecc_1bErrCnt)$(DCMA0_Ecc_1bErrCnt_ovf == true ? \\\\(ovf\\\\))
         DCMA1 Ecc1bErrCnt\\\\:                    $(DCMA1_Ecc_1bErrCnt)$(DCMA1_Ecc_1bErrCnt_ovf == true ? \\\\(ovf\\\\))
         DCMA0 Ecc2bErrCnt\\\\:                    $(DCMA0_Ecc_2bErrCnt)$(DCMA0_Ecc_2bErrCnt_ovf == true ? \\\\(ovf\\\\))
         DCMA1 Ecc2bErrCnt\\\\:                    $(DCMA1_Ecc_2bErrCnt)$(DCMA1_Ecc_2bErrCnt_ovf == true ? \\\\(ovf\\\\))
         DCMA0 ParityErrCnt\\\\:                   $(DCMA0_ParityErrCnt)$(DCMA0_ParityErrCnt_ovf == true ? \\\\(ovf\\\\))
         DCMA1 ParityErrCnt\\\\:                   $(DCMA1_ParityErrCnt)$(DCMA1_ParityErrCnt_ovf == true ? \\\\(ovf\\\\))
         )$(show_DCMB == true ?
         DCMB statistics\\\\: 
         ---------------------------------
         DCMB0 DcmmDroppedIp0\\\\:                 $(DCMB0_DcmmDroppedIp0)$(DCMB0_DcmmDroppedIp0_ovf == true ? \\\\(ovf\\\\))
         DCMB1 DcmmDroppedIp0\\\\:                 $(DCMB1_DcmmDroppedIp0)$(DCMB1_DcmmDroppedIp0_ovf == true ? \\\\(ovf\\\\))
         DCMB0 DcmmDroppedIp1\\\\:                 $(DCMB0_DcmmDroppedIp1)$(DCMB0_DcmmDroppedIp1_ovf == true ? \\\\(ovf\\\\))
         DCMB1 DcmmDroppedIp1\\\\:                 $(DCMB1_DcmmDroppedIp1)$(DCMB1_DcmmDroppedIp1_ovf == true ? \\\\(ovf\\\\))
         DCMB0 DcmmDroppedIp2\\\\:                 $(DCMB0_DcmmDroppedIp2)$(DCMB0_DcmmDroppedIp2_ovf == true ? \\\\(ovf\\\\))
         DCMB1 DcmmDroppedIp2\\\\:                 $(DCMB1_DcmmDroppedIp2)$(DCMB1_DcmmDroppedIp2_ovf == true ? \\\\(ovf\\\\))
         DCMB0 DcmmDroppedIp3\\\\:                 $(DCMB0_DcmmDroppedIp3)$(DCMB0_DcmmDroppedIp3_ovf == true ? \\\\(ovf\\\\))
         DCMB1 DcmmDroppedIp3\\\\:                 $(DCMB1_DcmmDroppedIp3)$(DCMB1_DcmmDroppedIp3_ovf == true ? \\\\(ovf\\\\))
         DCMB0 DcmmDroppedTotalCnt\\\\:            $(DCMB0_DcmmDroppedTotalCnt)$(DCMB0_DcmmDroppedTotalCnt_ovf == true ? \\\\(ovf\\\\))
         DCMB1 DcmmDroppedTotalCnt\\\\:            $(DCMB1_DcmmDroppedTotalCnt)$(DCMB1_DcmmDroppedTotalCnt_ovf == true ? \\\\(ovf\\\\))
         DCMB0 DcmuDroppedIp0\\\\:                 $(DCMB0_DcmuDroppedIp0)$(DCMB0_DcmuDroppedIp0_ovf == true ? \\\\(ovf\\\\))
         DCMB1 DcmuDroppedIp0\\\\:                 $(DCMB1_DcmuDroppedIp0)$(DCMB1_DcmuDroppedIp0_ovf == true ? \\\\(ovf\\\\))
         DCMB0 DcmuDroppedIp1\\\\:                 $(DCMB0_DcmuDroppedIp1)$(DCMB0_DcmuDroppedIp1_ovf == true ? \\\\(ovf\\\\))
         DCMB1 DcmuDroppedIp1\\\\:                 $(DCMB1_DcmuDroppedIp1)$(DCMB1_DcmuDroppedIp1_ovf == true ? \\\\(ovf\\\\))
         DCMB0 DcmmDroppedIp2\\\\:                 $(DCMB0_DcmuDroppedIp2)$(DCMB0_DcmuDroppedIp2_ovf == true ? \\\\(ovf\\\\))
         DCMB1 DcmuDroppedIp2\\\\:                 $(DCMB1_DcmuDroppedIp2)$(DCMB1_DcmuDroppedIp2_ovf == true ? \\\\(ovf\\\\))
         DCMB0 DcmuDroppedIp3\\\\:                 $(DCMB0_DcmuDroppedIp3)$(DCMB0_DcmuDroppedIp3_ovf == true ? \\\\(ovf\\\\))
         DCMB1 DcmuDroppedIp3\\\\:                 $(DCMB1_DcmuDroppedIp3)$(DCMB1_DcmuDroppedIp3_ovf == true ? \\\\(ovf\\\\))
         DCMB0 DcmuDroppedTotalCnt\\\\:            $(DCMB0_DcmuDroppedTotalCnt)$(DCMB0_DcmuDroppedTotalCnt_ovf == true ? \\\\(ovf\\\\))
         DCMB1 DcmuDroppedTotalCnt\\\\:            $(DCMB1_DcmuDroppedTotalCnt)$(DCMB1_DcmuDroppedTotalCnt_ovf == true ? \\\\(ovf\\\\))
         DCMB0 Ecc1bErrCnt\\\\:                    $(DCMB0_Ecc_1bErrCnt)$(DCMB0_Ecc_1bErrCnt_ovf == true ? \\\\(ovf\\\\))
         DCMB1 Ecc1bErrCnt\\\\:                    $(DCMB1_Ecc_1bErrCnt)$(DCMB1_Ecc_1bErrCnt_ovf == true ? \\\\(ovf\\\\))
         DCMB0 Ecc2bErrCnt\\\\:                    $(DCMB0_Ecc_2bErrCnt)$(DCMB0_Ecc_2bErrCnt_ovf == true ? \\\\(ovf\\\\))
         DCMB1 Ecc2bErrCnt\\\\:                    $(DCMB1_Ecc_2bErrCnt)$(DCMB1_Ecc_2bErrCnt_ovf == true ? \\\\(ovf\\\\))
         DCMB0 ParityErrCnt\\\\:                   $(DCMB0_ParityErrCnt)$(DCMB0_ParityErrCnt_ovf == true ? \\\\(ovf\\\\))
         DCMB1 ParityErrCnt\\\\:                   $(DCMB1_ParityErrCnt)$(DCMB1_ParityErrCnt_ovf == true ? \\\\(ovf\\\\))
         )$(show_ECI == true ?
         ECI statistics\\\\: 
         ---------------------------------
         ECI ParityErrCnt\\\\:                     $(ECI_ParityErrCnt)$(ECI_ParityErrCnt_ovf == true ? \\\\(ovf\\\\))
         )$(show_RTP == true ?
         RTP statistics\\\\: 
         ---------------------------------
         RTP Ecc1bErrCnt\\\\:                      $(RTP_Ecc_1bErrCnt)$(RTP_Ecc_1bErrCnt_ovf == true ? \\\\(ovf\\\\))
         RTP Ecc2bErrCnt\\\\:                      $(RTP_Ecc_2bErrCnt)$(RTP_Ecc_2bErrCnt_ovf == true ? \\\\(ovf\\\\))
         RTP ParityErrCnt\\\\:                     $(RTP_ParityErrCnt)$(RTP_ParityErrCnt_ovf == true ? \\\\(ovf\\\\))
         )$(show_FMAC == true ?
         FMAC statistics\\\\: 
         ---------------------------------
         FMAC0 Ecc1bErrCnt\\\\:                   $(FMAC0_Ecc_1bErrCnt)$(FMAC0_Ecc_1bErrCnt_ovf == true ? \\\\(ovf\\\\))
         FMAC1 Ecc1bErrCnt\\\\:                   $(FMAC1_Ecc_1bErrCnt)$(FMAC1_Ecc_1bErrCnt_ovf == true ? \\\\(ovf\\\\))
         FMAC2 Ecc1bErrCnt\\\\:                   $(FMAC2_Ecc_1bErrCnt)$(FMAC2_Ecc_1bErrCnt_ovf == true ? \\\\(ovf\\\\))
         FMAC3 Ecc1bErrCnt\\\\:                   $(FMAC3_Ecc_1bErrCnt)$(FMAC3_Ecc_1bErrCnt_ovf == true ? \\\\(ovf\\\\))
         FMAC4 Ecc1bErrCnt\\\\:                   $(FMAC4_Ecc_1bErrCnt)$(FMAC4_Ecc_1bErrCnt_ovf == true ? \\\\(ovf\\\\))
         FMAC5 Ecc1bErrCnt\\\\:                   $(FMAC5_Ecc_1bErrCnt)$(FMAC5_Ecc_1bErrCnt_ovf == true ? \\\\(ovf\\\\))
         FMAC6 Ecc1bErrCnt\\\\:                   $(FMAC6_Ecc_1bErrCnt)$(FMAC6_Ecc_1bErrCnt_ovf == true ? \\\\(ovf\\\\))
         FMAC7 Ecc1bErrCnt\\\\:                   $(FMAC7_Ecc_1bErrCnt)$(FMAC7_Ecc_1bErrCnt_ovf == true ? \\\\(ovf\\\\))
         FMAC8 Ecc1bErrCnt\\\\:                   $(FMAC8_Ecc_1bErrCnt)$(FMAC8_Ecc_1bErrCnt_ovf == true ? \\\\(ovf\\\\))
         FMAC9 Ecc1bErrCnt\\\\:                   $(FMAC9_Ecc_1bErrCnt)$(FMAC9_Ecc_1bErrCnt_ovf == true ? \\\\(ovf\\\\))
         FMAC10 Ecc1bErrCnt\\\\:                  $(FMAC10_Ecc_1bErrCnt)$(FMAC10_Ecc_1bErrCnt_ovf == true ? \\\\(ovf\\\\))
         FMAC11 Ecc1bErrCnt\\\\:                  $(FMAC11_Ecc_1bErrCnt)$(FMAC11_Ecc_1bErrCnt_ovf == true ? \\\\(ovf\\\\))
         FMAC12 Ecc1bErrCnt\\\\:                  $(FMAC12_Ecc_1bErrCnt)$(FMAC12_Ecc_1bErrCnt_ovf == true ? \\\\(ovf\\\\))
         FMAC13 Ecc1bErrCnt\\\\:                  $(FMAC13_Ecc_1bErrCnt)$(FMAC13_Ecc_1bErrCnt_ovf == true ? \\\\(ovf\\\\))
         FMAC14 Ecc1bErrCnt\\\\:                  $(FMAC14_Ecc_1bErrCnt)$(FMAC14_Ecc_1bErrCnt_ovf == true ? \\\\(ovf\\\\))
         FMAC15 Ecc1bErrCnt\\\\:                  $(FMAC15_Ecc_1bErrCnt)$(FMAC15_Ecc_1bErrCnt_ovf == true ? \\\\(ovf\\\\))
         FMAC16 Ecc1bErrCnt\\\\:                  $(FMAC16_Ecc_1bErrCnt)$(FMAC16_Ecc_1bErrCnt_ovf == true ? \\\\(ovf\\\\))
         FMAC17 Ecc1bErrCnt\\\\:                  $(FMAC17_Ecc_1bErrCnt)$(FMAC17_Ecc_1bErrCnt_ovf == true ? \\\\(ovf\\\\))
         FMAC18 Ecc1bErrCnt\\\\:                  $(FMAC18_Ecc_1bErrCnt)$(FMAC18_Ecc_1bErrCnt_ovf == true ? \\\\(ovf\\\\))
         FMAC19 Ecc1bErrCnt\\\\:                  $(FMAC19_Ecc_1bErrCnt)$(FMAC19_Ecc_1bErrCnt_ovf == true ? \\\\(ovf\\\\))
         FMAC20 Ecc1bErrCnt\\\\:                  $(FMAC20_Ecc_1bErrCnt)$(FMAC20_Ecc_1bErrCnt_ovf == true ? \\\\(ovf\\\\))
         FMAC21 Ecc1bErrCnt\\\\:                  $(FMAC21_Ecc_1bErrCnt)$(FMAC21_Ecc_1bErrCnt_ovf == true ? \\\\(ovf\\\\))
         FMAC22 Ecc1bErrCnt\\\\:                  $(FMAC22_Ecc_1bErrCnt)$(FMAC22_Ecc_1bErrCnt_ovf == true ? \\\\(ovf\\\\))
         FMAC23 Ecc1bErrCnt\\\\:                  $(FMAC23_Ecc_1bErrCnt)$(FMAC23_Ecc_1bErrCnt_ovf == true ? \\\\(ovf\\\\))
         FMAC24 Ecc1bErrCnt\\\\:                  $(FMAC24_Ecc_1bErrCnt)$(FMAC24_Ecc_1bErrCnt_ovf == true ? \\\\(ovf\\\\))
         FMAC25 Ecc1bErrCnt\\\\:                  $(FMAC25_Ecc_1bErrCnt)$(FMAC25_Ecc_1bErrCnt_ovf == true ? \\\\(ovf\\\\))
         FMAC26 Ecc1bErrCnt\\\\:                  $(FMAC26_Ecc_1bErrCnt)$(FMAC26_Ecc_1bErrCnt_ovf == true ? \\\\(ovf\\\\))
         FMAC27 Ecc1bErrCnt\\\\:                  $(FMAC27_Ecc_1bErrCnt)$(FMAC27_Ecc_1bErrCnt_ovf == true ? \\\\(ovf\\\\))
         FMAC28 Ecc1bErrCnt\\\\:                  $(FMAC28_Ecc_1bErrCnt)$(FMAC28_Ecc_1bErrCnt_ovf == true ? \\\\(ovf\\\\))
         FMAC29 Ecc1bErrCnt\\\\:                  $(FMAC29_Ecc_1bErrCnt)$(FMAC29_Ecc_1bErrCnt_ovf == true ? \\\\(ovf\\\\))
         FMAC30 Ecc1bErrCnt\\\\:                  $(FMAC30_Ecc_1bErrCnt)$(FMAC30_Ecc_1bErrCnt_ovf == true ? \\\\(ovf\\\\))
         FMAC31 Ecc1bErrCnt\\\\:                  $(FMAC31_Ecc_1bErrCnt)$(FMAC31_Ecc_1bErrCnt_ovf == true ? \\\\(ovf\\\\))
         FMAC0 Ecc2bErrCnt\\\\:                   $(FMAC0_Ecc_2bErrCnt)$(FMAC0_Ecc_2bErrCnt_ovf == true ? \\\\(ovf\\\\))
         FMAC1 Ecc2bErrCnt\\\\:                   $(FMAC1_Ecc_2bErrCnt)$(FMAC1_Ecc_2bErrCnt_ovf == true ? \\\\(ovf\\\\))
         FMAC2 Ecc2bErrCnt\\\\:                   $(FMAC2_Ecc_2bErrCnt)$(FMAC2_Ecc_2bErrCnt_ovf == true ? \\\\(ovf\\\\))
         FMAC3 Ecc2bErrCnt\\\\:                   $(FMAC3_Ecc_2bErrCnt)$(FMAC3_Ecc_2bErrCnt_ovf == true ? \\\\(ovf\\\\))
         FMAC4 Ecc2bErrCnt\\\\:                   $(FMAC4_Ecc_2bErrCnt)$(FMAC4_Ecc_2bErrCnt_ovf == true ? \\\\(ovf\\\\))
         FMAC5 Ecc2bErrCnt\\\\:                   $(FMAC5_Ecc_2bErrCnt)$(FMAC5_Ecc_2bErrCnt_ovf == true ? \\\\(ovf\\\\))
         FMAC6 Ecc2bErrCnt\\\\:                   $(FMAC6_Ecc_2bErrCnt)$(FMAC6_Ecc_2bErrCnt_ovf == true ? \\\\(ovf\\\\))
         FMAC7 Ecc2bErrCnt\\\\:                   $(FMAC7_Ecc_2bErrCnt)$(FMAC7_Ecc_2bErrCnt_ovf == true ? \\\\(ovf\\\\))
         FMAC8 Ecc2bErrCnt\\\\:                   $(FMAC8_Ecc_2bErrCnt)$(FMAC8_Ecc_2bErrCnt_ovf == true ? \\\\(ovf\\\\))
         FMAC9 Ecc2bErrCnt\\\\:                   $(FMAC9_Ecc_2bErrCnt)$(FMAC9_Ecc_2bErrCnt_ovf == true ? \\\\(ovf\\\\))
         FMAC10 Ecc2bErrCnt\\\\:                  $(FMAC10_Ecc_2bErrCnt)$(FMAC10_Ecc_2bErrCnt_ovf == true ? \\\\(ovf\\\\))
         FMAC11 Ecc2bErrCnt\\\\:                  $(FMAC11_Ecc_2bErrCnt)$(FMAC11_Ecc_2bErrCnt_ovf == true ? \\\\(ovf\\\\))
         FMAC12 Ecc2bErrCnt\\\\:                  $(FMAC12_Ecc_2bErrCnt)$(FMAC12_Ecc_2bErrCnt_ovf == true ? \\\\(ovf\\\\))
         FMAC13 Ecc2bErrCnt\\\\:                  $(FMAC13_Ecc_2bErrCnt)$(FMAC13_Ecc_2bErrCnt_ovf == true ? \\\\(ovf\\\\))
         FMAC14 Ecc2bErrCnt\\\\:                  $(FMAC14_Ecc_2bErrCnt)$(FMAC14_Ecc_2bErrCnt_ovf == true ? \\\\(ovf\\\\))
         FMAC15 Ecc2bErrCnt\\\\:                  $(FMAC15_Ecc_2bErrCnt)$(FMAC15_Ecc_2bErrCnt_ovf == true ? \\\\(ovf\\\\))
         FMAC16 Ecc2bErrCnt\\\\:                  $(FMAC16_Ecc_2bErrCnt)$(FMAC16_Ecc_2bErrCnt_ovf == true ? \\\\(ovf\\\\))
         FMAC17 Ecc2bErrCnt\\\\:                  $(FMAC17_Ecc_2bErrCnt)$(FMAC17_Ecc_2bErrCnt_ovf == true ? \\\\(ovf\\\\))
         FMAC18 Ecc2bErrCnt\\\\:                  $(FMAC18_Ecc_2bErrCnt)$(FMAC18_Ecc_2bErrCnt_ovf == true ? \\\\(ovf\\\\))
         FMAC19 Ecc2bErrCnt\\\\:                  $(FMAC19_Ecc_2bErrCnt)$(FMAC19_Ecc_2bErrCnt_ovf == true ? \\\\(ovf\\\\))
         FMAC20 Ecc2bErrCnt\\\\:                  $(FMAC20_Ecc_2bErrCnt)$(FMAC20_Ecc_2bErrCnt_ovf == true ? \\\\(ovf\\\\))
         FMAC21 Ecc2bErrCnt\\\\:                  $(FMAC21_Ecc_2bErrCnt)$(FMAC21_Ecc_2bErrCnt_ovf == true ? \\\\(ovf\\\\))
         FMAC22 Ecc2bErrCnt\\\\:                  $(FMAC22_Ecc_2bErrCnt)$(FMAC22_Ecc_2bErrCnt_ovf == true ? \\\\(ovf\\\\))
         FMAC23 Ecc2bErrCnt\\\\:                  $(FMAC23_Ecc_2bErrCnt)$(FMAC23_Ecc_2bErrCnt_ovf == true ? \\\\(ovf\\\\))
         FMAC24 Ecc2bErrCnt\\\\:                  $(FMAC24_Ecc_2bErrCnt)$(FMAC24_Ecc_2bErrCnt_ovf == true ? \\\\(ovf\\\\))
         FMAC25 Ecc2bErrCnt\\\\:                  $(FMAC25_Ecc_2bErrCnt)$(FMAC25_Ecc_2bErrCnt_ovf == true ? \\\\(ovf\\\\))
         FMAC26 Ecc2bErrCnt\\\\:                  $(FMAC26_Ecc_2bErrCnt)$(FMAC26_Ecc_2bErrCnt_ovf == true ? \\\\(ovf\\\\))
         FMAC27 Ecc2bErrCnt\\\\:                  $(FMAC27_Ecc_2bErrCnt)$(FMAC27_Ecc_2bErrCnt_ovf == true ? \\\\(ovf\\\\))
         FMAC28 Ecc2bErrCnt\\\\:                  $(FMAC28_Ecc_2bErrCnt)$(FMAC28_Ecc_2bErrCnt_ovf == true ? \\\\(ovf\\\\))
         FMAC29 Ecc2bErrCnt\\\\:                  $(FMAC29_Ecc_2bErrCnt)$(FMAC29_Ecc_2bErrCnt_ovf == true ? \\\\(ovf\\\\))
         FMAC30 Ecc2bErrCnt\\\\:                  $(FMAC30_Ecc_2bErrCnt)$(FMAC30_Ecc_2bErrCnt_ovf == true ? \\\\(ovf\\\\))
         FMAC31 Ecc2bErrCnt\\\\:                  $(FMAC31_Ecc_2bErrCnt)$(FMAC31_Ecc_2bErrCnt_ovf == true ? \\\\(ovf\\\\))
         )
         )";
      leaf instance-id {
        type fabric-types:sfe_instance_type;
      }
      leaf rack_num {
        type uint32;
        tailf:hidden "internal";
      }
      leaf slot_num {
        type uint32;
        tailf:hidden "internal";
      }
      leaf asic_instance {
        type uint32;
        tailf:hidden "internal";
      }
      leaf CCS0_UnreachableDestinationCellsCnt_ovf {
        type boolean;
        tailf:hidden "internal";
      }
      leaf CCS1_UnreachableDestinationCellsCnt_ovf {
        type boolean;
        tailf:hidden "internal";
      }
      leaf CCS0_CaptureFifoDiscardCnt_ovf {
        type boolean;
        tailf:hidden "internal";
      }
      leaf CCS1_CaptureFifoDiscardCnt_ovf {
        type boolean;
        tailf:hidden "internal";
      }
      leaf CCS0_CdmaLpCellsDiscardCnt_ovf {
        type boolean;
        tailf:hidden "internal";
      }
      leaf CCS1_CdmaLpCellsDiscardCnt_ovf {
        type boolean;
        tailf:hidden "internal";
      }
      leaf CCS0_CdmbLpCellsDiscardCnt_ovf {
        type boolean;
        tailf:hidden "internal";
      }
      leaf CCS1_CdmbLpCellsDiscardCnt_ovf {
        type boolean;
        tailf:hidden "internal";
      }
      leaf CCS0_CrpParityErrCnt_ovf {
        type boolean;
        tailf:hidden "internal";
      }
      leaf CCS1_CrpParityErrCnt_ovf {
        type boolean;
        tailf:hidden "internal";
      }
      leaf CCS0_Ecc_1bErrCnt_ovf {
        type boolean;
        tailf:hidden "internal";
      }
      leaf CCS1_Ecc_1bErrCnt_ovf {
        type boolean;
        tailf:hidden "internal";
      }
      leaf CCS0_Ecc_2bErrCnt_ovf {
        type boolean;
        tailf:hidden "internal";
      }
      leaf CCS1_Ecc_2bErrCnt_ovf {
        type boolean;
        tailf:hidden "internal";
      }
      leaf DCH0_FifoDiscardCounterP_ovf {
        type boolean;
        tailf:hidden "internal";
      }
      leaf DCH1_FifoDiscardCounterP_ovf {
        type boolean;
        tailf:hidden "internal";
      }
      leaf DCH2_FifoDiscardCounterP_ovf {
        type boolean;
        tailf:hidden "internal";
      }
      leaf DCH3_FifoDiscardCounterP_ovf {
        type boolean;
        tailf:hidden "internal";
      }
      leaf DCH0_DCHReordDiscardCounterP_ovf {
        type boolean;
        tailf:hidden "internal";
      }
      leaf DCH1_DCHReordDiscardCounterP_ovf {
        type boolean;
        tailf:hidden "internal";
      }
      leaf DCH2_DCHReordDiscardCounterP_ovf {
        type boolean;
        tailf:hidden "internal";
      }
      leaf DCH3_DCHReordDiscardCounterP_ovf {
        type boolean;
        tailf:hidden "internal";
      }
      leaf DCH0_FifoDiscardCounterS_ovf {
        type boolean;
        tailf:hidden "internal";
      }
      leaf DCH1_FifoDiscardCounterS_ovf {
        type boolean;
        tailf:hidden "internal";
      }
      leaf DCH2_FifoDiscardCounterS_ovf {
        type boolean;
        tailf:hidden "internal";
      }
      leaf DCH3_FifoDiscardCounterS_ovf {
        type boolean;
        tailf:hidden "internal";
      }
      leaf DCH0_DCHReordDiscardCounterS_ovf {
        type boolean;
        tailf:hidden "internal";
      }
      leaf DCH1_DCHReordDiscardCounterS_ovf {
        type boolean;
        tailf:hidden "internal";
      }
      leaf DCH2_DCHReordDiscardCounterS_ovf {
        type boolean;
        tailf:hidden "internal";
      }
      leaf DCH3_DCHReordDiscardCounterS_ovf {
        type boolean;
        tailf:hidden "internal";
      }
      leaf DCH0_UnreachDestCntP_ovf {
        type boolean;
        tailf:hidden "internal";
      }
      leaf DCH1_UnreachDestCntP_ovf {
        type boolean;
        tailf:hidden "internal";
      }
      leaf DCH2_UnreachDestCntP_ovf {
        type boolean;
        tailf:hidden "internal";
      }
      leaf DCH3_UnreachDestCntP_ovf {
        type boolean;
        tailf:hidden "internal";
      }
      leaf DCH0_UnreachDestCntS_ovf {
        type boolean;
        tailf:hidden "internal";
      }
      leaf DCH1_UnreachDestCntS_ovf {
        type boolean;
        tailf:hidden "internal";
      }
      leaf DCH2_UnreachDestCntS_ovf {
        type boolean;
        tailf:hidden "internal";
      }
      leaf DCH3_UnreachDestCntS_ovf {
        type boolean;
        tailf:hidden "internal";
      }
      leaf DCH0_DchDroppedLowMulCntP_ovf {
        type boolean;
        tailf:hidden "internal";
      }
      leaf DCH1_DchDroppedLowMulCntP_ovf {
        type boolean;
        tailf:hidden "internal";
      }
      leaf DCH2_DchDroppedLowMulCntP_ovf {
        type boolean;
        tailf:hidden "internal";
      }
      leaf DCH3_DchDroppedLowMulCntP_ovf {
        type boolean;
        tailf:hidden "internal";
      }
      leaf DCH0_DchDroppedLowMulCntS_ovf {
        type boolean;
        tailf:hidden "internal";
      }
      leaf DCH1_DchDroppedLowMulCntS_ovf {
        type boolean;
        tailf:hidden "internal";
      }
      leaf DCH2_DchDroppedLowMulCntS_ovf {
        type boolean;
        tailf:hidden "internal";
      }
      leaf DCH3_DchDroppedLowMulCntS_ovf {
        type boolean;
        tailf:hidden "internal";
      }
      leaf DCH0_ErrorFilterCntAP_ovf {
        type boolean;
        tailf:hidden "internal";
      }
      leaf DCH1_ErrorFilterCntAP_ovf {
        type boolean;
        tailf:hidden "internal";
      }
      leaf DCH2_ErrorFilterCntAP_ovf {
        type boolean;
        tailf:hidden "internal";
      }
      leaf DCH3_ErrorFilterCntAP_ovf {
        type boolean;
        tailf:hidden "internal";
      }
      leaf DCH0_ErrorFilterCntBP_ovf {
        type boolean;
        tailf:hidden "internal";
      }
      leaf DCH1_ErrorFilterCntBP_ovf {
        type boolean;
        tailf:hidden "internal";
      }
      leaf DCH2_ErrorFilterCntBP_ovf {
        type boolean;
        tailf:hidden "internal";
      }
      leaf DCH3_ErrorFilterCntBP_ovf {
        type boolean;
        tailf:hidden "internal";
      }
      leaf DCH0_ErrorFilterCntAS_ovf {
        type boolean;
        tailf:hidden "internal";
      }
      leaf DCH1_ErrorFilterCntAS_ovf {
        type boolean;
        tailf:hidden "internal";
      }
      leaf DCH2_ErrorFilterCntAS_ovf {
        type boolean;
        tailf:hidden "internal";
      }
      leaf DCH3_ErrorFilterCntAS_ovf {
        type boolean;
        tailf:hidden "internal";
      }
      leaf DCH0_ErrorFilterCntBS_ovf {
        type boolean;
        tailf:hidden "internal";
      }
      leaf DCH1_ErrorFilterCntBS_ovf {
        type boolean;
        tailf:hidden "internal";
      }
      leaf DCH2_ErrorFilterCntBS_ovf {
        type boolean;
        tailf:hidden "internal";
      }
      leaf DCH3_ErrorFilterCntBS_ovf {
        type boolean;
        tailf:hidden "internal";
      }
      leaf DCH0_DropLowPriCntP_ovf {
        type boolean;
        tailf:hidden "internal";
      }
      leaf DCH1_DropLowPriCntP_ovf {
        type boolean;
        tailf:hidden "internal";
      }
      leaf DCH2_DropLowPriCntP_ovf {
        type boolean;
        tailf:hidden "internal";
      }
      leaf DCH3_DropLowPriCntP_ovf {
        type boolean;
        tailf:hidden "internal";
      }
      leaf DCH0_DropLowPriCntS_ovf {
        type boolean;
        tailf:hidden "internal";
      }
      leaf DCH1_DropLowPriCntS_ovf {
        type boolean;
        tailf:hidden "internal";
      }
      leaf DCH2_DropLowPriCntS_ovf {
        type boolean;
        tailf:hidden "internal";
      }
      leaf DCH3_DropLowPriCntS_ovf {
        type boolean;
        tailf:hidden "internal";
      }
      leaf DCH0_Ecc_1bErrCnt_ovf {
        type boolean;
        tailf:hidden "internal";
      }
      leaf DCH1_Ecc_1bErrCnt_ovf {
        type boolean;
        tailf:hidden "internal";
      }
      leaf DCH2_Ecc_1bErrCnt_ovf {
        type boolean;
        tailf:hidden "internal";
      }
      leaf DCH3_Ecc_1bErrCnt_ovf {
        type boolean;
        tailf:hidden "internal";
      }
      leaf DCH0_Ecc_2bErrCnt_ovf {
        type boolean;
        tailf:hidden "internal";
      }
      leaf DCH1_Ecc_2bErrCnt_ovf {
        type boolean;
        tailf:hidden "internal";
      }
      leaf DCH2_Ecc_2bErrCnt_ovf {
        type boolean;
        tailf:hidden "internal";
      }
      leaf DCH3_Ecc_2bErrCnt_ovf {
        type boolean;
        tailf:hidden "internal";
      }
      leaf DCH0_ParityErrCnt_ovf {
        type boolean;
        tailf:hidden "internal";
      }
      leaf DCH1_ParityErrCnt_ovf {
        type boolean;
        tailf:hidden "internal";
      }
      leaf DCH2_ParityErrCnt_ovf {
        type boolean;
        tailf:hidden "internal";
      }
      leaf DCH3_ParityErrCnt_ovf {
        type boolean;
        tailf:hidden "internal";
      }
      leaf DCL0_DclDroppedP0CntP_ovf {
        type boolean;
        tailf:hidden "internal";
      }
      leaf DCL1_DclDroppedP0CntP_ovf {
        type boolean;
        tailf:hidden "internal";
      }
      leaf DCL2_DclDroppedP0CntP_ovf {
        type boolean;
        tailf:hidden "internal";
      }
      leaf DCL3_DclDroppedP0CntP_ovf {
        type boolean;
        tailf:hidden "internal";
      }
      leaf DCL0_DclDroppedP1CntP_ovf {
        type boolean;
        tailf:hidden "internal";
      }
      leaf DCL1_DclDroppedP1CntP_ovf {
        type boolean;
        tailf:hidden "internal";
      }
      leaf DCL2_DclDroppedP1CntP_ovf {
        type boolean;
        tailf:hidden "internal";
      }
      leaf DCL3_DclDroppedP1CntP_ovf {
        type boolean;
        tailf:hidden "internal";
      }
      leaf DCL0_DclDroppedP2CntP_ovf {
        type boolean;
        tailf:hidden "internal";
      }
      leaf DCL1_DclDroppedP2CntP_ovf {
        type boolean;
        tailf:hidden "internal";
      }
      leaf DCL2_DclDroppedP2CntP_ovf {
        type boolean;
        tailf:hidden "internal";
      }
      leaf DCL3_DclDroppedP2CntP_ovf {
        type boolean;
        tailf:hidden "internal";
      }
      leaf DCL0_DclDroppedP3CntP_ovf {
        type boolean;
        tailf:hidden "internal";
      }
      leaf DCL1_DclDroppedP3CntP_ovf {
        type boolean;
        tailf:hidden "internal";
      }
      leaf DCL2_DclDroppedP3CntP_ovf {
        type boolean;
        tailf:hidden "internal";
      }
      leaf DCL3_DclDroppedP3CntP_ovf {
        type boolean;
        tailf:hidden "internal";
      }
      leaf DCL0_DclDroppedP0CntS_ovf {
        type boolean;
        tailf:hidden "internal";
      }
      leaf DCL1_DclDroppedP0CntS_ovf {
        type boolean;
        tailf:hidden "internal";
      }
      leaf DCL2_DclDroppedP0CntS_ovf {
        type boolean;
        tailf:hidden "internal";
      }
      leaf DCL3_DclDroppedP0CntS_ovf {
        type boolean;
        tailf:hidden "internal";
      }
      leaf DCL0_DclDroppedP1CntS_ovf {
        type boolean;
        tailf:hidden "internal";
      }
      leaf DCL1_DclDroppedP1CntS_ovf {
        type boolean;
        tailf:hidden "internal";
      }
      leaf DCL2_DclDroppedP1CntS_ovf {
        type boolean;
        tailf:hidden "internal";
      }
      leaf DCL3_DclDroppedP1CntS_ovf {
        type boolean;
        tailf:hidden "internal";
      }
      leaf DCL0_DclDroppedP2CntS_ovf {
        type boolean;
        tailf:hidden "internal";
      }
      leaf DCL1_DclDroppedP2CntS_ovf {
        type boolean;
        tailf:hidden "internal";
      }
      leaf DCL2_DclDroppedP2CntS_ovf {
        type boolean;
        tailf:hidden "internal";
      }
      leaf DCL3_DclDroppedP2CntS_ovf {
        type boolean;
        tailf:hidden "internal";
      }
      leaf DCL0_DclDroppedP3CntS_ovf {
        type boolean;
        tailf:hidden "internal";
      }
      leaf DCL1_DclDroppedP3CntS_ovf {
        type boolean;
        tailf:hidden "internal";
      }
      leaf DCL2_DclDroppedP3CntS_ovf {
        type boolean;
        tailf:hidden "internal";
      }
      leaf DCL3_DclDroppedP3CntS_ovf {
        type boolean;
        tailf:hidden "internal";
      }
      leaf DCL0_CCP0CIfDscrdCnt_ovf {
        type boolean;
        tailf:hidden "internal";
      }
      leaf DCL1_CCP0CIfDscrdCnt_ovf {
        type boolean;
        tailf:hidden "internal";
      }
      leaf DCL2_CCP0CIfDscrdCnt_ovf {
        type boolean;
        tailf:hidden "internal";
      }
      leaf DCL3_CCP0CIfDscrdCnt_ovf {
        type boolean;
        tailf:hidden "internal";
      }
      leaf DCL0_CCP1CIfDscrdCnt_ovf {
        type boolean;
        tailf:hidden "internal";
      }
      leaf DCL1_CCP1CIfDscrdCnt_ovf {
        type boolean;
        tailf:hidden "internal";
      }
      leaf DCL2_CCP1CIfDscrdCnt_ovf {
        type boolean;
        tailf:hidden "internal";
      }
      leaf DCL3_CCP1CIfDscrdCnt_ovf {
        type boolean;
        tailf:hidden "internal";
      }
      leaf DCL0_Ecc_1bErrCnt_ovf {
        type boolean;
        tailf:hidden "internal";
      }
      leaf DCL1_Ecc_1bErrCnt_ovf {
        type boolean;
        tailf:hidden "internal";
      }
      leaf DCL2_Ecc_1bErrCnt_ovf {
        type boolean;
        tailf:hidden "internal";
      }
      leaf DCL3_Ecc_1bErrCnt_ovf {
        type boolean;
        tailf:hidden "internal";
      }
      leaf DCL0_Ecc_2bErrCnt_ovf {
        type boolean;
        tailf:hidden "internal";
      }
      leaf DCL1_Ecc_2bErrCnt_ovf {
        type boolean;
        tailf:hidden "internal";
      }
      leaf DCL2_Ecc_2bErrCnt_ovf {
        type boolean;
        tailf:hidden "internal";
      }
      leaf DCL3_Ecc_2bErrCnt_ovf {
        type boolean;
        tailf:hidden "internal";
      }
      leaf DCL0_ParityErrCnt_ovf {
        type boolean;
        tailf:hidden "internal";
      }
      leaf DCL1_ParityErrCnt_ovf {
        type boolean;
        tailf:hidden "internal";
      }
      leaf DCL2_ParityErrCnt_ovf {
        type boolean;
        tailf:hidden "internal";
      }
      leaf DCL3_ParityErrCnt_ovf {
        type boolean;
        tailf:hidden "internal";
      }
      leaf DCL0_TagParErrCnt_ovf {
        type boolean;
        tailf:hidden "internal";
      }
      leaf DCL1_TagParErrCnt_ovf {
        type boolean;
        tailf:hidden "internal";
      }
      leaf DCL2_TagParErrCnt_ovf {
        type boolean;
        tailf:hidden "internal";
      }
      leaf DCL3_TagParErrCnt_ovf {
        type boolean;
        tailf:hidden "internal";
      }
      leaf DCL0_DataCrcErrCnt_ovf {
        type boolean;
        tailf:hidden "internal";
      }
      leaf DCL1_DataCrcErrCnt_ovf {
        type boolean;
        tailf:hidden "internal";
      }
      leaf DCL2_DataCrcErrCnt_ovf {
        type boolean;
        tailf:hidden "internal";
      }
      leaf DCL3_DataCrcErrCnt_ovf {
        type boolean;
        tailf:hidden "internal";
      }
      leaf DCMA0_DcmmDroppedIp0_ovf {
        type boolean;
        tailf:hidden "internal";
      }
      leaf DCMA1_DcmmDroppedIp0_ovf {
        type boolean;
        tailf:hidden "internal";
      }
      leaf DCMA0_DcmmDroppedIp1_ovf {
        type boolean;
        tailf:hidden "internal";
      }
      leaf DCMA1_DcmmDroppedIp1_ovf {
        type boolean;
        tailf:hidden "internal";
      }
      leaf DCMA0_DcmmDroppedIp2_ovf {
        type boolean;
        tailf:hidden "internal";
      }
      leaf DCMA1_DcmmDroppedIp2_ovf {
        type boolean;
        tailf:hidden "internal";
      }
      leaf DCMA0_DcmmDroppedIp3_ovf {
        type boolean;
        tailf:hidden "internal";
      }
      leaf DCMA1_DcmmDroppedIp3_ovf {
        type boolean;
        tailf:hidden "internal";
      }
      leaf DCMA0_DcmmDroppedTotalCnt_ovf {
        type boolean;
        tailf:hidden "internal";
      }
      leaf DCMA1_DcmmDroppedTotalCnt_ovf {
        type boolean;
        tailf:hidden "internal";
      }
      leaf DCMA0_DcmuDroppedIp0_ovf {
        type boolean;
        tailf:hidden "internal";
      }
      leaf DCMA1_DcmuDroppedIp0_ovf {
        type boolean;
        tailf:hidden "internal";
      }
      leaf DCMA0_DcmuDroppedIp1_ovf {
        type boolean;
        tailf:hidden "internal";
      }
      leaf DCMA1_DcmuDroppedIp1_ovf {
        type boolean;
        tailf:hidden "internal";
      }
      leaf DCMA0_DcmuDroppedIp2_ovf {
        type boolean;
        tailf:hidden "internal";
      }
      leaf DCMA1_DcmuDroppedIp2_ovf {
        type boolean;
        tailf:hidden "internal";
      }
      leaf DCMA0_DcmuDroppedIp3_ovf {
        type boolean;
        tailf:hidden "internal";
      }
      leaf DCMA1_DcmuDroppedIp3_ovf {
        type boolean;
        tailf:hidden "internal";
      }
      leaf DCMA0_DcmuDroppedTotalCnt_ovf {
        type boolean;
        tailf:hidden "internal";
      }
      leaf DCMA1_DcmuDroppedTotalCnt_ovf {
        type boolean;
        tailf:hidden "internal";
      }
      leaf DCMA0_Ecc_1bErrCnt_ovf {
        type boolean;
        tailf:hidden "internal";
      }
      leaf DCMA1_Ecc_1bErrCnt_ovf {
        type boolean;
        tailf:hidden "internal";
      }
      leaf DCMA0_Ecc_2bErrCnt_ovf {
        type boolean;
        tailf:hidden "internal";
      }
      leaf DCMA1_Ecc_2bErrCnt_ovf {
        type boolean;
        tailf:hidden "internal";
      }
      leaf DCMA0_ParityErrCnt_ovf {
        type boolean;
        tailf:hidden "internal";
      }
      leaf DCMA1_ParityErrCnt_ovf {
        type boolean;
        tailf:hidden "internal";
      }
      leaf DCMB0_DcmmDroppedIp0_ovf {
        type boolean;
        tailf:hidden "internal";
      }
      leaf DCMB1_DcmmDroppedIp0_ovf {
        type boolean;
        tailf:hidden "internal";
      }
      leaf DCMB0_DcmmDroppedIp1_ovf {
        type boolean;
        tailf:hidden "internal";
      }
      leaf DCMB1_DcmmDroppedIp1_ovf {
        type boolean;
        tailf:hidden "internal";
      }
      leaf DCMB0_DcmmDroppedIp2_ovf {
        type boolean;
        tailf:hidden "internal";
      }
      leaf DCMB1_DcmmDroppedIp2_ovf {
        type boolean;
        tailf:hidden "internal";
      }
      leaf DCMB0_DcmmDroppedIp3_ovf {
        type boolean;
        tailf:hidden "internal";
      }
      leaf DCMB1_DcmmDroppedIp3_ovf {
        type boolean;
        tailf:hidden "internal";
      }
      leaf DCMB0_DcmmDroppedTotalCnt_ovf {
        type boolean;
        tailf:hidden "internal";
      }
      leaf DCMB1_DcmmDroppedTotalCnt_ovf {
        type boolean;
        tailf:hidden "internal";
      }
      leaf DCMB0_DcmuDroppedIp0_ovf {
        type boolean;
        tailf:hidden "internal";
      }
      leaf DCMB1_DcmuDroppedIp0_ovf {
        type boolean;
        tailf:hidden "internal";
      }
      leaf DCMB0_DcmuDroppedIp1_ovf {
        type boolean;
        tailf:hidden "internal";
      }
      leaf DCMB1_DcmuDroppedIp1_ovf {
        type boolean;
        tailf:hidden "internal";
      }
      leaf DCMB0_DcmuDroppedIp2_ovf {
        type boolean;
        tailf:hidden "internal";
      }
      leaf DCMB1_DcmuDroppedIp2_ovf {
        type boolean;
        tailf:hidden "internal";
      }
      leaf DCMB0_DcmuDroppedIp3_ovf {
        type boolean;
        tailf:hidden "internal";
      }
      leaf DCMB1_DcmuDroppedIp3_ovf {
        type boolean;
        tailf:hidden "internal";
      }
      leaf DCMB0_DcmuDroppedTotalCnt_ovf {
        type boolean;
        tailf:hidden "internal";
      }
      leaf DCMB1_DcmuDroppedTotalCnt_ovf {
        type boolean;
        tailf:hidden "internal";
      }
      leaf DCMB0_Ecc_1bErrCnt_ovf {
        type boolean;
        tailf:hidden "internal";
      }
      leaf DCMB1_Ecc_1bErrCnt_ovf {
        type boolean;
        tailf:hidden "internal";
      }
      leaf DCMB0_Ecc_2bErrCnt_ovf {
        type boolean;
        tailf:hidden "internal";
      }
      leaf DCMB1_Ecc_2bErrCnt_ovf {
        type boolean;
        tailf:hidden "internal";
      }
      leaf DCMB0_ParityErrCnt_ovf {
        type boolean;
        tailf:hidden "internal";
      }
      leaf DCMB1_ParityErrCnt_ovf {
        type boolean;
        tailf:hidden "internal";
      }
      leaf ECI_ParityErrCnt_ovf {
        type boolean;
        tailf:hidden "internal";
      }
      leaf RTP_Ecc_1bErrCnt_ovf {
        type boolean;
        tailf:hidden "internal";
      }
      leaf RTP_Ecc_2bErrCnt_ovf {
        type boolean;
        tailf:hidden "internal";
      }
      leaf RTP_ParityErrCnt_ovf {
        type boolean;
        tailf:hidden "internal";
      }
      leaf FMAC0_Ecc_1bErrCnt_ovf {
        type boolean;
        tailf:hidden "internal";
      }
      leaf FMAC1_Ecc_1bErrCnt_ovf {
        type boolean;
        tailf:hidden "internal";
      }
      leaf FMAC2_Ecc_1bErrCnt_ovf {
        type boolean;
        tailf:hidden "internal";
      }
      leaf FMAC3_Ecc_1bErrCnt_ovf {
        type boolean;
        tailf:hidden "internal";
      }
      leaf FMAC4_Ecc_1bErrCnt_ovf {
        type boolean;
        tailf:hidden "internal";
      }
      leaf FMAC5_Ecc_1bErrCnt_ovf {
        type boolean;
        tailf:hidden "internal";
      }
      leaf FMAC6_Ecc_1bErrCnt_ovf {
        type boolean;
        tailf:hidden "internal";
      }
      leaf FMAC7_Ecc_1bErrCnt_ovf {
        type boolean;
        tailf:hidden "internal";
      }
      leaf FMAC8_Ecc_1bErrCnt_ovf {
        type boolean;
        tailf:hidden "internal";
      }
      leaf FMAC9_Ecc_1bErrCnt_ovf {
        type boolean;
        tailf:hidden "internal";
      }
      leaf FMAC10_Ecc_1bErrCnt_ovf {
        type boolean;
        tailf:hidden "internal";
      }
      leaf FMAC11_Ecc_1bErrCnt_ovf {
        type boolean;
        tailf:hidden "internal";
      }
      leaf FMAC12_Ecc_1bErrCnt_ovf {
        type boolean;
        tailf:hidden "internal";
      }
      leaf FMAC13_Ecc_1bErrCnt_ovf {
        type boolean;
        tailf:hidden "internal";
      }
      leaf FMAC14_Ecc_1bErrCnt_ovf {
        type boolean;
        tailf:hidden "internal";
      }
      leaf FMAC15_Ecc_1bErrCnt_ovf {
        type boolean;
        tailf:hidden "internal";
      }
      leaf FMAC16_Ecc_1bErrCnt_ovf {
        type boolean;
        tailf:hidden "internal";
      }
      leaf FMAC17_Ecc_1bErrCnt_ovf {
        type boolean;
        tailf:hidden "internal";
      }
      leaf FMAC18_Ecc_1bErrCnt_ovf {
        type boolean;
        tailf:hidden "internal";
      }
      leaf FMAC19_Ecc_1bErrCnt_ovf {
        type boolean;
        tailf:hidden "internal";
      }
      leaf FMAC20_Ecc_1bErrCnt_ovf {
        type boolean;
        tailf:hidden "internal";
      }
      leaf FMAC21_Ecc_1bErrCnt_ovf {
        type boolean;
        tailf:hidden "internal";
      }
      leaf FMAC22_Ecc_1bErrCnt_ovf {
        type boolean;
        tailf:hidden "internal";
      }
      leaf FMAC23_Ecc_1bErrCnt_ovf {
        type boolean;
        tailf:hidden "internal";
      }
      leaf FMAC24_Ecc_1bErrCnt_ovf {
        type boolean;
        tailf:hidden "internal";
      }
      leaf FMAC25_Ecc_1bErrCnt_ovf {
        type boolean;
        tailf:hidden "internal";
      }
      leaf FMAC26_Ecc_1bErrCnt_ovf {
        type boolean;
        tailf:hidden "internal";
      }
      leaf FMAC27_Ecc_1bErrCnt_ovf {
        type boolean;
        tailf:hidden "internal";
      }
      leaf FMAC28_Ecc_1bErrCnt_ovf {
        type boolean;
        tailf:hidden "internal";
      }
      leaf FMAC29_Ecc_1bErrCnt_ovf {
        type boolean;
        tailf:hidden "internal";
      }
      leaf FMAC30_Ecc_1bErrCnt_ovf {
        type boolean;
        tailf:hidden "internal";
      }
      leaf FMAC31_Ecc_1bErrCnt_ovf {
        type boolean;
        tailf:hidden "internal";
      }
      leaf FMAC0_Ecc_2bErrCnt_ovf {
        type boolean;
        tailf:hidden "internal";
      }
      leaf FMAC1_Ecc_2bErrCnt_ovf {
        type boolean;
        tailf:hidden "internal";
      }
      leaf FMAC2_Ecc_2bErrCnt_ovf {
        type boolean;
        tailf:hidden "internal";
      }
      leaf FMAC3_Ecc_2bErrCnt_ovf {
        type boolean;
        tailf:hidden "internal";
      }
      leaf FMAC4_Ecc_2bErrCnt_ovf {
        type boolean;
        tailf:hidden "internal";
      }
      leaf FMAC5_Ecc_2bErrCnt_ovf {
        type boolean;
        tailf:hidden "internal";
      }
      leaf FMAC6_Ecc_2bErrCnt_ovf {
        type boolean;
        tailf:hidden "internal";
      }
      leaf FMAC7_Ecc_2bErrCnt_ovf {
        type boolean;
        tailf:hidden "internal";
      }
      leaf FMAC8_Ecc_2bErrCnt_ovf {
        type boolean;
        tailf:hidden "internal";
      }
      leaf FMAC9_Ecc_2bErrCnt_ovf {
        type boolean;
        tailf:hidden "internal";
      }
      leaf FMAC10_Ecc_2bErrCnt_ovf {
        type boolean;
        tailf:hidden "internal";
      }
      leaf FMAC11_Ecc_2bErrCnt_ovf {
        type boolean;
        tailf:hidden "internal";
      }
      leaf FMAC12_Ecc_2bErrCnt_ovf {
        type boolean;
        tailf:hidden "internal";
      }
      leaf FMAC13_Ecc_2bErrCnt_ovf {
        type boolean;
        tailf:hidden "internal";
      }
      leaf FMAC14_Ecc_2bErrCnt_ovf {
        type boolean;
        tailf:hidden "internal";
      }
      leaf FMAC15_Ecc_2bErrCnt_ovf {
        type boolean;
        tailf:hidden "internal";
      }
      leaf FMAC16_Ecc_2bErrCnt_ovf {
        type boolean;
        tailf:hidden "internal";
      }
      leaf FMAC17_Ecc_2bErrCnt_ovf {
        type boolean;
        tailf:hidden "internal";
      }
      leaf FMAC18_Ecc_2bErrCnt_ovf {
        type boolean;
        tailf:hidden "internal";
      }
      leaf FMAC19_Ecc_2bErrCnt_ovf {
        type boolean;
        tailf:hidden "internal";
      }
      leaf FMAC20_Ecc_2bErrCnt_ovf {
        type boolean;
        tailf:hidden "internal";
      }
      leaf FMAC21_Ecc_2bErrCnt_ovf {
        type boolean;
        tailf:hidden "internal";
      }
      leaf FMAC22_Ecc_2bErrCnt_ovf {
        type boolean;
        tailf:hidden "internal";
      }
      leaf FMAC23_Ecc_2bErrCnt_ovf {
        type boolean;
        tailf:hidden "internal";
      }
      leaf FMAC24_Ecc_2bErrCnt_ovf {
        type boolean;
        tailf:hidden "internal";
      }
      leaf FMAC25_Ecc_2bErrCnt_ovf {
        type boolean;
        tailf:hidden "internal";
      }
      leaf FMAC26_Ecc_2bErrCnt_ovf {
        type boolean;
        tailf:hidden "internal";
      }
      leaf FMAC27_Ecc_2bErrCnt_ovf {
        type boolean;
        tailf:hidden "internal";
      }
      leaf FMAC28_Ecc_2bErrCnt_ovf {
        type boolean;
        tailf:hidden "internal";
      }
      leaf FMAC29_Ecc_2bErrCnt_ovf {
        type boolean;
        tailf:hidden "internal";
      }
      leaf FMAC30_Ecc_2bErrCnt_ovf {
        type boolean;
        tailf:hidden "internal";
      }
      leaf FMAC31_Ecc_2bErrCnt_ovf {
        type boolean;
        tailf:hidden "internal";
      }
      leaf CCS0_UnreachableDestinationCellsCnt {
        type uint64;
        tailf:hidden "internal";
      }
      leaf CCS1_UnreachableDestinationCellsCnt {
        type uint64;
        tailf:hidden "internal";
      }
      leaf CCS0_CaptureFifoDiscardCnt {
        type uint64;
        tailf:hidden "internal";
      }
      leaf CCS1_CaptureFifoDiscardCnt {
        type uint64;
        tailf:hidden "internal";
      }
      leaf CCS0_CdmaLpCellsDiscardCnt {
        type uint64;
        tailf:hidden "internal";
      }
      leaf CCS1_CdmaLpCellsDiscardCnt {
        type uint64;
        tailf:hidden "internal";
      }
      leaf CCS0_CdmbLpCellsDiscardCnt {
        type uint64;
        tailf:hidden "internal";
      }
      leaf CCS1_CdmbLpCellsDiscardCnt {
        type uint64;
        tailf:hidden "internal";
      }
      leaf CCS0_CrpParityErrCnt {
        type uint64;
        tailf:hidden "internal";
      }
      leaf CCS1_CrpParityErrCnt {
        type uint64;
        tailf:hidden "internal";
      }
      leaf CCS0_Ecc_1bErrCnt {
        type uint64;
        tailf:hidden "internal";
      }
      leaf CCS1_Ecc_1bErrCnt {
        type uint64;
        tailf:hidden "internal";
      }
      leaf CCS0_Ecc_2bErrCnt {
        type uint64;
        tailf:hidden "internal";
      }
      leaf CCS1_Ecc_2bErrCnt {
        type uint64;
        tailf:hidden "internal";
      }
      leaf DCH0_FifoDiscardCounterP {
        type uint64;
        tailf:hidden "internal";
      }
      leaf DCH1_FifoDiscardCounterP {
        type uint64;
        tailf:hidden "internal";
      }
      leaf DCH2_FifoDiscardCounterP {
        type uint64;
        tailf:hidden "internal";
      }
      leaf DCH3_FifoDiscardCounterP {
        type uint64;
        tailf:hidden "internal";
      }
      leaf DCH0_DCHReordDiscardCounterP {
        type uint64;
        tailf:hidden "internal";
      }
      leaf DCH1_DCHReordDiscardCounterP {
        type uint64;
        tailf:hidden "internal";
      }
      leaf DCH2_DCHReordDiscardCounterP {
        type uint64;
        tailf:hidden "internal";
      }
      leaf DCH3_DCHReordDiscardCounterP {
        type uint64;
        tailf:hidden "internal";
      }
      leaf DCH0_FifoDiscardCounterS {
        type uint64;
        tailf:hidden "internal";
      }
      leaf DCH1_FifoDiscardCounterS {
        type uint64;
        tailf:hidden "internal";
      }
      leaf DCH2_FifoDiscardCounterS {
        type uint64;
        tailf:hidden "internal";
      }
      leaf DCH3_FifoDiscardCounterS {
        type uint64;
        tailf:hidden "internal";
      }
      leaf DCH0_DCHReordDiscardCounterS {
        type uint64;
        tailf:hidden "internal";
      }
      leaf DCH1_DCHReordDiscardCounterS {
        type uint64;
        tailf:hidden "internal";
      }
      leaf DCH2_DCHReordDiscardCounterS {
        type uint64;
        tailf:hidden "internal";
      }
      leaf DCH3_DCHReordDiscardCounterS {
        type uint64;
        tailf:hidden "internal";
      }
      leaf DCH0_UnreachDestCntP {
        type uint64;
        tailf:hidden "internal";
      }
      leaf DCH1_UnreachDestCntP {
        type uint64;
        tailf:hidden "internal";
      }
      leaf DCH2_UnreachDestCntP {
        type uint64;
        tailf:hidden "internal";
      }
      leaf DCH3_UnreachDestCntP {
        type uint64;
        tailf:hidden "internal";
      }
      leaf DCH0_UnreachDestCntS {
        type uint64;
        tailf:hidden "internal";
      }
      leaf DCH1_UnreachDestCntS {
        type uint64;
        tailf:hidden "internal";
      }
      leaf DCH2_UnreachDestCntS {
        type uint64;
        tailf:hidden "internal";
      }
      leaf DCH3_UnreachDestCntS {
        type uint64;
        tailf:hidden "internal";
      }
      leaf DCH0_DchDroppedLowMulCntP {
        type uint64;
        tailf:hidden "internal";
      }
      leaf DCH1_DchDroppedLowMulCntP {
        type uint64;
        tailf:hidden "internal";
      }
      leaf DCH2_DchDroppedLowMulCntP {
        type uint64;
        tailf:hidden "internal";
      }
      leaf DCH3_DchDroppedLowMulCntP {
        type uint64;
        tailf:hidden "internal";
      }
      leaf DCH0_DchDroppedLowMulCntS {
        type uint64;
        tailf:hidden "internal";
      }
      leaf DCH1_DchDroppedLowMulCntS {
        type uint64;
        tailf:hidden "internal";
      }
      leaf DCH2_DchDroppedLowMulCntS {
        type uint64;
        tailf:hidden "internal";
      }
      leaf DCH3_DchDroppedLowMulCntS {
        type uint64;
        tailf:hidden "internal";
      }
      leaf DCH0_ErrorFilterCntAP {
        type uint64;
        tailf:hidden "internal";
      }
      leaf DCH1_ErrorFilterCntAP {
        type uint64;
        tailf:hidden "internal";
      }
      leaf DCH2_ErrorFilterCntAP {
        type uint64;
        tailf:hidden "internal";
      }
      leaf DCH3_ErrorFilterCntAP {
        type uint64;
        tailf:hidden "internal";
      }
      leaf DCH0_ErrorFilterCntBP {
        type uint64;
        tailf:hidden "internal";
      }
      leaf DCH1_ErrorFilterCntBP {
        type uint64;
        tailf:hidden "internal";
      }
      leaf DCH2_ErrorFilterCntBP {
        type uint64;
        tailf:hidden "internal";
      }
      leaf DCH3_ErrorFilterCntBP {
        type uint64;
        tailf:hidden "internal";
      }
      leaf DCH0_ErrorFilterCntAS {
        type uint64;
        tailf:hidden "internal";
      }
      leaf DCH1_ErrorFilterCntAS {
        type uint64;
        tailf:hidden "internal";
      }
      leaf DCH2_ErrorFilterCntAS {
        type uint64;
        tailf:hidden "internal";
      }
      leaf DCH3_ErrorFilterCntAS {
        type uint64;
        tailf:hidden "internal";
      }
      leaf DCH0_ErrorFilterCntBS {
        type uint64;
        tailf:hidden "internal";
      }
      leaf DCH1_ErrorFilterCntBS {
        type uint64;
        tailf:hidden "internal";
      }
      leaf DCH2_ErrorFilterCntBS {
        type uint64;
        tailf:hidden "internal";
      }
      leaf DCH3_ErrorFilterCntBS {
        type uint64;
        tailf:hidden "internal";
      }
      leaf DCH0_DropLowPriCntP {
        type uint64;
        tailf:hidden "internal";
      }
      leaf DCH1_DropLowPriCntP {
        type uint64;
        tailf:hidden "internal";
      }
      leaf DCH2_DropLowPriCntP {
        type uint64;
        tailf:hidden "internal";
      }
      leaf DCH3_DropLowPriCntP {
        type uint64;
        tailf:hidden "internal";
      }
      leaf DCH0_DropLowPriCntS {
        type uint64;
        tailf:hidden "internal";
      }
      leaf DCH1_DropLowPriCntS {
        type uint64;
        tailf:hidden "internal";
      }
      leaf DCH2_DropLowPriCntS {
        type uint64;
        tailf:hidden "internal";
      }
      leaf DCH3_DropLowPriCntS {
        type uint64;
        tailf:hidden "internal";
      }
      leaf DCH0_Ecc_1bErrCnt {
        type uint64;
        tailf:hidden "internal";
      }
      leaf DCH1_Ecc_1bErrCnt {
        type uint64;
        tailf:hidden "internal";
      }
      leaf DCH2_Ecc_1bErrCnt {
        type uint64;
        tailf:hidden "internal";
      }
      leaf DCH3_Ecc_1bErrCnt {
        type uint64;
        tailf:hidden "internal";
      }
      leaf DCH0_Ecc_2bErrCnt {
        type uint64;
        tailf:hidden "internal";
      }
      leaf DCH1_Ecc_2bErrCnt {
        type uint64;
        tailf:hidden "internal";
      }
      leaf DCH2_Ecc_2bErrCnt {
        type uint64;
        tailf:hidden "internal";
      }
      leaf DCH3_Ecc_2bErrCnt {
        type uint64;
        tailf:hidden "internal";
      }
      leaf DCH0_ParityErrCnt {
        type uint64;
        tailf:hidden "internal";
      }
      leaf DCH1_ParityErrCnt {
        type uint64;
        tailf:hidden "internal";
      }
      leaf DCH2_ParityErrCnt {
        type uint64;
        tailf:hidden "internal";
      }
      leaf DCH3_ParityErrCnt {
        type uint64;
        tailf:hidden "internal";
      }
      leaf DCL0_DclDroppedP0CntP {
        type uint64;
        tailf:hidden "internal";
      }
      leaf DCL1_DclDroppedP0CntP {
        type uint64;
        tailf:hidden "internal";
      }
      leaf DCL2_DclDroppedP0CntP {
        type uint64;
        tailf:hidden "internal";
      }
      leaf DCL3_DclDroppedP0CntP {
        type uint64;
        tailf:hidden "internal";
      }
      leaf DCL0_DclDroppedP1CntP {
        type uint64;
        tailf:hidden "internal";
      }
      leaf DCL1_DclDroppedP1CntP {
        type uint64;
        tailf:hidden "internal";
      }
      leaf DCL2_DclDroppedP1CntP {
        type uint64;
        tailf:hidden "internal";
      }
      leaf DCL3_DclDroppedP1CntP {
        type uint64;
        tailf:hidden "internal";
      }
      leaf DCL0_DclDroppedP2CntP {
        type uint64;
        tailf:hidden "internal";
      }
      leaf DCL1_DclDroppedP2CntP {
        type uint64;
        tailf:hidden "internal";
      }
      leaf DCL2_DclDroppedP2CntP {
        type uint64;
        tailf:hidden "internal";
      }
      leaf DCL3_DclDroppedP2CntP {
        type uint64;
        tailf:hidden "internal";
      }
      leaf DCL0_DclDroppedP3CntP {
        type uint64;
        tailf:hidden "internal";
      }
      leaf DCL1_DclDroppedP3CntP {
        type uint64;
        tailf:hidden "internal";
      }
      leaf DCL2_DclDroppedP3CntP {
        type uint64;
        tailf:hidden "internal";
      }
      leaf DCL3_DclDroppedP3CntP {
        type uint64;
        tailf:hidden "internal";
      }
      leaf DCL0_DclDroppedP0CntS {
        type uint64;
        tailf:hidden "internal";
      }
      leaf DCL1_DclDroppedP0CntS {
        type uint64;
        tailf:hidden "internal";
      }
      leaf DCL2_DclDroppedP0CntS {
        type uint64;
        tailf:hidden "internal";
      }
      leaf DCL3_DclDroppedP0CntS {
        type uint64;
        tailf:hidden "internal";
      }
      leaf DCL0_DclDroppedP1CntS {
        type uint64;
        tailf:hidden "internal";
      }
      leaf DCL1_DclDroppedP1CntS {
        type uint64;
        tailf:hidden "internal";
      }
      leaf DCL2_DclDroppedP1CntS {
        type uint64;
        tailf:hidden "internal";
      }
      leaf DCL3_DclDroppedP1CntS {
        type uint64;
        tailf:hidden "internal";
      }
      leaf DCL0_DclDroppedP2CntS {
        type uint64;
        tailf:hidden "internal";
      }
      leaf DCL1_DclDroppedP2CntS {
        type uint64;
        tailf:hidden "internal";
      }
      leaf DCL2_DclDroppedP2CntS {
        type uint64;
        tailf:hidden "internal";
      }
      leaf DCL3_DclDroppedP2CntS {
        type uint64;
        tailf:hidden "internal";
      }
      leaf DCL0_DclDroppedP3CntS {
        type uint64;
        tailf:hidden "internal";
      }
      leaf DCL1_DclDroppedP3CntS {
        type uint64;
        tailf:hidden "internal";
      }
      leaf DCL2_DclDroppedP3CntS {
        type uint64;
        tailf:hidden "internal";
      }
      leaf DCL3_DclDroppedP3CntS {
        type uint64;
        tailf:hidden "internal";
      }
      leaf DCL0_CCP0CIfDscrdCnt {
        type uint64;
        tailf:hidden "internal";
      }
      leaf DCL1_CCP0CIfDscrdCnt {
        type uint64;
        tailf:hidden "internal";
      }
      leaf DCL2_CCP0CIfDscrdCnt {
        type uint64;
        tailf:hidden "internal";
      }
      leaf DCL3_CCP0CIfDscrdCnt {
        type uint64;
        tailf:hidden "internal";
      }
      leaf DCL0_CCP1CIfDscrdCnt {
        type uint64;
        tailf:hidden "internal";
      }
      leaf DCL1_CCP1CIfDscrdCnt {
        type uint64;
        tailf:hidden "internal";
      }
      leaf DCL2_CCP1CIfDscrdCnt {
        type uint64;
        tailf:hidden "internal";
      }
      leaf DCL3_CCP1CIfDscrdCnt {
        type uint64;
        tailf:hidden "internal";
      }
      leaf DCL0_Ecc_1bErrCnt {
        type uint64;
        tailf:hidden "internal";
      }
      leaf DCL1_Ecc_1bErrCnt {
        type uint64;
        tailf:hidden "internal";
      }
      leaf DCL2_Ecc_1bErrCnt {
        type uint64;
        tailf:hidden "internal";
      }
      leaf DCL3_Ecc_1bErrCnt {
        type uint64;
        tailf:hidden "internal";
      }
      leaf DCL0_Ecc_2bErrCnt {
        type uint64;
        tailf:hidden "internal";
      }
      leaf DCL1_Ecc_2bErrCnt {
        type uint64;
        tailf:hidden "internal";
      }
      leaf DCL2_Ecc_2bErrCnt {
        type uint64;
        tailf:hidden "internal";
      }
      leaf DCL3_Ecc_2bErrCnt {
        type uint64;
        tailf:hidden "internal";
      }
      leaf DCL0_ParityErrCnt {
        type uint64;
        tailf:hidden "internal";
      }
      leaf DCL1_ParityErrCnt {
        type uint64;
        tailf:hidden "internal";
      }
      leaf DCL2_ParityErrCnt {
        type uint64;
        tailf:hidden "internal";
      }
      leaf DCL3_ParityErrCnt {
        type uint64;
        tailf:hidden "internal";
      }
      leaf DCL0_TagParErrCnt {
        type uint64;
        tailf:hidden "internal";
      }
      leaf DCL1_TagParErrCnt {
        type uint64;
        tailf:hidden "internal";
      }
      leaf DCL2_TagParErrCnt {
        type uint64;
        tailf:hidden "internal";
      }
      leaf DCL3_TagParErrCnt {
        type uint64;
        tailf:hidden "internal";
      }
      leaf DCL0_DataCrcErrCnt {
        type uint64;
        tailf:hidden "internal";
      }
      leaf DCL1_DataCrcErrCnt {
        type uint64;
        tailf:hidden "internal";
      }
      leaf DCL2_DataCrcErrCnt {
        type uint64;
        tailf:hidden "internal";
      }
      leaf DCL3_DataCrcErrCnt {
        type uint64;
        tailf:hidden "internal";
      }
      leaf DCMA0_DcmmDroppedIp0 {
        type uint64;
        tailf:hidden "internal";
      }
      leaf DCMA1_DcmmDroppedIp0 {
        type uint64;
        tailf:hidden "internal";
      }
      leaf DCMA0_DcmmDroppedIp1 {
        type uint64;
        tailf:hidden "internal";
      }
      leaf DCMA1_DcmmDroppedIp1 {
        type uint64;
        tailf:hidden "internal";
      }
      leaf DCMA0_DcmmDroppedIp2 {
        type uint64;
        tailf:hidden "internal";
      }
      leaf DCMA1_DcmmDroppedIp2 {
        type uint64;
        tailf:hidden "internal";
      }
      leaf DCMA0_DcmmDroppedIp3 {
        type uint64;
        tailf:hidden "internal";
      }
      leaf DCMA1_DcmmDroppedIp3 {
        type uint64;
        tailf:hidden "internal";
      }
      leaf DCMA0_DcmmDroppedTotalCnt {
        type uint64;
        tailf:hidden "internal";
      }
      leaf DCMA1_DcmmDroppedTotalCnt {
        type uint64;
        tailf:hidden "internal";
      }
      leaf DCMA0_DcmuDroppedIp0 {
        type uint64;
        tailf:hidden "internal";
      }
      leaf DCMA1_DcmuDroppedIp0 {
        type uint64;
        tailf:hidden "internal";
      }
      leaf DCMA0_DcmuDroppedIp1 {
        type uint64;
        tailf:hidden "internal";
      }
      leaf DCMA1_DcmuDroppedIp1 {
        type uint64;
        tailf:hidden "internal";
      }
      leaf DCMA0_DcmuDroppedIp2 {
        type uint64;
        tailf:hidden "internal";
      }
      leaf DCMA1_DcmuDroppedIp2 {
        type uint64;
        tailf:hidden "internal";
      }
      leaf DCMA0_DcmuDroppedIp3 {
        type uint64;
        tailf:hidden "internal";
      }
      leaf DCMA1_DcmuDroppedIp3 {
        type uint64;
        tailf:hidden "internal";
      }
      leaf DCMA0_DcmuDroppedTotalCnt {
        type uint64;
        tailf:hidden "internal";
      }
      leaf DCMA1_DcmuDroppedTotalCnt {
        type uint64;
        tailf:hidden "internal";
      }
      leaf DCMA0_Ecc_1bErrCnt {
        type uint64;
        tailf:hidden "internal";
      }
      leaf DCMA1_Ecc_1bErrCnt {
        type uint64;
        tailf:hidden "internal";
      }
      leaf DCMA0_Ecc_2bErrCnt {
        type uint64;
        tailf:hidden "internal";
      }
      leaf DCMA1_Ecc_2bErrCnt {
        type uint64;
        tailf:hidden "internal";
      }
      leaf DCMA0_ParityErrCnt {
        type uint64;
        tailf:hidden "internal";
      }
      leaf DCMA1_ParityErrCnt {
        type uint64;
        tailf:hidden "internal";
      }
      leaf DCMB0_DcmmDroppedIp0 {
        type uint64;
        tailf:hidden "internal";
      }
      leaf DCMB1_DcmmDroppedIp0 {
        type uint64;
        tailf:hidden "internal";
      }
      leaf DCMB0_DcmmDroppedIp1 {
        type uint64;
        tailf:hidden "internal";
      }
      leaf DCMB1_DcmmDroppedIp1 {
        type uint64;
        tailf:hidden "internal";
      }
      leaf DCMB0_DcmmDroppedIp2 {
        type uint64;
        tailf:hidden "internal";
      }
      leaf DCMB1_DcmmDroppedIp2 {
        type uint64;
        tailf:hidden "internal";
      }
      leaf DCMB0_DcmmDroppedIp3 {
        type uint64;
        tailf:hidden "internal";
      }
      leaf DCMB1_DcmmDroppedIp3 {
        type uint64;
        tailf:hidden "internal";
      }
      leaf DCMB0_DcmmDroppedTotalCnt {
        type uint64;
        tailf:hidden "internal";
      }
      leaf DCMB1_DcmmDroppedTotalCnt {
        type uint64;
        tailf:hidden "internal";
      }
      leaf DCMB0_DcmuDroppedIp0 {
        type uint64;
        tailf:hidden "internal";
      }
      leaf DCMB1_DcmuDroppedIp0 {
        type uint64;
        tailf:hidden "internal";
      }
      leaf DCMB0_DcmuDroppedIp1 {
        type uint64;
        tailf:hidden "internal";
      }
      leaf DCMB1_DcmuDroppedIp1 {
        type uint64;
        tailf:hidden "internal";
      }
      leaf DCMB0_DcmuDroppedIp2 {
        type uint64;
        tailf:hidden "internal";
      }
      leaf DCMB1_DcmuDroppedIp2 {
        type uint64;
        tailf:hidden "internal";
      }
      leaf DCMB0_DcmuDroppedIp3 {
        type uint64;
        tailf:hidden "internal";
      }
      leaf DCMB1_DcmuDroppedIp3 {
        type uint64;
        tailf:hidden "internal";
      }
      leaf DCMB0_DcmuDroppedTotalCnt {
        type uint64;
        tailf:hidden "internal";
      }
      leaf DCMB1_DcmuDroppedTotalCnt {
        type uint64;
        tailf:hidden "internal";
      }
      leaf DCMB0_Ecc_1bErrCnt {
        type uint64;
        tailf:hidden "internal";
      }
      leaf DCMB1_Ecc_1bErrCnt {
        type uint64;
        tailf:hidden "internal";
      }
      leaf DCMB0_Ecc_2bErrCnt {
        type uint64;
        tailf:hidden "internal";
      }
      leaf DCMB1_Ecc_2bErrCnt {
        type uint64;
        tailf:hidden "internal";
      }
      leaf DCMB0_ParityErrCnt {
        type uint64;
        tailf:hidden "internal";
      }
      leaf DCMB1_ParityErrCnt {
        type uint64;
        tailf:hidden "internal";
      }
      leaf ECI_ParityErrCnt {
        type uint64;
        tailf:hidden "internal";
      }
      leaf RTP_Ecc_1bErrCnt {
        type uint64;
        tailf:hidden "internal";
      }
      leaf RTP_Ecc_2bErrCnt {
        type uint64;
        tailf:hidden "internal";
      }
      leaf RTP_ParityErrCnt {
        type uint64;
        tailf:hidden "internal";
      }
      leaf FMAC0_Ecc_1bErrCnt {
        type uint64;
        tailf:hidden "internal";
      }
      leaf FMAC1_Ecc_1bErrCnt {
        type uint64;
        tailf:hidden "internal";
      }
      leaf FMAC2_Ecc_1bErrCnt {
        type uint64;
        tailf:hidden "internal";
      }
      leaf FMAC3_Ecc_1bErrCnt {
        type uint64;
        tailf:hidden "internal";
      }
      leaf FMAC4_Ecc_1bErrCnt {
        type uint64;
        tailf:hidden "internal";
      }
      leaf FMAC5_Ecc_1bErrCnt {
        type uint64;
        tailf:hidden "internal";
      }
      leaf FMAC6_Ecc_1bErrCnt {
        type uint64;
        tailf:hidden "internal";
      }
      leaf FMAC7_Ecc_1bErrCnt {
        type uint64;
        tailf:hidden "internal";
      }
      leaf FMAC8_Ecc_1bErrCnt {
        type uint64;
        tailf:hidden "internal";
      }
      leaf FMAC9_Ecc_1bErrCnt {
        type uint64;
        tailf:hidden "internal";
      }
      leaf FMAC10_Ecc_1bErrCnt {
        type uint64;
        tailf:hidden "internal";
      }
      leaf FMAC11_Ecc_1bErrCnt {
        type uint64;
        tailf:hidden "internal";
      }
      leaf FMAC12_Ecc_1bErrCnt {
        type uint64;
        tailf:hidden "internal";
      }
      leaf FMAC13_Ecc_1bErrCnt {
        type uint64;
        tailf:hidden "internal";
      }
      leaf FMAC14_Ecc_1bErrCnt {
        type uint64;
        tailf:hidden "internal";
      }
      leaf FMAC15_Ecc_1bErrCnt {
        type uint64;
        tailf:hidden "internal";
      }
      leaf FMAC16_Ecc_1bErrCnt {
        type uint64;
        tailf:hidden "internal";
      }
      leaf FMAC17_Ecc_1bErrCnt {
        type uint64;
        tailf:hidden "internal";
      }
      leaf FMAC18_Ecc_1bErrCnt {
        type uint64;
        tailf:hidden "internal";
      }
      leaf FMAC19_Ecc_1bErrCnt {
        type uint64;
        tailf:hidden "internal";
      }
      leaf FMAC20_Ecc_1bErrCnt {
        type uint64;
        tailf:hidden "internal";
      }
      leaf FMAC21_Ecc_1bErrCnt {
        type uint64;
        tailf:hidden "internal";
      }
      leaf FMAC22_Ecc_1bErrCnt {
        type uint64;
        tailf:hidden "internal";
      }
      leaf FMAC23_Ecc_1bErrCnt {
        type uint64;
        tailf:hidden "internal";
      }
      leaf FMAC24_Ecc_1bErrCnt {
        type uint64;
        tailf:hidden "internal";
      }
      leaf FMAC25_Ecc_1bErrCnt {
        type uint64;
        tailf:hidden "internal";
      }
      leaf FMAC26_Ecc_1bErrCnt {
        type uint64;
        tailf:hidden "internal";
      }
      leaf FMAC27_Ecc_1bErrCnt {
        type uint64;
        tailf:hidden "internal";
      }
      leaf FMAC28_Ecc_1bErrCnt {
        type uint64;
        tailf:hidden "internal";
      }
      leaf FMAC29_Ecc_1bErrCnt {
        type uint64;
        tailf:hidden "internal";
      }
      leaf FMAC30_Ecc_1bErrCnt {
        type uint64;
        tailf:hidden "internal";
      }
      leaf FMAC31_Ecc_1bErrCnt {
        type uint64;
        tailf:hidden "internal";
      }
      leaf FMAC0_Ecc_2bErrCnt {
        type uint64;
        tailf:hidden "internal";
      }
      leaf FMAC1_Ecc_2bErrCnt {
        type uint64;
        tailf:hidden "internal";
      }
      leaf FMAC2_Ecc_2bErrCnt {
        type uint64;
        tailf:hidden "internal";
      }
      leaf FMAC3_Ecc_2bErrCnt {
        type uint64;
        tailf:hidden "internal";
      }
      leaf FMAC4_Ecc_2bErrCnt {
        type uint64;
        tailf:hidden "internal";
      }
      leaf FMAC5_Ecc_2bErrCnt {
        type uint64;
        tailf:hidden "internal";
      }
      leaf FMAC6_Ecc_2bErrCnt {
        type uint64;
        tailf:hidden "internal";
      }
      leaf FMAC7_Ecc_2bErrCnt {
        type uint64;
        tailf:hidden "internal";
      }
      leaf FMAC8_Ecc_2bErrCnt {
        type uint64;
        tailf:hidden "internal";
      }
      leaf FMAC9_Ecc_2bErrCnt {
        type uint64;
        tailf:hidden "internal";
      }
      leaf FMAC10_Ecc_2bErrCnt {
        type uint64;
        tailf:hidden "internal";
      }
      leaf FMAC11_Ecc_2bErrCnt {
        type uint64;
        tailf:hidden "internal";
      }
      leaf FMAC12_Ecc_2bErrCnt {
        type uint64;
        tailf:hidden "internal";
      }
      leaf FMAC13_Ecc_2bErrCnt {
        type uint64;
        tailf:hidden "internal";
      }
      leaf FMAC14_Ecc_2bErrCnt {
        type uint64;
        tailf:hidden "internal";
      }
      leaf FMAC15_Ecc_2bErrCnt {
        type uint64;
        tailf:hidden "internal";
      }
      leaf FMAC16_Ecc_2bErrCnt {
        type uint64;
        tailf:hidden "internal";
      }
      leaf FMAC17_Ecc_2bErrCnt {
        type uint64;
        tailf:hidden "internal";
      }
      leaf FMAC18_Ecc_2bErrCnt {
        type uint64;
        tailf:hidden "internal";
      }
      leaf FMAC19_Ecc_2bErrCnt {
        type uint64;
        tailf:hidden "internal";
      }
      leaf FMAC20_Ecc_2bErrCnt {
        type uint64;
        tailf:hidden "internal";
      }
      leaf FMAC21_Ecc_2bErrCnt {
        type uint64;
        tailf:hidden "internal";
      }
      leaf FMAC22_Ecc_2bErrCnt {
        type uint64;
        tailf:hidden "internal";
      }
      leaf FMAC23_Ecc_2bErrCnt {
        type uint64;
        tailf:hidden "internal";
      }
      leaf FMAC24_Ecc_2bErrCnt {
        type uint64;
        tailf:hidden "internal";
      }
      leaf FMAC25_Ecc_2bErrCnt {
        type uint64;
        tailf:hidden "internal";
      }
      leaf FMAC26_Ecc_2bErrCnt {
        type uint64;
        tailf:hidden "internal";
      }
      leaf FMAC27_Ecc_2bErrCnt {
        type uint64;
        tailf:hidden "internal";
      }
      leaf FMAC28_Ecc_2bErrCnt {
        type uint64;
        tailf:hidden "internal";
      }
      leaf FMAC29_Ecc_2bErrCnt {
        type uint64;
        tailf:hidden "internal";
      }
      leaf FMAC30_Ecc_2bErrCnt {
        type uint64;
        tailf:hidden "internal";
      }
      leaf FMAC31_Ecc_2bErrCnt {
        type uint64;
        tailf:hidden "internal";
      }
      leaf is_show {
        type boolean;
        tailf:hidden "internal";
      }
      leaf show_CCS {
        type boolean;
        tailf:hidden "internal";
      }
      leaf show_DCH {
        type boolean;
        tailf:hidden "internal";
      }
      leaf show_DCl {
        type boolean;
        tailf:hidden "internal";
      }
      leaf show_DCMA {
        type boolean;
        tailf:hidden "internal";
      }
      leaf show_DCMB {
        type boolean;
        tailf:hidden "internal";
      }
      leaf show_ECI {
        type boolean;
        tailf:hidden "internal";
      }
      leaf show_FMAC {
        type boolean;
        tailf:hidden "internal";
      }
      leaf show_RTP {
        type boolean;
        tailf:hidden "internal";
      }
    }
  }

  grouping sfe_trace {
    container sfe_driver {
      tailf:cli-incomplete-show-path;
      tailf:cli-drop-node-name;
      uses show-trace:traceable;
    }
  }

  grouping sfe_parse_link_instance {
    list instance {
      key "instance-id";
      tailf:cli-no-key-completion;
      tailf:cli-no-match-completion;
      tailf:cli-show-template-enter "";
      tailf:cli-suppress-table;
      tailf:cli-show-template
        "$(is_show == true ?
         ----------------------------------------------------------------------------------------------------
         Rack    Slot     Asic       Link    Logical  Physical   FAP    Unit    SFI     IP Address    Driver     
                        Instance    Number     slot    slot      /FE           number   for driver    runs on    
         -------------------------------------------------------------------------------------------------------
         $(link_idx_list|show))";
      leaf instance-id {
        type fabric-types:sfe_instance_type;
      }
      leaf is_show {
        type boolean;
        tailf:hidden "internal";
      }
      list link_idx_list {
        key "link_idx";
        tailf:cli-suppress-table;
        tailf:cli-show-template-enter "";
        tailf:cli-show-template "$(rack_id_str|ljust:7) $(slot_id_str|ljust:10) $(asic_inst_id|ljust:8) $(link_num_id|ljust:8) $(log_slot|ljust:9) $(phy_slot|ljust:8) $(fap_id|ljust:8) $(unit|ljust:7) $(sfi_id|ljust:6) $(ip_addr|ljust:15) $(driver_run|ljust:6)\n";
        leaf link_idx {
          type int64;
        }
        leaf rack_id_str {
          type string;
          tailf:hidden "internal";
        }
        leaf slot_id_str {
          type string;
          tailf:hidden "internal";
        }
        leaf asic_inst_id {
          type uint32;
          tailf:hidden "internal";
        }
        leaf link_num_id {
          type uint32;
          tailf:hidden "internal";
        }
        leaf log_slot {
          type uint32;
          tailf:hidden "internal";
        }
        leaf phy_slot {
          type uint32;
          tailf:hidden "internal";
        }
        leaf fap_id {
          type uint32;
          tailf:hidden "internal";
        }
        leaf unit {
          type uint32;
          tailf:hidden "internal";
        }
        leaf sfi_id {
          type uint32;
          tailf:hidden "internal";
        }
        leaf ip_addr {
          type string;
          tailf:hidden "internal";
        }
        leaf driver_run {
          type string;
          tailf:hidden "internal";
        }
      }
    }
  }

  grouping sfe {
    container sfe {
      description
        "Fabric SFE driver commands";
      tailf:hidden "internal-command";
      tailf:info "Fabric SFE driver commands";
      tailf:cli-incomplete-show-path;
      container driver {
        tailf:callpoint "sfe_drvr_cp";
        tailf:hidden "internal-command";
        tailf:info "SFE driver information";
        tailf:cli-incomplete-show-path;
        list rack {
          key "rack_num";
          tailf:cli-show-template-enter "";
          tailf:cli-suppress-table;
          leaf rack_num {
            type fabric-types:fabric_rack_num_type;
          }
          leaf description {
            type string;
            default "rack no.";
          }
          uses sfe_drvr_info;
        }
      }
      container statistics {
        tailf:callpoint "sfe_statistics_cp";
        tailf:hidden "internal-command";
        list location {
          key "loc_str";
          tailf:cli-show-template-enter "";
          tailf:cli-suppress-table;
          leaf loc_str {
            type fabric-types:sfe_location_type;
          }
          leaf description {
            type string;
            default "location (R/S).";
          }
          container asic {
            container CCS {
              uses sfe_statistics_asic_instance;
            }
            container DCH {
              uses sfe_statistics_asic_instance;
            }
            container DCl {
              uses sfe_statistics_asic_instance;
            }
            container DCMA {
              uses sfe_statistics_asic_instance;
            }
            container DCMB {
              uses sfe_statistics_asic_instance;
            }
            container ECI {
              uses sfe_statistics_asic_instance;
            }
            container FMAC {
              uses sfe_statistics_asic_instance;
            }
            container GCK {
              uses sfe_statistics_asic_instance;
            }
            container RTP {
              uses sfe_statistics_asic_instance;
            }
            container all {
              uses sfe_statistics_asic_instance;
            }
          }
        }
      }
      container link-info {
        tailf:callpoint "sfe_link_info_cp";
        tailf:info "Link Information";
        tailf:cli-incomplete-show-path;
        list location {
          key "loc_str";
          tailf:hidden "internal-command";
          tailf:cli-show-template-enter "";
          tailf:cli-suppress-table;
          leaf loc_str {
            type fabric-types:sfe_location_type;
          }
          leaf description {
            type string;
            default "location (R/S)";
          }
          list rx {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            container detail {
              container topo {
                uses sfe_link_info_asic_instance;
              }
              container flap {
                uses sfe_link_info_asic_instance;
              }
            }
            container topo {
              uses sfe_link_info_asic_instance;
            }
            container flap {
              uses sfe_link_info_asic_instance;
            }
            uses sfe_link_info_stats_asic_instance;
          }
          list tx {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            container detail {
              uses sfe_link_info_asic_instance;
            }
            uses sfe_link_info_asic_instance;
            uses sfe_link_info_stats_asic_instance;
          }
        }
      }
      container diagshell {
        tailf:hidden "internal-command";
        tailf:callpoint "sfe_diagshell_cmd";
        tailf:info "Diag shell cmd";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list instance {
            key "instance_num";
            tailf:cli-no-key-completion;
            tailf:cli-no-match-completion;
            tailf:cli-show-template-enter "";
            tailf:cli-suppress-table;
            leaf instance_num {
              type fabric-types:fabric_diag_shell_instance_num_type;
            }
            list diag_cmd {
              key "cmd_str";
              tailf:cli-no-key-completion;
              tailf:cli-no-match-completion;
              tailf:cli-show-template-enter "";
              tailf:cli-suppress-table;
              tailf:cli-show-template "$(bytes|show)";
              tailf:info "File name - double quote enclosed";
              leaf cmd_str {
                type fabric-types:fabric_diag_shell_cmd_type;
              }
              list bytes {
                key "byte_idx";
                tailf:cli-no-key-completion;
                tailf:cli-no-match-completion;
                tailf:cli-show-template-enter "";
                tailf:cli-suppress-table;
                tailf:cli-show-template "$(data)";
                leaf byte_idx {
                  type int64;
                }
                leaf data {
                  type string;
                  tailf:hidden "internal";
                }
              }
            }
          }
        }
      }
      container register {
        tailf:hidden "internal-command";
        tailf:callpoint "sfe_registers_cp";
        tailf:info "Dump the registers";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list instance {
            key "instance_num";
            tailf:cli-no-key-completion;
            tailf:cli-no-match-completion;
            tailf:cli-show-template-enter "";
            tailf:cli-suppress-table;
            leaf instance_num {
              type fabric-types:fabric_diag_shell_instance_num_type;
            }
            list bytes {
              key "byte_idx";
              tailf:cli-no-key-completion;
              tailf:cli-no-match-completion;
              tailf:cli-show-template-enter "";
              tailf:cli-suppress-table;
              tailf:cli-show-template "$(data)";
              leaf byte_idx {
                type int64;
              }
              leaf data {
                type string;
                tailf:hidden "internal";
              }
            }
          }
        }
      }
      container dump-file {
        tailf:hidden "internal-command";
        tailf:callpoint "sfe_dump_file";
        tailf:info "Dump file";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list file {
            key "file_name";
            tailf:cli-no-key-completion;
            tailf:cli-no-match-completion;
            tailf:cli-show-template-enter "";
            tailf:cli-suppress-table;
            tailf:cli-show-template "$(bytes|show)";
            tailf:info "File name - double quote enclosed";
            leaf file_name {
              type string;
            }
            list bytes {
              key "byte_idx";
              tailf:cli-no-key-completion;
              tailf:cli-no-match-completion;
              tailf:cli-show-template-enter "";
              tailf:cli-suppress-table;
              tailf:cli-show-template "$(data)";
              leaf byte_idx {
                type int64;
              }
              leaf data {
                type string;
                tailf:hidden "internal";
              }
            }
          }
        }
      }
      container parse {
        tailf:callpoint "sfe_parse_link_cp";
        tailf:info "Parse Link Information";
        tailf:cli-incomplete-show-path;
        list location {
          key "loc_str";
          tailf:hidden "internal-command";
          tailf:cli-show-template-enter "";
          tailf:cli-suppress-table;
          leaf loc_str {
            type fabric-types:sfe_location_type;
          }
          leaf description {
            type string;
            default "location (R/S)";
          }
          list link {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            uses sfe_parse_link_instance;
          }
        }
      }
    }
    container sfe_trace {
      tailf:hidden "internal-command";
      uses sfe_trace;
    }
  }
  tailf:id "http://www.cisco.com/panini/calvados/fabric/sfe";
}
