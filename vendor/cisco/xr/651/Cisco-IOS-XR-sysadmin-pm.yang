module Cisco-IOS-XR-sysadmin-pm {
  namespace "http://www.cisco.com/ns/yang/Cisco-IOS-XR-sysadmin-pm";
  prefix pmh;

  import tailf-common {
    prefix tailf;
  }
  import tailf-xsd-types {
    prefix xs;
  }
  import ietf-inet-types {
    prefix inet;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     The Process Manager (PM).
     
     Copyright(c) 2011-2017 by Cisco Systems, Inc.
     All rights reserved.";

  revision 2017-04-12 {
    description
      "Changed the namespace and module name";
  }
  revision 2016-05-11 {
    description
      "Initial version.";
  }

  typedef startupMode {
    type enumeration {
      enum "ON-BOOTUP";
      enum "ON-SELECTION";
      enum "ON-DEMAND";
    }
  }

  typedef processState {
    type enumeration {
      enum "IDLE";
      enum "RUNNING";
      enum "STOPPING";
      enum "STOPPED";
      enum "DESELECTING";
      enum "DESELECTED";
    }
  }

  typedef serviceScope {
    type enumeration {
      enum "SYSTEM";
      enum "RACK";
    }
  }

  typedef serviceState {
    type enumeration {
      enum "SS_IDLE";
      enum "SS_RUNNING";
      enum "SS_ACK_PENDING";
    }
  }

  typedef serviceRole {
    type enumeration {
      enum "NONE";
      enum "ACTIVE";
      enum "STANDBY";
    }
  }

  typedef proc-name-type {
    type string;
    tailf:info "WORD;;Name of the executable";
  }

  typedef user-name-type {
    type string;
    tailf:info "WORD;;Name of the user";
  }

  typedef task-name-type {
    type string;
    tailf:info "String[In quotes];;Task";
  }

  typedef folder-name-type {
    type string;
    tailf:info "WORD;;Name of the folder";
  }

  typedef source-name-type {
    type string;
    tailf:info "WORD;;Copy From Source";
  }

  typedef dest-name-type {
    type string;
    tailf:info "WORD;;Copy To Destination";
  }

  typedef file-name-type {
    type string;
    tailf:info "WORD;;Name of the file";
  }

  typedef folder-file-name-type {
    type string;
    tailf:info "WORD;;Name of the folder or file";
  }

  typedef instance-id-type {
    type uint32;
    tailf:info "IID;;Process Instance ID";
  }

  typedef service-name-type {
    type string;
    tailf:info "WORD;;Name of the service";
  }

  typedef proc-id-type {
    type uint32;
    tailf:info "PID;;Process ID";
  }

  typedef node-name-type {
    type string;
    tailf:info "WORD;;all/node ID in #/RP# format";
  }
  tailf:id "http://cisco.com/calvados/pm";

  container processes {
    config false;
    description
      "Process Info";
    tailf:callpoint "pm_show_location";
    tailf:hidden "internal-command";
    list all-locations {
      key "location";
      tailf:cli-drop-node-name;
      tailf:cli-suppress-table;
      tailf:display-groups "proc-brief proc-detail proc-summary proc-abort-info svc-summary svc-brief svc-detail none";
      tailf:cli-show-template-enter
        "----------------------------------------------------------------------
         node\\\\:      $(location)
        ";
      tailf:cli-show-template "$(name|show)";
      leaf location {
        type string;
        tailf:cli-expose-key-name;
        tailf:cli-disallow-value "(proc-brief)|(proc-details)|(proc-summary)|(proc-abort-info)|(svc-summary)|(svc-brief)|(svc-detail)|(name)";
        tailf:display-groups "proc-summary proc-abort-info none";
        tailf:cli-allow-range;
      }
      leaf ip-addr {
        type inet:ip-address;
        description
          "IP address of the location";
      }
      leaf pcbs {
        type uint32;
        description
          "Total number of process control blocks";
      }
      list name {
        key "proc-name instance-id";
        tailf:display-groups "proc-brief proc-summary proc-detail proc-abort-info svc-summary svc-summary-legend svc-brief svc-detail none";
        tailf:cli-suppress-table;
        tailf:cli-show-template-enter "";
        tailf:cli-show-template
          "$(.display_groups~=proc-summary?$(start-time|ljust:23) $($(proc-state|dict:IDLE=Idle:RUNNING=Run:STOPPED=Stop)|ljust:5)    $(respawns|ljust:5)   $($(mandatory|dict:true=M:false= )|ljust:6)  $($(maint-mode|dict:true=Y:false= )|ljust:6) $(proc-name)\\\\($(instance-id)\\\\) $(args)
           )$(.display_groups~=proc-abort-info?$(exit-status?$(last-exit-time) $(proc-name)\\\\($(instance-id)\\\\) $(exit-status), current state\\\\: $(proc-state|dict:IDLE=Idle:RUNNING=Run:STOPPED=Stop)
           ))$(.display_groups~=proc-brief?----------------------------------------------------------------------
                                PID\\\\: $(pid)
                    Executable path\\\\: $(path)
                         Instance #\\\\: $(instance-id)
           $(args?                    Args\\\\: $(args)
           )                 Respawn\\\\: ON
                      Respawn count\\\\: $(respawns)
             Max. spawns per $(respawn-reset-timer) mins\\\\: $(max-restarts)
                       Last started\\\\: $(start-time)
                      Process state\\\\: $(proc-state|dict:IDLE=Idle:RUNNING=Run:STOPPED=Stop) $(exit-status?\\\\($(exit-status)\\\\))
                       startup_path\\\\: $(startup-file)
                              Ready\\\\: $(ready-time?$(ready-time|floatformat:-3)s:Not ready)
           )$(.display_groups~=proc-detail?            Startup Mode\\\\: $(startup-mode)
                  Heartbeat Timeout\\\\: $(heart-beat-timeout?$(heart-beat-timeout)s:Disabled)
                     Last Heartbeat\\\\: $(last-heart-beat-time?$(last-heart-beat-time|floatformat:-3)s ago:Not detected)
                          Mandatory\\\\: $(mandatory|dict:true=Y:false=N)
             Run during Maint. mode\\\\: $(maint-mode|dict:true=Y:false=N)
           $(last-exit-time?          Last Exit Time\\\\: $(last-exit-time)
           ))$(.display_groups~=svc-summary?$(.display_groups~=svc-summary-legend?$(services|show):$(services?Table of services hosted on this process\\\\:
           ----------------------------------------------------------------------
           LAST STARTED            SCOPE   SELE-  ROLE  STATE  HA-  SERVICE NAME
                                           CTED                RDY
           ----------------------------------------------------------------------
           $(services|show)
           ----------------------------------------------------------------------
           
           )))$(.display_groups~=svc-brief?$(services|show))";
        tailf:cli-show-template-legend
          "$(.display_groups~=proc-summary?----------------------------------------------------------------------
           LAST STARTED            STATE    RE-     MANDA-  MAINT- NAME\\\\(IID\\\\) ARGS
                                            START   TORY    MODE
           ----------------------------------------------------------------------
           )$(.display_groups~=svc-summary-legend?----------------------------------------------------------------------
           LAST STARTED            SCOPE   SELE-  ROLE  STATE  HA-  SERVICE NAME
                                           CTED                RDY
           ----------------------------------------------------------------------
           )";
        tailf:cli-show-template-footer
          "$(.display_groups~=svc-summary-legend?----------------------------------------------------------------------
           
           )$(.display_groups~=proc-summary?----------------------------------------------------------------------
           Total pcbs\\\\: $(../pcbs)
           ----------------------------------------------------------------------
           
           )";
        leaf proc-name {
          type proc-name-type;
          description
            "Name of the process";
          tailf:display-groups "proc-brief proc-detail proc-summary proc-abort-info svc-summary svc-summary-legend svc-brief svc-detail none";
          tailf:cli-disallow-value "(proc-brief)|(proc-details)|(proc-summary)|(proc-abort-info)|(svc-summary)|(svc-brief)|(svc-detail)";
        }
        leaf instance-id {
          type instance-id-type;
          description
            "Instance identifier";
          tailf:cli-allow-range;
        }
        leaf path {
          type string;
          description
            "Process path";
        }
        leaf startup-file {
          type string;
          description
            "Process startup file";
        }
        leaf startup-mode {
          type startupMode;
          description
            "When is a process started";
        }
        leaf heart-beat-timeout {
          type uint32;
          description
            "Heart beat timeout in sec";
        }
        leaf last-heart-beat-time {
          type xs:double;
          description
            "How long ago last heart beat was detected";
        }
        leaf max-restarts {
          type uint32;
          description
            "Maximum num of restarts";
        }
        leaf respawn-reset-timer {
          type uint32;
          description
            "Respawn reset timer in min";
        }
        leaf mandatory {
          type boolean;
          description
            "Mandatory process";
        }
        leaf maint-mode {
          type boolean;
          description
            "Should run during maintenance mode";
        }
        leaf args {
          type string;
          description
            "Process arguments";
        }
        leaf proc-state {
          type processState;
          description
            "State of the process";
        }
        leaf pid {
          type int32;
          description
            "Process ID";
        }
        leaf proc-aborted {
          type boolean;
          description
            "Whether the processes ever aborted";
        }
        leaf exit-status {
          type string;
          description
            "Last exit status/info of the process";
        }
        leaf respawns {
          type int32;
          description
            "Total number of respawns of the process";
        }
        leaf start-time {
          type string;
          description
            "Last start date and time";
        }
        leaf ready-time {
          type xs:double;
          description
            "Time for ready from start-time";
        }
        leaf last-exit-time {
          type string;
          description
            "Last exit date and time";
        }
        list services {
          key "service-name";
          tailf:cli-suppress-table;
          tailf:display-groups "proc-brief svc-summary svc-brief svc-detail none";
          tailf:cli-show-template-enter "";
          tailf:cli-show-template
            "$(.display_groups~=svc-summary?$(svc-start-time|ljust:23) $($(scope|dict:SYSTEM=SYS)|ljust:6)  $($(selected|dict:true=Y:false=N)|ljust:3)   $(selected==true? $($(ha-role|dict:NONE=NONE:STANDBY=STBY:ACTIVE=ACT)|ljust:4)  $($(service-state|dict:SS_IDLE=Idle:SS_RUNNING=Run:SS_ACK_PENDING=APend)|ljust:5)  $(ha-role==STANDBY?$($(ha-ready|dict:true=Y:false=N)|ljust:3)  :     ):                   )$(service-name)
             )$(.display_groups~=svc-brief?----------------------------------------------------------------------
                                  Service\\\\: $(service-name)
                   Host Process\\\\(IID\\\\) ARGS\\\\: $(../../proc-name)\\\\($(../../instance-id)\\\\) $(../../args)
                                    Scope\\\\: $(scope)
                               Redundancy\\\\: $(redundancy|dict:true=Y:false=N)
                                 Selected\\\\: $(selected|dict:true=Y:false=N)
                             Last started\\\\: $(svc-start-time)
             $(selected==true?                     HA-Role\\\\: $(ha-role)
             $(new-ha-role?                 New HA-Role\\\\: $(new-ha-role)
             )                       State\\\\: $(service-state|dict:SS_IDLE=Idle:SS_RUNNING=Run:SS_ACK_PENDING=Ack Pending)
                          Last Ready Time\\\\: $(svc-ready-time?$(svc-ready-time|floatformat:-3)s:Not ready)
             $(ha-role==STANDBY?                    HA-Ready\\\\: $(ha-ready|dict:true=Y:false=N)
                       Last HA Ready Time\\\\: $(svc-haready-time?$(svc-haready-time|floatformat:-3):Not ready)
             )))$(.display_groups~=svc-detail?            Selection Result\\\\: $(ip1?$(ip1)$(ip2?, $(ip2)):None)
             )";
          leaf service-name {
            type string;
            description
              "Name of the service";
            tailf:display-groups "proc-brief svc-summary svc-brief svc-detail none";
            tailf:cli-disallow-value "(svc-summary)|(svc-brief)|(svc-detail)";
          }
          leaf scope {
            type serviceScope;
            description
              "Scope of the service";
          }
          leaf redundancy {
            type boolean;
            description
              "Service redundancy support";
          }
          leaf ha-ready {
            type boolean;
            description
              "Standby ready for HA";
          }
          leaf service-state {
            type serviceState;
            description
              "State of the service";
          }
          leaf ha-role {
            type serviceRole;
            description
              "Service role";
          }
          leaf new-ha-role {
            type serviceRole;
            description
              "New service role, different if PM in process of assigning";
          }
          leaf selected {
            type boolean;
            description
              "Service seleted to run on the node";
          }
          leaf ip1 {
            type inet:ip-address;
            description
              "First IP address in the selection";
          }
          leaf ip2 {
            type inet:ip-address;
            description
              "Second IP address in the selection";
          }
          leaf svc-start-time {
            type string;
            description
              "Last start date and time";
          }
          leaf svc-ready-time {
            type xs:double;
            description
              "Time it took to get ready since start time";
          }
          leaf svc-haready-time {
            type xs:double;
            description
              "Time it took to get HA-ready since start time";
          }
        }
        tailf:action "proc-action" {
          tailf:actionpoint "proc-action";
          input {
            leaf do-what {
              type enumeration {
                enum "crash";
                enum "restart";
                enum "disable-heartbeat";
                enum "enable-heartbeat";
                enum "start";
                enum "shutdown";
                enum "mandatory-toggle";
              }
              mandatory true;
            }
            leaf user-name {
              type string;
              mandatory true;
              description
                "Name of the logged in user";
            }
            leaf user-ip {
              type string;
              mandatory true;
              description
                "IP address of the user";
            }
          }
          output {
            leaf proc-action-status {
              type string;
              mandatory true;
            }
          }
        }
      }
    }
  }
  container process-manager {
    config false;
    description
      "Process Manager Info";
    tailf:callpoint "pm_info_show_location";
    tailf:hidden "internal-command";
    list all-locations-info {
      key "location-info";
      tailf:cli-drop-node-name;
      tailf:cli-suppress-table;
      tailf:cli-show-template-enter "";
      tailf:cli-show-template
        "----------------------------------------------------------------------
         node\\\\:      $(location-info)
         ----------------------------------------------------------------------
                            Node IP address\\\\: $(ip-addr-info)
                        PM Start Time Stamp\\\\: $(pm-start-time)
               Mandatory process down state\\\\: $(mand-proc-down|dict:true=Y:false=N)
                   vm-manager connection up\\\\: $(vmm-capi-up|dict:true=Y:false=N)
                        wdmon connection up\\\\: $(wdmon-capi-up|dict:true=Y:false=N)
               Last wdmon connect timestamp\\\\: $(wdmon-capi-timestamp)
                         Num wdmon connects\\\\: $(wdmon-num-capi-connects)
         ----------------------------------------------------------------------
        ";
      leaf location-info {
        type string;
        tailf:cli-allow-range;
        tailf:cli-expose-key-name;
      }
      leaf ip-addr-info {
        type inet:ip-address;
        description
          "IP address of the location";
      }
      leaf pm-start-time {
        type string;
        description
          "Last start date and time for PM";
      }
      leaf mand-proc-down {
        type boolean;
        description
          "PM in mandatory process down state";
      }
      leaf vmm-capi-up {
        type boolean;
        description
          "Status of CAPI with vm-manager";
      }
      leaf wdmon-capi-up {
        type boolean;
        description
          "Status of CAPI with wdmon";
      }
      leaf wdmon-capi-timestamp {
        type string;
        description
          "Date and time of last wdmon CAPI connection establish";
      }
      leaf wdmon-num-capi-connects {
        type uint32;
        description
          "Number of times wdmon CAPI connection extablished";
      }
    }
  }
  container pm {
    config false;
    tailf:cli-incomplete-show-path;
    tailf:info "Show Process Manager information";
    container pm {
      tailf:cli-drop-node-name;
      uses show_trace:traceable;
    }
  }
}
