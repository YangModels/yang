module Cisco-IOS-XR-sysadmin-ds {
  namespace "http://www.cisco.com/ns/yang/Cisco-IOS-XR-sysadmin-ds";
  prefix ds;

  import tailf-common {
    prefix tailf;
  }
  import ietf-inet-types {
    prefix inet;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     The Directory Services (DS).
     
     Copyright(c) 2010-2017 by Cisco Systems, Inc.
     All rights reserved.";

  revision 2017-04-12 {
    description
      "Changed the namespace and module name";
  }
  revision 2016-10-12 {
    description
      "Unhide commands and configs. Moved to advanced-grp";
  }
  revision 2016-05-11 {
    description
      "Initial version.";
  }

  typedef service-scope {
    type enumeration {
      enum "None" {
        tailf:code-name "ds-service-scope-None";
      }
      enum "Rack" {
        tailf:code-name "ds-service-scope-Rack";
      }
      enum "System" {
        tailf:code-name "ds-service-scope-System";
      }
      enum "Node" {
        tailf:code-name "ds-service-scope-Node";
      }
    }
  }

  typedef process-role {
    type enumeration {
      enum "NoRole" {
        tailf:code-name "ds-process-role-NoRole";
      }
      enum "Active" {
        tailf:code-name "ds-process-role-Active";
      }
      enum "Standby" {
        tailf:code-name "ds-process-role-Standby";
      }
      enum "None" {
        tailf:code-name "ds-process-role-None";
      }
      enum "Unknown" {
        value 254;
      }
    }
  }

  typedef process-issu-role {
    type enumeration {
      enum "Primary" {
        value 1;
      }
      enum "Secondary" {
        value 2;
      }
      enum "Tertiary" {
        value 3;
      }
      enum "Unknown" {
        value 254;
      }
    }
  }

  grouping servicesGroup {
    list services {
      key "name";
      tailf:cli-drop-node-name;
      tailf:cli-enforce-table;
      leaf name {
        type string;
        description
          "Name of the service";
      }
      list endpoint {
        description
          "endpoint info for a service in DS";
        leaf scope {
          type service-scope;
        }
        leaf ip {
          type inet:ipv4-address;
        }
        leaf port {
          type inet:port-number;
        }
        leaf role {
          type process-role;
        }
        leaf issu_role {
          type process-issu-role;
        }
        leaf node {
          type string;
          description
            "Ethernet address of the node hosting the endpoint";
        }
      }
      list registrations {
        description
          "clients registered for a service in DS";
        leaf client {
          type string;
        }
        leaf pid {
          type uint32;
        }
      }
    }
  }
  tailf:id "http://cisco.com/panini/calvados/ds";

  container services {
    config false;
    description
      "Directory Services Entries";
    tailf:callpoint "ds_show_services";
    tailf:hidden "advanced-grp";
    list all-locations {
      key "location";
      tailf:cli-drop-node-name;
      tailf:cli-show-template-enter "Services found at location $(location)\n";
      leaf location {
        type string;
        description
          "Node Location";
        tailf:cli-expose-key-name;
      }
      uses servicesGroup;
    }
  }
  container services-stats {
    config false;
    description
      "Directory Services Stats";
    tailf:alt-name "ds";
    tailf:cdb-oper;
    tailf:cli-incomplete-show-path;
    container ds {
      config false;
      tailf:cdb-oper;
      tailf:cli-drop-node-name;
      tailf:cli-incomplete-show-path;
      uses show_trace:traceable;
    }
    list all-locations {
      key "location";
      tailf:cli-drop-node-name;
      tailf:cli-show-template-enter "DS server stats at location $(location)\n";
      tailf:callpoint "ds_show_stats";
      leaf location {
        type string;
        tailf:cli-expose-key-name;
      }
      list stats {
        key "name";
        leaf name {
          type string;
          description
            "Name of the service";
        }
        leaf published {
          type uint32;
          description
            "number of endpoints published for this service";
          tailf:alt-name "Pub";
        }
        leaf deleted {
          type uint32;
          description
            "number of endpoints deleted for this service";
          tailf:alt-name "Del";
        }
        leaf modified {
          type uint32;
          description
            "number of endpoints modified for this service";
          tailf:alt-name "Mod";
        }
        leaf registered {
          type uint32;
          description
            "number of clients registered for this service";
          tailf:alt-name "Reg";
        }
        leaf unregistered {
          type uint32;
          description
            "number of clients un-registered for this service";
          tailf:alt-name "Unreg";
        }
        leaf notifications {
          type uint32;
          description
            "number of clients notified for this service";
          tailf:alt-name "Notif";
        }
        leaf remote_sent {
          type uint32;
          description
            "number of remote service updates sent to remote nodes";
          tailf:alt-name "Rem-Sent";
        }
        leaf remote_recv {
          type uint32;
          description
            "number of remote service received from remote nodes";
          tailf:alt-name "Rem-Rcv";
        }
      }
    }
  }
}
