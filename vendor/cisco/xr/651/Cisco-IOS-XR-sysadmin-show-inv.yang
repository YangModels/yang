module Cisco-IOS-XR-sysadmin-show-inv {
  namespace "http://www.cisco.com/ns/yang/Cisco-IOS-XR-sysadmin-show-inv";
  prefix inv;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Calvados Inventory Service maintain entity database
     
     Copyright(c) 2011-2017 by Cisco Systems, Inc.
     All rights reserved.";

  revision 2017-04-12 {
    description
      "Changed the namespace and module name";
  }
  revision 2013-07-20 {
    description
      "MC revision of show inventory commands";
  }

  grouping target_str {
    leaf name {
      type string;
      description
        "Name of the entity";
      tailf:display-column-name "Name";
      tailf:cli-suppress-show-path;
      tailf:cli-suppress-show-match;
    }
    leaf Description {
      type string;
      description
        "Description of the entity";
      tailf:display-column-name "Description";
      tailf:cli-suppress-show-path;
      tailf:cli-suppress-show-match;
    }
    leaf PID {
      type string;
      description
        "Product ID of the entity";
      tailf:display-column-name "PID";
      tailf:cli-suppress-show-path;
      tailf:cli-suppress-show-match;
    }
    leaf VID {
      type string;
      description
        "Version ID of the entity";
      tailf:display-column-name "VID";
      tailf:cli-suppress-show-path;
      tailf:cli-suppress-show-match;
    }
    leaf SN {
      type string;
      description
        "Serial Numbe of the entity";
      tailf:display-column-name "SN";
      tailf:cli-suppress-show-path;
      tailf:cli-suppress-show-match;
    }
    leaf loc {
      type string;
      description
        "Node id of the entity";
      tailf:display-column-name "Location";
    }
    leaf index {
      type uint32;
      description
        "Index for the entity";
      tailf:info "";
      tailf:display-column-name "INDEX";
      tailf:cli-suppress-show-path;
      tailf:cli-suppress-show-match;
    }
  }

  grouping inv-loc {
    list location {
      key "loc";
      tailf:callpoint "location_cp";
      tailf:info "Select node location";
      tailf:cli-suppress-table;
      tailf:cli-show-template-legend " ";
      tailf:cli-show-template-enter " ";
      tailf:cli-show-template
        "
          Name: $(name|ljust:20)  Descr: $(Description|ljust:60)
          PID: $(PID|ljust:22) VID: $(VID|ljust:20)  SN: $(SN|ljust:12)
        ";
      uses target_str;
    }
  }

  grouping inv-all {
    list all {
      key "index";
      tailf:callpoint "all_cp";
      tailf:info "Get all FRU info";
      tailf:cli-suppress-table;
      tailf:cli-show-template-legend " ";
      tailf:cli-show-template-enter " ";
      tailf:cli-full-command;
      tailf:cli-full-show-path;
      tailf:cli-no-key-completion;
      tailf:cli-no-match-completion;
      tailf:cli-show-template
        "
          Name: $(name|ljust:20)  Descr: $(Description|ljust:60)
          PID: $(PID|ljust:22) VID: $(VID|ljust:20)  SN: $(SN|ljust:12)
        ";
      uses target_str;
    }
  }

  grouping inv-chassis {
    list chassis {
      key "index";
      tailf:callpoint "chassis_cp";
      tailf:info "Get chassis info";
      tailf:cli-suppress-table;
      tailf:cli-show-template-legend " ";
      tailf:cli-show-template-enter " ";
      tailf:cli-full-command;
      tailf:cli-full-show-path;
      tailf:cli-no-key-completion;
      tailf:cli-no-match-completion;
      tailf:cli-show-template
        "
          Name: $(name|ljust:20)  Descr: $(Description|ljust:60)
          PID: $(PID|ljust:22) VID: $(VID|ljust:20)  SN: $(SN|ljust:12)
        ";
      uses target_str;
    }
  }

  grouping inv-power {
    list power {
      key "index";
      tailf:callpoint "power_cp";
      tailf:info "Get Power info";
      tailf:cli-suppress-table;
      tailf:cli-show-template-legend " ";
      tailf:cli-show-template-enter " ";
      tailf:cli-full-command;
      tailf:cli-full-show-path;
      tailf:cli-no-key-completion;
      tailf:cli-no-match-completion;
      tailf:cli-show-template
        "
          Name: $(name|ljust:20)  Descr: $(Description|ljust:60)
          PID: $(PID|ljust:22) VID: $(VID|ljust:20)  SN: $(SN|ljust:12)
        ";
      uses target_str;
    }
  }

  grouping inv-fan {
    list fan {
      key "index";
      tailf:callpoint "fan_cp";
      tailf:info "Get Fan info";
      tailf:cli-suppress-table;
      tailf:cli-show-template-legend " ";
      tailf:cli-show-template-enter " ";
      tailf:cli-full-command;
      tailf:cli-full-show-path;
      tailf:cli-no-key-completion;
      tailf:cli-no-match-completion;
      tailf:cli-show-template
        "
          Name: $(name|ljust:20)  Descr: $(Description|ljust:60)
          PID: $(PID|ljust:22) VID: $(VID|ljust:20)  SN: $(SN|ljust:12)
        ";
      uses target_str;
    }
  }

  grouping inv-raw {
    list raw {
      key "index";
      tailf:callpoint "raw_cp";
      tailf:info "Get all entity info";
      tailf:cli-suppress-table;
      tailf:cli-show-template-legend " ";
      tailf:cli-show-template-enter " ";
      tailf:cli-full-command;
      tailf:cli-full-show-path;
      tailf:cli-no-key-completion;
      tailf:cli-no-match-completion;
      tailf:cli-show-template
        "
          Name: $(name|ljust:20)  Descr: $(Description|ljust:60)
          PID: $(PID|ljust:22) VID: $(VID|ljust:20)  SN: $(SN|ljust:12)
        ";
      uses target_str;
    }
  }
  tailf:id "http://cisco.com/calvados/inv";

  container inventory {
    config false;
    description
      "show inventory";
    uses inv-loc;
    uses inv-all;
    uses inv-chassis;
    uses inv-power;
    uses inv-fan;
    uses inv-raw;
  }
}
