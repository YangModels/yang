module Cisco-IOS-XR-ncs1k-mxp-lldp-oper {
  namespace "http://cisco.com/ns/yang/Cisco-IOS-XR-ncs1k-mxp-lldp-oper";
  prefix ncs1k-mxp-lldp-oper;

  import Cisco-IOS-XR-types {
    prefix xr;
  }
  include Cisco-IOS-XR-ncs1k-mxp-lldp-oper-sub1 {
    revision-date 2016-10-13;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-mxp-lldp package operational data.
     
     This module contains definitions
     for the following management objects:
       lldp-snoop-data: Information related to LLDP Snoop
     
     Copyright (c) 2013-2018 by Cisco Systems, Inc.
     All rights reserved.";

  revision 2016-10-13 {
    description
      "Added Additional bag for show lldp neighbor command.";
  }
  revision 2015-11-09 {
    description
      "IOS XR 6.0 revision.";
  }

  container lldp-snoop-data {
    config false;
    description
      "Information related to LLDP Snoop";
    container ethernet-controller-names {
      description
        "Ethernet controller snoop data";
      list ethernet-controller-name {
        key "name";
        description
          "port Name";
        leaf name {
          type xr:Interface-name;
          description
            "Port name";
        }
        uses MXP-LLDP-NEIGHBOR;
      }
    }
  }
}
