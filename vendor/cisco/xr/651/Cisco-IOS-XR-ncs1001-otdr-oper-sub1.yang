submodule Cisco-IOS-XR-ncs1001-otdr-oper-sub1 {
  belongs-to Cisco-IOS-XR-ncs1001-otdr-oper {
    prefix Cisco-IOS-XR-ncs1001-otdr-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs1001-otdr package operational data.
     
     Copyright (c) 2013-2018 by Cisco Systems, Inc.
     All rights reserved.";

  revision 2018-03-15 {
    description
      "first release.";
  }
  revision 2015-11-09 {
    description
      "IOS XR 6.0 revision.";
  }

  typedef Otdr-status {
    type enumeration {
      enum "otdr-status-unknown" {
        value 0;
        description
          "Unknown";
      }
      enum "otdr-status-ok" {
        value 1;
        description
          "Ok";
      }
      enum "otdr-status-orl-progress" {
        value 2;
        description
          "ORL Progress";
      }
      enum "otdr-status-otdr-progress" {
        value 3;
        description
          "OTDR Progress";
      }
      enum "otdr-status-progress" {
        value 4;
        description
          "Progress";
      }
      enum "otdr-status-failure" {
        value 5;
        description
          "Failure";
      }
      enum "otdr-status-aborted" {
        value 6;
        description
          "Aborted";
      }
    }
    description
      "Otdr status";
  }

  typedef Otdr-event {
    type enumeration {
      enum "otdr-event-type-loss" {
        value 1;
        description
          "Loss";
      }
      enum "otdr-event-type-reflect-ion" {
        value 2;
        description
          "Reflection";
      }
      enum "otdr-event-type-loss-and-reflect-ion" {
        value 3;
        description
          "Loss And Reflection";
      }
      enum "otdr-event-type-end-of-fiber" {
        value 4;
        description
          "End Of Fiber";
      }
    }
    description
      "Otdr event";
  }

  typedef Otdr-scan-mode {
    type enumeration {
      enum "otdr-scan-auto" {
        value 0;
        description
          "Auto";
      }
      enum "otdr-scan-expert" {
        value 1;
        description
          "Expert";
      }
    }
    description
      "Otdr scan mode";
  }

  typedef Direction {
    type enumeration {
      enum "direction-tx" {
        value 0;
        description
          "Tx";
      }
      enum "direction-rx" {
        value 1;
        description
          "Rx";
      }
    }
    description
      "Direction";
  }

  grouping HWMOD-OTDR-STATUS-B {
    description
      "HWMOD OTDR STATUS B";
    leaf otdr-id {
      type uint8;
      description
        "Otdr Id";
    }
    leaf direction {
      type Direction;
      description
        "Direction";
    }
    leaf timestamp {
      type string {
        length "0..16";
      }
      description
        "Timestamp";
    }
    leaf training-status {
      type Otdr-status;
      description
        "Training Status";
    }
    leaf measurement-status {
      type Otdr-status;
      description
        "Measurement Status";
    }
    leaf progress-pc {
      type uint16;
      description
        "Progress %";
    }
  }

  grouping HWMOD-OTDR-EVENT-DATA-B {
    description
      "HWMOD OTDR EVENT DATA B";
    leaf event-id {
      type uint16;
      description
        "Event Id";
    }
    leaf type {
      type Otdr-event;
      description
        "Event Type";
    }
    leaf position {
      type string {
        length "0..16";
      }
      description
        "Event Position in Km";
    }
    leaf accuracy {
      type string {
        length "0..16";
      }
      description
        "Event accuracy in meters";
    }
    leaf magnitude {
      type string {
        length "0..16";
      }
      description
        "Event Magnitude in dB";
    }
    leaf attenuation {
      type string {
        length "0..16";
      }
      description
        "Event Attenuation in dB";
    }
    leaf eof-confidence {
      type uint32;
      description
        "Event End of Fiber Confidence";
    }
    leaf threshold-crossing {
      type uint8;
      description
        "Threshold Crossing";
    }
  }

  grouping HWMOD-OTDR-ITEM-B {
    description
      "HWMOD OTDR ITEM B";
    leaf otdr-number {
      type uint8;
      description
        "Otdr Number";
    }
    leaf direction {
      type Direction;
      description
        "Scan Direction";
    }
    leaf timestamp {
      type string {
        length "0..16";
      }
      description
        "Timestamp";
    }
    leaf sor-file {
      type string {
        length "0..64";
      }
      description
        "Sor file name";
    }
    leaf sor-directory {
      type string {
        length "0..64";
      }
      description
        "Sor file location";
    }
    leaf scan-mode {
      type Otdr-scan-mode;
      description
        "Scan Mode";
    }
    leaf distance {
      type string {
        length "0..16";
      }
      description
        "Distance in Km";
    }
    leaf total-orl {
      type string {
        length "0..16";
      }
      description
        "Total Orl in dB";
    }
    list otdr-event {
      description
        "Event list";
      uses HWMOD-OTDR-EVENT-DATA-B;
    }
  }

  grouping HWMOD-OTDR-SCAN-LIST-B {
    description
      "HWMOD OTDR SCAN LIST B";
    leaf index {
      type uint16;
      description
        "Index";
    }
    leaf otdr-number {
      type uint8;
      description
        "Otdr Number";
    }
    leaf direction {
      type Direction;
      description
        "Direction";
    }
    leaf scan-mode {
      type Otdr-scan-mode;
      description
        "Scan Mode";
    }
    leaf timestamp {
      type string {
        length "0..16";
      }
      description
        "Timestamp";
    }
    leaf sor-file {
      type string {
        length "0..64";
      }
      description
        "Sor File Name";
    }
  }

  grouping OTS-HWMOD-OTDR-OP {
    description
      "OTS HWMOD OTDR OP";
    container otdr-item {
      description
        "otdr item";
      uses HWMOD-OTDR-ITEM-B;
    }
    list otdr-scan {
      description
        "otdr scan";
      uses HWMOD-OTDR-SCAN-LIST-B;
    }
    list otdr-status {
      description
        "otdr status";
      uses HWMOD-OTDR-STATUS-B;
    }
  }
}
