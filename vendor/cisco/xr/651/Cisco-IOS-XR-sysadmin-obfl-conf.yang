module Cisco-IOS-XR-sysadmin-obfl-conf {
  namespace "http://www.cisco.com/ns/yang/Cisco-IOS-XR-sysadmin-obfl-conf";
  prefix obflconf;

  import tailf-common {
    prefix tailf;
  }

  organization
    "Cisco Systems Inc.";
  description
    "This module is for setting certain OBFL params.";

  revision 2017-07-31 {
    description
      "Changed namespace to Cisco guidelines on naming convention";
  }
  revision 2011-12-03 {
    description
      "Initial revision.";
  }

  grouping hw-module-config-group {
    uses hw-module-obfl-config-group;
  }

  grouping hw-module-obfl-config-group {
    list location {
      key "location";
      tailf:cli-incomplete-command;
      tailf:info "Select location";
      leaf location {
        type string;
        tailf:info "Select target location";
      }
      container logging {
        tailf:info "OBFL logging";
        container onboard {
          tailf:info "OBFL onboard logging";
          choice onboard_target {
            case target_disable {
              leaf disable {
                type empty;
                tailf:info "OBFL disable logging";
              }
            }
          }
        }
      }
    }
  }
  tailf:id "http://www.cisco.com/calvados/obflconf";
}
