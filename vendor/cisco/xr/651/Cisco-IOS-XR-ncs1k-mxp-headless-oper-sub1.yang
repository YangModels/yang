submodule Cisco-IOS-XR-ncs1k-mxp-headless-oper-sub1 {
  belongs-to Cisco-IOS-XR-ncs1k-mxp-headless-oper {
    prefix Cisco-IOS-XR-ncs1k-mxp-headless-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs1k-mxp-headless package operational data.
     
     Copyright (c) 2013-2018 by Cisco Systems, Inc.
     All rights reserved.";

  revision 2017-03-30 {
    description
      "PRBS stats added";
  }
  revision 2015-11-09 {
    description
      "IOS XR 6.0 revision.";
  }

  typedef Mxp-otn-prbs-status {
    type enumeration {
      enum "locked" {
        value 0;
        description
          "Locked";
      }
      enum "not-locked" {
        value 1;
        description
          "Not Locked";
      }
      enum "not-applicable" {
        value 2;
        description
          "Not Applicable";
      }
      enum "locked-with-errors" {
        value 3;
        description
          "Locked With Errors";
      }
    }
    description
      "Mxp otn prbs status";
  }

  grouping MXP-ETHER-PRIM-INFO {
    description
      "Ether statistics";
    leaf rx-pkts-over-sized {
      type uint64;
      description
        "RxPktsOverSized";
    }
    leaf rx-pkts-bad-fcs {
      type uint64;
      description
        "RxPktsBadFcs";
    }
    leaf rx-error-jabbers {
      type uint64;
      description
        "RxErrorJabbers";
    }
    leaf rx-pkts-multicast {
      type uint64;
      description
        "RxPktsMulticast";
    }
    leaf rx-pkts-broadcast {
      type uint64;
      description
        "RxPktsBroadcast";
    }
    leaf rx-pkts-under-sized {
      type uint64;
      description
        "RxPktsUnderSized";
    }
    leaf rx-packets {
      type uint64;
      description
        "RxPackets";
    }
    leaf rx-total-bytes {
      type uint64;
      description
        "RxTotalBytes";
    }
    leaf rx-bytes-good {
      type uint64;
      description
        "RxBytesGood";
    }
    leaf rx-pkts-good {
      type uint64;
      description
        "RxPktsGood";
    }
    leaf tx-bytes-good {
      type uint64;
      description
        "TxBytesGood";
    }
    leaf tx-pkts-good {
      type uint64;
      description
        "TxPktsGood";
    }
    leaf rx-recv-fragments {
      type uint64;
      description
        "RxRecvFragments";
    }
    leaf rx-pkts64-bytes {
      type uint64;
      description
        "RxPkts64Bytes";
    }
    leaf rx-pkts65-to127-bytes {
      type uint64;
      description
        "RxPkts65To127Bytes";
    }
    leaf rx-pkts128to255-bytes {
      type uint64;
      description
        "RxPkts128to255Bytes";
    }
    leaf rx-pkts256-to511-bytes {
      type uint64;
      description
        "RxPkts256To511Bytes";
    }
    leaf rx-pkts512-to1023-bytes {
      type uint64;
      description
        "RxPkts512To1023Bytes";
    }
    leaf rx-pkts1024-to1518-bytes {
      type uint64;
      description
        "RxPkts1024To1518Bytes";
    }
    leaf rx-pkts-unicast {
      type uint64;
      description
        "RxPktsUnicast";
    }
    leaf tx-packets {
      type uint64;
      description
        "TxPackets";
    }
    leaf tx-total-bytes {
      type uint64;
      description
        "TxTotalBytes";
    }
    leaf tx-pkts-under-sized {
      type uint64;
      description
        "TxPktsUnderSized";
    }
    leaf tx-pkts-over-sized {
      type uint64;
      description
        "TxPktsOverSized";
    }
    leaf tx-fragments {
      type uint64;
      description
        "TxFragments";
    }
    leaf tx-jabber {
      type uint64;
      description
        "TxJabber";
    }
    leaf tx-bad-fcs {
      type uint64;
      description
        "TxBadFCS";
    }
    leaf rx-pkt-drop {
      type uint64;
      description
        "RxPktDrop";
    }
    leaf rx-pause {
      type uint64;
      description
        "RxPause";
    }
    leaf tx-pause {
      type uint64;
      description
        "TxPause";
    }
    leaf rx-lldp-pkt {
      type uint64;
      description
        "RxLldpPkt";
    }
    leaf rx8021q-pkt {
      type uint64;
      description
        "Rx8021QPkt";
    }
  }

  grouping MXP-HEADLESS-ETHER-PRIM-INFO {
    description
      "Ether Headless Statistics";
    container ether-statistics {
      description
        "Ether Statistics";
      uses MXP-ETHER-PRIM-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping MXP-OTN-PRBS-INFO {
    description
      "PRBS Statistics";
    leaf ebc {
      type uint64;
      description
        "EBC";
    }
    leaf sync-status {
      type Mxp-otn-prbs-status;
      description
        "SyncStatus";
    }
  }

  grouping MXP-OTN-CNT-INFO {
    description
      "OTN statistics";
    leaf sm-bip {
      type uint64;
      description
        "SmBip";
    }
    leaf sm-bei {
      type uint64;
      description
        "SmBei";
    }
    leaf fec-ec {
      type uint64;
      description
        "FecEc";
    }
    leaf fec-uc {
      type uint64;
      description
        "FecUc";
    }
  }

  grouping MXP-HEADLESS-OTN-CNT-INFO {
    description
      "OTN Headless Statistics";
    container otn-statistics {
      description
        "OTN statistics";
      uses MXP-OTN-CNT-INFO;
    }
    container prbs-statistics {
      description
        "PRBS Statistics";
      uses MXP-OTN-PRBS-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }
}
