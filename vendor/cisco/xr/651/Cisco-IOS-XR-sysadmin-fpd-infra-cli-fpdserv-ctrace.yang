module Cisco-IOS-XR-sysadmin-fpd-infra-cli-fpdserv-ctrace {
  namespace "http://www.cisco.com/ns/yang/Cisco-IOS-XR-sysadmin-fpd-infra-cli-fpdserv-ctrace";
  prefix fpdserv;

  import tailf-common {
    prefix tailf;
  }
  import Cisco-IOS-XR-sysadmin-show-trace {
    prefix show_trace;
  }

  revision 2017-05-01 {
    description
      "Namespace change to comply with Cisco guidelines on namespace";
  }
  tailf:id "http://cisco.com/calvados/fpdserv";

  container fpdserv {
    config false;
    tailf:info "fpdserv process";
    tailf:cli-incomplete-show-path;
    uses show_trace:traceable;
  }
}
