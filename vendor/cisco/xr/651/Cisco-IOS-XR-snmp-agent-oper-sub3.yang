submodule Cisco-IOS-XR-snmp-agent-oper-sub3 {
  belongs-to Cisco-IOS-XR-snmp-agent-oper {
    prefix Cisco-IOS-XR-snmp-agent-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR snmp-agent package operational data.
     
     Copyright (c) 2013-2018 by Cisco Systems, Inc.
     All rights reserved.";

  revision 2017-09-07 {
    description
      "Fixed type translation error.";
  }
  revision 2017-05-01 {
    description
      "Fixing backward compatibility error in module.";
  }
  revision 2016-06-01 {
    description
      "IOS XR 6.0.1 revision.";
  }
  revision 2015-01-07 {
    description
      "IOS XR 5.3.1 revision.";
  }

  typedef Dup-req-drop-status {
    type enumeration {
      enum "disabled" {
        description
          "Disabled";
      }
      enum "enabled" {
        description
          "Enabled";
      }
    }
    description
      "Dup req drop status";
  }

  grouping SNMP-TRAPQUE {
    description
      "SNMP Trap  queue statistics";
    leaf trap-min {
      type uint32;
      description
        "trap min";
    }
    leaf trap-avg {
      type uint32;
      description
        "trap avg";
    }
    leaf trap-max {
      type uint32;
      description
        "trap max";
    }
    list trap-q {
      max-elements "300";
      description
        "trap q";
      uses SNMP-QUEUE;
    }
  }

  grouping SNMP-SYSOBJID {
    description
      "SNMP sysObjID";
    leaf sys-obj-id {
      type string;
      description
        "sysObjID  1.3.6.1.2.1.1.2";
    }
  }

  grouping SNMP-SYSDESCR {
    description
      "SNMP sysDescr";
    leaf sys-descr {
      type string;
      description
        "sysDescr  1.3.6.1.2.1.1.1";
    }
  }

  grouping SNMP-PDU-DROP-STATS {
    description
      "SNMP Agent Req PDU Drop Stats";
    leaf nms-address {
      type string;
      description
        "NMS address of server";
    }
    leaf incoming-q-count {
      type uint32;
      description
        "Drop Count at Incoming Q";
    }
    leaf threshold-incoming-q-count {
      type uint32;
      description
        "Drop Count at Incoming Q after threshold limit";
    }
    leaf encode-count {
      type uint32;
      description
        "Drop Count with Encode errors";
    }
    leaf duplicate-count {
      type uint32;
      description
        "Duplicate request drop count";
    }
    leaf stack-count {
      type uint32;
      description
        "Drop Count at snmp Stack";
    }
    leaf aipc-count {
      type uint32;
      description
        "drop count with AIPC Buffer Full";
    }
    leaf overload-count {
      type uint32;
      description
        "Drop Count with overload notification";
    }
    leaf timeout-count {
      type uint32;
      description
        "Drop count with timeout";
    }
    leaf internal-count {
      type uint32;
      description
        " drop with Internal Errors";
    }
  }

  grouping SNMP-PDU-STATS {
    description
      "SNMP PDU STATS";
    leaf nms {
      type string;
      description
        " NMS address Rx PDU";
    }
    leaf request-id {
      type uint32;
      description
        " SNMP request id per PDU";
    }
    leaf port-xr {
      type uint16;
      description
        "NMS port number";
    }
    leaf pdu-type {
      type uint16;
      description
        " PDU type";
    }
    leaf error-status {
      type uint16;
      description
        "Is reques dropped due to error";
    }
    leaf serial-num {
      type uint32;
      description
        "Serial number per PDU processing";
    }
    leaf input-q {
      type string;
      description
        "Request inserted into input queue";
    }
    leaf output-q {
      type uint32;
      description
        "De-queue the request from the input queue";
    }
    leaf pending-q {
      type uint32;
      description
        "Enqueue the request into pending queue";
    }
    leaf response-out {
      type uint32;
      description
        "Response sent";
    }
  }

  grouping SNMP-MIB-INFO {
    description
      "SNMP MIB Information";
    leaf mib-name {
      type string;
      description
        "Name of the MIB module";
    }
    leaf dll-name {
      type string;
      description
        "MIB DLL filename, non-DLL MIBs will have no
         value";
    }
    leaf mib-config-filename {
      type string;
      description
        "MIB config filename, non-DLL MIBs will have no
         value";
    }
    leaf is-mib-loaded {
      type boolean;
      description
        "TRUE if MIB DLL is currently loaded, will always
         be TRUE for non-DLL MIBs";
    }
    leaf dll-capabilities {
      type uint32;
      description
        "DLL capabilities";
    }
    leaf trap-strings {
      type string;
      description
        "List of trapstring configured";
    }
    leaf timeout {
      type boolean;
      description
        "TRUE is mib is in phase 1 timeout";
    }
    leaf load-time {
      type uint32;
      description
        "Load time";
    }
  }

  grouping SNMP-TRAPS-COUNT {
    description
      "SNMP TRAPS COUNT";
    leaf trap-oid-count {
      type uint32;
      description
        "Total number of OID's sent";
    }
    leaf trap-oid-xr {
      type string;
      description
        "TRAP OID";
    }
  }

  grouping SNMP-CTX-MAPPING-ENTRY-XML {
    description
      "SNMP context mapping entry xml";
    leaf context {
      type string;
      description
        "Context name";
    }
    leaf feature-name {
      type string;
      description
        "Feature name";
    }
    leaf instance {
      type string;
      description
        "Instance name";
    }
    leaf topology {
      type string;
      description
        "Topology name";
    }
    leaf feature {
      type string;
      description
        "Feature";
    }
  }

  grouping SNMP-CTX-MAPPING-XML {
    description
      "SNMP context mapping";
    list contex-mapping {
      description
        "Context Mapping";
      uses SNMP-CTX-MAPPING-ENTRY-XML;
    }
  }

  grouping SNMP-INQ-DETAIL {
    description
      "SNMP Address Information";
    leaf address-of-queue {
      type string;
      description
        "Address of NMS Q";
    }
    leaf request-count {
      type uint32;
      description
        "Request Count of Each Queue.";
    }
    leaf processed-request-count {
      type uint32;
      description
        "Processed request Count.";
    }
    leaf last-access-time {
      type string;
      description
        "Last Access time of Each Queue.";
    }
    leaf priority {
      type uint8;
      description
        "Priority of Each Queue.";
    }
  }

  grouping SNMP-INCOMING-Q-STATS-ENTRY {
    description
      "SNMP IncomingQ Stats Entry";
    leaf queue-count {
      type uint32;
      description
        "Number of NMS Queues Exist.";
    }
    list inq-entry {
      max-elements "16";
      description
        "Each Entry Details.";
      uses SNMP-INQ-DETAIL;
    }
  }

  grouping SNMP-STATS {
    description
      "SNMP statistics";
    leaf packets-received {
      type uint32;
      description
        "snmpInPkts";
    }
    leaf bad-versions-received {
      type uint32;
      description
        "snmpInBadVersions";
    }
    leaf bad-community-names-received {
      type uint32;
      description
        "snmpInBadCommunityNames";
    }
    leaf bad-community-uses-received {
      type uint32;
      description
        "snmpInBadCommunityUses";
    }
    leaf asn-parse-errors-received {
      type uint32;
      description
        "snmpInASNParseErrs";
    }
    leaf silent-drop-count {
      type uint32;
      description
        "snmpSilentDrops";
    }
    leaf proxy-drop-count {
      type uint32;
      description
        "snmpProxyDrops";
    }
    leaf too-big-packet-received {
      type uint32;
      description
        "snmpInTooBigs";
    }
    leaf max-packet-size {
      type uint32;
      description
        "snmp maximum packet size";
    }
    leaf no-such-names-received {
      type uint32;
      description
        "snmpInNoSuchNames";
    }
    leaf bad-values-received {
      type uint32;
      description
        "snmpInBadValues";
    }
    leaf read-only-received {
      type uint32;
      description
        "snmpInReadOnlys";
    }
    leaf total-general-errors {
      type uint32;
      description
        "snmpInGenErrs";
    }
    leaf total-requested-variables {
      type uint32;
      description
        "snmpInTotalReqVars";
    }
    leaf total-set-variables-received {
      type uint32;
      description
        "snmpInTotalSetVars";
    }
    leaf get-requests-received {
      type uint32;
      description
        "snmpInGetRequests";
    }
    leaf get-next-requests-received {
      type uint32;
      description
        "snmpInGetNexts";
    }
    leaf set-requests-received {
      type uint32;
      description
        "snmpInSetRequests";
    }
    leaf get-responses-received {
      type uint32;
      description
        "snmpInGetResponses";
    }
    leaf traps-received {
      type uint32;
      description
        "snmpInTraps";
    }
    leaf total-packets-sent {
      type uint32;
      description
        "snmpOutPkts";
    }
    leaf too-big-packets-sent {
      type uint32;
      description
        "snmpOutTooBigs";
    }
    leaf no-such-names-sent {
      type uint32;
      description
        "snmpOutNoSuchNames";
    }
    leaf bad-values-sent {
      type uint32;
      description
        "snmpOutBadValues";
    }
    leaf general-errors-sent {
      type uint32;
      description
        "snmpOutGenErrs";
    }
    leaf get-requests-sent {
      type uint32;
      description
        "snmpOutGetRequests";
    }
    leaf get-next-request-sent {
      type uint32;
      description
        "snmpOutGetNexts";
    }
    leaf set-requests-sent {
      type uint32;
      description
        "snmpOutSetRequests";
    }
    leaf get-responses-sent {
      type uint32;
      description
        "snmpOutGetResponses";
    }
    leaf traps-sent {
      type uint32;
      description
        "snmpOutTraps";
    }
  }

  grouping SNMP-TRAP-OID-INFO {
    description
      "SNMP TRAP OID INFO";
    leaf trap-oid {
      type string;
      description
        "TRAP OID";
    }
    leaf count {
      type uint32;
      description
        "Number of traps sent";
    }
    leaf drop-count {
      type uint32;
      description
        "Number of Traps Dropped";
    }
    leaf retry-count {
      type uint32;
      description
        "Num of times retry";
    }
    leaf lastsent-time {
      type string;
      description
        "Timestamp of latest successfully sent";
    }
    leaf lasrdrop-time {
      type string;
      description
        "Timestamp of latest droped";
    }
  }

  grouping SNMP-TRAPS-INFO {
    description
      "SNMP TRAPS INFO";
    leaf host {
      type string;
      description
        "NMS/Host address";
    }
    leaf port-xr {
      type uint16;
      description
        "udp port number";
    }
    leaf trap-oid-count {
      type uint32;
      description
        "Total number of OID's sent";
    }
    list trap-oi-dinfo {
      description
        "Per trap OID statistics";
      uses SNMP-TRAP-OID-INFO;
    }
  }

  grouping SNMP-BULKSTATS-B {
    description
      "SNMP Bulkstats transfer Information";
    leaf transfer-name-xr {
      type string;
      description
        "Name of the bulkstats transfer session";
    }
    leaf url-primary {
      type string;
      description
        "Bulkstats transfer primary URL";
    }
    leaf url-secondary {
      type string;
      description
        "Bulkstats transfer secondary URL";
    }
    leaf retained-file {
      type string;
      description
        "Bulkstats transfer retained file name";
    }
    leaf time-left {
      type uint32;
      units "second";
      description
        "Bulkstats transfer retry time left in seconds";
    }
    leaf retry-left {
      type uint32;
      description
        "Bulkstats transfer retry attempt left";
    }
  }

  grouping SNMP-STATISTICS {
    description
      "SNMP Statistics extension";
    leaf duplicate-request-status {
      type Dup-req-drop-status;
      description
        "Duplicate requests drop feature status.";
    }
    leaf last-status-change-time {
      type string;
      description
        "Duplicate request drop feature last enable
         disable time (Day Mon Date HH:MM:SS)";
    }
    leaf duplicate-drop-configured-timeout {
      type uint32;
      description
        "Configured Duplicate Drop feature Timeout.";
    }
    leaf duplicate-dropped-requests {
      type uint32;
      description
        "Number of duplicate SNMP requests are dropped.";
    }
    leaf retry-processed-requests {
      type uint32;
      description
        "Number of Retry SNMP requests are Processed.";
    }
    leaf first-enable-time {
      type string;
      description
        "Duplicate request drop feature first  enable
         time (Day Mon Date HH:MM:SS)";
    }
    leaf latest-duplicate-dropped-requests {
      type uint32;
      description
        "Number of duplicate SNMP requests dropped, from
         the last enable time.";
    }
    leaf latest-retry-processed-requests {
      type uint32;
      description
        "Number of retry SNMP requests processed, from
         the last enable time.";
    }
    leaf duplicate-request-latest-enable-time {
      type string;
      description
        "Duplicate request drop feature last enable
         time(Day Mon Date HH:MM:SS)";
    }
    leaf duplicate-drop-enable-count {
      type uint32;
      description
        " Number of times duplicate request drop feature
         is enabled.";
    }
    leaf duplicate-drop-disable-count {
      type uint32;
      description
        " Number of times duplicate request drop feature
         is disabled.";
    }
  }

  grouping SNMP-Q-STATS-B {
    description
      "SNMP incomming/processing queue statistics";
    leaf total-count {
      type uint32;
      description
        "Total request count for each managment station
         or client";
    }
    leaf agent-request-count {
      type uint32;
      description
        "Processing agent request count for each client
         for particluar managment station";
    }
    leaf interface-request-count {
      type uint32;
      description
        "Processing interfce request count for each
         client for particluar managment station";
    }
    leaf entity-request-count {
      type uint32;
      description
        "Processing entity request count for each client
         for particluar managment station";
    }
    leaf route-request-count {
      type uint32;
      description
        "Processing route request count for each client
         for particluar Managment station";
    }
    leaf infra-request-count {
      type uint32;
      description
        "Processing infra request count for each client
         for particluar Managment station";
    }
  }

  grouping SNMP-SYSNAME {
    description
      "SNMP sysName";
    leaf system-name {
      type string;
      description
        "sysName  1.3.6.1.2.1.1.5";
    }
  }

  grouping SNMP-QUEUE {
    description
      "SNMP QUEUE";
    leaf min {
      type uint32;
      description
        "min";
    }
    leaf avg {
      type uint32;
      description
        "avg";
    }
    leaf max {
      type uint32;
      description
        "max";
    }
  }

  grouping SNMP-RXQUE {
    description
      "SNMP Incoming queue statistics";
    leaf qlen {
      type uint32;
      description
        "qlen";
    }
    leaf in-min {
      type uint32;
      description
        "in min";
    }
    leaf in-avg {
      type uint32;
      description
        "in avg";
    }
    leaf in-max {
      type uint32;
      description
        "in max";
    }
    leaf pend-min {
      type uint32;
      description
        "pend min";
    }
    leaf pend-avg {
      type uint32;
      description
        "pend avg";
    }
    leaf pend-max {
      type uint32;
      description
        "pend max";
    }
    list incoming-q {
      max-elements "300";
      description
        "incoming q";
      uses SNMP-QUEUE;
    }
    list pending-q {
      max-elements "300";
      description
        "pending q";
      uses SNMP-QUEUE;
    }
  }

  grouping SNMP-ENGINEID {
    description
      "SNMPv3 engineID Information";
    leaf engine-id {
      type string;
      description
        "SNMPv3 engineID";
    }
  }

  grouping SNMP-REQ-NMS-SUM {
    description
      "SNMP Agent Req NMS Summary ";
    leaf nms-address {
      type string;
      description
        "NMS address of server";
    }
    leaf get-request-count {
      type uint32;
      description
        "Get Request Count";
    }
    leaf getnext-request-count {
      type uint32;
      description
        "Getnext Request Count";
    }
    leaf getbulk-request-count {
      type uint32;
      description
        "Getbulk Request Count";
    }
    leaf set-request-count {
      type uint32;
      description
        "Set Request Count";
    }
    leaf test-request-count {
      type uint32;
      description
        "Test Request Count";
    }
  }

  grouping SNMP-SYSUPTIME-EDM {
    description
      "SNMP sysUpTime in days time format for edm";
    leaf system-up-time-edm {
      type string;
      description
        "sysUpTime  1.3.6.1.2.1.1.3";
    }
  }
}
