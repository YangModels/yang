module Cisco-IOS-XR-infra-xtc-agent-cfg {
  namespace "http://cisco.com/ns/yang/Cisco-IOS-XR-infra-xtc-agent-cfg";
  prefix infra-xtc-agent-cfg;

  import ietf-inet-types {
    prefix inet;
  }
  import Cisco-IOS-XR-types {
    prefix xr;
  }
  import Cisco-IOS-XR-segment-routing-ms-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-xtc-agent package configuration.
     
     This YANG module augments the
       Cisco-IOS-XR-segment-routing-ms-cfg
     module with configuration data.
     
     Copyright (c) 2013-2018 by Cisco Systems, Inc.
     All rights reserved.";

  revision 2018-07-07 {
    description
      "Modified the allowed range for policy path weight.";
  }
  revision 2018-07-03 {
    description
      "Added TE-latency algorithm configuration.";
  }
  revision 2018-01-31 {
    description
      "Added BW configuration option for On Demand Color policy.";
  }
  revision 2017-12-21 {
    description
      "Added BW configuration option for SR policy.";
  }
  revision 2017-09-30 {
    description
      "Ensure propagation of MDA mandatory state to YANG model.";
  }
  revision 2017-09-11 {
    description
      "Initial version";
  }
  revision 2015-11-09 {
    description
      "IOS XR 6.0 revision.";
  }

  typedef Xtc-metric-value {
    type enumeration {
      enum "relative" {
        value 1;
        description
          "Relative metric value";
      }
      enum "absolute" {
        value 2;
        description
          "Absolute metric value";
      }
    }
    description
      "Xtc metric value";
  }

  typedef Xtc-binding-sidexplicit-rule {
    type enumeration {
      enum "fallback-dynamic" {
        value 1;
        description
          "Fallback dynamic option";
      }
      enum "enforce-srlb" {
        value 2;
        description
          "SRLB enforcement option";
      }
    }
    description
      "Xtc binding sidexplicit rule";
  }

  typedef Xtc-path-hop {
    type enumeration {
      enum "mpls" {
        value 1;
        description
          "Segment-routing MPLS";
      }
      enum "srv6" {
        value 2;
        description
          "Segment-routing v6";
      }
    }
    description
      "Xtc path hop";
  }

  typedef Xtc-steering-application {
    type enumeration {
      enum "bgp" {
        value 1;
        description
          "BGP as steering client";
      }
      enum "isis" {
        value 2;
        description
          "ISIS as steering client";
      }
      enum "ospf" {
        value 3;
        description
          "OSPF as steering client";
      }
    }
    description
      "Xtc steering application";
  }

  typedef Xtc-affinity-rule {
    type enumeration {
      enum "affinity-include-all" {
        value 0;
        description
          "Include-all affinity rule";
      }
      enum "affinity-exclude-any" {
        value 1;
        description
          "Exclude-any affinity rule";
      }
      enum "affinity-include-any" {
        value 2;
        description
          "Include-any affinity rule";
      }
    }
    description
      "Xtc affinity rule";
  }

  typedef Xtc-path {
    type enumeration {
      enum "explicit" {
        value 1;
        description
          "Explicit";
      }
      enum "dynamic" {
        value 2;
        description
          "Dynamic";
      }
    }
    description
      "Xtc path";
  }

  typedef Xtc-metric {
    type enumeration {
      enum "igp" {
        value 1;
        description
          "IGP metric type";
      }
      enum "te" {
        value 2;
        description
          "TE metric type";
      }
      enum "latency" {
        value 3;
        description
          "Latency metric type";
      }
    }
    description
      "Xtc metric";
  }

  typedef Xtc-address-family {
    type enumeration {
      enum "af-type-ipv4" {
        value 1;
        description
          "IPv4 address family";
      }
      enum "xtc-af-type-ipv6" {
        value 2;
        description
          "IPv6 address family";
      }
    }
    description
      "Xtc address family";
  }

  typedef Xtc-segment {
    type enumeration {
      enum "ipv4-address" {
        value 1;
        description
          "IPv4 Address";
      }
      enum "mpls-label" {
        value 3;
        description
          "MPLS Label";
      }
    }
    description
      "Xtc segment";
  }

  typedef Xtc-binding-sid {
    type enumeration {
      enum "mpls-label-specified" {
        value 1;
        description
          "Use specified BSID MPLS label";
      }
      enum "mpls-label-any" {
        value 2;
        description
          "Allocate BSID MPLS label";
      }
    }
    description
      "Xtc binding sid";
  }

  typedef Xtc-disjointness {
    type enumeration {
      enum "link" {
        value 1;
        description
          "Link Disjointness";
      }
      enum "node" {
        value 2;
        description
          "Node Disjointness";
      }
      enum "srlg" {
        value 3;
        description
          "SRLG Disjointness";
      }
      enum "srlg-node" {
        value 4;
        description
          "SRLG Node Disjointness";
      }
    }
    description
      "Xtc disjointness";
  }

  typedef Xtc-auto-route-metric {
    type enumeration {
      enum "relative" {
        value 1;
        description
          "Autoroute relative metric type";
      }
      enum "constant" {
        value 3;
        description
          "Autoroute constant metric type";
      }
    }
    description
      "Xtc auto route metric";
  }

  typedef Xtc-end-point {
    type enumeration {
      enum "end-point-type-ipv4" {
        value 1;
        description
          "IPv4 endpoint address";
      }
      enum "end-point-type-ipv6" {
        value 2;
        description
          "IPv6 endpoint address";
      }
    }
    description
      "Xtc end point";
  }

  grouping ENABLE {
    description
      "Common node of traffic-engineering, policy,
       segment-list, candidate-paths, preference,
       path-info, metric, constraints, srte-interface,
       auto-route, on-demand-color, pcep";
    leaf enable {
      type empty;
      description
        "True only";
    }
  }

  augment "/a1:sr" {
    description
      "This augment extends the configuration data of
       'Cisco-IOS-XR-segment-routing-ms-cfg'";
    container traffic-engineering {
      presence "Indicates a traffic-engineering node is configured.";
      description
        "Traffic Engineering configuration data";
      container on-demand-colors {
        description
          "On-demand color configuration";
        list on-demand-color {
          key "color";
          description
            "On-demand color configuration";
          container on-demand-color-dyn-mpls {
            presence "Indicates a on-demand-color-dyn-mpls node is configured.";
            description
              "Dynamic MPLS path properties";
            container on-demand-color-dyn-mpls-metric {
              presence "Indicates a on-demand-color-dyn-mpls-metric node is configured.";
              description
                "Metric type";
              leaf metric-type {
                type Xtc-metric;
                mandatory true;
                description
                  "Metric Type";
              }
              leaf enable {
                type empty;
                description
                  "Metric submode Enable";
              }
            }
            container on-demand-color-dyn-mpls-pce {
              description
                "Use Path Computation Element";
              leaf enable {
                type empty;
                description
                  "PCE submode Enable";
              }
            }
            container disjoint-path {
              presence "Indicates a disjoint-path node is configured.";
              description
                "Disjoint path";
              leaf group-id {
                type uint32 {
                  range "1..65535";
                }
                mandatory true;
                description
                  "Group ID";
              }
              leaf disjointness-type {
                type Xtc-disjointness;
                mandatory true;
                description
                  "Disjointness Type";
              }
              leaf sub-id {
                type uint32 {
                  range "1..65535";
                }
                description
                  "Sub ID";
              }
            }
            leaf on-demand-color-dyn-mpls-flex-algorithm {
              type uint32 {
                range "128..255";
              }
              mandatory true;
              description
                "Prefix-SID algorithm";
            }
            leaf enable {
              type empty;
              description
                "Dynamic MPLS path properties submode Enable";
            }
          }
          leaf bandwidth {
            type uint32 {
              range "1..4294967295";
            }
            description
              "The value of the bandwidth reserved by this
               policy in kbps";
          }
          leaf color {
            type uint32 {
              range "1..4294967295";
            }
            description
              "Color";
          }
          uses ENABLE;
        }
      }
      container segments {
        description
          "Segment-lists configuration";
        list segment {
          key "path-name";
          description
            "Segment-list configuration";
          container segments {
            description
              "Segments/hops configuration for given
               Segment-list";
            list segment {
              key "segment-index";
              description
                "Configure Segment/hop at the index";
              leaf segment-index {
                type uint32 {
                  range "1..65535";
                }
                description
                  "Segment index";
              }
              leaf segment-type {
                type Xtc-segment;
                description
                  "Segment/hop type";
              }
              leaf address {
                when "../segment-type = 'ipv4-address'" {
                  description
                    "../SegmentType = IPv4Address";
                }
                type inet:ipv4-address-no-zone;
                description
                  "IPv4 Address";
              }
              leaf mpls-label {
                when "../segment-type = 'mpls-label'" {
                  description
                    "../SegmentType = MPLSLabel";
                }
                type uint32 {
                  range "0..1048575";
                }
                description
                  "MPLS Label";
              }
            }
          }
          leaf path-name {
            type xr:Cisco-ios-xr-string {
              length "1..128";
            }
            description
              "Segment-list name";
          }
          uses ENABLE;
        }
      }
      container logging {
        presence "Indicates a logging node is configured.";
        description
          "Logging configuration";
        leaf policy-status {
          type empty;
          mandatory true;
          description
            "Enable logging for policy status";
        }
      }
      container binding-sid-rules {
        description
          "Binding sid rules";
        container explicit {
          presence "Indicates a explicit node is configured.";
          description
            "Binding sid explicit options";
          leaf rule {
            type Xtc-binding-sidexplicit-rule;
            mandatory true;
            description
              "Binding sid explicit rule";
          }
        }
      }
      container policies {
        description
          "Policy configuration";
        list policy {
          key "policy-name";
          description
            "Policy configuration";
          container steering {
            description
              "Steering options for the policy";
            container applications {
              description
                "Application table that steering options need
                 to be applied";
              list application {
                key "application";
                description
                  "Application that steering options need to
                   be applied";
                leaf disable {
                  type empty;
                  description
                    "Disable all steering services";
                }
                leaf application {
                  type Xtc-steering-application;
                  description
                    "Steering application";
                }
              }
            }
          }
          container binding-sid {
            description
              "Binding Segment ID";
            leaf binding-sid-type {
              type Xtc-binding-sid;
              description
                "Binding SID type";
            }
            leaf mpls-label {
              when "../binding-sid-type = 'mpls-label-specified'" {
                description
                  "../BindingSIDType = MPLSLabelSpecified";
              }
              type uint32 {
                range "16..1048575";
              }
              description
                "MPLS Label";
            }
          }
          container policy-color-endpoint {
            presence "Indicates a policy-color-endpoint node is configured.";
            description
              "Color and endpoint of a policyColor,
               EndPointType, Endpoint";
            leaf color {
              type uint32 {
                range "1..4294967295";
              }
              mandatory true;
              description
                "Color";
            }
            leaf end-point-type {
              type Xtc-end-point;
              mandatory true;
              description
                "End point type";
            }
            leaf end-point-address {
              type inet:ip-address-no-zone;
              mandatory true;
              description
                "End point address";
            }
          }
          container auto-route {
            description
              "Autoroute configuration";
            container auto-route-metric {
              description
                "Autoroute metric";
              leaf autoroute-metric-type {
                type Xtc-auto-route-metric;
                description
                  "Metric type";
              }
              leaf metric-relative-value {
                type int32 {
                  range "-10..10";
                }
                description
                  "Autoroute relative metric";
              }
              leaf metric-constant-value {
                type uint32 {
                  range "1..2147483647";
                }
                description
                  "Autoroute constant metric";
              }
            }
            container include-prefixes {
              description
                "Autoroute include prefix table configuration";
              list include-prefix {
                key "af-type prefix-address prefix-length";
                description
                  "Autoroute IP prefix to include";
                leaf af-type {
                  type Xtc-address-family;
                  description
                    "Address family type";
                }
                leaf prefix-address {
                  type inet:ip-address-no-zone;
                  description
                    "Autoroute prefix IP address";
                }
                leaf prefix-length {
                  type uint32 {
                    range "0..32";
                  }
                  description
                    "Autoroute IP prefix length";
                }
              }
            }
            uses ENABLE;
          }
          container candidate-paths {
            description
              "Policy candidate-paths configuration";
            container preferences {
              description
                "Policy path-option preference table";
              list preference {
                key "path-index";
                description
                  "Policy path-option preference entry";
                container constraints {
                  description
                    "SR path computation and verification
                     constraints";
                  container disjoint-path {
                    presence "Indicates a disjoint-path node is configured.";
                    description
                      "Disjoint path";
                    leaf group-id {
                      type uint32 {
                        range "1..65535";
                      }
                      mandatory true;
                      description
                        "Group ID";
                    }
                    leaf disjointness-type {
                      type Xtc-disjointness;
                      mandatory true;
                      description
                        "Disjointness Type";
                    }
                    leaf sub-id {
                      type uint32 {
                        range "1..65535";
                      }
                      description
                        "Sub ID";
                    }
                  }
                  container segment-rules {
                    presence "Indicates a segment-rules node is configured.";
                    description
                      "SR path computation segment specific
                       rules";
                    leaf sid-algorithm {
                      type uint32 {
                        range "128..255";
                      }
                      mandatory true;
                      description
                        "Prefix-SID algorithm";
                    }
                  }
                  container affinity-rules {
                    description
                      "SR path computation and verification
                       affinity rules";
                    list affinity-rule {
                      key "rule color";
                      description
                        "SR path computation and verification
                         affinity rule";
                      leaf rule {
                        type Xtc-affinity-rule;
                        description
                          "Path-option preference";
                      }
                      leaf color {
                        type xr:Cisco-ios-xr-string {
                          length "1..59";
                        }
                        description
                          "The color";
                      }
                    }
                  }
                  uses ENABLE;
                }
                container path-infos {
                  description
                    "Policy path-option preference
                     configuration";
                  list path-info {
                    key "type hop-type segment-list-name";
                    description
                      "Policy configuration";
                    container metric {
                      presence "Indicates a metric node is configured.";
                      description
                        "Metric configuration, valid only for
                         dynamic path-options";
                      container margin {
                        description
                          "Metric type";
                        leaf value-type {
                          type Xtc-metric-value;
                          description
                            "Metric value type";
                        }
                        leaf absolute-value {
                          when "../value-type = 'absolute'" {
                            description
                              "../ValueType = Absolute";
                          }
                          type uint32 {
                            range "0..2147483647";
                          }
                          description
                            "Absolute metric value";
                        }
                        leaf relative-value {
                          when "../value-type = 'relative'" {
                            description
                              "../ValueType = Relative";
                          }
                          type uint32 {
                            range "0..100";
                          }
                          description
                            "Relative metric value";
                        }
                      }
                      leaf sid-limit {
                        type uint32 {
                          range "0..255";
                        }
                        mandatory true;
                        description
                          "Maximum number of SIDs";
                      }
                      leaf metric-type {
                        type Xtc-metric;
                        mandatory true;
                        description
                          "Metric type";
                      }
                      uses ENABLE;
                    }
                    container pcep {
                      description
                        "Path Computation Element Protocol";
                      uses ENABLE;
                    }
                    leaf weight {
                      type uint32 {
                        range "1..4294967295";
                      }
                      description
                        "Path-option weight";
                    }
                    leaf type {
                      type Xtc-path;
                      description
                        "Path-option type";
                    }
                    leaf hop-type {
                      type Xtc-path-hop;
                      description
                        "Type of dynamic path to be computed";
                    }
                    leaf segment-list-name {
                      type xr:Cisco-ios-xr-string {
                        length "1..128";
                      }
                      description
                        "Segment-list name";
                    }
                    uses ENABLE;
                  }
                }
                leaf path-index {
                  type uint32 {
                    range "1..65535";
                  }
                  description
                    "Path-option preference";
                }
                uses ENABLE;
              }
            }
            uses ENABLE;
          }
          leaf forward-class {
            type uint32 {
              range "1..7";
            }
            description
              "Forward class associated with the policy";
          }
          leaf ipv6-disable {
            type empty;
            description
              "IPv6 disable";
          }
          leaf shutdown {
            type empty;
            description
              "Administratively shutdown policy";
          }
          leaf bandwidth {
            type uint32 {
              range "1..4294967295";
            }
            description
              "The value of the bandwidth reserved by this
               policy in kbps";
          }
          leaf policy-name {
            type xr:Cisco-ios-xr-string {
              length "1..59";
            }
            description
              "Policy name";
          }
          uses ENABLE;
        }
      }
      container srte-interfaces {
        description
          "SR-TE interfaces";
        list srte-interface {
          key "srte-interface-name";
          description
            "SR-TE interface";
          container interface-affinities {
            description
              "Set user defined interface attribute flags";
            list interface-affinity {
              key "color";
              description
                "Set user defined interface attribute flags";
              leaf color {
                type xr:Cisco-ios-xr-string {
                  length "1..32";
                }
                description
                  "Interface affinity colors";
              }
            }
          }
          leaf interface-metric {
            type uint32 {
              range "0..2147483647";
            }
            description
              "Interface TE metric configuration";
          }
          leaf srte-interface-name {
            type xr:Interface-name;
            description
              "SR-TE Interface name";
          }
          uses ENABLE;
        }
      }
      container pcc {
        description
          "Path Computation Client";
        container pce-peers {
          description
            "PCE peer configuration";
          list pce-peer {
            key "pce-address";
            description
              "PCE peer";
            leaf password {
              type string {
                length "1..25";
              }
              description
                "PCC Peer MD5 Password";
            }
            leaf keychain {
              type string {
                length "1..32";
              }
              description
                "PCC Peer Keychain";
            }
            leaf enable {
              type empty;
              description
                "PCC Peer Enable";
            }
            leaf precedence {
              type uint32 {
                range "0..255";
              }
              description
                "Precedence value of this PCE";
            }
            leaf pce-address {
              type inet:ip-address-no-zone;
              description
                "Remote PCE address";
            }
          }
        }
        container pce-addresses {
          description
            "PCE peer configuration";
          list pce-address {
            key "pce-address";
            description
              "PCE peer address";
            leaf pce-address {
              type inet:ip-address-no-zone;
              description
                "Remote PCE address";
            }
            leaf precedence {
              type uint32 {
                range "0..255";
              }
              mandatory true;
              description
                "Precedence value of this PCE";
            }
          }
        }
        leaf dead-timer-interval {
          type uint32 {
            range "1..255";
          }
          description
            "Amount of time after which the peer can
             declare this session down, if no PCEP message
             has been received";
        }
        leaf pcc-centric {
          type empty;
          description
            "Enable PCC centric model, where PCC only
             allows the lowest precedence PCE to initiate
             policies";
        }
        leaf report-all {
          type empty;
          description
            "Report all local SR policies to connected PCEP
             peers";
        }
        leaf keepalive-timer-interval {
          type uint32 {
            range "0..255";
          }
          description
            "Maximum time between two consecutive PCEP
             messages sent by this node";
        }
        leaf initiated-state-interval {
          type uint32 {
            range "15..14400";
          }
          description
            "Amount of time a PCE Initiated policy can
             remain orphan";
        }
        leaf source-address {
          type inet:ip-address-no-zone;
          description
            "Local source IP address to use on PCEP
             sessions";
        }
        leaf max-sid-depth {
          type uint32 {
            range "1..32";
          }
          description
            "Override the platform Maximum SID Depth value
             with a user configured explicit value";
        }
        leaf enable {
          type empty;
          description
            "PCC Enable";
        }
        leaf initiated-orphan-interval {
          type uint32 {
            range "10..180";
          }
          description
            "Amount of time that a policy will be owned by
             a PCE after that PCE has gone down";
        }
        leaf delegation-timeout {
          type uint32 {
            range "0..3600";
          }
          description
            "The maximum time delegated SR-TE policies can
             remain up without an active connection to a
             PCE";
        }
      }
      container affinity-maps {
        description
          "Affinity-map configuration";
        list affinity-map {
          key "color";
          description
            "Affinity-map entry";
          leaf color {
            type xr:Cisco-ios-xr-string {
              length "1..32";
            }
            description
              "Affinity-map bit-position";
          }
          leaf bit-position {
            type uint32 {
              range "0..31";
            }
            mandatory true;
            description
              "Affinity-map bit-position";
          }
        }
      }
      leaf te-latency {
        type empty;
        description
          "Use TE-latency algorithm";
      }
      leaf maximum-sid-depth {
        type uint32 {
          range "1..255";
        }
        mandatory true;
        description
          "Maximum SID Depth Configuration";
      }
      uses ENABLE;
    }
  }
}
