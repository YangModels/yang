submodule Cisco-IOS-XR-ocni-oper-sub1 {
  belongs-to Cisco-IOS-XR-ocni-oper {
    prefix Cisco-IOS-XR-ocni-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ocni package operational data.
     
     Copyright (c) 2013-2018 by Cisco Systems, Inc.
     All rights reserved.";

  revision 2017-11-23 {
    description
      "Support for telemetry backend code.";
  }
  revision 2015-11-09 {
    description
      "IOS XR 6.0 revision.";
  }

  typedef Yang2bag-string {
    type string;
    description
      "Yang2bag string";
  }

  grouping STATE {
    description
      "STATE";
    leaf name {
      type Yang2bag-string;
      description
        "An operator-assigned unique name for the
         forwarding instance";
    }
    leaf type {
      type Yang2bag-string;
      description
        "The type of network instance. The value of this
         leaf indicates the type of forwarding entries
         that should be supported by this network
         instance";
    }
    leaf enabled {
      type boolean;
      description
        "Whether the network instance should be
         configured to be active on the network element";
    }
    leaf description {
      type Yang2bag-string;
      description
        "A free-form string to be used by the network
         operator to describe the function of this
         network instance";
    }
    leaf-list enabled-address-family {
      type Yang2bag-string;
      description
        "The address families that are to be enabled for
         this network instance.";
    }
  }

  grouping OVERLAY-OCNI-NI-BASE-NETWORK-INSTANCE {
    description
      "Network instances configured on the local system";
    container state {
      description
        "Operational state parameters relating to a
         network instance";
      uses STATE;
    }
  }
}
