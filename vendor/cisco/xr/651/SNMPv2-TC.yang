module SNMPv2-TC {
  namespace "http://tail-f.com/ns/mibs/SNMPv2-TC/1.0";
  prefix SNMPv2_TC;
  import ietf-yang-types {
    prefix yang;
  }
  import tailf-common {
    prefix tailf;
  }
  import ietf-yang-smiv2 {
    prefix smiv2;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2016-08-18 {
    description
      "Initial revision";
  }


  typedef DisplayString {
    type string {
      length "min .. 255";
    }
  }

  typedef PhysAddress {
    type tailf:hex-list {
      pattern "(((([0-9A-Fa-f]{2}):)*([0-9A-Fa-f]{2}))){0,1}";
    }
  }

  typedef MacAddress {
    type tailf:hex-list {
      pattern "(((([0-9A-Fa-f]{2}):){5,5})([0-9A-Fa-f]{2}))";
    }
  }

  typedef TruthValue {
    type enumeration {
      enum "true" {
        value 1;
      }
      enum "false" {
        value 2;
      }
    }
  }

  typedef TestAndIncr {
    type int32 {
      range "0 .. 2147483647";
    }
  }

  typedef AutonomousType {
    type yang:object-identifier;
  }

  typedef InstancePointer {
    type yang:object-identifier;
  }

  typedef VariablePointer {
    type yang:object-identifier;
  }

  typedef RowPointer {
    type yang:object-identifier;
  }

  typedef RowStatus {
    type enumeration {
      enum "active" {
        value 1;
      }
      enum "notInService" {
        value 2;
      }
      enum "notReady" {
        value 3;
      }
      enum "createAndGo" {
        value 4;
      }
      enum "createAndWait" {
        value 5;
      }
      enum "destroy" {
        value 6;
      }
    }
  }

  typedef TimeStamp {
    type uint32 {
      range "0 .. 4294967295";
    }
  }

  typedef TimeInterval {
    type int32 {
      range "0 .. 2147483647";
    }
  }

  typedef DateAndTime {
    smiv2:display-hint "2d-1d-1d,1d:1d:1d.1d,1a1d:1d";
    type string;
  }

  typedef StorageType {
    type enumeration {
      enum "other" {
        value 1;
      }
      enum "volatile" {
        value 2;
      }
      enum "nonVolatile" {
        value 3;
      }
      enum "permanent" {
        value 4;
      }
      enum "readOnly" {
        value 5;
      }
    }
  }

  typedef TDomain {
    type yang:object-identifier;
  }

  typedef TAddress {
    type tailf:octet-list {
    }
  }
}
