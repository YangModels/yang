module Cisco-IOS-XR-sysadmin-dumper {
  namespace "http://www.cisco.com/ns/yang/Cisco-IOS-XR-sysadmin-dumper";
  prefix dumper;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin dumper to
     configure file path options to copy the core files to.
     
     Copyright(c) 2015-2017 by Cisco Systems, Inc.
     All rights reserved.";

  revision 2017-05-09 {
    description
      "Modified module name, namespace and filename 
       to adhere to standard notation";
  }
  revision 2016-05-12 {
    description
      "Initial Version";
  }
  tailf:id "http://www.cisco.com/calvados/dumper";

  container exception {
    tailf:info "Set exception choice";
    tailf:cli-incomplete-no;
    list choice {
      key "order";
      tailf:info "Order of Preference";
      tailf:cli-sequence-commands;
      tailf:cli-compact-syntax;
      tailf:cli-suppress-mode;
      tailf:cli-incomplete-command;
      leaf order {
        type int32 {
          range "1 .. 3";
        }
        tailf:cli-full-no;
        tailf:cli-incomplete-command;
        tailf:cli-suppress-range;
      }
      leaf filepath {
        type string;
        mandatory true;
        tailf:info "File path to copy the core";
      }
    }
  }
}
