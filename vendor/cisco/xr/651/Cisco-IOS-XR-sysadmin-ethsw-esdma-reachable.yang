module Cisco-IOS-XR-sysadmin-ethsw-esdma-reachable {
  namespace "http://www.cisco.com/ns/yang/Cisco-IOS-XR-sysadmin-ethsw-esdma-reachable";
  prefix esdma_reachable;

  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains the YANG definitions
     for the Cisco IOS-XR SysAdmin
     'show controller switch reachable' command.
     
     Copyright(c) 2011-2017 by Cisco Systems, Inc.
     All rights reserved.
     
     Copyright (c) 2012-2018 by Cisco Systems, Inc.
     All rights reserved.";

  revision 2017-05-01 {
    description
      "Namespace change to comply with Cisco guidelines on namespace";
  }

  grouping switch-reachable-data {
    container reachable {
      list location {
        key "rack card switch-id";
        leaf rack {
          type esdma_types:esdma-rack-num-enum;
        }
        leaf card {
          type esdma_types:esdma-cpu;
        }
        leaf switch-id {
          type esdma_types:esdma-switch-type-enum;
        }
      }
    }
  }
}
