module Cisco-IOS-XR-ipv4-cinetd-cfg {
  namespace "http://cisco.com/ns/yang/Cisco-IOS-XR-ipv4-cinetd-cfg";
  prefix ipv4-cinetd-cfg;

  import Cisco-IOS-XR-ip-tcp-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-cinetd package configuration.
     
     This YANG module augments the
       Cisco-IOS-XR-ip-tcp-cfg
     module with configuration data.
     
     Copyright (c) 2013-2018 by Cisco Systems, Inc.
     All rights reserved.";

  revision 2017-06-22 {
    description
      "IOS XR 6.4.1 revision.";
  }
  revision 2015-11-09 {
    description
      "IOS XR 6.0 revision.";
  }

  augment "/a1:ip/a1:cinetd" {
    description
      "This augment extends the configuration data of
       'Cisco-IOS-XR-ip-tcp-cfg'";
    leaf rate-limit {
      type uint32 {
        range "1..100";
      }
      default "1";
      description
        "Number of service requests accepted per second";
    }
  }
}
