module Cisco-IOS-XR-sysadmin-card-mgr {
  namespace "http://www.cisco.com/ns/yang/Cisco-IOS-XR-sysadmin-card-mgr";
  prefix card_mgr;

  import tailf-common {
    prefix tailf;
  }
  import Cisco-IOS-XR-sysadmin-show-trace {
    prefix show_trace;
  }
  import Cisco-IOS-XR-sysadmin-types {
    prefix calvados;
  }

  description
    "The 'card_mgr' module provides support for access to detail card HW information like power status, card state, inventory info, etc.";

  revision 2017-05-01 {
    description
      "Namespace change to comply with Cisco guidelines on namespace";
  }
  revision 2015-03-29 {
    description
      "Initial revision.";
  }

  typedef startHexOffset {
    type string;
    tailf:info "Start address in Hex between 0x0 and 0x400";
  }

  typedef endHexOffset {
    type string;
    tailf:info "End address in Hex between 0x0 and 0x400";
  }

  typedef HexOffset {
    type string;
    tailf:info "Address in Hex between 0x0 and 0x400";
  }

  grouping card_mgr-group {
    container card_mgr {
      tailf:info "Card Manager module information";
      tailf:alt-name "card-mgr";
      tailf:cli-incomplete-show-path;
      uses show_trace:traceable;
      uses inventory-group;
      uses event-hist-group;
      uses notif-hist-group;
      uses oir-hist-group;
      uses iofpga-group;
      uses bootldr-group;
    }
  }

  grouping inventory-group {
    container inventory {
      config false;
      tailf:alt-name "inventory";
      tailf:info "Card inventory information";
      uses inventory-summary-group;
      uses inventory-detail-group;
    }
  }

  grouping inventory-summary-group {
    container summary {
      config false;
      tailf:cli-full-command;
      tailf:info "Card inventory summary";
      tailf:callpoint "card_mgr_inv_summary";
      list card_mgr_inv_summary {
        key "location";
        tailf:info "Card location";
        tailf:alt-name "location";
        tailf:cli-table-legend "Card Manager Inventory Summary :";
        tailf:cli-enforce-table;
        leaf location {
          type string;
          mandatory true;
          tailf:info "Card location";
          tailf:display-column-name "Location";
          tailf:cli-column-width "7";
        }
        leaf card_mgr_inv_PID_string {
          type string;
          tailf:display-column-name "Card Type";
          tailf:cli-column-width "20";
          tailf:cli-suppress-show-path;
          tailf:cli-suppress-show-match;
        }
        leaf card_mgr_inv_slot_number {
          type uint32;
          tailf:display-column-name "BP ID";
          tailf:cli-column-width "2";
          tailf:cli-suppress-show-path;
          tailf:cli-suppress-show-match;
        }
        leaf card_mgr_inv_serial_number {
          type string;
          tailf:display-column-name "Serial Number";
          tailf:cli-column-width "13";
          tailf:cli-suppress-show-path;
          tailf:cli-suppress-show-match;
        }
        leaf card_mgr_inv_hw_version {
          type string;
          tailf:display-column-name "HW Ver";
          tailf:cli-column-width "5";
          tailf:cli-suppress-show-path;
          tailf:cli-suppress-show-match;
        }
        leaf card_mgr_inv_card_state {
          type string;
          tailf:display-column-name "Card State";
          tailf:cli-column-width "19";
          tailf:cli-suppress-show-path;
          tailf:cli-suppress-show-match;
        }
      }
    }
  }

  grouping inventory-detail-group {
    container detail {
      config false;
      tailf:info "Card Manager inventory detail information";
      tailf:cli-full-command;
      tailf:callpoint "card_mgr_inventory_detail";
      list card_mgr_inv_detail {
        key "location";
        tailf:alt-name "location";
        tailf:cli-suppress-table;
        tailf:info "Card location";
        tailf:cli-show-template-enter
          "
             Card Manager Inventory detail information for $(location):
          ";
        tailf:cli-show-template "$(card_mgr_inv_detail_list|show)\n";
        leaf location {
          type string;
          tailf:info "Card location";
        }
        container card_mgr_inv_detail_list {
          tailf:cli-drop-node-name;
          leaf-list card_mgr_inv_detail_values {
            type string;
            tailf:cli-drop-node-name;
            tailf:cli-list-syntax;
          }
        }
      }
    }
  }

  grouping event-hist-group {
    container event-history {
      config false;
      tailf:info "Card Event History";
      tailf:cli-incomplete-show-path;
      container brief {
        config false;
        tailf:info "Show all events in brief format";
        tailf:cli-incomplete-show-path;
        tailf:callpoint "card_mgr_event_history_brief";
        uses event-hist-group-brief;
      }
      container detail {
        config false;
        tailf:info "Show all events with additional detail information";
        tailf:cli-incomplete-show-path;
        tailf:callpoint "card_mgr_event_history_detail";
        uses event-hist-group-detail;
      }
    }
  }

  grouping event-hist-group-brief {
    list location {
      key "location";
      tailf:info "Select Location";
      tailf:cli-full-command;
      tailf:cli-no-match-completion;
      tailf:cli-suppress-table;
      tailf:cli-show-template-enter
        "
         Card Event History for: $(location)
        ";
      tailf:cli-show-template "$(card_event_hist_brief|show)\n";
      leaf location {
        type string;
        tailf:display-column-name "Location";
      }
      container card_event_hist_brief {
        tailf:cli-drop-node-name;
        leaf-list card_event_hist_brief_values {
          type string;
          tailf:cli-drop-node-name;
          tailf:cli-list-syntax;
        }
      }
    }
  }

  grouping event-hist-group-detail {
    list location {
      key "location";
      tailf:info "Select Location";
      tailf:cli-full-command;
      tailf:cli-no-match-completion;
      tailf:cli-suppress-table;
      tailf:cli-show-template-enter
        "
         Card Event History for: $(location)
        ";
      tailf:cli-show-template "$(card_event_hist_detail|show)\n";
      leaf location {
        type string;
        tailf:display-column-name "Location";
      }
      container card_event_hist_detail {
        tailf:cli-drop-node-name;
        leaf-list card_event_hist_detail_values {
          type string;
          tailf:cli-drop-node-name;
          tailf:cli-list-syntax;
        }
      }
    }
  }

  grouping notif-hist-group {
    container notif-history {
      config false;
      tailf:info "Card State Notification History";
      tailf:cli-incomplete-show-path;
      container brief {
        config false;
        tailf:info "Show all state notifications in brief format";
        tailf:cli-incomplete-show-path;
        tailf:callpoint "card_mgr_notif_history_brief";
        uses notif-hist-group-brief;
      }
      container detail {
        config false;
        tailf:info "Show all state notifications with additional detail information";
        tailf:cli-incomplete-show-path;
        tailf:callpoint "card_mgr_notif_history_detail";
        uses notif-hist-group-detail;
      }
    }
  }

  grouping notif-hist-group-brief {
    list location {
      key "location";
      tailf:info "Select Location";
      tailf:cli-full-command;
      tailf:cli-no-match-completion;
      tailf:cli-suppress-table;
      tailf:cli-show-template-enter
        "
         Card State Notification History for: $(location)
        ";
      tailf:cli-show-template "$(card_notif_hist_brief|show)\n";
      leaf location {
        type string;
        tailf:display-column-name "Location";
      }
      container card_notif_hist_brief {
        tailf:cli-drop-node-name;
        leaf-list card_notif_hist_brief_values {
          type string;
          tailf:cli-drop-node-name;
          tailf:cli-list-syntax;
        }
      }
    }
  }

  grouping notif-hist-group-detail {
    list location {
      key "location";
      tailf:info "Select Location";
      tailf:cli-full-command;
      tailf:cli-no-match-completion;
      tailf:cli-suppress-table;
      tailf:cli-show-template-enter
        "
         Card State Notification History for: $(location)
        ";
      tailf:cli-show-template "$(card_notif_hist_detail|show)\n";
      leaf location {
        type string;
        tailf:display-column-name "Location";
      }
      container card_notif_hist_detail {
        tailf:cli-drop-node-name;
        leaf-list card_notif_hist_detail_values {
          type string;
          tailf:cli-drop-node-name;
          tailf:cli-list-syntax;
        }
      }
    }
  }

  grouping oir-hist-group {
    container oir-history {
      config false;
      tailf:info "Cards OIR History";
      tailf:cli-full-command;
      tailf:callpoint "card_mgr_oir_history";
      list rack {
        key "rack";
        tailf:info "Select Rack";
        tailf:cli-full-command;
        tailf:cli-no-match-completion;
        tailf:cli-suppress-table;
        tailf:cli-show-template-enter
          "
           Cards OIR History of rack: $(rack)
          ";
        tailf:cli-show-template "$(card_oir_hist|show)\n";
        leaf rack {
          type string;
          tailf:display-column-name "Rack";
        }
        container card_oir_hist {
          tailf:cli-drop-node-name;
          leaf-list card_oir_events {
            type string;
            tailf:cli-drop-node-name;
            tailf:cli-list-syntax;
          }
        }
      }
    }
  }

  grouping iofpga-group {
    container iofpga {
      config false;
      tailf:info "IOFPGA information";
      tailf:cli-incomplete-show-path;
      uses iofpga-register-group;
      uses iofpga-flash-group;
    }
  }

  grouping iofpga-register-group {
    container register {
      config false;
      tailf:cli-incomplete-show-path;
      tailf:info "IOFPGA Register information";
      uses cpu-register-group;
      uses mb-register-group;
      uses dc-register-group;
    }
  }

  grouping cpu-register-group {
    container cpu {
      config false;
      tailf:cli-incomplete-show-path;
      tailf:info "CPU-IOFPGA Register information";
      tailf:callpoint "card_mgr_mgbl_register_cpu";
      list register_location {
        key "register_location";
        config false;
        tailf:info "Card location";
        tailf:alt-name "location";
        leaf register_location {
          type string;
          tailf:display-column-name "Location";
        }
        uses iofpga-block-number-group;
        uses iofpga-offset-group;
        uses iofpga-address-group;
      }
    }
  }

  grouping mb-register-group {
    container mb {
      config false;
      tailf:cli-incomplete-show-path;
      tailf:info "Mother Board(MB)-IOFPGA Register information";
      tailf:callpoint "card_mgr_mgbl_register_mb";
      list register_location {
        key "register_location";
        config false;
        tailf:info "Card location";
        tailf:alt-name "location";
        leaf register_location {
          type string;
          tailf:display-column-name "Location";
        }
        uses iofpga-block-number-group;
        uses iofpga-offset-group;
        uses iofpga-address-group;
      }
    }
  }

  grouping dc-register-group {
    container dc {
      config false;
      tailf:cli-incomplete-show-path;
      tailf:info "Daughter Card(DC)-IOFPGA Register information";
      tailf:callpoint "card_mgr_mgbl_register_dc";
      list register_location {
        key "register_location";
        config false;
        tailf:info "Card location";
        tailf:alt-name "location";
        leaf register_location {
          type string;
          tailf:display-column-name "Location";
        }
        uses iofpga-block-number-group;
        uses iofpga-offset-group;
        uses iofpga-address-group;
      }
    }
  }

  grouping iofpga-block-number-group {
    list iofpga_block_number {
      key "iofpga_block_num";
      config false;
      tailf:info "Register Group ID";
      tailf:alt-name "group";
      tailf:cli-no-match-completion;
      tailf:cli-table-legend
        "
         IOFPGA Register Group Information:";
      tailf:cli-enforce-table;
      tailf:cli-instance-info-leafs "iofpga_block_nm";
      leaf iofpga_block_num {
        type uint32;
        tailf:display-column-name "GP";
        tailf:cli-column-width "1";
        tailf:cli-suppress-show-path;
      }
      leaf block_location {
        type string;
        tailf:display-column-name "Loc";
        tailf:cli-column-width "5";
        tailf:cli-suppress-show-path;
      }
      leaf iofpga_block_nm {
        type string;
        tailf:hidden "full";
        tailf:cli-suppress-show-path;
      }
      list iofpga_register_number {
        key "index";
        tailf:info "Register Number";
        tailf:alt-name "index";
        tailf:cli-instance-info-leafs "card_mgr_register_name";
        tailf:cli-no-match-completion;
        leaf index {
          type uint32;
          tailf:hidden "full";
          tailf:display-column-name "IDX";
          tailf:cli-suppress-show-path;
        }
        leaf iofpga_register_name {
          type string;
          tailf:hidden "full";
          tailf:cli-suppress-show-path;
        }
        list iofpga_data {
          tailf:cli-suppress-show-path;
          leaf name {
            type string;
            tailf:display-column-name "REGISTER NAME";
            tailf:cli-column-width "40";
            tailf:cli-suppress-show-path;
          }
          leaf offset {
            type uint32;
            tailf:cli-suppress-show-path;
            tailf:cli-value-display-template "0x$(.|hex)";
          }
          leaf value {
            type uint32;
            tailf:cli-suppress-show-path;
            tailf:cli-value-display-template "0x$(.|hex)";
          }
        }
      }
    }
  }

  grouping iofpga-offset-group {
    list iofpga_offset {
      key "hex_offset";
      config false;
      tailf:cli-no-key-completion;
      tailf:alt-name "offset";
      tailf:info "Register Offset Address";
      tailf:cli-suppress-table;
      tailf:cli-no-match-completion;
      tailf:cli-incomplete-show-path {
        tailf:cli-min-keys "1";
      }
      leaf hex_offset {
        type HexOffset;
        tailf:hidden "full";
      }
      list iofpga_reg_offset_data {
        tailf:cli-suppress-show-path;
        leaf iofpga_reg_off_addr {
          type uint32;
          tailf:cli-value-display-template "0x$(.|hex)";
          tailf:display-column-name "Reg Addr";
          tailf:cli-column-width "5";
        }
        leaf reg_off_value {
          type string;
          tailf:display-column-name "Reg Val";
          tailf:cli-column-width "10";
        }
      }
    }
  }

  grouping iofpga-address-group {
    list iofpga_address {
      key "start_hex_addr end_hex_addr";
      config false;
      tailf:alt-name "range";
      tailf:info "Register Range to fetch data";
      tailf:cli-no-key-completion;
      tailf:cli-no-match-completion;
      tailf:cli-suppress-table;
      tailf:cli-incomplete-show-path {
        tailf:cli-min-keys "2";
      }
      leaf start_hex_addr {
        type startHexOffset;
        tailf:hidden "full";
      }
      leaf end_hex_addr {
        type endHexOffset;
        tailf:hidden "full";
      }
      list iofpga_reg_range_addr_list {
        key "iofpga_reg_range_addr";
        tailf:cli-suppress-show-path;
        leaf iofpga_reg_range_addr {
          type uint32;
          tailf:cli-value-display-template "0x$(.|hex)";
          tailf:display-column-name "Register Offset";
          tailf:cli-column-width "10";
        }
        list iofpga_reg_data {
          tailf:cli-suppress-show-path;
          leaf iofpga_reg_addr {
            type uint32;
            tailf:hidden "full";
          }
          leaf reg_value {
            type string;
            tailf:display-column-name "Register Value";
            tailf:cli-column-width "8";
          }
        }
      }
    }
  }

  grouping iofpga-flash-group {
    container flash {
      config false;
      tailf:alt-name "flash";
      tailf:info "IOFPGA SPI flash information";
      tailf:cli-incomplete-show-path;
      uses iofpga-flash-info-group;
      uses iofpga-flash-status-group;
    }
  }

  grouping iofpga-flash-info-group {
    container info {
      config false;
      tailf:cli-incomplete-show-path;
      tailf:info "IOFPGA SPI flash content";
      tailf:callpoint "cmgr_mgbl_iofpga_spiflash_info";
      list flash_location {
        key "flash_location";
        tailf:info "Select Location";
        tailf:cli-full-command;
        tailf:cli-no-match-completion;
        tailf:cli-suppress-table;
        tailf:alt-name "location";
        tailf:cli-show-template-enter
          "
           I/O FPGA SPI flash information for: $(flash_location)
          ";
        tailf:cli-show-template "$(iofpga_flash_info|show)\n";
        leaf flash_location {
          type calvados:location-id;
        }
        container iofpga_flash_info {
          tailf:cli-drop-node-name;
          leaf-list iofpga_flash_info_values {
            type string;
            tailf:cli-drop-node-name;
            tailf:cli-list-syntax;
          }
        }
      }
    }
  }

  grouping iofpga-flash-status-group {
    container status {
      config false;
      tailf:cli-incomplete-show-path;
      tailf:info "IOFPGA SPI flash status";
      tailf:callpoint "cmgr_mgbl_iofpga_spiflash_status";
      list flash_location {
        key "flash_location";
        tailf:info "Select Location";
        tailf:cli-full-command;
        tailf:cli-no-match-completion;
        tailf:cli-suppress-table;
        tailf:alt-name "location";
        tailf:cli-show-template-enter
          "
           I/O FPGA SPI flash status for: $(flash_location)
          ";
        tailf:cli-show-template "$(iofpga_flash_status|show)\n";
        leaf flash_location {
          type calvados:location-id;
        }
        container iofpga_flash_status {
          tailf:cli-drop-node-name;
          leaf-list iofpga_flash_status_values {
            type string;
            tailf:cli-drop-node-name;
            tailf:cli-list-syntax;
          }
        }
      }
    }
  }

  grouping bootldr-group {
    container bootloader {
      config false;
      tailf:info "Bootloader information";
      tailf:cli-incomplete-show-path;
      uses bootldr-flash-group;
    }
  }

  grouping bootldr-flash-group {
    container flash {
      config false;
      tailf:alt-name "flash";
      tailf:info "Bootloader SPI flash information";
      tailf:cli-incomplete-show-path;
      uses bootldr-flash-info-group;
      uses bootldr-flash-status-group;
    }
  }

  grouping bootldr-flash-info-group {
    container info {
      config false;
      tailf:cli-incomplete-show-path;
      tailf:info "Bootloader SPI flash content";
      tailf:callpoint "cmgr_mgbl_bootldr_spiflash_info";
      list flash_location {
        key "flash_location";
        tailf:info "Select Location";
        tailf:cli-full-command;
        tailf:cli-no-match-completion;
        tailf:cli-suppress-table;
        tailf:alt-name "location";
        tailf:cli-show-template-enter
          "
           Bootloader SPI flash information for: $(flash_location)
          ";
        tailf:cli-show-template "$(bootldr_flash_info|show)\n";
        leaf flash_location {
          type calvados:location-id;
        }
        container bootldr_flash_info {
          tailf:cli-drop-node-name;
          leaf-list bootldr_flash_info_values {
            type string;
            tailf:cli-drop-node-name;
            tailf:cli-list-syntax;
          }
        }
      }
    }
  }

  grouping bootldr-flash-status-group {
    container status {
      config false;
      tailf:cli-incomplete-show-path;
      tailf:info "Bootloader SPI flash status";
      tailf:callpoint "cmgr_mgbl_bootldr_spiflash_status";
      list flash_location {
        key "flash_location";
        tailf:info "Select Location";
        tailf:cli-full-command;
        tailf:cli-no-match-completion;
        tailf:cli-suppress-table;
        tailf:alt-name "location";
        tailf:cli-show-template-enter "\\Bootloader SPI flash status for: $(flash_location)\n";
        tailf:cli-show-template "$(bootldr_flash_status|show)\n";
        leaf flash_location {
          type calvados:location-id;
        }
        container bootldr_flash_status {
          tailf:cli-drop-node-name;
          leaf-list bootldr_flash_status_values {
            type string;
            tailf:cli-drop-node-name;
            tailf:cli-list-syntax;
          }
        }
      }
    }
  }
  tailf:id "http://cisco.com/calvados/card_mgr";
}
