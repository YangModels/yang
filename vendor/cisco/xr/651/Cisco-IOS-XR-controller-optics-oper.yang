module Cisco-IOS-XR-controller-optics-oper {
  namespace "http://cisco.com/ns/yang/Cisco-IOS-XR-controller-optics-oper";
  prefix controller-optics-oper;

  import Cisco-IOS-XR-types {
    prefix xr;
  }
  include Cisco-IOS-XR-controller-optics-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-optics package operational data.
     
     This module contains definitions
     for the following management objects:
       optics-oper: Optics operational data
     
     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  container optics-oper {
    config false;
    description
      "Optics operational data";
    container optics-ports {
      description
        "All Optics Port operational data";
      list optics-port {
        key "name";
        description
          "Optics operational data";
        container optics-dwdm-carrier-channel-map {
          description
            "Optics operational data";
          uses OPTICS-EDM-WAVE-INFO;
        }
        container ots-spectrum-info {
          description
            "Ots Spectrum Operational data";
          uses OPTICS-EDM-SPECTRUM-INFO;
        }
        container optics-dwdm-carrier-channel-map-flexi {
          description
            "Optics operational data";
          uses OPTICS-EDM-WAVE-INFO;
        }
        container optics-info {
          description
            "Optics operational data";
          uses OPTICS-EDM-INFO;
        }
        container optics-lanes {
          description
            "All Optics Port operational data";
          list optics-lane {
            key "number";
            description
              "Lane Information";
            leaf number {
              type uint32;
              description
                "Lane Index";
            }
            uses OPTICS-EDM-LANE-DATA;
          }
        }
        container optics-db-info {
          description
            "Optics operational data";
          uses OPTICS-DB-INFO;
        }
        leaf name {
          type xr:Interface-name;
          description
            "Port name";
        }
      }
    }
  }
}
