module Cisco-IOS-XR-sysadmin-fabric-mgr-fgid {
  namespace "http://www.cisco.com/ns/yang/Cisco-IOS-XR-sysadmin-fabric-mgr-fgid";
  prefix fabric_fgid;

  import tailf-common {
    prefix tailf;
  }
  import Cisco-IOS-XR-sysadmin-fabric-types {
    prefix fabric-types;
  }
  import Cisco-IOS-XR-sysadmin-show-trace {
    prefix show-trace;
  }

  revision 2017-05-01 {
    description
      "Namespace change to comply with Cisco guidelines on namespace";
  }

  grouping fgid_conf_resource {
    container fgid {
      tailf:hidden "internal";
      container resource {
        container sdr {
          container allocation {
            leaf percent {
              type int32 {
                range "20..50";
              }
            }
          }
        }
      }
    }
  }

  grouping fgid_information_show {
    list id {
      key "fgid_id";
      tailf:display-groups "fabric-brief fabric-detail fabric-diagnostics none";
      tailf:cli-no-key-completion;
      tailf:cli-no-match-completion;
      tailf:cli-show-template
        "$(.legend_shown != true ?
         Displaying FGID\\\\: $(fgid_id)
         FGID Information\\\\:
         
         )
         FGID number\\\\:      $(fgid_id|rjust:10)
         $(.display_groups ~= fabric-detail ?
         FGID Hex bitmap\\\\:
         $(hex_bitmaps|show)
         FGID Binary bitmap\\\\:
         $(binary_bitmaps|show)
         )$(.display_groups ~= fabric-diagnostics ?
         FGID Hex bitmap\\\\:
         $(hex_bitmaps|show)
         FGID Binary bitmap\\\\:
         $(binary_bitmaps|show)
         )
         FGID associated fabricq Ids\\\\:
         [$(total_asso_fabricq_ids)] \\\\:= 
         $(total_asso_fabricq_ids == 0?        No fgid associated fabricq Ids are found
         :$(asso_fabricq_ids|show)
         )
         FGID associated client application\\\\:
         $(asso_client_info)
         $(drivers|show)";
      tailf:cli-show-template-enter "";
      tailf:cli-suppress-table;
      tailf:cli-show-template-legend
        "
         Starting FGID\\\\: 0
         The requested number of FGIDs to display\\\\: ALL
         
         FGID Information\\\\:
        ";
      leaf fgid_id {
        type fabric-types:fabric_fgid_id_type;
        tailf:display-groups "fabric-brief fabric-detail fabric-diagnostics none";
      }
      list hex_bitmaps {
        key "rack_number";
        tailf:display-groups "fabric-detail fabric-diagnostics";
        tailf:cli-show-template-enter "        $(bitmap)\n";
        tailf:cli-suppress-table;
        leaf rack_number {
          type int32;
          tailf:display-groups "fabric-detail fabric-diagnostics";
        }
        leaf bitmap {
          type string;
          tailf:hidden "internal";
        }
      }
      list binary_bitmaps {
        key "rack_number";
        tailf:display-groups "fabric-detail fabric-diagnostics";
        tailf:cli-show-template-enter "        $(bitmap)\n";
        tailf:cli-suppress-table;
        leaf rack_number {
          type int32;
          tailf:display-groups "fabric-detail fabric-diagnostics";
        }
        leaf bitmap {
          type string;
          tailf:hidden "internal";
        }
      }
      leaf total_asso_fabricq_ids {
        type int32;
        tailf:hidden "internal";
      }
      list asso_fabricq_ids {
        key "fabricq_id";
        tailf:display-groups "fabric-brief fabric-detail fabric-diagnostics none";
        tailf:cli-show-template-enter "";
        tailf:cli-show-template "        $(fabricq_id)";
        tailf:cli-suppress-table;
        leaf fabricq_id {
          type string;
          tailf:display-groups "fabric-brief fabric-detail fabric-diagnostics none";
        }
      }
      leaf asso_client_info {
        type string;
        tailf:hidden "internal";
      }
      list drivers {
        key "rack_number";
        tailf:callpoint "fabric_fgid_drvr_info";
        tailf:display-groups "fabric-diagnostics";
        leaf rack_number {
          type int32;
          tailf:display-groups "fabric-diagnostics";
        }
        tailf:cli-suppress-table;
        tailf:cli-show-template-enter "";
        tailf:cli-show-template "$(clients|show)";
        list clients {
          key "client_idx";
          tailf:cli-suppress-table;
          tailf:cli-show-template-enter "";
          tailf:cli-show-template
            "$(show_asic_0 == true ?
             FGID bitmap at location $(asic_0_bitmap)
             )$(show_asic_1 == true ?
             FGID bitmap at location $(asic_1_bitmap)
             )$(show_asic_2 == true ?
             FGID bitmap at location $(asic_2_bitmap)
             )$(show_asic_3 == true ?
             FGID bitmap at location $(asic_3_bitmap)
             )$(show_asic_4 == true ?
             FGID bitmap at location $(asic_4_bitmap)
             )$(show_asic_5 == true ?
             FGID bitmap at location $(asic_5_bitmap)
             )$(show_asic_6 == true ?
             FGID bitmap at location $(asic_6_bitmap)
             )$(show_asic_7 == true ?
             FGID bitmap at location $(asic_7_bitmap)
             )$(show_asic_8 == true ?
             FGID bitmap at location $(asic_8_bitmap)
             )$(show_asic_9 == true ?
             FGID bitmap at location $(asic_9_bitmap)
             )$(show_asic_10 == true ?
             FGID bitmap at location $(asic_10_bitmap)
             )$(show_asic_11 == true ?
             FGID bitmap at location $(asic_11_bitmap)
             )$(show_asic_12 == true ?
             FGID bitmap at location $(asic_12_bitmap)
             )$(show_asic_13 == true ?
             FGID bitmap at location $(asic_13_bitmap)
             )$(show_asic_14 == true ?
             FGID bitmap at location $(asic_14_bitmap)
             )$(show_asic_15 == true ?
             FGID bitmap at location $(asic_15_bitmap)
             )$(show_asic_16 == true ?
             FGID bitmap at location $(asic_16_bitmap)
             )$(show_asic_17 == true ?
             FGID bitmap at location $(asic_17_bitmap)
             )$(show_asic_18 == true ?
             FGID bitmap at location $(asic_18_bitmap)
             )$(show_asic_19 == true ?
             FGID bitmap at location $(asic_19_bitmap)
             )$(show_asic_20 == true ?
             FGID bitmap at location $(asic_20_bitmap)
             )$(show_asic_21 == true ?
             FGID bitmap at location $(asic_21_bitmap)
             )$(show_asic_22 == true ?
             FGID bitmap at location $(asic_22_bitmap)
             )$(show_asic_23 == true ?
             FGID bitmap at location $(asic_23_bitmap)
             )$(show_asic_24 == true ?
             FGID bitmap at location $(asic_24_bitmap)
             )$(show_asic_25 == true ?
             FGID bitmap at location $(asic_25_bitmap)
             )$(show_asic_26 == true ?
             FGID bitmap at location $(asic_26_bitmap)
             )$(show_asic_27 == true ?
             FGID bitmap at location $(asic_27_bitmap)
             )$(show_asic_28 == true ?
             FGID bitmap at location $(asic_28_bitmap)
             )$(show_asic_29 == true ?
             FGID bitmap at location $(asic_29_bitmap)
             )$(show_asic_30 == true ?
             FGID bitmap at location $(asic_30_bitmap)
             )$(show_asic_31 == true ?
             FGID bitmap at location $(asic_31_bitmap)
             )$(show_asic_32 == true ?
             FGID bitmap at location $(asic_32_bitmap)
             )$(show_asic_33 == true ?
             FGID bitmap at location $(asic_33_bitmap)
             )$(show_asic_34 == true ?
             FGID bitmap at location $(asic_34_bitmap)
             )$(show_asic_35 == true ?
             FGID bitmap at location $(asic_35_bitmap)
             )
            ";
          leaf client_idx {
            type int32;
            tailf:display-groups "fabric-diagnostics";
          }
          leaf show_asic_0 {
            type boolean;
            default "false";
            tailf:hidden "internal";
          }
          leaf asic_0_bitmap {
            type string;
            tailf:hidden "internal";
          }
          leaf show_asic_1 {
            type boolean;
            default "false";
            tailf:hidden "internal";
          }
          leaf asic_1_bitmap {
            type string;
            tailf:hidden "internal";
          }
          leaf show_asic_2 {
            type boolean;
            default "false";
            tailf:hidden "internal";
          }
          leaf asic_2_bitmap {
            type string;
            tailf:hidden "internal";
          }
          leaf show_asic_3 {
            type boolean;
            default "false";
            tailf:hidden "internal";
          }
          leaf asic_3_bitmap {
            type string;
            tailf:hidden "internal";
          }
          leaf show_asic_4 {
            type boolean;
            default "false";
            tailf:hidden "internal";
          }
          leaf asic_4_bitmap {
            type string;
            tailf:hidden "internal";
          }
          leaf show_asic_5 {
            type boolean;
            default "false";
            tailf:hidden "internal";
          }
          leaf asic_5_bitmap {
            type string;
            tailf:hidden "internal";
          }
          leaf show_asic_6 {
            type boolean;
            default "false";
            tailf:hidden "internal";
          }
          leaf asic_6_bitmap {
            type string;
            tailf:hidden "internal";
          }
          leaf show_asic_7 {
            type boolean;
            default "false";
            tailf:hidden "internal";
          }
          leaf asic_7_bitmap {
            type string;
            tailf:hidden "internal";
          }
          leaf show_asic_8 {
            type boolean;
            default "false";
            tailf:hidden "internal";
          }
          leaf asic_8_bitmap {
            type string;
            tailf:hidden "internal";
          }
          leaf show_asic_9 {
            type boolean;
            default "false";
            tailf:hidden "internal";
          }
          leaf asic_9_bitmap {
            type string;
            tailf:hidden "internal";
          }
          leaf show_asic_10 {
            type boolean;
            default "false";
            tailf:hidden "internal";
          }
          leaf asic_10_bitmap {
            type string;
            tailf:hidden "internal";
          }
          leaf show_asic_11 {
            type boolean;
            default "false";
            tailf:hidden "internal";
          }
          leaf asic_11_bitmap {
            type string;
            tailf:hidden "internal";
          }
          leaf show_asic_12 {
            type boolean;
            default "false";
            tailf:hidden "internal";
          }
          leaf asic_12_bitmap {
            type string;
            tailf:hidden "internal";
          }
          leaf show_asic_13 {
            type boolean;
            default "false";
            tailf:hidden "internal";
          }
          leaf asic_13_bitmap {
            type string;
            tailf:hidden "internal";
          }
          leaf show_asic_14 {
            type boolean;
            default "false";
            tailf:hidden "internal";
          }
          leaf asic_14_bitmap {
            type string;
            tailf:hidden "internal";
          }
          leaf show_asic_15 {
            type boolean;
            default "false";
            tailf:hidden "internal";
          }
          leaf asic_15_bitmap {
            type string;
            tailf:hidden "internal";
          }
          leaf show_asic_16 {
            type boolean;
            default "false";
            tailf:hidden "internal";
          }
          leaf asic_16_bitmap {
            type string;
            tailf:hidden "internal";
          }
          leaf show_asic_17 {
            type boolean;
            default "false";
            tailf:hidden "internal";
          }
          leaf asic_17_bitmap {
            type string;
            tailf:hidden "internal";
          }
          leaf show_asic_18 {
            type boolean;
            default "false";
            tailf:hidden "internal";
          }
          leaf asic_18_bitmap {
            type string;
            tailf:hidden "internal";
          }
          leaf show_asic_19 {
            type boolean;
            default "false";
            tailf:hidden "internal";
          }
          leaf asic_19_bitmap {
            type string;
            tailf:hidden "internal";
          }
          leaf show_asic_20 {
            type boolean;
            default "false";
            tailf:hidden "internal";
          }
          leaf asic_20_bitmap {
            type string;
            tailf:hidden "internal";
          }
          leaf show_asic_21 {
            type boolean;
            default "false";
            tailf:hidden "internal";
          }
          leaf asic_21_bitmap {
            type string;
            tailf:hidden "internal";
          }
          leaf show_asic_22 {
            type boolean;
            default "false";
            tailf:hidden "internal";
          }
          leaf asic_22_bitmap {
            type string;
            tailf:hidden "internal";
          }
          leaf show_asic_23 {
            type boolean;
            default "false";
            tailf:hidden "internal";
          }
          leaf asic_23_bitmap {
            type string;
            tailf:hidden "internal";
          }
          leaf show_asic_24 {
            type boolean;
            default "false";
            tailf:hidden "internal";
          }
          leaf asic_24_bitmap {
            type string;
            tailf:hidden "internal";
          }
          leaf show_asic_25 {
            type boolean;
            default "false";
            tailf:hidden "internal";
          }
          leaf asic_25_bitmap {
            type string;
            tailf:hidden "internal";
          }
          leaf show_asic_26 {
            type boolean;
            default "false";
            tailf:hidden "internal";
          }
          leaf asic_26_bitmap {
            type string;
            tailf:hidden "internal";
          }
          leaf show_asic_27 {
            type boolean;
            default "false";
            tailf:hidden "internal";
          }
          leaf asic_27_bitmap {
            type string;
            tailf:hidden "internal";
          }
          leaf show_asic_28 {
            type boolean;
            default "false";
            tailf:hidden "internal";
          }
          leaf asic_28_bitmap {
            type string;
            tailf:hidden "internal";
          }
          leaf show_asic_29 {
            type boolean;
            default "false";
            tailf:hidden "internal";
          }
          leaf asic_29_bitmap {
            type string;
            tailf:hidden "internal";
          }
          leaf show_asic_30 {
            type boolean;
            default "false";
            tailf:hidden "internal";
          }
          leaf asic_30_bitmap {
            type string;
            tailf:hidden "internal";
          }
          leaf show_asic_31 {
            type boolean;
            default "false";
            tailf:hidden "internal";
          }
          leaf asic_31_bitmap {
            type string;
            tailf:hidden "internal";
          }
          leaf show_asic_32 {
            type boolean;
            default "false";
            tailf:hidden "internal";
          }
          leaf asic_32_bitmap {
            type string;
            tailf:hidden "internal";
          }
          leaf show_asic_33 {
            type boolean;
            default "false";
            tailf:hidden "internal";
          }
          leaf asic_33_bitmap {
            type string;
            tailf:hidden "internal";
          }
          leaf show_asic_34 {
            type boolean;
            default "false";
            tailf:hidden "internal";
          }
          leaf asic_34_bitmap {
            type string;
            tailf:hidden "internal";
          }
          leaf show_asic_35 {
            type boolean;
            default "false";
            tailf:hidden "internal";
          }
          leaf asic_35_bitmap {
            type string;
            tailf:hidden "internal";
          }
        }
      }
    }
  }

  grouping fgid_resource_show {
    list sdr {
      key "sdr_name";
      tailf:cli-show-template-enter "";
      tailf:cli-suppress-table;
      leaf sdr_name {
        type string;
      }
      leaf description {
        type string;
        default "Secure Domain Router name.";
        tailf:hidden "internal";
      }
      list application {
        key "app_name";
        tailf:cli-suppress-table;
        tailf:cli-show-template-enter "";
        leaf app_name {
          type string;
        }
        leaf description {
          type string;
          default "application.";
          tailf:hidden "internal";
        }
        list ids_range {
          key "id elements";
          tailf:cli-drop-node-name;
          tailf:cli-no-key-completion;
          tailf:cli-no-match-completion;
          tailf:cli-suppress-table;
          tailf:cli-show-template-enter "";
          leaf id {
            type fabric-types:fabric_fgid_id_type;
            tailf:cli-expose-key-name;
          }
          leaf elements {
            type fabric-types:fabric_fgid_elements_type;
            tailf:cli-expose-key-name;
          }
          list fgid_ids {
            key "fgid_id line_idx";
            tailf:cli-no-key-completion;
            tailf:cli-no-match-completion;
            tailf:cli-show-template
              "$(line_idx == 0?
               ====================================================
               Displaying FGID Info for\\\\:
               SDR\\\\: $(sdr_name_h)          APPLICATION \\\\: $(app_name_h)
               )$(fgid_id)";
            tailf:cli-show-template-enter "";
            tailf:cli-show-template-footer "\n";
            tailf:cli-suppress-table;
            leaf fgid_id {
              type string;
            }
            leaf line_idx {
              type int32;
            }
            leaf sdr_name_h {
              type string;
              tailf:hidden "internal";
            }
            leaf app_name_h {
              type string;
              tailf:hidden "internal";
            }
          }
        }
      }
    }
  }

  grouping fgid_trace {
    container fgid_mgr {
      tailf:cli-incomplete-show-path;
      tailf:cli-drop-node-name;
      uses show-trace:traceable;
    }
  }

  grouping fgid_statistics_app_show {
    list application {
      key "app_name";
      tailf:display-groups "fabric-detail";
      tailf:cli-suppress-table;
      tailf:cli-show-template-enter "";
      tailf:cli-show-template-legend
        "
         Per client basis FGID resource utilization\\\\:
         
         $(Appl|rjust:15) $(Appl|rjust:4) $(Pool|rjust:4) $(Current    |rjust:12) $(HighWater Mark|rjust:15)
         $(Name|rjust:15) $(ID|rjust:4) $(ID|rjust:4) $(InUse FGIDs|rjust:12) $(InUse FGIDs|rjust:15)
         ----------------------------------------------------------------------------
        ";
      tailf:cli-show-template "$(app_name|rjust:15) $(app_id|rjust:4) $(pool_id|rjust:4) $(inuse_fgids|rjust:12)$(hwm_fgids|rjust:15)\n";
      leaf app_name {
        type string;
        tailf:display-groups "fabric-detail";
      }
      leaf description {
        type string;
        default "application.";
        tailf:hidden "internal";
      }
      leaf app_id {
        type uint32;
        tailf:hidden "internal";
      }
      leaf pool_id {
        type uint32;
        tailf:hidden "internal";
      }
      leaf inuse_fgids {
        type uint32;
        tailf:hidden "internal";
      }
      leaf hwm_fgids {
        type uint32;
        tailf:hidden "internal";
      }
    }
  }

  grouping fgid_statistics_pool_show {
    list pool_list {
      key "pool_id";
      tailf:display-groups "fabric-brief fabric-detail none";
      tailf:cli-show-template-enter "";
      tailf:cli-suppress-table;
      tailf:cli-show-template-legend
        "$(.path ~= pool ?
         Fabric FGID Resource Statistics Information\\\\:
         
         )Per pool basis Fabric multicast resource statistics\\\\:
         
         $(.display_groups ~= fabric-brief ?$(Pool|ljust:10) $(Pool|rjust:15) $(Pool|rjust:15) $(Total|rjust:8) $(Current|rjust:8) $(High Water Mark|rjust:15)
         $(ID|ljust:10) $(Name|rjust:15) $(Type|rjust:15) $(FGIDs|rjust:8) $(FGIDs |rjust:8) $(InUse FGIDs |rjust:15)
         --------------------------------------------------------------------------------
         )";
      tailf:cli-show-template
        "$(.display_groups ~= fabric-brief ?$(pool_id|ljust:10) $(pool_name|rjust:15) $(pool_type|rjust:15) $(total_fgids|rjust:8) $(current_fgids|rjust:8) $(hwm_fgids|rjust:15):\tPool Identifier is $(pool_id)
         \tPool Name is $(pool_name)
         \tPool type is $(pool_type)
         \tThe starting FGID of this pool is $(start_fgid)
         \tTotal FGIDS of this pool is $(total_fgids)
         \tInUse FGIDs of this pool is $(current_fgids)
         \tHigh Water Mark InUse FGIDs of this pool is $(hwm_fgids)
         )
        ";
      leaf pool_id {
        type uint32;
        tailf:display-groups "fabric-brief fabric-detail none";
      }
      leaf pool_name {
        type string;
        tailf:hidden "internal";
      }
      leaf pool_type {
        type string;
        tailf:hidden "internal";
      }
      leaf start_fgid {
        type string;
        tailf:hidden "internal";
      }
      leaf total_fgids {
        type uint32;
        tailf:hidden "internal";
      }
      leaf current_fgids {
        type uint32;
        tailf:hidden "internal";
      }
      leaf hwm_fgids {
        type uint32;
        tailf:hidden "internal";
      }
    }
  }

  grouping fgid_statistics_sdr_show {
    list sdr_list {
      key "sdr_name";
      tailf:display-groups "fabric-brief fabric-detail none";
      tailf:cli-show-template-enter "";
      tailf:cli-suppress-table;
      tailf:cli-show-template-legend
        "$(.path ~= sdr ?
         Fabric FGID Resource Statistics Information\\\\:
         
         )Per SDR basis Fabric multicast resource statistics\\\\:
         
         $(.display_groups ~= fabric-brief ?$(SDR|rjust:32) $(Current|rjust:20) $(HighWater Mark|rjust:20)
         $(Name|rjust:32) $(FGIDs|rjust:20) $(InUse FGIDs|rjust:20)
         --------------------------------------------------------------------------------
         )";
      tailf:cli-show-template
        "$(.display_groups ~= fabric-brief ?$(sdr_name|rjust:32) $(sdr_inuse_fgids|rjust:20) $(sdr_hwm_fgids|rjust:20):\tSecure Domain Router Name is $(sdr_name)
         \tTotal Fgids is $(sdr_total_fgids)
         \tInUse FGIDs is $(sdr_inuse_fgids)
         \tHigh Water Mark InUse FGIDs is $(sdr_hwm_fgids)
         $(application|show))
        ";
      leaf sdr_name {
        type string;
        tailf:display-groups "fabric-brief fabric-detail none";
      }
      leaf description {
        type string;
        default "Secure Domain Router name.";
        tailf:hidden "internal";
      }
      leaf sdr_total_fgids {
        type uint32;
        tailf:hidden "internal";
      }
      leaf sdr_inuse_fgids {
        type uint32;
        tailf:hidden "internal";
      }
      leaf sdr_hwm_fgids {
        type uint32;
        tailf:hidden "internal";
      }
      uses fgid_statistics_app_show;
    }
  }

  grouping fgid_statistics_system_show {
    list stats_list {
      key "system_stats";
      tailf:display-groups "fabric-brief fabric-detail";
      tailf:cli-no-key-completion;
      tailf:cli-no-match-completion;
      tailf:cli-show-template-enter "";
      tailf:cli-suppress-table;
      tailf:cli-show-template-legend
        "
         Fabric FGID Resource Statistics Information\\\\:
         
        ";
      tailf:cli-show-template
        "System wide Fabric multicast resource statistics\\\\:
         
         \tTotal number of FGIDS in the system is $(system_total_fgids)
         \tCurrent number of InUse FGIDS in the system is $(system_inuse_fgids)
         \tHigh Water Mark of InUse FGIDS in the system is $(system_hwm_fgids)
         
        ";
      leaf system_stats {
        type int32;
        tailf:display-groups "fabric-brief fabric-detail";
      }
      leaf system_total_fgids {
        type uint32;
        tailf:hidden "internal";
      }
      leaf system_inuse_fgids {
        type uint32;
        tailf:hidden "internal";
      }
      leaf system_hwm_fgids {
        type uint32;
        tailf:hidden "internal";
      }
    }
  }

  grouping fgid_statistics_show {
    uses fgid_statistics_system_show;
    uses fgid_statistics_sdr_show;
    uses fgid_statistics_pool_show;
  }

  grouping fgid_program_error_show {
    list program_error {
      key "start end";
      tailf:cli-no-key-completion;
      tailf:cli-no-match-completion;
      tailf:hidden "internal-command";
      tailf:cli-show-template-enter "";
      tailf:cli-suppress-table;
      leaf start {
        type fabric-types:fabric_fgid_start_id_type;
      }
      leaf end {
        type fabric-types:fabric_fgid_end_id_type;
      }
      list rack {
        key "rack_id";
        tailf:cli-show-template-enter "";
        tailf:cli-suppress-table;
        tailf:cli-show-template
          "Rack $(rack_id_str)\\\\: $(incorrect_fgids_range == true ?Incorrect range.:$(cmd_not_supported == true ?Not supported platform or No FC driver Clients.:
             Fgids\\\\:$(found_fgids_in_error == true ?$(fgids_in_error)
             Total\\\\: $(total_error_fgids):Ok)))
           
          ";
        leaf rack_id {
          type int32;
        }
        leaf rack_id_str {
          type string;
          tailf:hidden "internal";
        }
        leaf fgids_in_error {
          type string;
          tailf:hidden "internal";
        }
        leaf found_fgids_in_error {
          type boolean;
          tailf:hidden "internal";
        }
        leaf total_error_fgids {
          type int32;
          tailf:hidden "internal";
        }
        leaf incorrect_fgids_range {
          type boolean;
          tailf:hidden "internal";
        }
        leaf cmd_not_supported {
          type boolean;
          tailf:hidden "internal";
        }
      }
    }
  }

  grouping fgid {
    container fgid {
      description
        "FGID management information";
      tailf:hidden "internal-command";
      tailf:cli-incomplete-show-path;
      tailf:callpoint "fabric_fgid_cp";
      tailf:info "FGID management information";
      container information {
        tailf:hidden "internal-command";
        uses fgid_information_show;
      }
      container resource {
        tailf:hidden "internal-command";
        uses fgid_resource_show;
      }
      container statistics {
        tailf:callpoint "fabric_fgid_statistics";
        tailf:hidden "internal-command";
        tailf:info "FGID resource statistics";
        container all {
          uses fgid_statistics_show;
          tailf:info "All FGID resource statistics option.";
        }
        container sdr {
          uses fgid_statistics_sdr_show;
          tailf:info "FGID resource secure domain router basis statistics option.";
        }
        container pool {
          uses fgid_statistics_pool_show;
          tailf:info "FGID resource pool basis statistics option.";
        }
        container system {
          uses fgid_statistics_system_show;
          tailf:info "FGID resource system basis statistics option.";
        }
      }
      uses fgid_trace;
      uses fgid_program_error_show;
    }
  }
  tailf:id "http://www.cisco.com/panini/calvados/fabric/fgid";
}
