module Cisco-IOS-XR-sysadmin-instmgr-oper {
  namespace "http://www.cisco.com/ns/yang/Cisco-IOS-XR-sysadmin-instmgr-oper";
  prefix install;

  import tailf-common {
    prefix tailf;
  }

  organization
    "Cisco Systems Inc.";
  contact
    "Cisco Systems, Inc.
     Customer Service
     
     Postal: 170 West Tasman Drive
     San Jose, CA 95134
     
     Tel: +1 800 553-NETS
     E-mail: cs-yang@cisco.com";
  description
    "This module contains a collection of YANG
     definitions for Cisco IOS-XR sysadmin-instmgr 
     operational model";

  revision 2017-10-13 {
    description
      "Changed file name's suffix from -cfg.yang to -oper.yang";
  }
  revision 2017-08-02 {
    description
      "Added container for show version CLI";
  }
  revision 2017-04-11 {
    description
      "Reverting description for install_node_type to remove claim of wildcard support.
        Addition of install_node_wildcard_type, a copy of the above, with description indicating wildcard support.";
  }

  typedef install_add_pkg_type {
    type string {
      tailf:info
        "Package;;Enter package name(s) separated by space.
         
         Example:file1 file2 file3
        ";
    }
  }

  typedef install_add_source_type {
    type string {
      tailf:info
        "Source;;Enter source directory for the package(s) to be added.
         
         Example:  
         
         tftp://server/directory/
         
         sftp://user@server:/directory/ files_to_download
         
         ftp://user@server:/directory/ files_to_download
         
         scp://user@server:/directory/
         
         harddisk:/directory
         
         /dir/
        ";
    }
  }

  typedef install_backup_zipfile {
    type string {
      tailf:info
        "Tarfile;;Enter the directory and Tar File name.
         
         Example: 
         
         /harddisk:/directory/tarfile";
    }
  }

  typedef install_pkg_type {
    type string {
      tailf:info
        "Package;;Enter package name(s) separated by space.
         
         Example:  sysadmin.iso sysadmin_upgrade.iso";
    }
  }

  typedef install_node_type {
    type string {
      tailf:info
        "Location;;Enter Location(s) separated by space.
         
         Example:  0/RP0 0/RP1";
    }
  }

  typedef install_node_wildcard_type {
    type string {
      tailf:info
        "Location;;Location(s) separated by space.
         
         Example:  0/RP0 0/RP1.
         
         Or one of the following wildcarded combinations:
         
         */RP1 */SC1,
         
         */SC1 */RP1,
         
         */RP0 */SC0,
         
         */SC1 */RP1.";
    }
  }

  typedef install_id_type {
    type uint32 {
      tailf:info "Id;;Enter add operation id(s) separated by space";
    }
  }

  typedef install_log_id_type {
    type uint32 {
      tailf:info "1-4294967295;;Enter install operation id";
    }
  }

  typedef node_location_type {
    type string {
      pattern "((0?[0-9]|1[1-5])/(([rR][pP]|[lL][cC])?\\d{1,2}))(/[cC][pP][uU]0)?|all";
    }
    description
      "A system location in Rack/Slot/Instance";
  }

  typedef install_which_file {
    type string {
      tailf:info "File;;Enter the filename\n";
    }
  }

  container install {
    config false;
    tailf:callpoint "install_show";
    tailf:display-status-name "";
    tailf:info "Show system install information";
    tailf:cli-incomplete-show-path {
      tailf:cli-min-keys "1";
    }
    container version {
      description
        "Gives sysadmin version information";
      tailf:info "Shows version information";
      tailf:cli-show-template "$(img_info|show:noalign)";
      leaf-list img_info {
        type string;
        tailf:cli-drop-node-name;
        tailf:cli-list-syntax;
        tailf:display-column-name "";
      }
    }
    container inactive {
      description
        "Calvados inactive package(s) list for this node";
      tailf:info "Shows inactive package(s).";
      tailf:cli-show-template "$(si_inactive_output|show:noalign)";
      container summary {
        description
          "shows summary information of the inactive install software";
        tailf:info "Shows summary information about inactive install software.";
        tailf:cli-show-template "$(si_inactive_summary_output|show:noalign)";
        leaf-list si_inactive_summary_output {
          type string;
          tailf:cli-drop-node-name;
          tailf:cli-list-syntax;
          tailf:display-column-name "";
        }
      }
      leaf-list si_inactive_output {
        type string;
        tailf:cli-drop-node-name;
        tailf:cli-list-syntax;
        tailf:display-column-name "";
      }
    }
    container prepare {
      description
        "Calvados prepared package(s) list for this node";
      tailf:info "Shows prepared package(s).";
      tailf:cli-show-template "$(si_prepare_output|show:noalign)";
      leaf-list si_prepare_output {
        type string;
        tailf:cli-drop-node-name;
        tailf:cli-list-syntax;
        tailf:display-column-name "";
      }
    }
    container package {
      description
        "Package Name(s) to get info for";
      tailf:info "Shows package(s) info.";
      tailf:cli-show-template "$(si_package_output|show:noalign)";
      tailf:cli-incomplete-show-path;
      list pkg_list {
        key "pkg_name";
        tailf:cli-drop-node-name;
        tailf:cli-incomplete-show-path {
          tailf:cli-min-keys "1";
        }
        tailf:cli-show-template "$(si_package_output|show:noalign)";
        leaf pkg_name {
          type string;
        }
        container detail {
          tailf:cli-show-template "$(si_package_detail_output|show:noalign)";
          leaf-list si_package_detail_output {
            type string;
            tailf:cli-list-syntax;
            tailf:display-column-name "";
            tailf:cli-drop-node-name;
          }
        }
        container verbose {
          tailf:cli-show-template "$(si_package_verbose_output|show:noalign)";
          leaf-list si_package_verbose_output {
            type string;
            tailf:cli-list-syntax;
            tailf:display-column-name "";
            tailf:cli-drop-node-name;
          }
        }
        leaf-list si_package_output {
          type string;
          tailf:cli-drop-node-name;
          tailf:cli-list-syntax;
          tailf:display-column-name "";
        }
      }
    }
    container active {
      description
        "Calvados active package(s) list for this node";
      tailf:info "Shows active package(s).";
      tailf:cli-show-template "$(si_active_output|show:noalign)";
      tailf:display-status-name "";
      container summary {
        description
          "shows summary information of the active install software";
        tailf:info "Shows summary information about active install software.";
        tailf:cli-show-template "$(si_active_summary_output|show:noalign)";
        leaf-list si_active_summary_output {
          type string;
          tailf:cli-drop-node-name;
          tailf:cli-list-syntax;
          tailf:display-column-name "";
        }
      }
      leaf-list si_active_output {
        type string;
        tailf:cli-drop-node-name;
        tailf:cli-list-syntax;
        tailf:display-column-name "";
      }
    }
    container superseded {
      description
        "Calvados superseded package(s) list for this node";
      tailf:info "Shows superseded package(s).";
      tailf:cli-show-template "$(si_superseded_output|show:noalign)";
      tailf:display-status-name "";
      container summary {
        description
          "shows summary information of the show install superseded";
        tailf:info "Shows summary information about superseded packages";
        tailf:cli-show-template "$(si_superseded_summary_output|show:noalign)";
        leaf-list si_superseded_summary_output {
          type string;
          tailf:cli-drop-node-name;
          tailf:cli-list-syntax;
          tailf:display-column-name "";
        }
      }
      leaf-list si_superseded_output {
        type string;
        tailf:cli-drop-node-name;
        tailf:cli-list-syntax;
        tailf:display-column-name "";
      }
    }
    container request {
      description
        "Sysadmin current install operation details";
      tailf:info "Shows details about install operation in progress";
      tailf:cli-show-template "$(curr_inst_oper|show:noalign)";
      leaf-list curr_inst_oper {
        type string;
        tailf:cli-drop-node-name;
        tailf:cli-list-syntax;
        tailf:display-column-name "";
      }
    }
    container repository {
      description
        "Shows information about the install software repository.";
      tailf:info "Shows information about the install software repository.";
      tailf:cli-show-template "$(si_repository_output|show:noalign)";
      tailf:display-status-name "";
      container all {
        description
          "shows contents of all the install software repositories";
        tailf:info "Shows information about all the install software repositories.";
        tailf:cli-show-template "$(si_repository_all_output|show:noalign)";
        leaf-list si_repository_all_output {
          type string;
          tailf:cli-drop-node-name;
          tailf:cli-list-syntax;
          tailf:display-column-name "";
        }
      }
      leaf-list si_repository_output {
        type string;
        tailf:cli-drop-node-name;
        tailf:cli-list-syntax;
        tailf:display-column-name "";
      }
    }
    container log {
      tailf:info "Shows log of install operations.";
      tailf:cli-show-template "$(si_log_output|show:noalign)";
      list id {
        key "opid";
        tailf:cli-no-key-completion;
        tailf:cli-no-match-completion;
        tailf:cli-drop-node-name;
        tailf:cli-show-template "$(si_log_id_output|show:noalign)";
        leaf opid {
          type install_log_id_type;
        }
        container detail {
          tailf:info "Shows detailed log information for the install operation id.";
          tailf:cli-full-command;
          tailf:cli-show-template "$(si_log_id_detail_output|show:noalign)";
          leaf-list si_log_id_detail_output {
            type string;
            tailf:cli-list-syntax;
            tailf:display-column-name "";
            tailf:cli-drop-node-name;
          }
        }
        leaf-list si_log_id_output {
          type string;
          tailf:cli-drop-node-name;
          tailf:cli-list-syntax;
          tailf:display-column-name "";
        }
      }
      container reverse {
        tailf:info "Shows log of install operations in reverse order.";
        tailf:cli-show-template "$(si_log_reverse_output|show:noalign)";
        container detail {
          tailf:info "Shows detailed log of install operations in reverse order.";
          tailf:cli-full-command;
          tailf:cli-show-template "$(si_log_reverse_detail_output|show:noalign)";
          leaf-list si_log_reverse_detail_output {
            type string;
            tailf:cli-drop-node-name;
            tailf:cli-list-syntax;
            tailf:display-column-name "";
          }
        }
        leaf-list si_log_reverse_output {
          type string;
          tailf:cli-drop-node-name;
          tailf:cli-list-syntax;
          tailf:display-column-name "";
        }
      }
      container detail {
        tailf:info "Shows detailed log information for install operations.";
        tailf:cli-full-command;
        tailf:cli-show-template "$(si_log_detail_output|show:noalign)";
        leaf-list si_log_detail_output {
          type string;
          tailf:cli-drop-node-name;
          tailf:cli-list-syntax;
          tailf:display-column-name "";
        }
      }
      leaf-list si_log_output {
        type string;
        tailf:cli-drop-node-name;
        tailf:cli-list-syntax;
        tailf:display-column-name "";
      }
    }
    container which {
      description
        "Filename to get info for";
      tailf:info "Shows info about a file.";
      tailf:cli-show-template "$(si_which_output|show:noalign)";
      tailf:cli-incomplete-show-path;
      list file_list {
        key "file_name";
        tailf:cli-no-key-completion;
        tailf:cli-no-match-completion;
        tailf:cli-drop-node-name;
        tailf:cli-show-template "$(si_which_output|show:noalign)";
        leaf file_name {
          type string {
            tailf:info "File;;Enter the filename\n";
          }
        }
        container detail {
          tailf:info "detailed file information output";
          tailf:cli-show-template "$(si_which_detail_output|show:noalign)";
          leaf-list si_which_detail_output {
            type string;
            tailf:cli-list-syntax;
            tailf:display-column-name "";
            tailf:cli-drop-node-name;
          }
        }
        leaf-list si_which_output {
          type string;
          tailf:cli-list-syntax;
          tailf:display-column-name "";
          tailf:cli-drop-node-name;
        }
      }
    }
    container committed {
      description
        "Calvados committed package(s) list for this node";
      tailf:info "Shows committed package(s).";
      tailf:cli-show-template "$(si_committed_output|show:noalign)";
      tailf:display-status-name "";
      container summary {
        description
          "shows summary information of the committed install software";
        tailf:info "Shows summary information about committed install software.";
        tailf:cli-show-template "$(si_committed_summary_output|show:noalign)";
        leaf-list si_committed_summary_output {
          type string;
          tailf:cli-drop-node-name;
          tailf:cli-list-syntax;
          tailf:display-column-name "";
        }
      }
      leaf-list si_committed_output {
        type string;
        tailf:cli-drop-node-name;
        tailf:cli-list-syntax;
        tailf:display-column-name "";
      }
    }
    tailf:action "activate-internal-nopackages" {
      tailf:actionpoint "activate-point-nopackages";
      tailf:hidden "internal-command";
      description
        "Install activate";
      input {
        choice prompt_choice {
          mandatory false;
          case noprompt_choice {
            leaf noprompt {
              type empty;
              mandatory false;
            }
          }
        }
      }
      output {
        leaf result {
          type string;
        }
      }
    }
    tailf:action "activate-internal-packages" {
      tailf:actionpoint "activate-point";
      tailf:hidden "internal-command";
      description
        "Install activate";
      input {
        choice prompt_choice {
          mandatory false;
          case noprompt_choice {
            leaf noprompt {
              type empty;
              mandatory false;
            }
          }
        }
        choice activate_choice {
          mandatory true;
          case package_choice {
            leaf-list packages {
              type string;
              description
                "List of packages to activate";
              tailf:cli-full-command;
            }
          }
          case location_choice {
            leaf-list locationlist {
              type string;
              description
                "List of nodes where Activate is requested";
              tailf:cli-full-command;
            }
          }
          case id_choice {
            leaf-list idlist {
              type uint32;
              description
                "IDs of add operations whose packages are to be activated";
              tailf:cli-full-command;
            }
          }
        }
      }
      output {
        leaf result {
          type string;
        }
      }
    }
    tailf:action "add-internal" {
      tailf:actionpoint "add-point";
      tailf:hidden "internal-command";
      description
        "Install scp add operation implemenation";
      input {
        leaf addtype {
          type enumeration {
            enum "cp";
            enum "tftp";
            enum "scp";
            enum "sftp";
            enum "ftp";
          }
        }
        leaf src {
          type string;
          mandatory false;
        }
        leaf user {
          type string;
          mandatory false;
        }
        leaf password {
          type string;
          mandatory false;
        }
        leaf server {
          type string;
          mandatory false;
        }
        leaf source_dir {
          type string;
        }
        leaf-list files {
          type string;
        }
      }
      output {
        leaf result {
          type string;
        }
      }
    }
    tailf:action "prepare-internal" {
      tailf:actionpoint "prepare-point";
      description
        "Install prepare";
      tailf:hidden "internal-command";
      input {
        choice prepare_choice {
          mandatory true;
          case package_choice {
            leaf-list packages {
              type string;
              description
                "List of packages to prepare";
              tailf:cli-full-command;
            }
          }
          case clean_choice {
            leaf clean {
              type empty;
              mandatory false;
              description
                "clean prepare";
              tailf:cli-full-command;
            }
          }
          case id_choice {
            leaf-list idlist {
              type uint32;
              description
                "IDs of add operations whose packages are to be prepared";
              tailf:cli-full-command;
            }
          }
        }
      }
      output {
        leaf result {
          type string;
        }
      }
    }
    tailf:action "deactivate-internal" {
      tailf:actionpoint "deactivate-point";
      description
        "Install deactivate";
      tailf:hidden "internal-command";
      input {
        choice prompt_choice {
          mandatory false;
          case noprompt_choice {
            leaf noprompt {
              type empty;
              mandatory false;
            }
          }
        }
        choice deactivate_choice {
          mandatory true;
          case package_choice {
            leaf-list packages {
              type string;
              description
                "List of packages to deactivate";
              tailf:cli-full-command;
            }
          }
          case id_choice {
            leaf-list idlist {
              type uint32;
              description
                "IDs of add operations whose packages are to be deactivated";
              tailf:cli-full-command;
            }
          }
          case superseded_choice {
            leaf superseded {
              type empty;
              description
                "Remove Sysadmin superseded packages";
            }
          }
        }
      }
      output {
        leaf result {
          type string;
        }
      }
    }
    tailf:action "extract-internal" {
      tailf:actionpoint "extract-point";
      tailf:hidden "internal-command";
      description
        "Install extract";
      input {
        choice remove_choice {
          mandatory true;
          case package_choice {
            leaf-list packages {
              type string;
              description
                "List of packages to extracted";
              tailf:cli-full-command;
            }
          }
          case id_choice {
            leaf-list idlist {
              type uint32;
              description
                "IDs of add operations whose packages are to be extracted";
              tailf:cli-full-command;
            }
          }
        }
      }
      output {
        leaf result {
          type string;
        }
      }
    }
    tailf:action "remove-internal" {
      tailf:actionpoint "remove-point";
      tailf:hidden "internal-command";
      description
        "Install remove";
      input {
        choice remove_choice {
          mandatory true;
          case package_choice {
            leaf-list packages {
              type string;
              description
                "List of packages to remove";
              tailf:cli-full-command;
            }
          }
          case id_choice {
            leaf-list idlist {
              type uint32;
              description
                "IDs of add operations whose packages are to be removed";
              tailf:cli-full-command;
            }
          }
          case inactive_choice {
            leaf inactive {
              type empty;
              description
                "Remove Sysadmin inactive packages";
            }
          }
        }
      }
      output {
        leaf result {
          type string;
        }
      }
    }
    tailf:action "commit-internal" {
      tailf:actionpoint "commit-point";
      tailf:hidden "internal-command";
      description
        "Install commit";
      output {
        leaf result {
          type string;
        }
      }
    }
    tailf:action "verify-internal-packages" {
      tailf:actionpoint "verify-point";
      tailf:hidden "internal-command";
      description
        "Install verify";
      input {
        choice location_choice {
          mandatory true;
          case location {
            leaf-list locations {
              type string;
              description
                "locations at which packages are to be verified";
              tailf:cli-full-command;
            }
          }
        }
      }
      output {
        leaf result {
          type string;
        }
      }
    }
    tailf:action "verify-internal-nolocation" {
      tailf:actionpoint "verify-point-nolocation";
      tailf:hidden "internal-command";
      description
        "Install verify";
      output {
        leaf result {
          type string;
        }
      }
    }
    tailf:action "backup-internal-cli" {
      tailf:actionpoint "backup-point";
      tailf:hidden "internal-command";
      description
        "Install Backup";
      input {
        choice location_choice {
          mandatory true;
          case location {
            leaf-list locations {
              type string;
              description
                "locations at which recovery image to be updated ";
              tailf:cli-full-command;
            }
          }
        }
      }
      output {
        leaf result {
          type string;
        }
      }
    }
  }
}
