module Cisco-IOS-XR-sysadmin-time-of-day-timezone {
  namespace "http://cisco.com/calvados/Cisco-IOS-XR-sysadmin-time-of-day-timezone";
  prefix timezone;

  import tailf-common {
    prefix tailf;
  }
  import Cisco-IOS-XR-sysadmin-show-trace {
    prefix show_trace;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR syadmin TOD configuration and cli.
     
     This module contains definitions
     for the following management objects:
     Time of the Day(TOD) Cli and configuration data
     
     Copyright (c) 2013-2017 by Cisco Systems, Inc.
     All rights reserved.";

  revision 2016-07-04 {
    description
      "Remove refine stmt";
  }
  revision 2016-05-12 {
    description
      "Initial version";
  }
  tailf:id "http://cisco.com/calvados/timezone";

  container clock {
    tailf:info "Configure time-of-day clock";
    container timezone {
      tailf:info "Configure time zone";
      tailf:validate "val_tz" {
        tailf:dependency ".";
      }
      tailf:cli-compact-syntax;
      tailf:cli-sequence-commands;
      leaf tzname {
        type string;
        tailf:cli-completion-actionpoint "tzname-complete";
        tailf:cli-drop-node-name;
        tailf:cli-incomplete-command;
      }
      leaf area {
        type string;
        tailf:cli-completion-actionpoint "area-complete";
        tailf:cli-drop-node-name;
      }
    }
  }
  container trace {
    config false;
    tailf:cdb-oper;
    tailf:cli-incomplete-show-path;
    tailf:info "Display Timezone Traces";
    container timezone_config {
      tailf:cli-incomplete-show-path;
      tailf:info "Timezone Config Traces";
      uses show_trace:traceable;
    }
    container timezone_notify {
      tailf:cli-incomplete-show-path;
      tailf:info "Timezone Notify Traces";
      uses show_trace:traceable;
    }
  }
}
