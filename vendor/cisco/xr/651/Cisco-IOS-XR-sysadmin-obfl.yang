module Cisco-IOS-XR-sysadmin-obfl {
  namespace "http://www.cisco.com/ns/yang/Cisco-IOS-XR-sysadmin-obfl";
  prefix obfl;

  import tailf-common {
    prefix tailf;
  }
  import Cisco-IOS-XR-sysadmin-show-trace {
    prefix show_trace;
  }

  organization
    "Cisco Systems Inc.";
  description
    "This module holds OBFL data.";

  revision 2017-07-31 {
    description
      "Changed namespace to follow Cisco guidelines on naming convention";
  }
  revision 2012-10-10 {
    description
      "Initial revision of show obfl related commands";
  }

  grouping obfl_trace {
    container obfl_mgr {
      tailf:info "OBFL Manager Process data";
      tailf:cli-incomplete-show-path;
      uses show_trace:traceable;
    }
    container obfl_show {
      tailf:info "OBFL Show Process data";
      tailf:cli-incomplete-show-path;
      uses show_trace:traceable;
    }
  }
  tailf:id "http://www.cisco.com/panini/calvados/obfl";

  container obfl {
    config false;
    tailf:info "OBFL Show Process data";
    tailf:cli-incomplete-show-path;
    uses obfl_trace;
  }
}
