module cisco-xr-openconfig-bgp-policy-deviations {

  /*** NAMESPACE / PREFIX DEFINITION ***/

  namespace "http://cisco.com/ns/yang/cisco-xr-openconfig-bgp-policy-deviations";


  prefix "cisco-xr-oc-bgp-pol-devs";

  /*** LINKAGE (IMPORTS / INCLUDES) ***/
  import openconfig-routing-policy { prefix rpol; }
  import openconfig-bgp-policy { prefix bgp-pol; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains the deviations of Open Config BGP Policy YANG 
    set for Cisco IOS-XR.

     Copyright (c) 2015-2017 by Cisco Systems, Inc.
     All rights reserved.";

  revision "2017-02-02" {
    description
      "Updated revision applicable to IOS-XR 6.2.2";
  }

  deviation /rpol:routing-policy/rpol:defined-sets/bgp-pol:bgp-defined-sets/bgp-pol:ext-community-sets {
    deviate not-supported;
  }

  deviation /rpol:routing-policy/rpol:policy-definitions/rpol:policy-definition/rpol:statements/rpol:statement/rpol:conditions/bgp-pol:bgp-conditions/bgp-pol:config/bgp-pol:afi-safi-in {
    deviate not-supported;
  }

  deviation /rpol:routing-policy/rpol:policy-definitions/rpol:policy-definition/rpol:statements/rpol:statement/rpol:conditions/bgp-pol:bgp-conditions/bgp-pol:config/bgp-pol:route-type {
    deviate not-supported;
  }

  deviation /rpol:routing-policy/rpol:policy-definitions/rpol:policy-definition/rpol:statements/rpol:statement/rpol:conditions/bgp-pol:bgp-conditions/bgp-pol:state/bgp-pol:afi-safi-in {
    deviate not-supported;
  }

  deviation /rpol:routing-policy/rpol:policy-definitions/rpol:policy-definition/rpol:statements/rpol:statement/rpol:conditions/bgp-pol:bgp-conditions/bgp-pol:state/bgp-pol:route-type {
    deviate not-supported;
  }

  deviation /rpol:routing-policy/rpol:policy-definitions/rpol:policy-definition/rpol:statements/rpol:statement/rpol:conditions/bgp-pol:bgp-conditions/bgp-pol:community-count {
    deviate not-supported;
  }

  deviation /rpol:routing-policy/rpol:policy-definitions/rpol:policy-definition/rpol:statements/rpol:statement/rpol:conditions/bgp-pol:bgp-conditions/bgp-pol:match-ext-community-set {
    deviate not-supported;
  }

  deviation /rpol:routing-policy/rpol:policy-definitions/rpol:policy-definition/rpol:statements/rpol:statement/rpol:actions/bgp-pol:bgp-actions/bgp-pol:set-community/bgp-pol:config/bgp-pol:method {
    deviate not-supported;
  }

  deviation /rpol:routing-policy/rpol:policy-definitions/rpol:policy-definition/rpol:statements/rpol:statement/rpol:actions/bgp-pol:bgp-actions/bgp-pol:set-community/bgp-pol:state/bgp-pol:method {
    deviate not-supported;
  }

  deviation /rpol:routing-policy/rpol:policy-definitions/rpol:policy-definition/rpol:statements/rpol:statement/rpol:actions/bgp-pol:bgp-actions/bgp-pol:set-ext-community {
    deviate not-supported;
  }
}
