module Cisco-IOS-XR-ip-rib-cfg {

  /*** NAMESPACE / PREFIX DEFINITION ***/

  namespace "http://cisco.com/ns/yang/Cisco-IOS-XR-ip-rib-cfg";


  prefix "ip-rib-cfg";

  /*** LINKAGE (IMPORTS / INCLUDES) ***/

  import Cisco-IOS-XR-types { prefix "xr"; }

  import Cisco-IOS-XR-infra-rsi-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib package configuration.

     This module contains definitions
     for the following management objects:
       rib: RIB configuration.

     This YANG module augments the
       Cisco-IOS-XR-infra-rsi-cfg
     module with configuration data.

     Copyright (c) 2013-2016 by Cisco Systems, Inc.
     All rights reserved.";

  revision "2015-11-09" {
    description
      "IOS XR 6.0 revision.";
  }


  grouping NEXT-HOP-DAMPENING-DISABLE {
    description "Common node of ipv4, ipv6";
    leaf next-hop-dampening-disable {
      type empty;
      description "Disable next-hop dampening";
    }
  }

  grouping REDISTRIBUTION-HISTORY {
    description "Common node of ipv4, ipv6";

    container redistribution-history {
      description "Redistribution history related configs";

      container keep {
        description
          "Retain redistribution history after disconnect.";
        leaf bcdl {
          type empty;
          description "Enable retain BCDL history";
        }
      }
      leaf bcdl-client {
        type uint32 {
          range "10..2000000";
        }
        description "Maximum BCDL redistribution history size.";
      }
      leaf protocol-client {
        type uint32 {
          range "10..250000";
        }
        description "Maximum protocol redistribution history size.";
      }
    }
  }

  container rib {
    description "RIB configuration.";

    container af {
      description "RIB address family configuration";

      container ipv4 {
        description "IPv4 configuration";
        uses NEXT-HOP-DAMPENING-DISABLE;
        uses REDISTRIBUTION-HISTORY;
      }

      container ipv6 {
        description "IPv6 configuration";
        uses NEXT-HOP-DAMPENING-DISABLE;
        uses REDISTRIBUTION-HISTORY;
      }
    }
    leaf max-recursion-depth {
      type uint32 {
        range "5..16";
      }
      description "Set maximum depth for route recursion check";
    }
  }

  augment "/a1:vrfs/a1:vrf/a1:afs/a1:af" {

    container maximum-prefix {
      presence "Indicates a maximum-prefix node is configured.";
      description "Set maximum prefix limits";
      leaf prefix-limit {
        type uint32 {
          range "32..5000000";
        }
        mandatory true;
        description "Set table's maximum prefix limit";
      }
      leaf mid-threshold {
        type uint32 {
          range "1..100";
        }
        description "Mid-threshold (% of maximum)";
      }
    }
    description
      "This augment extends the configuration data of
      'Cisco-IOS-XR-infra-rsi-cfg'";
  }
}
