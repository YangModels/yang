module Cisco-IOS-XR-man-ems-cfg {

  /*** NAMESPACE / PREFIX DEFINITION ***/

  namespace "http://cisco.com/ns/yang/Cisco-IOS-XR-man-ems-cfg";


  prefix "man-ems-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ems package configuration.

     This module contains definitions
     for the following management objects:
       grpc: GRPC configruation

     Copyright (c) 2013-2016 by Cisco Systems, Inc.
     All rights reserved.";

  revision "2015-11-09" {
    description
      "IOS XR 6.0 revision.";
  }


  container grpc {
    description "GRPC configruation";

    container service-layer {
      description "Service Layer";
      leaf enable {
        type empty;
        description "Enable ServiceLayer";
      }
    }

    container tls {
      description "Transport Layer Security (TLS)";
      leaf trustpoint {
        type string;
        description "Trustpoint Name";
      }
      leaf enable {
        type empty;
        description "Enable TLS";
      }
    }
    leaf port {
      type uint32 {
        range "10000..57999";
      }
      description "Server listening port";
    }
    leaf enable {
      type empty;
      description "Enable GRPC";
    }
    leaf max-request-per-user {
      type uint32 {
        range "1..32";
      }
      description "Maximum concurrent requests per user";
    }
    leaf address-family {
      type string;
      description "Address family identifier type";
    }
    leaf max-request-total {
      type uint32 {
        range "1..256";
      }
      description "Maximum concurrent requests in total";
    }
  }
}
