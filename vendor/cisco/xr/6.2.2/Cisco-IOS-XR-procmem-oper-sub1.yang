submodule Cisco-IOS-XR-procmem-oper-sub1 {

  belongs-to Cisco-IOS-XR-procmem-oper {
    prefix Cisco-IOS-XR-procmem-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR procmem package operational data.

     Copyright (c) 2013-2016 by Cisco Systems, Inc.
     All rights reserved.";

  revision "2015-11-09" {
    description
      "IOS XR 6.0 revision.";
  }

  revision "2015-07-30" {
    description
      "IOS XR 6.0.0 revision.";
  }


  grouping PROCESSESMEMORY-ENTRY {
    description " Per Process Information";
    leaf name {
      type string;
      description "Process name";
    }
    leaf jid {
      type uint32;
      description "Job ID";
    }
    leaf pid {
      type uint32;
      description "Process ID";
    }
    leaf text-seg-size {
      type uint32;
      description "Text Segment Size";
    }
    leaf data-seg-size {
      type uint32;
      description "Data Segment Size";
    }
    leaf stack-seg-size {
      type uint32;
      description "Stack Segment Size";
    }
    leaf malloc-size {
      type uint32;
      description "Malloced Memory Size";
    }
    leaf dyn-limit {
      type uint32;
      description "Dynamic memory limit";
    }
    leaf shared-mem {
      type uint32;
      description "Shared memory size";
    }
    leaf physical-mem {
      type uint32;
      description "Physical memory size";
    }
  }
}
