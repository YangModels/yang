module Cisco-IOS-XR-lib-keychain-macsec-cfg {

  /*** NAMESPACE / PREFIX DEFINITION ***/

  namespace "http://cisco.com/ns/yang"+
    "/Cisco-IOS-XR-lib-keychain-macsec-cfg";


  prefix "lib-keychain-macsec-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-keychain-macsec package configuration.

     This module contains definitions
     for the following management objects:
       mac-sec-keychains: Configure a Key Chain

     Copyright (c) 2013-2016 by Cisco Systems, Inc.
     All rights reserved.";

  revision "2015-11-09" {
    description
      "IOS XR 6.0 revision.";
  }

  typedef Mac-sec-key-chain-month {
    type enumeration {
      enum jan {
        value 0;
        description "January";
      }
      enum feb {
        value 1;
        description "February";
      }
      enum mar {
        value 2;
        description "March";
      }
      enum apr {
        value 3;
        description "April";
      }
      enum may {
        value 4;
        description "May";
      }
      enum jun {
        value 5;
        description "June";
      }
      enum jul {
        value 6;
        description "July";
      }
      enum aug {
        value 7;
        description "August";
      }
      enum sep {
        value 8;
        description "September";
      }
      enum oct {
        value 9;
        description "October";
      }
      enum nov {
        value 10;
        description "November";
      }
      enum dec {
        value 11;
        description "December";
      }
    }
    description "Mac sec key chain month";
  }
  typedef Mac-sec-crypto-alg {
    type enumeration {
      enum aes-128-cmac {
        value 7;
        description "aes 128 cmac";
      }
      enum aes-256-cmac {
        value 8;
        description "aes 256 cmac";
      }
    }
    description "Mac sec crypto alg";
  }

  container mac-sec-keychains {
    description "Configure a Key Chain";

    list mac-sec-keychain {
      key "chain-name";
      description "Name of the key chain for MACSec";

      container keies {
        description "Configure a Key";

        list key {
          key "key-id";
          description "Key Identifier";

          container lifetime {
            description "Configure a key Lifetime";
            leaf start-hour {
              type uint32 {
                range "0..23";
              }
              description "Start Hour";
            }
            leaf start-minutes {
              type uint32 {
                range "0..59";
              }
              units "minute";
              description "Start Minutes";
            }
            leaf start-seconds {
              type uint32 {
                range "0..59";
              }
              units "second";
              description "Start Seconds";
            }
            leaf start-date {
              type uint32 {
                range "1..31";
              }
              description "Start Date";
            }
            leaf start-month {
              type Mac-sec-key-chain-month;
              description "Start Month";
            }
            leaf start-year {
              type uint32 {
                range "1993..2035";
              }
              description "Start Year";
            }
            leaf life-time {
              type uint32 {
                range "1..2147483647";
              }
              units "second";
              description "Lifetime duration in seconds";
            }
            leaf infinite-flag {
              type boolean;
              description "Infinite Lifetime flag";
            }
            leaf end-hour {
              type uint32 {
                range "0..23";
              }
              description "End Hour";
            }
            leaf end-minutes {
              type uint32 {
                range "0..59";
              }
              units "minute";
              description "End Minutes";
            }
            leaf end-seconds {
              type uint32 {
                range "0..59";
              }
              units "second";
              description "End Seconds";
            }
            leaf end-date {
              type uint32 {
                range "1..31";
              }
              description "End Date";
            }
            leaf end-month {
              type Mac-sec-key-chain-month;
              description "End Month";
            }
            leaf end-year {
              type uint32 {
                range "1993..2035";
              }
              description "End Year";
            }
          }

          container key-string {
            presence "Indicates a key-string node is configured.";
            description
              "Configure a clear text/encrypted Key string
              along with cryptographic algorithm";
            leaf string {
              type xr:Proprietary-password;
              mandatory true;
              description "Key String";
            }
            leaf cryptographic-algorithm {
              type Mac-sec-crypto-alg;
              mandatory true;
              description "Cryptographic Algorithm";
            }
            leaf encryption-type {
              type int32;
              default "0";
              description "encryption type used to store key";
            }
          }
          leaf key-id {
            type xr:Cisco-ios-xr-string;
            description "48-bit Key identifier";
          }
        }
      }
      leaf chain-name {
        type xr:Cisco-ios-xr-string;
        description "Name of the key chain";
      }
    }
  }
}
