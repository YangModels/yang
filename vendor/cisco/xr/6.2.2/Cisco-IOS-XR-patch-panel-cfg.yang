module Cisco-IOS-XR-patch-panel-cfg {

  /*** NAMESPACE / PREFIX DEFINITION ***/

  namespace "http://cisco.com/ns/yang/Cisco-IOS-XR-patch-panel-cfg";


  prefix "patch-panel-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR patch-panel package configuration.

     This module contains definitions
     for the following management objects:
       patch-panel: patch-panel service submode

     Copyright (c) 2013-2016 by Cisco Systems, Inc.
     All rights reserved.";

  revision "2015-11-09" {
    description
      "IOS XR 6.0 revision.";
  }


  container patch-panel {
    presence "Indicates a patch-panel node is configured.";
    description "patch-panel service submode";
    leaf enable {
      type empty;
      mandatory true;
      description "Enable patch-panel service";
    }
    leaf user-name {
      type string;
      description
        "User name to be used for Authentication with
        Patch-Panel";
    }
    leaf password {
      type xr:Proprietary-password;
      description
        "Password name to be used for Authentication with
        Patch-Panel";
    }
    leaf ipv4 {
      type inet:ipv4-address-no-zone;
      description "IP address for patch-panel";
    }
  }
}
