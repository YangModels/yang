submodule Cisco-IOS-XR-icpe-infra-oper-sub10 {

  belongs-to Cisco-IOS-XR-icpe-infra-oper {
    prefix Cisco-IOS-XR-icpe-infra-oper;
  }

  /*** LINKAGE (IMPORTS / INCLUDES) ***/

  import ietf-yang-types { prefix "yang"; }

  import Cisco-IOS-XR-types { prefix "xr"; }

  include Cisco-IOS-XR-icpe-infra-oper-sub3 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2016 by Cisco Systems, Inc.
     All rights reserved.";

  revision "2015-11-09" {
    description
      "IOS XR 6.0 revision.";
  }

  typedef Icpe-opm-resync-fsm-state {
    type enumeration {
      enum icpe-opm-resync-fsm-state-not-open {
        description "Not open";
      }
      enum icpe-opm-resync-fsm-state-stable {
        description "Stable";
      }
      enum icpe-opm-resync-fsm-state-in-resync {
        description "In resync";
      }
      enum icpe-opm-resync-fsm-state-queued {
        description "Queued";
      }
      enum icpe-opm-resync-fsm-state-resync-req {
        description "Resync req";
      }
    }
    description "Icpe opm resync fsm state";
  }
  typedef Icpe-opm-chan-fsm-state {
    type enumeration {
      enum icpe-opm-chan-fsm-state-down {
        description "Down";
      }
      enum icpe-opm-chan-fsm-state-closed {
        description "Closed";
      }
      enum icpe-opm-chan-fsm-state-opening {
        description "Opening";
      }
      enum icpe-opm-chan-fsm-state-opened {
        description "Opened";
      }
      enum icpe-opm-chan-fsm-state-open {
        description "Open";
      }
    }
    description "Icpe opm chan fsm state";
  }
  typedef Icpe-opm-controller {
    type enumeration {
      enum icpe-opm-controller-unknown {
        description "Unknown";
      }
      enum icpe-opm-controller-primary {
        description "Primary";
      }
      enum icpe-opm-controller-secondary {
        description "Secondary";
      }
    }
    description "Icpe opm controller";
  }
  typedef Icpe-opm-sync-fsm-state {
    type enumeration {
      enum icpe-opm-sync-fsm-state-split-brain {
        description "Split brain";
      }
      enum icpe-opm-sync-fsm-state-waiting {
        description "Waiting";
      }
      enum icpe-opm-sync-fsm-state-whole-brain {
        description "Whole brain";
      }
    }
    description "Icpe opm sync fsm state";
  }
  typedef Icpe-opm-arbitration-fsm-state {
    type enumeration {
      enum icpe-opm-arbitration-fsm-state-unarbitrated {
        description "Unarbitrated";
      }
      enum icpe-opm-arbitration-fsm-state-waiting {
        description "Waiting";
      }
      enum icpe-opm-arbitration-fsm-state-arbitrating {
        description "Arbitrating";
      }
      enum icpe-opm-arbitration-fsm-state-arbitrated {
        description "Arbitrated";
      }
    }
    description "Icpe opm arbitration fsm state";
  }
  typedef Icpe-opm-auth-fsm-state {
    type enumeration {
      enum icpe-opm-auth-fsm-state-unauth {
        description "Unauth";
      }
      enum icpe-opm-auth-fsm-state-waiting {
        description "Waiting";
      }
      enum icpe-opm-auth-fsm-state-waiting-for-auth {
        description "Waiting for auth";
      }
      enum icpe-opm-auth-fsm-state-waiting-for-reply {
        description "Waiting for reply";
      }
      enum icpe-opm-auth-fsm-state-authed {
        description "Authed";
      }
    }
    description "Icpe opm auth fsm state";
  }
  typedef Icpe-opm-transport-state {
    type enumeration {
      enum icpe-opm-transport-state-disconnected {
        description "Disconnected";
      }
      enum icpe-opm-transport-state-iccp-unavailable {
        description "ICCP unavailable";
      }
      enum icpe-opm-transport-state-no-member-present {
        description "No member present";
      }
      enum icpe-opm-transport-state-member-down {
        description "Member down";
      }
      enum icpe-opm-transport-state-member-not-reachable {
        description "Member not reachable";
      }
      enum icpe-opm-transport-state-waiting-for-app-connect {
        description "Waiting for app connect";
      }
      enum "icpe-opm-transport-state-waiting-for-app-connect"+
        "-response" {
        description "Waiting for app connect response";
      }
      enum icpe-opm-transport-state-connected {
        description "Connected";
      }
    }
    description "Icpe opm transport state";
  }
  typedef Icpe-opm-sess-state {
    type enumeration {
      enum icpe-opm-sess-state-disconnected {
        description "Disconnected";
      }
      enum icpe-opm-sess-state-connecting {
        description "Connecting";
      }
      enum icpe-opm-sess-state-authenticating {
        description "Authenticating";
      }
      enum icpe-opm-sess-state-arbitrating {
        description "Arbitrating";
      }
      enum icpe-opm-sess-state-waiting-for-resyncs {
        description "Waiting for resyncs";
      }
      enum icpe-opm-sess-state-connected {
        description "Connected";
      }
    }
    description "Icpe opm sess state";
  }

  grouping ICPE-REDUNDANCY-CHAN-TYPE {
    description "ICPE REDUNDANCY CHAN TYPE";

    container channel-state-timestamp {
      description "Timestamp";
      uses ICPE-TIMESTAMP-TYPE;
    }

    container resync-state-timestamp {
      description "Timestamp";
      uses ICPE-TIMESTAMP-TYPE;
    }
    leaf channel-id {
      type uint32;
      description "Channel ID";
    }
    leaf chan-state {
      type Icpe-opm-chan-fsm-state;
      description "Chan state";
    }
    leaf resync-state {
      type Icpe-opm-resync-fsm-state;
      description "Resync state";
    }
    leaf control-messages-sent {
      type uint64;
      description "Control messages sent";
    }
    leaf normal-messages-sent {
      type uint64;
      description "Normal messages sent";
    }
    leaf control-messages-received {
      type uint64;
      description "Control messages received";
    }
    leaf normal-messages-received {
      type uint64;
      description "Normal messages received";
    }
  }

  grouping ICPE-REDUNDANCY-SESSION {
    description "nV Satellite Redundancy Protocol Information";

    container protocol-state-timestamp {
      description "Timestamp";
      uses ICPE-TIMESTAMP-TYPE;
    }
    leaf iccp-group-xr {
      type uint32;
      description "ICCP group";
    }
    leaf protocol-state {
      type Icpe-opm-sess-state;
      description "Protocol state";
    }
    leaf transport-state {
      type Icpe-opm-transport-state;
      description "Transport state";
    }
    leaf authentication-state {
      type Icpe-opm-auth-fsm-state;
      description "Authentication state";
    }
    leaf arbitration-state {
      type Icpe-opm-arbitration-fsm-state;
      description "Arbitration state";
    }
    leaf synchronization-state {
      type Icpe-opm-sync-fsm-state;
      description "Synchronization state";
    }
    leaf primacy {
      type Icpe-opm-controller;
      description "Primacy";
    }
    leaf system-mac {
      type yang:mac-address;
      description "System MAC";
    }
    leaf isolated {
      type boolean;
      description "Isolated";
    }

    list channel {
      description "Channels on this session table";
      uses ICPE-REDUNDANCY-CHAN-TYPE;
    }
  }
}
