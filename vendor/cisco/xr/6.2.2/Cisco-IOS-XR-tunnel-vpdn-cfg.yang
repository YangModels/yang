module Cisco-IOS-XR-tunnel-vpdn-cfg {

  /*** NAMESPACE / PREFIX DEFINITION ***/

  namespace "http://cisco.com/ns/yang/Cisco-IOS-XR-tunnel-vpdn-cfg";


  prefix "tunnel-vpdn-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tunnel-vpdn package configuration.

     This module contains definitions
     for the following management objects:
       vpdn: VPDN configuration

     Copyright (c) 2013-2016 by Cisco Systems, Inc.
     All rights reserved.";

  revision "2015-11-09" {
    description
      "IOS XR 6.0 revision.";
  }

  typedef Df-bit {
    type enumeration {
      enum clear {
        value 0;
        description "Clear df bit";
      }
      enum reflect {
        value 1;
        description "Reflect df bit from inner ip header";
      }
      enum set {
        value 2;
        description "Set df bit";
      }
    }
    description "Df bit";
  }
  typedef Option {
    type enumeration {
      enum local {
        value 1;
        description "Log VPDN events locally";
      }
      enum user {
        value 2;
        description "Log VPDN user events";
      }
      enum dead-cache {
        value 8;
        description "Log VPDN dead cache";
      }
      enum tunnel-drop {
        value 16;
        description "Log VPDN tunnel drops";
      }
    }
    description "Option";
  }

  container vpdn {
    description "VPDN configuration";

    container history {
      description "VPDN history logging";
      leaf failure {
        type empty;
        description "User failure";
      }
    }

    container redundancy {
      description "Enable VPDN redundancy";

      container process-failures {
        description "Process crash configuration";
        leaf switchover {
          type empty;
          description "Force a switchover if the process crashes";
        }
      }
      leaf enable {
        type empty;
        description
          "Enable Enable VPDN redundancy. Deletion of this
          object also causes deletion of all associated
          objects under Redundancy.";
      }
    }

    container local {
      description "VPDN Local radius process configuration";
      leaf secret-text {
        type string {
          length "1..32";
        }
        description "secret password";
      }
      leaf path {
        type string {
          length "1..64";
        }
        description "local path of the saved profile";
      }
      leaf cache-disabled {
        type empty;
        description "Set constant integer";
      }
      leaf port {
        type xr:Cisco-ios-xr-port-number;
        description "port value";
      }
    }

    container templates {
      description "Table of Template";

      list template {
        key "template-name";
        description "VPDN template configuration";

        container caller-id {
          description "Options to apply on calling station id";
          leaf mask {
            type string {
              length "1..63";
            }
            description "Mask characters by method";
          }
        }

        container vpn {
          description "VPN ID/VRF name";

          container id {
            description "VPN ID";
            leaf oui {
              type xr:Hex-integer;
              description
                "VPN ID, (OUI:VPN-Index) format(hex), 3 bytes
                OUI Part";
            }
            leaf index {
              type xr:Hex-integer;
              description
                "VPN ID, (OUI:VPN-Index) format(hex), 4 bytes
                VPN_Index Part";
            }
          }
          leaf vrf {
            type xr:Cisco-ios-xr-string {
              length "1..32";
            }
            description "VRF name";
          }
        }

        container tunnel {
          description "L2TP tunnel commands";
          leaf busy-timeout {
            type uint32 {
              range "60..65535";
            }
            units "second";
            description "Busy time out value in seconds";
          }
        }

        container ip {
          description "Set IP TOS value";
          leaf tos {
            type int32;
            description "Set constant integer";
          }
        }

        container ipv4 {
          description "IPv4 settings for tunnel";
          leaf df-bit {
            type Df-bit;
            description "IPv4 don't fragment bit set/clear/reflect";
          }
          leaf source {
            type inet:ipv4-address-no-zone;
            description "Enter an IP address";
          }
        }
        leaf cisco-avp100-format-e-enable {
          type empty;
          description
            "To support NAS-Port format e in Cisco AVP 100";
        }
        leaf description {
          type string {
            length "1..100";
          }
          description
            "Up to 100 characters describing this VPDN
            template";
        }
        leaf l2tp-class {
          type xr:Cisco-ios-xr-string {
            length "1..79";
          }
          description "L2TP class  command";
        }
        leaf dsl-line-forwarding {
          type empty;
          description "Forward DSL Line Info attributes";
        }
        leaf template-name {
          type xr:Cisco-ios-xr-string {
            length "1..63";
          }
          description "VPDN template name";
        }
      }
    }

    container caller-id {
      description "Options to apply on calling station ID";
      leaf mask {
        type string {
          length "1..63";
        }
        description "Mask characters by method";
      }
    }

    container vpd-ngroups {
      description "Table of VPDNgroup";

      list vpd-ngroup {
        key "vpd-ngroupname";
        description "vpdn-group configuration";

        container vpn-id {
          description "Vpn id";
          leaf vpn-id-oui {
            type xr:Hex-integer;
            description
              "VPN ID, (OUI:VPN-Index) format(hex), 3 bytes
              OUI Part";
          }
          leaf vpn-id-index {
            type xr:Hex-integer;
            description
              "VPN ID, (OUI:VPN-Index) format(hex), 4 bytes
              VPN_Index Part";
          }
        }

        container ip {
          description "set ip tos value";
          leaf tos {
            type uint32 {
              range "0..255";
            }
            description "ip tos value";
          }
        }
        leaf dsl-line-forwarding {
          type empty;
          description "Forward DSL Line Info attributes";
        }
        leaf cisco-avp100-format-e-enable {
          type empty;
          description
            "To support NAS-Port format e in cisco AVP 100";
        }
        leaf desc {
          type string {
            length "1..100";
          }
          description
            "upto 100 characters describing this VPDN group";
        }
        leaf attribute {
          type string {
            length "1..63";
          }
          description "match substring";
        }
        leaf l2tp-class {
          type string {
            length "1..79";
          }
          description "l2tp class name";
        }
        leaf tunnel-busy-timeout {
          type uint32 {
            range "1..65535";
          }
          description "Busy list timeout length";
        }
        leaf vrf-name {
          type xr:Cisco-ios-xr-string {
            length "1..32";
          }
          description "Vrf name";
        }
        leaf sr-ctemplate {
          type string {
            length "1..63";
          }
          description "Source vpdn-template";
        }
        leaf vpd-ngroupname {
          type xr:Cisco-ios-xr-string {
            length "1..63";
          }
          description "vpdn-group name";
        }
      }
    }

    container loggings {
      description "Table of Logging";

      list logging {
        key "option";
        description "Configure logging for VPDN";
        leaf option {
          type Option;
          description "VPDN logging options";
        }
      }
    }

    container l2tp {
      description "L2TPv2 protocol commands";

      container session-id {
        description "Session ID commands";

        container space {
          description "Session ID space commands";
          leaf hierarchy {
            type empty;
            description "Session ID space hierarchical command";
          }
        }
      }
      leaf tcp-mss-adjust {
        type uint32 {
          range "1280..1460";
        }
        description
          "TCP MSS adjust value. The acceptable values
          might be further limited depending on platform.";
      }
      leaf reassembly {
        type empty;
        description "L2TP IP packet reassembly enable";
      }
    }
    leaf session-limit {
      type uint32 {
        range "1..131072";
      }
      description "Maximum simultaneous VPDN sessions";
    }
    leaf enable {
      type empty;
      description
        "Enable VPDN configuration. Deletion of this
        object also causes deletion of all associated
        objects under VPDN.";
    }
    leaf soft-shut {
      type empty;
      description "New session no longer allowed";
    }
  }
}
