submodule Cisco-IOS-XR-mpls-oam-oper-sub1 {

  belongs-to Cisco-IOS-XR-mpls-oam-oper {
    prefix Cisco-IOS-XR-mpls-oam-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-oam package operational data.

     Copyright (c) 2013-2016 by Cisco Systems, Inc.
     All rights reserved.";

  revision "2015-11-09" {
    description
      "IOS XR 6.0 revision.";
  }

  typedef Lspv-bag-interface-state {
    type enumeration {
      enum not-ready {
        description "Not ready";
      }
      enum admin-down {
        description "Admin down";
      }
      enum down {
        description "Down";
      }
      enum up {
        description "UP";
      }
      enum shutdown {
        description "Shutdown";
      }
      enum error-disable {
        description "Error disable";
      }
      enum down-immediate {
        description "Immediate down";
      }
      enum admin-immediate {
        description "Immediate admin";
      }
      enum graceful-down {
        description "Graceful down";
      }
      enum begin-shutdown {
        description "Begin shutdown";
      }
      enum end-shutdown {
        description "End shutdown";
      }
      enum begin-error-disable {
        description "Begin error disable";
      }
      enum end-error-disable {
        description "End error disable";
      }
      enum begin-graceful-down {
        description "Begin graceful down";
      }
      enum reset {
        description "Reset";
      }
      enum operational {
        description "Operational";
      }
      enum not-operational {
        description "Not operational";
      }
      enum not-known {
        description "Unknown";
      }
    }
    description "LSPV interface state";
  }

  grouping LSPV-COLLAB-COUNTER {
    description "LSPV collaborator counters";
    leaf ups {
      type uint32;
      description "Collaborator up counter";
    }
    leaf downs {
      type uint32;
      description "Collaborator down counter";
    }
  }

  grouping LSPV-COLLAB-STATISTICS {
    description "LSPV collaborator statistics";

    container collaborator-i-parm {
      description "Collaborator IPARM counts";
      uses LSPV-COLLAB-COUNTER;
    }

    container collaborator-im {
      description "Collaborator IM counts";
      uses LSPV-COLLAB-COUNTER;
    }

    container collaborator-net-io {
      description "Collaborator NetIO counts";
      uses LSPV-COLLAB-COUNTER;
    }

    container collaborator-rib {
      description "Collaborator RIB counts";
      uses LSPV-COLLAB-COUNTER;
    }
  }

  grouping LSPV-MSG-STATISTICS {
    description "LSPV verification process message statistics";
    leaf register-messages {
      type uint32;
      description "Message register count";
    }
    leaf unregister-messages {
      type uint32;
      description "Message unregister count";
    }
    leaf echo-submit-messages {
      type uint32;
      description "Message echo submit count";
    }
    leaf echo-cancel-messages {
      type uint32;
      description "Message echo cancel count";
    }
    leaf get-result-messages {
      type uint32;
      description "Message get results count";
    }
    leaf get-config-messages {
      type uint32;
      description "Message get configiuration count";
    }
    leaf get-response-messages {
      type uint32;
      description "Message get response count";
    }
    leaf property-response-messages {
      type uint32;
      description "Message property response count";
    }
    leaf property-request-messages {
      type uint32;
      description "Message property request count";
    }
    leaf property-block-messages {
      type uint32;
      description "Message property block count";
    }
    leaf thread-request-messages {
      type uint32;
      description "Message thread request count";
    }
  }

  grouping LSPV-GLOBAL-TYPE {
    description "LSPV global information";

    container message-statistics {
      description "Message statistics";
      uses LSPV-MSG-STATISTICS;
    }

    container collaborator-statistics {
      description "Collaborator statistics";
      uses LSPV-COLLAB-STATISTICS;
    }
    leaf total-clients {
      type uint32;
      description "Number of clients";
    }
  }

  grouping LSPV-BAG-STATS-TX {
    description "LSPV transmission statistics";

    container transmit-good {
      description "Transmit good packets";
      uses LSPV-PKT-COUNTER;
    }

    container transmit-drop {
      description "Transmit drop packets";
      uses LSPV-PKT-COUNTER;
    }

    container transmit-bfd-good {
      description "Transmit good BFD request packets";
      uses LSPV-PKT-COUNTER;
    }

    container bfd-no-reply {
      description
        "No Reply action for echo reqeust of BFD
        bootstrap";
      uses LSPV-PKT-COUNTER;
    }
  }

  grouping LSPV-PKT-COUNTER {
    description "LSPV verification packet count";
    leaf packets {
      type uint64;
      description "Packet counter";
    }
    leaf bytes {
      type uint64;
      units "byte";
      description "Byte counter";
    }
  }

  grouping LSPV-BAG-STATS-RX {
    description "LSPV reception statistics";

    container received-good-request {
      description "Received good request";
      uses LSPV-PKT-COUNTER;
    }

    container received-good-reply {
      description "Received good reply";
      uses LSPV-PKT-COUNTER;
    }

    container received-unknown {
      description "Received unknown packets";
      uses LSPV-PKT-COUNTER;
    }

    container received-error-ip-header {
      description "IP header error";
      uses LSPV-PKT-COUNTER;
    }

    container received-error-udp-header {
      description "UDP header error";
      uses LSPV-PKT-COUNTER;
    }

    container received-error-runt {
      description "RUNT error";
      uses LSPV-PKT-COUNTER;
    }

    container received-error-queue-full {
      description "Dropped queue full";
      uses LSPV-PKT-COUNTER;
    }

    container received-error-general {
      description "General error";
      uses LSPV-PKT-COUNTER;
    }

    container received-error-no-interface {
      description "Error no Interfaces";
      uses LSPV-PKT-COUNTER;
    }

    container received-error-no-memory {
      description "Error no memory";
      uses LSPV-PKT-COUNTER;
    }

    container protect-protocol-received-good-request {
      description "Protect Protocol Received good request";
      uses LSPV-PKT-COUNTER;
    }

    container protect-protocol-received-good-reply {
      description "Protect Protocol Received good reply";
      uses LSPV-PKT-COUNTER;
    }

    container received-good-bfd-request {
      description "Received Reqeust with BFD TLV";
      uses LSPV-PKT-COUNTER;
    }

    container received-good-bfd-reply {
      description "Received Reply with BFD TLV";
      uses LSPV-PKT-COUNTER;
    }
  }

  grouping LSPV-PACKET-STATISTICS {
    description "Receive and transmit packet counts";

    container received {
      description "Packet reception counts";
      uses LSPV-BAG-STATS-RX;
    }

    container sent {
      description "Packet transmit counts";
      uses LSPV-BAG-STATS-TX;
    }

    container working-req-sent {
      description "Working Request Packet transmit counts";
      uses LSPV-BAG-STATS-TX;
    }

    container working-rep-sent {
      description "Working Reply Packet transmit counts";
      uses LSPV-BAG-STATS-TX;
    }

    container protect-req-sent {
      description "Protect Request Packet transmit counts";
      uses LSPV-BAG-STATS-TX;
    }

    container protect-rep-sent {
      description "Protect Reply Packet transmit counts";
      uses LSPV-BAG-STATS-TX;
    }
  }

  grouping LSPV-INTERFACE-INFO {
    description "LSPV interface information";

    container interface-brief {
      description "Interface brief";
      uses LSPV-INTERFACE-INFO-BRIEF;
    }

    container packet-statistics {
      description "Packet statistics";
      uses LSPV-PACKET-STATISTICS;
    }
  }

  grouping LSPV-INTERFACE-INFO-BRIEF {
    description "LSPV interface brief information";
    leaf interface-name-xr {
      type xr:Interface-name;
      description "Interface name";
    }
    leaf state {
      type Lspv-bag-interface-state;
      description "Interface state";
    }
    leaf mtu {
      type uint32;
      description "Interface MTU";
    }
    leaf prefix-length {
      type uint32;
      description "Prefix length (IPv4)";
    }
    leaf prefix-length-v6 {
      type uint32;
      description "Prefix length (IPv6)";
    }
    leaf primary-address {
      type inet:ipv4-address;
      description "Primary interface address (IPv4)";
    }
    leaf primary-address-v6 {
      type inet:ipv6-address;
      description "Primary interface address (IPv6)";
    }
  }
}
