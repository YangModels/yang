submodule Cisco-IOS-XR-ipv6-ma-oper-sub1 {

  belongs-to Cisco-IOS-XR-ipv6-ma-oper {
    prefix Cisco-IOS-XR-ipv6-ma-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-ma package operational data.

     Copyright (c) 2013-2016 by Cisco Systems, Inc.
     All rights reserved.";

  revision "2015-10-20" {
    description
      "IPV6 MA schema file has all the latest changes.";
  }

  revision "2015-01-07" {
    description
      "IOS XR 5.3.1 revision.";
  }

  typedef Str {
    type string;
    description "Str";
  }
  typedef Ipv6-ma-oper-state {
    type enumeration {
      enum oper-up {
        value 1;
        description "Interface oper state is up";
      }
      enum oper-down {
        value 2;
        description "Interface oper state is down";
      }
    }
    description "Interface oper states";
  }
  typedef Ipv6-ma-if-addr-state {
    type enumeration {
      enum active {
        value 1;
        description
          "This is an active address that can appear as
          the destination or source address of a packet";
      }
      enum deprecated {
        value 2;
        description
          "This is a valid but deprecated address that
          should no longer be used as a source address in
          new communications";
      }
      enum duplicate {
        value 3;
        description
          "This is a duplicate (invalid) address because
          of conflict";
      }
      enum inaccessible {
        value 4;
        description
          "This is not accessible because the interface to
          which this address is assigned is not
          operational";
      }
      enum tentative {
        value 5;
        description "Status can not be determined for some reason";
      }
    }
    description "Interface address states";
  }
  typedef Ipv6-ma-if-line-state {
    type enumeration {
      enum down {
        value 1;
        description "Interface state is down";
      }
      enum up {
        value 2;
        description "Interface state is up";
      }
      enum unknown {
        value 3;
        description "Interface state is unknown";
      }
      enum error {
        value 4;
        description "Interface state is incorrect";
      }
    }
    description "Interface line states";
  }

  grouping IF-SUMMARY {
    description "Count of assigned/unnumbered interfaces";
    leaf ip-assigned {
      type uint32;
      description "Number of interfaces with explicit addresses";
    }
    leaf ip-unnumbered {
      type uint32;
      description
        "Number of unnumbered interfaces with explicit
        addresses";
    }
    leaf ip-unassigned {
      type uint32;
      description
        "Number of unassigned interfaces without explicit
        address";
    }
  }

  grouping IPV6-IF-SUMMARY {
    description "Summary info of IPv6 interfaces";

    container if-up-up {
      description "Number of interfaces (up,up)";
      uses IF-SUMMARY;
    }

    container if-up-down {
      description "Number of interfaces (up,down)";
      uses IF-SUMMARY;
    }

    container if-down-down {
      description "Number of interfaces (down,down)";
      uses IF-SUMMARY;
    }

    container if-shutdown-down {
      description "Number of interfaces (shutdown,down)";
      uses IF-SUMMARY;
    }
    leaf if-up-down-basecaps-up {
      type uint32;
      description "Number of interfaces (up,down) with basecaps up";
    }
  }

  grouping TIMEVAL-ENTRY {
    description "Creatation or Update Time";
  }

  grouping BGP-PA-DIR {
    description "BGP PA config for ingress/egress direction";
    leaf enable {
      type uint32;
      description "Enable BGP PA for ingress/egress";
    }
    leaf source {
      type boolean;
      description "Enable source accouting";
    }
    leaf destination {
      type boolean;
      description "Enable destination accouting";
    }
  }

  grouping BGP-PA-CONFIG {
    description "BGP PA config information";

    container input {
      description "BGP PA input config";
      uses BGP-PA-DIR;
    }

    container output {
      description "BGP PA output config";
      uses BGP-PA-DIR;
    }
  }

  grouping RPF-CONFIG {
    description "RPF config information";
    leaf enable {
      type boolean;
      description "Enable RPF config";
    }
    leaf allow-default-route {
      type boolean;
      description "Allow Default Route";
    }
    leaf allow-self-ping {
      type boolean;
      description "Allow Self Ping";
    }
    leaf mode {
      type uint32;
      description "RPF Mode (loose/strict)";
    }
  }

  grouping IPV6-MULTI-ACL-CONFIG {
    description "IPV6 MULTI ACL CONFIG";
    leaf-list inbound {
      type Str;
      max-elements "5";
      description "Inbound ACLs";
    }
    leaf-list outbound {
      type Str;
      max-elements "5";
      description "Outbound ACLs";
    }
    leaf-list common {
      type Str;
      max-elements "5";
      description "Common ACLs";
    }
  }

  grouping IPV6-ACL-CONFIG {
    description "IPV6 ACL CONFIG";
    leaf in-bound {
      type string;
      description "ACL applied to incoming packets";
    }
    leaf out-bound {
      type string;
      description "ACL applied to outgoing packets";
    }
    leaf common-in-bound {
      type string;
      description "Common ACL applied to incoming packets";
    }
    leaf common-out-bound {
      type string;
      description "Common ACL applied to outgoing packets";
    }
  }

  grouping IPV6-MCAST-GROUP {
    description "MCast Group ";
    leaf address {
      type inet:ipv6-address;
      description "IPv6 Address of Multicast Group";
    }
  }

  grouping IPV6-IF-DETAIL {
    description "Detailed Info of IPv6 Interface";

    container link-local-address {
      description "Link Local Address";
      uses IPV6-ADDR-NODE;
    }

    container access-control-list {
      description "IPv6 Access Control List";
      uses IPV6-ACL-CONFIG;
    }

    container multi-access-control-list {
      description "Multi IPv6 Access Control List";
      uses IPV6-MULTI-ACL-CONFIG;
    }

    container rpf {
      description "RPF config on the interface";
      uses RPF-CONFIG;
    }

    container bgp-pa {
      description "BGP PA config on the interface";
      uses BGP-PA-CONFIG;
    }

    container utime {
      description "Address Publish Time";
      uses TIMEVAL-ENTRY;
    }

    container idb-utime {
      description "IDB Create Time";
      uses TIMEVAL-ENTRY;
    }

    container caps-utime {
      description "CAPS Add Time";
      uses TIMEVAL-ENTRY;
    }

    container fwd-en-utime {
      description "FWD ENABLE Time";
      uses TIMEVAL-ENTRY;
    }

    container fwd-dis-utime {
      description "FWD DISABLE Time";
      uses TIMEVAL-ENTRY;
    }
    leaf line-state {
      type Ipv6-ma-if-line-state;
      description "State of Interface Line";
    }
    leaf mtu {
      type uint32;
      description "IPv6 MTU";
    }
    leaf operation-state {
      type Ipv6-ma-oper-state;
      description "IPv6 Operation State";
    }
    leaf vrf-name {
      type string {
        length "0..32";
      }
      description "VRF Name";
    }
    leaf is-icmp-unreach-enabled {
      type boolean;
      description "ICMP unreach Enable";
    }
    leaf rg-id-exists {
      type boolean;
      description "Does ICCP RG ID exist on the interface?";
    }
    leaf mlacp-active {
      type boolean;
      description "Is mLACP state Active (valid if RG ID exists)";
    }
    leaf flow-tag-src {
      type boolean;
      description "Is BGP Flow Tag Source is enable";
    }
    leaf flow-tag-dst {
      type boolean;
      description "Is BGP Flow Tag Destination is enable";
    }

    list multicast-group {
      description "IPv6 Multicast Group";
      uses IPV6-MCAST-GROUP;
    }

    list address {
      description "Address List";
      uses IPV6-ADDR-NODE;
    }

    list client-multicast-group {
      description "IPv6 Client Multicast Group";
      uses IPV6-MCAST-GROUP;
    }
  }

  grouping IPV6-ADDR-NODE {
    description "List of IPv6 Addresses ";
    leaf address {
      type inet:ipv6-address;
      description "IPv6 Address";
    }
    leaf prefix-length {
      type uint32;
      description "Prefix Length of IPv6 Address";
    }
    leaf address-state {
      type Ipv6-ma-if-addr-state;
      description "State of Address";
    }
    leaf is-anycast {
      type boolean;
      description "Anycast address";
    }
    leaf route-tag {
      type uint32;
      description "Route-tag of the Address";
    }
  }

  grouping IPV6-IF-BRIEF {
    description "Brief Summary of IPv6 Interface";

    container link-local-address {
      description "Link Local Address";
      uses IPV6-ADDR-NODE;
    }
    leaf line-state {
      type Ipv6-ma-if-line-state;
      description "State of Interface Line";
    }
    leaf vrf-name {
      type string {
        length "0..32";
      }
      description "VRF Name";
    }

    list address {
      description "Address List";
      uses IPV6-ADDR-NODE;
    }
  }
}
