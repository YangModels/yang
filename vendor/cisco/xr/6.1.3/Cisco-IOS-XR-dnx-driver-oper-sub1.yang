submodule Cisco-IOS-XR-dnx-driver-oper-sub1 {

  belongs-to Cisco-IOS-XR-dnx-driver-oper {
    prefix Cisco-IOS-XR-dnx-driver-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-driver package operational data.

     Copyright (c) 2013-2016 by Cisco Systems, Inc.
     All rights reserved.";

  revision "2015-11-09" {
    description
      "IOS XR 6.0 revision.";
  }

  typedef Asic-init-method {
    type enumeration {
      enum asic-init-method-unset {
        value -1;
        description "asic init method unset";
      }
      enum asic-init-method-no-reset {
        value 0;
        description "asic init method no reset";
      }
      enum asic-init-method-pon-reset {
        value 1;
        description "asic init method pon reset";
      }
      enum asic-init-method-pon-reset-on-intr {
        value 2;
        description "asic init method pon reset on intr";
      }
      enum asic-init-method-hard-reset {
        value 3;
        description "asic init method hard reset";
      }
      enum asic-init-method-warmboot {
        value 4;
        description "asic init method warmboot";
      }
      enum asic-init-method-issu-wb {
        value 5;
        description "asic init method issu wb";
      }
      enum asic-init-method-pci-shutdown {
        value 6;
        description "asic init method pci shutdown";
      }
      enum asic-init-method-quiesce {
        value 7;
        description "asic init method quiesce";
      }
      enum asic-init-method-issu-started {
        value 8;
        description "asic init method issu started";
      }
      enum asic-init-method-issu-rollback {
        value 9;
        description "asic init method issu rollback";
      }
      enum asic-init-method-issu-abort {
        value 10;
        description "asic init method issu abort";
      }
      enum asic-init-method-slice-cleanup {
        value 11;
        description "asic init method slice cleanup";
      }
      enum asic-init-method-lc-remove {
        value 12;
        description "asic init method lc remove";
      }
      enum asic-init-method-node-down {
        value 13;
        description "asic init method node down";
      }
      enum asic-init-method-intr {
        value 14;
        description "asic init method intr";
      }
      enum asic-init-method-board-reload {
        value 15;
        description "asic init method board reload";
      }
      enum asic-init-method-max {
        value 16;
        description "asic init method max";
      }
    }
    description "Asic init method";
  }
  typedef Asic-access-state {
    type enumeration {
      enum asic-state-unset {
        value -1;
        description "asic state unset";
      }
      enum asic-state-none {
        value 0;
        description "asic state none";
      }
      enum asic-state-device-off-line {
        value 1;
        description "asic state device off line";
      }
      enum asic-state-device-created {
        value 2;
        description "asic state device created";
      }
      enum asic-state-device-online {
        value 3;
        description "asic state device online";
      }
      enum asic-state-warmboot {
        value 4;
        description "asic state warmboot";
      }
      enum asic-state-de-init-start {
        value 5;
        description "asic state de init start";
      }
      enum asic-state-intr-de-init {
        value 6;
        description "asic state intr de init";
      }
      enum asic-state-bcm-detach {
        value 7;
        description "asic state bcm detach";
      }
      enum asic-state-soc-de-init {
        value 8;
        description "asic state soc de init";
      }
      enum asic-state-de-init-done {
        value 9;
        description "asic state de init done";
      }
      enum asic-state-soc-init {
        value 10;
        description "asic state soc init";
      }
      enum asic-state-bcm-init {
        value 11;
        description "asic state bcm init";
      }
      enum asic-state-intr-init {
        value 12;
        description "asic state intr init";
      }
      enum asic-state-soc-init-start {
        value 13;
        description "asic state soc init start";
      }
      enum asic-state-bcm-init-start {
        value 14;
        description "asic state bcm init start";
      }
      enum asic-state-intr-init-start {
        value 15;
        description "asic state intr init start";
      }
      enum asic-state-hard-reset {
        value 16;
        description "asic state hard reset";
      }
      enum asic-state-normal {
        value 17;
        description "asic state normal";
      }
      enum asic-state-exception {
        value 18;
        description "asic state exception";
      }
      enum asic-state-hp-attached {
        value 19;
        description "asic state hp attached";
      }
      enum asic-state-quiesce {
        value 20;
        description "asic state quiesce";
      }
      enum asic-state-issu-started {
        value 21;
        description "asic state issu started";
      }
      enum asic-state-issu-started-nn {
        value 22;
        description "asic state issu started nn";
      }
      enum asic-state-issu-abort {
        value 23;
        description "asic state issu abort";
      }
      enum asic-state-max {
        value 24;
        description "asic state max";
      }
    }
    description "Asic access state";
  }
  typedef Asic-oper-state {
    type enumeration {
      enum asic-oper-unset {
        value -1;
        description "asic oper unset";
      }
      enum asic-oper-unknown {
        value 0;
        description "asic oper unknown";
      }
      enum asic-oper-up {
        value 1;
        description "asic oper up";
      }
      enum asic-oper-down {
        value 2;
        description "asic oper down";
      }
      enum asic-card-down {
        value 3;
        description "asic card down";
      }
    }
    description "Asic oper state";
  }
  typedef Slice-state {
    type enumeration {
      enum slice-oper-unset {
        value -1;
        description "slice oper unset";
      }
      enum slice-oper-down {
        value 0;
        description "slice oper down";
      }
      enum slice-oper-up {
        value 1;
        description "slice oper up";
      }
      enum slice-oper-na {
        value 2;
        description "slice oper na";
      }
    }
    description "Slice state";
  }
  typedef Fc-mode {
    type enumeration {
      enum fc-mode-unset {
        value -1;
        description "fc mode unset";
      }
      enum fc-mode-unavail {
        value 0;
        description "fc mode unavail";
      }
      enum fc-mode-inband {
        value 1;
        description "fc mode inband";
      }
      enum fc-mode-oob {
        value 2;
        description "fc mode oob";
      }
    }
    description "Fc mode";
  }
  typedef Link-error-state {
    type enumeration {
      enum link-error-unset {
        value -1;
        description "link error unset";
      }
      enum link-error-none {
        value 0;
        description "link error none";
      }
      enum link-error-shut {
        value 1;
        description "link error shut";
      }
      enum link-error-max {
        value 2;
        description "link error max";
      }
    }
    description "Link error state";
  }
  typedef Oper-state {
    type enumeration {
      enum oper-unset {
        value -1;
        description "oper unset";
      }
      enum oper-unknown {
        value 0;
        description "oper unknown";
      }
      enum oper-up {
        value 1;
        description "oper up";
      }
      enum oper-down {
        value 2;
        description "oper down";
      }
      enum card-down {
        value 3;
        description "card down";
      }
    }
    description "Oper state";
  }
  typedef Admin-state {
    type enumeration {
      enum admin-unset {
        value -1;
        description "admin unset";
      }
      enum admin-up {
        value 0;
        description "admin up";
      }
      enum admin-down {
        value 1;
        description "admin down";
      }
    }
    description "Admin state";
  }
  typedef Link-stage {
    type enumeration {
      enum link-stage-unset {
        value -1;
        description "link stage unset";
      }
      enum link-stage-unused {
        value 0;
        description "link stage unused";
      }
      enum link-stage-fia {
        value 1;
        description "link stage fia";
      }
      enum link-stage-s1 {
        value 2;
        description "link stage s1";
      }
      enum link-stage-s2 {
        value 3;
        description "link stage s2";
      }
      enum link-stage-s3 {
        value 4;
        description "link stage s3";
      }
      enum link-stage-unknown {
        value 5;
        description "link stage unknown";
      }
    }
    description "Link stage";
  }
  typedef Link {
    type enumeration {
      enum link-type-unset {
        value -1;
        description "link type unset";
      }
      enum link-type-unavail {
        value 0;
        description "link type unavail";
      }
      enum link-type-tx {
        value 1;
        description "link type tx";
      }
      enum link-type-rx {
        value 2;
        description "link type rx";
      }
    }
    description "Link";
  }
  typedef Asic {
    type enumeration {
      enum asic-unset {
        value -1;
        description "asic unset";
      }
      enum asic-unavail {
        value 0;
        description "asic unavail";
      }
      enum asic-fia {
        value 1;
        description "asic fia";
      }
      enum asic-s123 {
        value 2;
        description "asic s123";
      }
      enum asic-s13 {
        value 3;
        description "asic s13";
      }
      enum asic-s2 {
        value 4;
        description "asic s2";
      }
      enum asic-b2b {
        value 5;
        description "asic b2b";
      }
      enum asic-unknown {
        value 6;
        description "asic unknown";
      }
    }
    description "Asic";
  }
  typedef Rack {
    type enumeration {
      enum rack-type-unset {
        value -1;
        description "rack type unset";
      }
      enum rack-type-lcc {
        value 0;
        description "rack type lcc";
      }
      enum rack-type-fcc {
        value 1;
        description "rack type fcc";
      }
    }
    description "Rack";
  }

  grouping FIA-EDM-LINK-OVF-COUNTERS {
    description "FIA EDM LINK OVF COUNTERS";
    leaf tx-control-cells-counter {
      type string {
        length "0..6";
      }
      description "TX Control cells counter";
    }
    leaf tx-data-cell-counter {
      type string {
        length "0..6";
      }
      description "TX Data cell counter";
    }
    leaf tx-data-byte-counter {
      type string {
        length "0..6";
      }
      description "TX Data byte counter";
    }
    leaf rx-crc-errors-counter {
      type string {
        length "0..6";
      }
      description "RX CRC errors counter";
    }
    leaf rx-lfec-fec-correctable-error {
      type string {
        length "0..6";
      }
      description "RX LFEC FEC correctable error";
    }
    leaf rx-8b-10b-disparity-errors {
      type string {
        length "0..6";
      }
      description "RX 8b 10b disparity errors";
    }
    leaf rx-control-cells-counter {
      type string {
        length "0..6";
      }
      description "RX Control cells counter";
    }
    leaf rx-data-cell-counter {
      type string {
        length "0..6";
      }
      description "RX Data cell counter";
    }
    leaf rx-data-byte-counter {
      type string {
        length "0..6";
      }
      description "RX Data byte counter";
    }
    leaf rx-dropped-retransmitted-control {
      type string {
        length "0..6";
      }
      description "RX dropped retransmitted control";
    }
    leaf tx-asyn-fifo-rate {
      type string {
        length "0..6";
      }
      description "TX Asyn fifo rate";
    }
    leaf rx-asyn-fifo-rate {
      type string {
        length "0..6";
      }
      description "RX Asyn fifo rate";
    }
    leaf rx-lfec-fec-uncorrectable-errors {
      type string {
        length "0..6";
      }
      description "RX LFEC FEC uncorrectable errors";
    }
    leaf rx-8b-10b-code-errors {
      type string {
        length "0..6";
      }
      description "RX 8b 10b code errors";
    }
  }

  grouping FIA-EDM-LINK-COUNTERS {
    description "FIA EDM LINK COUNTERS";
    leaf tx-control-cells-counter {
      type uint64;
      description "TX Control cells counter";
    }
    leaf tx-data-cell-counter {
      type uint64;
      description "TX Data cell counter";
    }
    leaf tx-data-byte-counter {
      type uint64;
      description "TX Data byte counter";
    }
    leaf rx-crc-errors-counter {
      type uint64;
      description "RX CRC errors counter";
    }
    leaf rx-lfec-fec-correctable-error {
      type uint64;
      description "RX LFEC FEC correctable error";
    }
    leaf rx-8b-10b-disparity-errors {
      type uint64;
      description "RX 8b 10b disparity errors";
    }
    leaf rx-control-cells-counter {
      type uint64;
      description "RX Control cells counter";
    }
    leaf rx-data-cell-counter {
      type uint64;
      description "RX Data cell counter";
    }
    leaf rx-data-byte-counter {
      type uint64;
      description "RX Data byte counter";
    }
    leaf rx-dropped-retransmitted-control {
      type uint64;
      description "RX dropped retransmitted control";
    }
    leaf tx-asyn-fifo-rate {
      type uint64;
      description "TX Asyn fifo rate";
    }
    leaf rx-asyn-fifo-rate {
      type uint64;
      description "RX Asyn fifo rate";
    }
    leaf rx-lfec-fec-uncorrectable-errors {
      type uint64;
      description "RX LFEC FEC uncorrectable errors";
    }
    leaf rx-8b-10b-code-errors {
      type uint64;
      description "RX 8b 10b code errors";
    }
  }

  grouping FIA-EDM-LINK-ERROR-STATUS {
    description "FIA EDM LINK ERROR STATUS";
    leaf link-crc-error {
      type uint32;
      description "link crc error";
    }
    leaf link-size-error {
      type uint32;
      description "link size error";
    }
    leaf link-mis-align-error {
      type uint32;
      description "link mis align error";
    }
    leaf link-code-group-error {
      type uint32;
      description "link code group error";
    }
    leaf link-no-sig-lock-error {
      type uint32;
      description "link no sig lock error";
    }
    leaf link-no-sig-accept-error {
      type uint32;
      description "link no sig accept error";
    }
    leaf link-tokens-error {
      type uint32;
      description "link tokens error";
    }
    leaf error-token-count {
      type uint32;
      description "error token count";
    }
  }

  grouping FIA-EDM-STATS-ASIC-FMAC {
    description "FIA EDM STATS ASIC FMAC";

    container link-error-status {
      description "link error status";
      uses FIA-EDM-LINK-ERROR-STATUS;
    }

    container link-counters {
      description "link counters";
      uses FIA-EDM-LINK-COUNTERS;
    }

    container ovf-status {
      description "ovf status";
      uses FIA-EDM-LINK-OVF-COUNTERS;
    }
  }

  grouping FIA-EDM-STATS-ASIC-FMAC-INFO {
    description "FIA EDM STATS ASIC FMAC INFO";

    container aggr-stats {
      description "aggr stats";
      uses FIA-EDM-STATS-ASIC-FMAC;
    }

    container incr-stats {
      description "incr stats";
      uses FIA-EDM-STATS-ASIC-FMAC;
    }
    leaf valid {
      type boolean;
      description "valid";
    }
    leaf rack-no {
      type uint32;
      description "rack no";
    }
    leaf slot-no {
      type uint32;
      description "slot no";
    }
    leaf asic-instance {
      type uint32;
      description "asic instance";
    }
    leaf link-no {
      type uint32;
      description "link no";
    }
    leaf link-valid {
      type boolean;
      description "link valid";
    }
  }

  grouping FIA-EDM-DEVICE-STATS-FIELD-INFO {
    description "FIA EDM DEVICE STATS FIELD INFO";
    leaf field-name {
      type string {
        length "0..51";
      }
      description "Field Name";
    }
    leaf field-value {
      type uint64;
      description "Field Value";
    }
    leaf is-ovf {
      type boolean;
      description "Is Ovf";
    }
  }

  grouping FIA-EDM-DEVICE-STATS-BLK-INFO {
    description "FIA EDM DEVICE STATS BLK INFO";
    leaf block-name {
      type string {
        length "0..11";
      }
      description "Block Name";
    }
    leaf num-fields {
      type uint8;
      description "Num Fields";
    }

    list field-info {
      max-elements "200";
      description "field info";
      uses FIA-EDM-DEVICE-STATS-FIELD-INFO;
    }
  }

  grouping FIA-EDM-DEVICE-STATS-ASIC-INFO {
    description "FIA EDM DEVICE STATS ASIC INFO";
    leaf num-blocks {
      type uint8;
      description "Num Blocks";
    }

    list block-info {
      max-elements "15";
      description "block info";
      uses FIA-EDM-DEVICE-STATS-BLK-INFO;
    }
  }

  grouping FIA-EDM-STATS-INFO {
    description "FIA EDM STATS INFO";

    container stats-info {
      description "stats info";
      uses FIA-EDM-DEVICE-STATS-ASIC-INFO;
    }
    leaf valid {
      type boolean;
      description "valid";
    }
    leaf rack-no {
      type uint32;
      description "rack no";
    }
    leaf slot-no {
      type uint32;
      description "slot no";
    }
    leaf asic-instance {
      type uint32;
      description "asic instance";
    }
    leaf chip-ver {
      type uint16;
      description "chip ver";
    }
  }

  grouping FIA-EDM-DIAG-SHELL-OUTPUT {
    description "FIA EDM DIAG SHELL OUTPUT";
    leaf output-xr {
      type string;
      description "output xr";
    }
  }

  grouping FIA-EDM-REG-INFO {
    description "FIA EDM REG INFO";
    leaf output {
      type string;
      description "output";
    }
  }

  grouping FIA-EDM-TXLINK-STATS {
    description "FIA EDM TXLINK STATS";
    leaf dummy {
      type uint32;
      description "dummy";
    }
  }

  grouping FIA-EDM-TXLINK {
    description "FIA EDM TXLINK";

    container this-link {
      description "this link";
      uses FIA-EDM-LINK-IDENTITY;
    }

    container far-end-link {
      description "far end link";
      uses FIA-EDM-LINK-IDENTITY;
    }

    container stats {
      description "stats";
      uses FIA-EDM-TXLINK-STATS;
    }

    container history {
      description "history";
      uses FIA-EDM-HISTORY;
    }
    leaf speed {
      type uint32;
      description "speed";
    }
    leaf stage {
      type uint8;
      description "stage";
    }
    leaf is-link-valid {
      type boolean;
      description "is link valid";
    }
    leaf is-conf-pending {
      type boolean;
      description "is conf pending";
    }
    leaf is-power-enabled {
      type boolean;
      description "is power enabled";
    }
    leaf coeff1 {
      type uint32;
      description "coeff1";
    }
    leaf coeff2 {
      type uint32;
      description "coeff2";
    }
    leaf admin-state {
      type Admin-state;
      description "Admin State";
    }
    leaf oper-state {
      type Oper-state;
      description "Oper State";
    }
    leaf error-state {
      type Link-error-state;
      description "Error State";
    }
    leaf num-admin-shuts {
      type uint32;
      description "num admin shuts";
    }
  }

  grouping FIA-EDM-OIR-HISTORY {
    description "FIA EDM OIR HISTORY";
    leaf card-flag {
      type int32;
      description "card flag";
    }
    leaf card-type {
      type int32;
      description "card type";
    }
    leaf reg-flag {
      type int32;
      description "reg flag";
    }
    leaf evt-flag {
      type int32;
      description "evt flag";
    }
    leaf rack-num {
      type int32;
      description "rack num";
    }
    leaf instance {
      type int32;
      description "instance";
    }
    leaf cur-card-state {
      type int32;
      description "cur card state";
    }
  }

  grouping FIA-EDM-OIR-RECORD-CIRCULAR-BUFFER {
    description "FIA EDM OIR RECORD CIRCULAR BUFFER";
    leaf count {
      type int32;
      description "count";
    }
    leaf start {
      type int32;
      description "start";
    }
    leaf end {
      type int32;
      description "end";
    }

    list fia-oir-info {
      max-elements "10";
      description "fia oir info";
      uses FIA-EDM-OIR-HISTORY;
    }
  }

  grouping FIA-EDM-CARD-INFO {
    description "FIA EDM CARD INFO";

    container oir-circular-buffer {
      description "oir circular buffer";
      uses FIA-EDM-OIR-RECORD-CIRCULAR-BUFFER;
    }
    leaf card-type {
      type int32;
      description "card type";
    }
    leaf card-name {
      type string;
      description "card name";
    }
    leaf slot-no {
      type int32;
      description "slot no";
    }
    leaf card-flag {
      type int32;
      description "card flag";
    }
    leaf evt-flag {
      type int32;
      description "evt flag";
    }
    leaf reg-flag {
      type int32;
      description "reg flag";
    }
    leaf instance {
      type int32;
      description "instance";
    }
    leaf card-state {
      type uint8;
      description "card state";
    }
    leaf exp-num-asics {
      type uint32;
      description "exp num asics";
    }
    leaf exp-num-asics-per-fsdb {
      type uint32;
      description "exp num asics per fsdb";
    }
    leaf is-powered {
      type boolean;
      description "is powered";
    }
    leaf cxp-avail-bitmap {
      type uint64;
      description "cxp avail bitmap";
    }
    leaf num-ilkns-per-asic {
      type uint32;
      description "num ilkns per asic";
    }
    leaf num-local-ports-per-ilkn {
      type uint32;
      description "num local ports per ilkn";
    }
    leaf num-cos-per-port {
      type uint8;
      description "num cos per port";
    }
  }

  grouping FIA-EDM-DEVICE {
    description "FIA EDM DEVICE";

    container asic-id {
      description "asic id";
      uses FIA-EDM-ASIC-IDENTITY;
    }
    leaf is-valid {
      type boolean;
      description "is valid";
    }
    leaf fapid {
      type uint32;
      description "fapid";
    }
    leaf hotplug-event {
      type uint32;
      description "hotplug event";
    }
    leaf slice-state {
      type Slice-state;
      description "Slice State";
    }
    leaf admin-state {
      type Admin-state;
      description "Admin State";
    }
    leaf oper-state {
      type Asic-oper-state;
      description "Oper State";
    }
    leaf asic-state {
      type Asic-access-state;
      description "Asic State";
    }
    leaf last-init-cause {
      type Asic-init-method;
      description "last init cause";
    }
    leaf num-pon-resets {
      type uint32;
      description "num pon resets";
    }
    leaf num-hard-resets {
      type uint32;
      description "num hard resets";
    }
    leaf local-switch-state {
      type boolean;
      description "local switch state";
    }
  }

  grouping FIA-EDM-DRIVER-INFO {
    description "FIA EDM DRIVER INFO";
    leaf drv-version {
      type uint32;
      description "drv version";
    }
    leaf coeff-major-rev {
      type uint32;
      description "coeff major rev";
    }
    leaf coeff-minor-rev {
      type uint32;
      description "coeff minor rev";
    }
    leaf functional-role {
      type uint8;
      description "functional role";
    }
    leaf issu-role {
      type uint8;
      description "issu role";
    }
    leaf rack-name {
      type string;
      description "rack name";
    }
    leaf rack-type {
      type int32;
      description "rack type";
    }
    leaf rack-num {
      type uint8;
      description "rack num";
    }
    leaf is-driver-ready {
      type boolean;
      description "is driver ready";
    }
    leaf card-avail-mask {
      type uint32;
      description "card avail mask";
    }
    leaf asic-avail-mask {
      type uint64;
      description "asic avail mask";
    }
    leaf exp-asic-avail-mask {
      type uint64;
      description "exp asic avail mask";
    }
    leaf ucmc-ratio {
      type uint32;
      description "ucmc ratio";
    }
    leaf asic-oper-notify-to-fsdb-pending-bmap {
      type uint64;
      description "asic oper notify to fsdb pending bmap";
    }
    leaf is-full-fgid-download-req {
      type boolean;
      description "is full fgid download req";
    }
    leaf is-fgid-download-in-progress {
      type boolean;
      description "is fgid download in progress";
    }
    leaf is-fgid-download-completed {
      type boolean;
      description "is fgid download completed";
    }
    leaf fsdb-conn-active {
      type boolean;
      description "fsdb conn active";
    }
    leaf fgid-conn-active {
      type boolean;
      description "fgid conn active";
    }
    leaf issu-mgr-conn-active {
      type boolean;
      description "issu mgr conn active";
    }
    leaf fsdb-reg-active {
      type boolean;
      description "fsdb reg active";
    }
    leaf fgid-reg-active {
      type boolean;
      description "fgid reg active";
    }
    leaf issu-mgr-reg-active {
      type boolean;
      description "issu mgr reg active";
    }
    leaf num-pm-conn-reqs {
      type uint8;
      description "num pm conn reqs";
    }
    leaf num-fsdb-conn-reqs {
      type uint8;
      description "num fsdb conn reqs";
    }
    leaf num-fgid-conn-reqs {
      type uint8;
      description "num fgid conn reqs";
    }
    leaf num-fstats-conn-reqs {
      type uint8;
      description "num fstats conn reqs";
    }
    leaf num-cm-conn-reqs {
      type uint8;
      description "num cm conn reqs";
    }
    leaf num-issu-mgr-conn-reqs {
      type uint8;
      description "num issu mgr conn reqs";
    }
    leaf num-peer-fia-conn-reqs {
      type uint8;
      description "num peer fia conn reqs";
    }
    leaf is-gaspp-registered {
      type boolean;
      description "is gaspp registered";
    }
    leaf is-cih-registered {
      type boolean;
      description "is cih registered";
    }
    leaf drvr-initial-startup-timestamp {
      type string;
      description "drvr initial startup timestamp";
    }
    leaf drvr-current-startup-timestamp {
      type string;
      description "drvr current startup timestamp";
    }
    leaf num-intf-ports {
      type uint32;
      description "num intf ports";
    }
    leaf uc-weight {
      type uint8;
      description "uc weight";
    }
    leaf respawn-count {
      type uint8;
      description "respawn count";
    }
    leaf total-asics {
      type uint8;
      description "total asics";
    }
    leaf issu-ready-ntfy-pending {
      type boolean;
      description "issu ready ntfy pending";
    }
    leaf issu-abort-sent {
      type boolean;
      description "issu abort sent";
    }
    leaf issu-abort-rcvd {
      type boolean;
      description "issu abort rcvd";
    }
    leaf fc-mode {
      type Fc-mode;
      description "FC Mode";
    }
    leaf board-rev-id {
      type uint32;
      description "board rev id";
    }

    list device-info {
      max-elements "32";
      description "device info";
      uses FIA-EDM-DEVICE;
    }

    list card-info {
      max-elements "16";
      description "card info";
      uses FIA-EDM-CARD-INFO;
    }
  }

  grouping FIA-EDM-STATE-CHANGE {
    description "FIA EDM STATE CHANGE";
    leaf admin-state {
      type Admin-state;
      description "Admin State";
    }
    leaf oper-state {
      type Oper-state;
      description "Oper State";
    }
    leaf error-state {
      type Link-error-state;
      description "Error State";
    }
    leaf timestamp {
      type uint64;
      description "timestamp";
    }
    leaf reasons {
      type string;
      description "reasons";
    }
  }

  grouping FIA-EDM-HISTORY {
    description "FIA EDM HISTORY";
    leaf histnum {
      type uint8;
      description "histnum";
    }
    leaf start-index {
      type uint8;
      description "start index";
    }

    list hist {
      max-elements "5";
      description "hist";
      uses FIA-EDM-STATE-CHANGE;
    }
  }

  grouping FIA-EDM-ASIC-IDENTITY {
    description "FIA EDM ASIC IDENTITY";
    leaf rack-type {
      type Rack;
      description "Rack Type";
    }
    leaf asic-type {
      type Asic;
      description "Asic Type";
    }
    leaf rack-num {
      type uint32;
      description "rack num";
    }
    leaf slot-num {
      type uint32;
      description "slot num";
    }
    leaf asic-instance {
      type uint32;
      description "asic instance";
    }
  }

  grouping FIA-EDM-LINK-IDENTITY {
    description "FIA EDM LINK IDENTITY";

    container asic-id {
      description "asic id";
      uses FIA-EDM-ASIC-IDENTITY;
    }
    leaf link-type {
      type Link;
      description "Link Type";
    }
    leaf link-stage {
      type Link-stage;
      description "Link Stage";
    }
    leaf link-num {
      type uint32;
      description "link num";
    }
    leaf phy-link-num {
      type uint32;
      description "phy link num";
    }
  }

  grouping FIA-EDM-RXLINK {
    description "FIA EDM RXLINK";

    container this-link {
      description "this link";
      uses FIA-EDM-LINK-IDENTITY;
    }

    container far-end-link {
      description "far end link";
      uses FIA-EDM-LINK-IDENTITY;
    }

    container far-end-link-in-hw {
      description "far end link in hw";
      uses FIA-EDM-LINK-IDENTITY;
    }

    container history {
      description "history";
      uses FIA-EDM-HISTORY;
    }
    leaf speed {
      type uint32;
      description "speed";
    }
    leaf stage {
      type Link-stage;
      description "Stage";
    }
    leaf is-link-valid {
      type boolean;
      description "is link valid";
    }
    leaf is-conf-pending {
      type boolean;
      description "is conf pending";
    }
    leaf admin-state {
      type Admin-state;
      description "Admin State";
    }
    leaf oper-state {
      type Oper-state;
      description "Oper State";
    }
    leaf error-state {
      type Link-error-state;
      description "Error State";
    }
    leaf flags {
      type string;
      description "flags";
    }
    leaf flap-cnt {
      type uint32;
      description "flap cnt";
    }
    leaf num-admin-shuts {
      type uint32;
      description "num admin shuts";
    }
  }
}
