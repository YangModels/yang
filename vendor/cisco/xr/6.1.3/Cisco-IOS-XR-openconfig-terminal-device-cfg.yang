module Cisco-IOS-XR-openconfig-terminal-device-cfg {

  /*** NAMESPACE / PREFIX DEFINITION ***/

  namespace "http://cisco.com/ns/yang"+
    "/Cisco-IOS-XR-openconfig-terminal-device-cfg";


  prefix "openconfig-terminal-device-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR openconfig-terminal-device package configuration.

     This module contains definitions
     for the following management objects:
       logical-channels: Logical channel in mxp
       optical-channels: optical channels

     Copyright (c) 2013-2016 by Cisco Systems, Inc.
     All rights reserved.";

  revision "2015-11-09" {
    description
      "IOS XR 6.0 revision.";
  }

  typedef Logical-channel-otn-tti-auto {
    type enumeration {
      enum false {
        value 0;
        description "Otn tti auto mode false";
      }
      enum true {
        value 1;
        description "Otn tti auto mode true";
      }
    }
    description "Logical channel otn tti auto";
  }
  typedef Logical-admin-state {
    type enumeration {
      enum enable {
        value 1;
        description "Enable";
      }
      enum disable {
        value 2;
        description "Disable";
      }
      enum maintenance {
        value 3;
        description "Maintenance";
      }
    }
    description "Logical admin state";
  }
  typedef Logical-loopback-mode {
    type enumeration {
      enum none {
        value 1;
        description "None";
      }
      enum facility {
        value 2;
        description "Facility";
      }
      enum terminal {
        value 3;
        description "Terminal";
      }
    }
    description "Logical loopback mode";
  }
  typedef Logical-trib-rate {
    type enumeration {
      enum trib-rate1g {
        value 0;
        description "TribRate1G";
      }
      enum trib-rate2-5g {
        value 1;
        description "TribRate25G";
      }
      enum trib-rate10g {
        value 2;
        description "TribRate10G";
      }
      enum trib-rate40g {
        value 3;
        description "TribRate40G";
      }
      enum trib-rate100g {
        value 4;
        description "TribRate100G";
      }
    }
    description "Logical trib rate";
  }
  typedef Logical-trib-protocol {
    type enumeration {
      enum trib-proto-type1ge {
        value 1;
        description "1G Ethernet protocol";
      }
      enum trib-proto-type-oc48 {
        value 2;
        description "OC48 protocol";
      }
      enum trib-proto-type-stm16 {
        value 3;
        description "STM 16 protocol";
      }
      enum trib-proto-type10gelan {
        value 4;
        description "10G Ethernet LAN protocol";
      }
      enum trib-proto-type10gewan {
        value 5;
        description "10G Ethernet WAN protocol";
      }
      enum trib-proto-type-oc192 {
        value 6;
        description "OC 192 (9.6GB) port protocol";
      }
      enum trib-proto-type-stm64 {
        value 7;
        description "STM 64 protocol";
      }
      enum trib-proto-type-otu2 {
        value 8;
        description "OTU 2 protocol";
      }
      enum trib-proto-type-otu2e {
        value 9;
        description "OTU 2e protocol";
      }
      enum trib-proto-type-otu1e {
        value 10;
        description "OTU 1e protocol";
      }
      enum trib-proto-type-odu2 {
        value 11;
        description "ODU 2 protocol";
      }
      enum trib-proto-type-odu2e {
        value 12;
        description "ODU 2e protocol";
      }
      enum trib-proto-type40ge {
        value 13;
        description "40G Ethernet port protocol";
      }
      enum trib-proto-type-oc768 {
        value 14;
        description "OC 768 protocol";
      }
      enum trib-proto-type-stm256 {
        value 15;
        description "STM 256 protocol";
      }
      enum trib-proto-type-otu3 {
        value 16;
        description "OTU 3 protocol";
      }
      enum trib-proto-type-odu3 {
        value 17;
        description "ODU 3 protocol";
      }
      enum trib-proto-type100ge {
        value 18;
        description "100G Ethernet protocol";
      }
      enum trib-proto-type100g-mlg {
        value 19;
        description "100G MLG protocol";
      }
      enum trib-proto-type-otu4 {
        value 20;
        description
          "OTU4 signal protocol (112G) for transporting
          100GE signal";
      }
      enum trib-proto-type-otu-cn {
        value 21;
        description "OTU Cn protocol";
      }
      enum trib-proto-type-odu4 {
        value 22;
        description "ODU 4 protocol";
      }
    }
    description "Logical trib protocol";
  }
  typedef Logical-channel-assignment {
    type enumeration {
      enum type-logical-channel {
        value 1;
        description "Type Logical channel";
      }
      enum type-optical-channel {
        value 2;
        description "Type Optical channel";
      }
    }
    description "Logical channel assignment";
  }
  typedef Logical-protocol {
    type enumeration {
      enum type-ethernet {
        value 1;
        description "Type Ethernet";
      }
      enum type-otn {
        value 2;
        description "Type OTN";
      }
    }
    description "Logical protocol";
  }

  container logical-channels {
    description "Logical channel in mxp";

    list channel {
      key "channel-index";
      description "Logical channel index";

      container logical-channel-assignments {
        description
          "Logical channel assignment for logical channel";

        list logical-channel-assignment {
          key "assignment-index";
          description "Logical Channel Assignment id";
          leaf description {
            type string {
              length "0..255";
            }
            description "Configure description for this assignment";
          }
          leaf logical-channel-id {
            type int32;
            description
              "Configure logical channel for this assignment";
          }
          leaf assignment-type {
            type Logical-channel-assignment;
            description "Type of assignment for logical channel";
          }
          leaf allocation {
            type int32;
            description
              "Configure Allocation for this assignment(10,
              40 or 100G)";
          }
          leaf optical-channel-id {
            type string;
            description
              "Configure optical channel for this assignment";
          }
          leaf assignment-index {
            type int32;
            description "Logical channel assignment index";
          }
        }
      }

      container otn {
        description "Otn Related configs for Logical channel";
        leaf tti-msg-auto {
          type Logical-channel-otn-tti-auto;
          description
            "Trail trace identifier (TTI) transmit message
            automatically created. If True, then setting a
            custom transmit message would be invalid.
            Trail trace identifier (TTI) transmit message
            automatically created.";
        }
        leaf tti-msg-expected {
          type string {
            length "0..255";
          }
          description
            "Trail trace identifier (TTI) message
            expectedTrail trace identifier (TTI) message
            expected";
        }
        leaf tti-msg-transmit {
          type string {
            length "0..255";
          }
          description
            "Trail trace identifier (TTI) message
            transmittedTrail trace identifier (TTI)
            message transmitted";
        }
      }
      leaf trib-protocol {
        type Logical-trib-protocol;
        description "Protocol framing of the tributary signal";
      }
      leaf description {
        type string {
          length "0..255";
        }
        description "Description (Max 255 characters)";
      }
      leaf ingress-client-port {
        type xr:Interface-name;
        description
          "Configure ingress client port for this logical
          channel";
      }
      leaf ingress-physical-channel {
        type int32;
        description
          "Configure ingress physical channel for this
          logical channel";
      }
      leaf admin-state {
        type Logical-admin-state;
        description "Configure the admin-state ";
      }
      leaf loopback-mode {
        type Logical-loopback-mode;
        description "Configure the loopback mode ";
      }
      leaf logical-channel-type {
        type Logical-protocol;
        description "Configure the logical-channel-type ";
      }
      leaf rate-class {
        type Logical-trib-rate;
        description "Rounded bit rate of the tributary signal";
      }
      leaf channel-index {
        type int32;
        description "Logical Channel Index";
      }
    }
  }

  container optical-channels {
    description "optical channels";

    list optical-channel {
      key "ifname";
      description "Optical Channel index";
      leaf operational-mode {
        type uint32 {
          range "1..100000";
        }
        description "Configure operational mode";
      }
      leaf line-port {
        type xr:Interface-name;
        description "Specify R/S/I/P";
      }
      leaf ifname {
        type xr:Cisco-ios-xr-string;
        description "Optical Channel Name";
      }
    }
  }
}
