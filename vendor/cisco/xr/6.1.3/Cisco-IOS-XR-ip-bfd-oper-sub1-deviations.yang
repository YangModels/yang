module Cisco-IOS-XR-ip-bfd-oper-sub1-deviations {

  /*** NAMESPACE / PREFIX DEFINITION ***/
  namespace "http://cisco.com/ns/yang/Cisco-IOS-XR-ip-bfd-oper-sub1-deviations.yang";

  prefix "cisco-xr-bfd-devs";

  /*** LINKAGE (IMPORTS / INCLUDES) ***/
  import Cisco-IOS-XR-ip-bfd-oper { prefix bfd; }


  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a set of deviations of ip-bfd package
     model set for Cisco IOS-XR.

     Copyright (c) 2016 by Cisco Systems, Inc.
     All rights reserved.";

  revision "2016-10-16" {
    description
      "Initial revision applicable to IOS-XR 6.1.2 and older releases";
  }

  deviation /bfd:bfd/bfd:ipv4-multi-hop-session-details/bfd:ipv4-multi-hop-session-detail/bfd:lsp-ping-info/bfd:lsp-ping-tx-last-time/bfd:seconds {
    deviate replace {
        type "uint32";
    }
  }

  deviation /bfd:bfd/bfd:ipv4-multi-hop-session-details/bfd:ipv4-multi-hop-session-detail/bfd:mp-download-state/bfd:change-time/bfd:seconds {
    deviate replace {
        type "uint32";
    }
  }

  deviation /bfd:bfd/bfd:ipv4-single-hop-session-details/bfd:ipv4-single-hop-session-detail/bfd:lsp-ping-info/bfd:lsp-ping-tx-last-time/bfd:seconds {
    deviate replace {
        type "uint32";
    }
  }

  deviation /bfd:bfd/bfd:ipv4-single-hop-session-details/bfd:ipv4-single-hop-session-detail/bfd:mp-download-state/bfd:change-time/bfd:seconds {
    deviate replace {
        type "uint32";
    }
  }

  deviation /bfd:bfd/bfd:ipv4bf-do-mplste-tail-session-details/bfd:ipv4bf-do-mplste-tail-session-detail/bfd:lsp-ping-info/bfd:lsp-ping-tx-last-time/bfd:seconds {
    deviate replace {
        type "uint32";
    }
  }

  deviation /bfd:bfd/bfd:ipv4bf-do-mplste-tail-session-details/bfd:ipv4bf-do-mplste-tail-session-detail/bfd:mp-download-state/bfd:change-time/bfd:seconds {
    deviate replace {
        type "uint32";
    }
  }

  deviation /bfd:bfd/bfd:ipv6-multi-hop-session-details/bfd:ipv6-multi-hop-session-detail/bfd:lsp-ping-info/bfd:lsp-ping-tx-last-time/bfd:seconds {
    deviate replace {
        type "uint32";
    }
  }

  deviation /bfd:bfd/bfd:ipv6-multi-hop-session-details/bfd:ipv6-multi-hop-session-detail/bfd:mp-download-state/bfd:change-time/bfd:seconds {
    deviate replace {
        type "uint32";
    }
  }

  deviation /bfd:bfd/bfd:label-session-details/bfd:label-session-detail/bfd:lsp-ping-info/bfd:lsp-ping-tx-last-time/bfd:seconds {
    deviate replace {
        type "uint32";
    }
  }

  deviation /bfd:bfd/bfd:label-session-details/bfd:label-session-detail/bfd:mp-download-state/bfd:change-time/bfd:seconds {
    deviate replace {
        type "uint32";
    }
  }

  deviation /bfd:bfd/bfd:ipv6-single-hop-session-details/bfd:ipv6-single-hop-session-detail/bfd:lsp-ping-info/bfd:lsp-ping-tx-last-time/bfd:seconds {
    deviate replace {
        type "uint32";
    }
  }

  deviation /bfd:bfd/bfd:ipv6-single-hop-session-details/bfd:ipv6-single-hop-session-detail/bfd:mp-download-state/bfd:change-time/bfd:seconds {
    deviate replace {
        type "uint32";
    }
  }

  deviation /bfd:bfd/bfd:session-details/bfd:session-detail/bfd:lsp-ping-info/bfd:lsp-ping-tx-last-time/bfd:seconds {
    deviate replace {
        type "uint32";
    }
  }

  deviation /bfd:bfd/bfd:session-details/bfd:session-detail/bfd:mp-download-state/bfd:change-time/bfd:seconds {
    deviate replace {
        type "uint32";
    }
  }

  deviation /bfd:bfd/bfd:ipv4bf-do-mplste-head-session-details/bfd:ipv4bf-do-mplste-head-session-detail/bfd:lsp-ping-info/bfd:lsp-ping-tx-last-time/bfd:seconds {
    deviate replace {
        type "uint32";
    }
  }

  deviation /bfd:bfd/bfd:ipv4bf-do-mplste-head-session-details/bfd:ipv4bf-do-mplste-head-session-detail/bfd:mp-download-state/bfd:change-time/bfd:seconds {
    deviate replace {
        type "uint32";
    }
  }

  deviation /bfd:bfd/bfd:ipv4-multi-hop-session-details/bfd:ipv4-multi-hop-session-detail/bfd:lsp-ping-info/bfd:lsp-ping-tx-last-error-time/bfd:seconds {
    deviate replace {
        type "uint32";
    }
  }

  deviation /bfd:bfd/bfd:ipv4-single-hop-session-details/bfd:ipv4-single-hop-session-detail/bfd:lsp-ping-info/bfd:lsp-ping-tx-last-error-time/bfd:seconds {
    deviate replace {
        type "uint32";
    }
  }

  deviation /bfd:bfd/bfd:ipv4bf-do-mplste-tail-session-details/bfd:ipv4bf-do-mplste-tail-session-detail/bfd:lsp-ping-info/bfd:lsp-ping-tx-last-error-time/bfd:seconds {
    deviate replace {
        type "uint32";
    }
  }

  deviation /bfd:bfd/bfd:ipv6-multi-hop-session-details/bfd:ipv6-multi-hop-session-detail/bfd:lsp-ping-info/bfd:lsp-ping-tx-last-error-time/bfd:seconds {
    deviate replace {
        type "uint32";
    }
  }

  deviation /bfd:bfd/bfd:label-session-details/bfd:label-session-detail/bfd:lsp-ping-info/bfd:lsp-ping-tx-last-error-time/bfd:seconds {
    deviate replace {
        type "uint32";
    }
  }

  deviation /bfd:bfd/bfd:ipv6-single-hop-session-details/bfd:ipv6-single-hop-session-detail/bfd:lsp-ping-info/bfd:lsp-ping-tx-last-error-time/bfd:seconds {
    deviate replace {
        type "uint32";
    }
  }

  deviation /bfd:bfd/bfd:session-details/bfd:session-detail/bfd:lsp-ping-info/bfd:lsp-ping-tx-last-error-time/bfd:seconds {
    deviate replace {
        type "uint32";
    }
  }

  deviation /bfd:bfd/bfd:ipv4bf-do-mplste-head-session-details/bfd:ipv4bf-do-mplste-head-session-detail/bfd:lsp-ping-info/bfd:lsp-ping-tx-last-error-time/bfd:seconds {
    deviate replace {
        type "uint32";
    }
  }

  deviation /bfd:bfd/bfd:ipv4-multi-hop-session-details/bfd:ipv4-multi-hop-session-detail/bfd:lsp-ping-info/bfd:lsp-ping-rx-last-time/bfd:seconds {
    deviate replace {
        type "uint32";
    }
  }

  deviation /bfd:bfd/bfd:ipv4-single-hop-session-details/bfd:ipv4-single-hop-session-detail/bfd:lsp-ping-info/bfd:lsp-ping-rx-last-time/bfd:seconds {
    deviate replace {
        type "uint32";
    }
  }

  deviation /bfd:bfd/bfd:ipv4bf-do-mplste-tail-session-details/bfd:ipv4bf-do-mplste-tail-session-detail/bfd:lsp-ping-info/bfd:lsp-ping-rx-last-time/bfd:seconds {
    deviate replace {
        type "uint32";
    }
  }

  deviation /bfd:bfd/bfd:ipv6-multi-hop-session-details/bfd:ipv6-multi-hop-session-detail/bfd:lsp-ping-info/bfd:lsp-ping-rx-last-time/bfd:seconds {
    deviate replace {
        type "uint32";
    }
  }

  deviation /bfd:bfd/bfd:label-session-details/bfd:label-session-detail/bfd:lsp-ping-info/bfd:lsp-ping-rx-last-time/bfd:seconds {
    deviate replace {
        type "uint32";
    }
  }

  deviation /bfd:bfd/bfd:ipv6-single-hop-session-details/bfd:ipv6-single-hop-session-detail/bfd:lsp-ping-info/bfd:lsp-ping-rx-last-time/bfd:seconds {
    deviate replace {
        type "uint32";
    }
  }

  deviation /bfd:bfd/bfd:session-details/bfd:session-detail/bfd:lsp-ping-info/bfd:lsp-ping-rx-last-time/bfd:seconds {
    deviate replace {
        type "uint32";
    }
  }

  deviation /bfd:bfd/bfd:ipv4bf-do-mplste-head-session-details/bfd:ipv4bf-do-mplste-head-session-detail/bfd:lsp-ping-info/bfd:lsp-ping-rx-last-time/bfd:seconds {
    deviate replace {
        type "uint32";
    }
  }
}
