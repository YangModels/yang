submodule Cisco-IOS-XR-ncs5500-qos-oper-sub1 {

  belongs-to Cisco-IOS-XR-ncs5500-qos-oper {
    prefix Cisco-IOS-XR-ncs5500-qos-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-qos package operational data.

     Copyright (c) 2013-2016 by Cisco Systems, Inc.
     All rights reserved.";

  revision "2015-11-09" {
    description
      "IOS XR 6.0 revision.";
  }


  grouping WRED-PROFILE {
    description "WRED PROFILE";
    leaf min-threshold {
      type uint32;
      description "Minimum Threshold";
    }
    leaf max-threshold {
      type uint32;
      description "Maximum Threshold";
    }
    leaf drop-probability {
      type uint32;
      description "Drop Probability";
    }
  }

  grouping REMOTE-CLASS {
    description "REMOTE CLASS";
    leaf class-name {
      type string {
        length "0..64";
      }
      description "Class Name";
    }
    leaf class-id {
      type uint32;
      description "Class ID";
    }
    leaf cos-q {
      type uint32;
      description "Class of Service Queue";
    }
    leaf queue-limit {
      type uint32;
      units "byte";
      description "Default/Configured queue limit in bytes";
    }
    leaf hardware-queue-limit {
      type uint32;
      units "byte";
      description "Hardware queue limit in bytes";
    }

    list wred {
      max-elements "4";
      description "Default/Configured WRED profiles";
      uses WRED-PROFILE;
    }

    list hw-wred {
      max-elements "4";
      description "Hardware WRED profiles";
      uses WRED-PROFILE;
    }
  }

  grouping DNX-QOSEA-SHOW-REMOTE-IF-INFO-ST {
    description "Remote Interface Info";
    leaf policy-name {
      type string {
        length "0..64";
      }
      description "Policy Name";
    }
    leaf virtual-output-queue-statistics-handle {
      type uint64;
      description "Virtual output queue statistics handle";
    }
    leaf interface-handle {
      type uint32;
      description "Interface Handle";
    }
    leaf number-of-virtual-output-queues {
      type uint32;
      description "Number of Virtual Output Queues";
    }
    leaf number-of-classes {
      type uint32;
      description "Number of Classes";
    }

    list remote-class {
      description "Remote Class array";
      uses REMOTE-CLASS;
    }
  }
}
