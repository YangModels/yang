submodule Cisco-IOS-XR-ncs5500-coherent-node-oper-sub1 {

  belongs-to Cisco-IOS-XR-ncs5500-coherent-node-oper {
    prefix Cisco-IOS-XR-ncs5500-coherent-node-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-coherent-node package operational data.

     Copyright (c) 2013-2016 by Cisco Systems, Inc.
     All rights reserved.";

  revision "2015-11-09" {
    description
      "IOS XR 6.0 revision.";
  }


  grouping PORTMODE-INFO {
    description "portmode entry of optics controller";
    leaf intf-name {
      type string;
      description "Interface Name";
    }
    leaf speed {
      type string;
      description "Optics speed";
    }
    leaf fec {
      type string;
      description "Optics fec";
    }
    leaf diff {
      type string;
      description "Optics diff";
    }
    leaf modulation {
      type string;
      description "Optics modulation";
    }
  }

  grouping COH-PORTMODE-ALL-DETAILS {
    description "Optics controllers port Information";
    leaf num-entries {
      type uint32;
      description "Number of dev map entries";
    }

    list portmode-entry {
      max-elements "32";
      description "portmode entry";
      uses PORTMODE-INFO;
    }
  }

  grouping COH-ETH-INTERFACE-DATA {
    description "Hundredgig interface data";
    leaf ifname {
      type string {
        length "0..64";
      }
      description "ifname";
    }
    leaf intf-handle {
      type uint32;
      description "intf handle";
    }
    leaf admin-state {
      type boolean;
      description "admin state";
    }
  }

  grouping COH-ETH-INTERFACE-INFO {
    description "Hundredgig interface info";
    leaf intf-count {
      type int32;
      description "intf count";
    }

    list eth-data {
      max-elements "2";
      description "eth data";
      uses COH-ETH-INTERFACE-DATA;
    }
  }

  grouping COH-PLUGGABLE-INFO {
    description "Coherent pluggable information";
    leaf deviation {
      type string {
        length "0..16";
      }
      description "deviation";
    }
    leaf part-number {
      type string {
        length "0..16";
      }
      description "part number";
    }
    leaf serial-number {
      type string {
        length "0..16";
      }
      description "serial number";
    }
    leaf date-code-number {
      type string {
        length "0..10";
      }
      description "date code number";
    }
    leaf clei-code-number {
      type string {
        length "0..10";
      }
      description "CLEI code number";
    }
    leaf module-hardware-version-number {
      type uint16;
      description "module hardware version number";
    }
    leaf module-firmware-running-version-number {
      type uint16;
      description "module firmware running version number";
    }
    leaf module-firmware-committed-version-number {
      type uint16;
      description "module firmware committed version number";
    }
    leaf vendorname {
      type string {
        length "0..16";
      }
      description "vendorname";
    }
    leaf description {
      type string {
        length "0..64";
      }
      description "description";
    }
    leaf pid {
      type string {
        length "0..16";
      }
      description "pid";
    }
    leaf vid {
      type string {
        length "0..16";
      }
      description "vid";
    }
    leaf ctp-type {
      type uint32;
      description "ctp type";
    }
  }

  grouping COH-PORT-DATA {
    description "Coherent front panel port data";

    container ctp-info {
      description "ctp info";
      uses COH-PLUGGABLE-INFO;
    }

    container interface-info {
      description "interface info";
      uses COH-ETH-INTERFACE-INFO;
    }
    leaf optics-ctrl-created {
      type boolean;
      description "optics ctrl created";
    }
    leaf dsp-ctrl-created {
      type boolean;
      description "dsp ctrl created";
    }
    leaf has-pluggable {
      type boolean;
      description "has pluggable";
    }
    leaf optics-admin-up {
      type boolean;
      description "optics admin up";
    }
    leaf dsp-admin-up {
      type boolean;
      description "dsp admin up";
    }
    leaf laser-state {
      type boolean;
      description "laser state";
    }
    leaf fp-port-idx {
      type uint32;
      description "fp port idx";
    }
    leaf wavelength {
      type uint32;
      description "wavelength";
    }
    leaf traffic-type {
      type uint32;
      description "traffic type";
    }
    leaf laser-op-rc {
      type int32;
      description "laser op rc";
    }
    leaf wlen-op-rc {
      type int32;
      description "wlen op rc";
    }
    leaf traffic-op-rc {
      type int32;
      description "traffic op rc";
    }
  }

  grouping COH-HEALTH-DATA {
    description "Coherent health Data";
    leaf im-state {
      type boolean;
      description "im state";
    }
    leaf aipc-srvr-state {
      type boolean;
      description "aipc srvr state";
    }
    leaf sysdb-state {
      type boolean;
      description "sysdb state";
    }
    leaf pm-state {
      type boolean;
      description "pm state";
    }
    leaf optics-ea-conn {
      type boolean;
      description "optics ea conn";
    }
    leaf dsp-ea-conn {
      type boolean;
      description "dsp ea conn";
    }
    leaf vether-state {
      type boolean;
      description "vether state";
    }
    leaf morgoth-alive {
      type boolean;
      description "morgoth alive";
    }
    leaf prov-infra-state {
      type boolean;
      description "prov infra state";
    }
    leaf sdk-fpga-compatible {
      type boolean;
      description "sdk fpga compatible";
    }
    leaf sdk-version {
      type string {
        length "0..255";
      }
      description "sdk version";
    }
    leaf morgoth-running-version {
      type string {
        length "0..255";
      }
      description "morgoth running version";
    }
    leaf morgoth-downloaded-version {
      type string {
        length "0..255";
      }
      description "morgoth downloaded version";
    }
    leaf morgoth-golden-version {
      type string {
        length "0..255";
      }
      description "morgoth golden version";
    }
    leaf denali-version {
      type string {
        length "0..255";
      }
      description "denali version";
    }
    leaf board-type {
      type string {
        length "0..255";
      }
      description "board type";
    }
    leaf jlink-op {
      type string {
        length "0..1024";
      }
      description "jlink op";
    }

    list port-data {
      max-elements "6";
      description "port data";
      uses COH-PORT-DATA;
    }
  }

  grouping COH-DEV-MAP-ENTRY {
    description "coherent device mapping entry";
    leaf device-address {
      type uint32;
      description "Device address";
    }
    leaf ifhandle {
      type uint32;
      description "Interface handle";
    }
    leaf intf-name {
      type string;
      description "Interface Name";
    }
  }

  grouping COH-DEV-MAP-DATA {
    description "Coherent device mapping Information";
    leaf num-entries {
      type uint32;
      description "Number of dev map entries";
    }

    list dev-map {
      max-elements "32";
      description "dev map";
      uses COH-DEV-MAP-ENTRY;
    }
  }

  grouping COH-PORT-OP-STATS {
    description "Port specific op stats";

    container laser-on-stats {
      description "laser on stats";
      uses COH-OP-TIME-STATS;
    }

    container laser-off-stats {
      description "laser off stats";
      uses COH-OP-TIME-STATS;
    }

    container wl-op-stats {
      description "wl op stats";
      uses COH-OP-TIME-STATS;
    }

    container txpwr-op-stats {
      description "txpwr op stats";
      uses COH-OP-TIME-STATS;
    }

    container cdmin-op-stats {
      description "cdmin op stats";
      uses COH-OP-TIME-STATS;
    }

    container cdmax-op-stats {
      description "cdmax op stats";
      uses COH-OP-TIME-STATS;
    }

    container traffictype-op-stats {
      description "traffictype op stats";
      uses COH-OP-TIME-STATS;
    }
    leaf laser-state {
      type boolean;
      description "laser state";
    }
    leaf wavelength {
      type uint32;
      description "wavelength";
    }
    leaf tx-power {
      type uint32;
      description "tx power";
    }
    leaf cd-min {
      type uint32;
      description "cd min";
    }
    leaf cd-max {
      type uint32;
      description "cd max";
    }
    leaf traffic-type {
      type uint32;
      description "traffic type";
    }
  }

  grouping COH-OP-TIME-STATS {
    description "Coherent operation stats";
    leaf start {
      type string {
        length "0..255";
      }
      description "start";
    }
    leaf end {
      type string {
        length "0..255";
      }
      description "end";
    }
    leaf time-taken {
      type string {
        length "0..255";
      }
      description "time taken";
    }
    leaf worst-time {
      type string {
        length "0..255";
      }
      description "worst time";
    }
  }

  grouping COH-TIME-STATS {
    description "Coherent driver time stats";

    container opts-ea-bulk-create {
      description "opts ea bulk create";
      uses COH-OP-TIME-STATS;
    }

    container opts-ea-bulk-update {
      description "opts ea bulk update";
      uses COH-OP-TIME-STATS;
    }

    container dsp-ea-bulk-create {
      description "dsp ea bulk create";
      uses COH-OP-TIME-STATS;
    }

    container dsp-ea-bulk-update {
      description "dsp ea bulk update";
      uses COH-OP-TIME-STATS;
    }
    leaf driver-init {
      type string {
        length "0..255";
      }
      description "driver init";
    }
    leaf driver-operational {
      type string {
        length "0..255";
      }
      description "driver operational";
    }
    leaf device-created {
      type string {
        length "0..255";
      }
      description "device created";
    }
    leaf optics-controllers-created {
      type string {
        length "0..255";
      }
      description "optics controllers created";
    }
    leaf dsp-controllers-created {
      type string {
        length "0..255";
      }
      description "dsp controllers created";
    }
    leaf eth-intf-created {
      type string {
        length "0..255";
      }
      description "eth intf created";
    }

    list port-stat {
      max-elements "6";
      description "port stat";
      uses COH-PORT-OP-STATS;
    }
  }
}
