module Cisco-IOS-XR-infra-policymgr-oper {

  /*** NAMESPACE / PREFIX DEFINITION ***/

  namespace "http://cisco.com/ns/yang"+
    "/Cisco-IOS-XR-infra-policymgr-oper";


  prefix "infra-policymgr-oper";

  /*** LINKAGE (IMPORTS / INCLUDES) ***/

  import Cisco-IOS-XR-types { prefix "xr"; }

  include Cisco-IOS-XR-infra-policymgr-oper-sub2 {
    revision-date 2015-11-09;
  }

  include Cisco-IOS-XR-infra-policymgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-policymgr package operational data.

     This module contains definitions
     for the following management objects:
       policy-manager: Policy-map operational data

     Copyright (c) 2013-2016 by Cisco Systems, Inc.
     All rights reserved.";

  revision "2015-11-09" {
    description
      "IOS XR 6.0 revision.";
  }

  typedef Policymgr-policy-map {
    type enumeration {
      enum qos {
        value 1;
        description "QoS Policymap";
      }
      enum pbr {
        value 2;
        description "PBR Policymap";
      }
      enum traffic {
        value 3;
        description "TRAFFIC Policymap";
      }
      enum subscriber-control {
        value 4;
        description "SUBSCONTROL Policymap";
      }
      enum accounting {
        value 5;
        description "ACCOUNTING Policymap";
      }
      enum redirect {
        value 6;
        description "REDIRECT Policy map";
      }
      enum flow-monitor {
        value 7;
        description "FlOWMONITOR Policy map";
      }
    }
    description "Policymgr policy map";
  }
  typedef Policymgr-class-map {
    type enumeration {
      enum qos {
        value 1;
        description "QoS Classmap";
      }
      enum pbr {
        value 2;
        description "PBR Classmap";
      }
      enum traffic {
        value 3;
        description "TRAFFIC Classmap";
      }
      enum subscriber-control {
        value 4;
        description "SUBSCONTROL Classmap";
      }
    }
    description "Policymgr class map";
  }

  grouping TARGETS {
    description "Common node of node, global";

    container target-policy-map-types {
      description "Targets of a policymap";

      list target-policy-map-type {
        key "type";
        description "Policymgr application type";

        container policy-map-targets {
          description "Policy-map table";

          list policy-map-target {
            key "policy-map-name";
            description "Policy-map targets";
            leaf policy-map-name {
              type string {
                length "0..63";
              }
              description "Name of policy-map";
            }
            uses PLMGR-PMAP-STR-TARGETS-BG;
          }
        }

        container policy-map-target-summary {
          description "Policy-map table";
          uses PLMGR-PMAP-TARGETS-SUMMARY-BG;
        }

        container target-summary-per-policy-maps {
          description "Policy-map table per Policy-map";

          list target-summary-per-policy-map {
            key "policy-map-name";
            description "Policy-map targets summary";
            leaf policy-map-name {
              type string {
                length "0..63";
              }
              description "Name of policy-map";
            }
            uses PLMGR-PMAP-TARGETS-SUMMARY-BG;
          }
        }
        leaf type {
          type Policymgr-policy-map;
          description "The application type";
        }
      }
    }
  }

  grouping CLASS-MAP {
    description "Common node of node, global";

    container class-map {
      description "List of classmap details";

      container class-map-types {
        description "Application type of a classmap";

        list class-map-type {
          key "type";
          description "Policymgr application type";

          container class-map-details {
            description "Class-map detail table";

            list class-map-detail {
              key "class-map-name";
              description "Class-map detail information";
              leaf class-map-name {
                type string {
                  length "0..63";
                }
                description "Name of class-map";
              }
              uses PLMGR-APP-DB-BG;
            }
          }

          container class-maps {
            description "Class-map definition table";

            list class-map {
              key "class-map-name";
              description "Class-map configuration";
              leaf class-map-name {
                type string {
                  length "0..63";
                }
                description "Name of class-map";
              }
              uses CLASS-MAP-BG;
            }
          }

          container class-map-briefs {
            description "Class-map brief table";

            list class-map-brief {
              key "class-map-name";
              description "Class-map brief information";
              leaf class-map-name {
                type string {
                  length "0..63";
                }
                description "Name of class-map";
              }
              uses PLMGR-APP-DB-BG;
            }
          }
          leaf type {
            type Policymgr-class-map;
            description "The application type";
          }
        }
      }
    }
  }

  grouping SUMMARY {
    description "Common node of node, global";

    container summary {
      description
        "Summary of policy-maps and class-maps configured";
      uses PLMGR-SUMMARY-BG;
    }
  }

  grouping POLICY-MAP {
    description "Common node of node, global";

    container policy-map {
      description "List of policymap details";

      container transient-policy-map-type-xr {
        description "Application type of transient policy-map";

        list transient-policy-map-type {
          key "type";
          description "Transient policy-map type";

          container transient-policy-map-names {
            description "Transient policy-map definition table";

            list transient-policy-map-name {
              key "policy-map-name";
              description "Transient policy-map definition table";

              container class-handles {
                description
                  "Transient policy-map class handle table";

                list class-handle {
                  key "inline-classhandle";
                  description "Transient policy-map class handle";
                  leaf inline-classhandle {
                    type int32;
                    description "inline class handle";
                  }
                  uses POLICY-MAP-BG;
                }
              }

              container class-seq-nums {
                description
                  "Transient policy-map sequence number table";

                list class-seq-num {
                  key "sequence-num";
                  description
                    "Transient policy-map sequence number";
                  leaf sequence-num {
                    type int32;
                    description "sequence number";
                  }
                  uses POLICY-MAP-BG;
                }
              }

              container definition {
                description "Transient Policy-map type name";
                uses POLICY-MAP-BG;
              }
              leaf policy-map-name {
                type string {
                  length "0..63";
                }
                description "Name of policy-map";
              }
            }
          }
          leaf type {
            type Policymgr-policy-map;
            description "The application type";
          }
        }
      }

      container policy-map-unused-types {
        description "Policy-map unused table";

        list policy-map-unused-type {
          key "type";
          description "Policy-map unused";

          container unuseds {
            description "Policy-map unused";

            list unused {
              key "policy-map-name";
              description "Policy-map unused information";
              leaf policy-map-name {
                type string {
                  length "0..63";
                }
                description "Name of policy-map";
              }
              uses PLMGR-APP-DB-BG;
            }
          }
          leaf type {
            type Policymgr-policy-map;
            description "The application type";
          }
        }
      }

      container policy-map-types {
        description "Application type of a policymap";

        list policy-map-type {
          key "type";
          description "Policymgr application type";

          container policy-maps {
            description "Policy-map definition table";

            list policy-map {
              key "policy-map-name";
              description "Policy-map configuration";
              leaf policy-map-name {
                type string {
                  length "0..63";
                }
                description "Name of policy-map";
              }
              uses POLICY-MAP-BG;
            }
          }

          container policy-map-details {
            description "Policy-map table";

            list policy-map-detail {
              key "policy-map-name";
              description "Policy-map detail information";
              leaf policy-map-name {
                type string {
                  length "0..63";
                }
                description "Name of policy-map";
              }
              uses PLMGR-APP-DB-BG;
            }
          }
          leaf type {
            type Policymgr-policy-map;
            description "The application type";
          }
        }
      }

      container transient-policy-map-types {
        description "Application type of transient policy-map list";

        list transient-policy-map-type {
          key "type";
          description "Transient policy-map type";

          container transient-list-unuseds {
            description "Transient policy-map list unused table";

            list transient-list-unused {
              key "policy-map-name";
              description "Policy-map list unused";
              leaf policy-map-name {
                type string {
                  length "0..63";
                }
                description "Name of policy-map";
              }
              uses PLMGR-APP-DB-BG;
            }
          }
          leaf type {
            type Policymgr-policy-map;
            description "The application type";
          }
        }
      }
    }
  }

  grouping DETAIL {
    description "Common node of transient-input, transient-output";

    container detail {
      description "Policy map";
      uses POLICY-MAP-APPLIED-SHOW-BG;
    }
  }

  grouping POLICYMGR-OPER-DETAIL {
    description
      "Common node of transient-input,
      transient-outputCommon node of output, input";

    container detail {
      description "WORD interface name";
      uses POLICY-MAP-APPLIED-SHOW-BG;
    }
  }

  container policy-manager {
    config false;
    description "Policy-map operational data";

    container global {
      description "Global QOS operational data";

      container policy-map-applied-types {
        description "List of Applied policymap details";

        list policy-map-applied-type {
          key "type";
          description "Policymgr application type";

          container if-names {
            description "Interface table";

            list if-name {
              key "interface-name";
              description "WORD interface name";

              container input {
                description "Input direction table";
                uses POLICYMGR-OPER-DETAIL;
              }

              container output {
                description "Output direction table";
                uses POLICYMGR-OPER-DETAIL;
              }
              leaf interface-name {
                type xr:Interface-name;
                description "Name of the interface";
              }
            }
          }
          leaf type {
            type Policymgr-policy-map;
            description "The application type";
          }
        }
      }

      container transient-policy-map-targets-types {
        description "Transient policy-map target table";

        list transient-policy-map-targets-type {
          key "type";
          description "Transient Policymgr application type";

          container transient-target-summary-per-policy-maps {
            description "Transient Policy-map table per Policy-map";

            list transient-target-summary-per-policy-map {
              key "policy-map-name";
              description "Policy-map targets summary";
              leaf policy-map-name {
                type string {
                  length "0..63";
                }
                description "Name of policy-map";
              }
              uses PLMGR-PMAP-TARGETS-SUMMARY-BG;
            }
          }

          container transient-policy-map-target-summary {
            description "Transient Policy-map table";
            uses PLMGR-PMAP-TARGETS-SUMMARY-BG;
          }

          container transient-policy-map-targets {
            description "Transient Policy-map table";

            list transient-policy-map-target {
              key "policy-map-name";
              description "Transient Policy-map targets";
              leaf policy-map-name {
                type string {
                  length "0..63";
                }
                description "Name of policy-map";
              }
              uses PLMGR-PMAP-STR-TARGETS-BG;
            }
          }
          leaf type {
            type Policymgr-policy-map;
            description "The application type";
          }
        }
      }

      container transient-policy-map-applied-types {
        description "Transient policy-map applied type";

        list transient-policy-map-applied-type {
          key "type";
          description "Transient policy-map applied type";

          container transient-interface-names {
            description "Interface table";

            list transient-interface-name {
              key "interface-name";
              description "WORD interface name";

              container transient-output {
                description "Output direction table";
                uses DETAIL;
              }

              container transient-input {
                description "Input direction table";
                uses DETAIL;
              }
              leaf interface-name {
                type xr:Interface-name;
                description "Name of the interface";
              }
            }
          }
          leaf type {
            type Policymgr-policy-map;
            description "The application type";
          }
        }
      }
      uses TARGETS;
      uses CLASS-MAP;
      uses POLICY-MAP;
      uses SUMMARY;
    }

    container nodes {
      description "Node-specific Policymgr operational data";

      list node {
        key "node-name";
        description
          "Policymgr operational data for a particular
          node";
        leaf node-name {
          type xr:Node-id;
          description "Node name";
        }
        uses TARGETS;
        uses CLASS-MAP;
        uses POLICY-MAP;
        uses SUMMARY;
      }
    }
  }
}
