submodule Cisco-IOS-XR-aaa-locald-oper-sub1 {

  belongs-to Cisco-IOS-XR-aaa-locald-oper {
    prefix Cisco-IOS-XR-aaa-locald-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-locald package operational data.

     Copyright (c) 2013-2016 by Cisco Systems, Inc.
     All rights reserved.";

  revision "2015-11-09" {
    description
      "IOS XR 6.0 revision.";
  }

  typedef String1 {
    type string;
    description "String1";
  }

  grouping USERGROUP-DET {
    description "Detailed information regarding a usergroup";

    container task-map {
      description "Computed task map";
      uses TASKMAP;
    }
    leaf name-xr {
      type string;
      description "Name of the usergroup";
    }

    list taskgroup {
      description "Component taskgroups";
      uses TASKGROUP-DET;
    }
  }

  grouping USER-DET {
    description "Detailed information about a single user";

    container task-map {
      description "Computed taskmap";
      uses TASKMAP;
    }
    leaf name-xr {
      type string;
      description "Username";
    }
    leaf admin-user {
      type boolean;
      description "Is admin plane user ?";
    }
    leaf first-user {
      type boolean;
      description "Is first user ?";
    }
    leaf-list usergroup {
      type String1;
      description "Member usergroups";
    }
  }

  grouping TASKID {
    description "Information about a single Task ID";
    leaf task-id {
      type string;
      description "Name of the task-id";
    }
    leaf read {
      type boolean;
      description "Is read permitted?";
    }
    leaf write {
      type boolean;
      description "Is write permitted?";
    }
    leaf execute {
      type boolean;
      description "Is execute permitted?";
    }
    leaf debug {
      type boolean;
      description "Is debug permitted?";
    }
  }

  grouping TASKMAP {
    description
      "Computed taskmap of a user/usergroup/taskgroup or
      Task IDs included in a taskgroup";

    list tasks {
      description "List of permitted tasks";
      uses TASKID;
    }
  }

  grouping TASKGROUP-DET {
    description "Detailed information regarding a taskgroup";

    container included-task-ids {
      description "Task-ids included";
      uses TASKMAP;
    }

    container task-map {
      description "Computed task map";
      uses TASKMAP;
    }
    leaf name-xr {
      type string;
      description "Name of the taskgroup";
    }
  }

  grouping REMOTEUSR-DET {
    description "Detailed information regarding a usergroup";
    leaf name {
      type string;
      description "Name of the usergroup";
    }
    leaf authenmethod {
      type int32;
      description "Authentication method";
    }
    leaf-list usergroup {
      type String1;
      description "Component usergroups";
    }
    leaf-list taskmap {
      type String1;
      description "Task map details";
    }
  }

  grouping SYSTEM-SUPPORTED-TASKS {
    description "List of all tasks available in the system";
    leaf-list task-id {
      type String1;
      description "Names of available task-ids";
    }
  }
}
