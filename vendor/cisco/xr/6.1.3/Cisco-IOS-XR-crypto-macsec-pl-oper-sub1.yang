submodule Cisco-IOS-XR-crypto-macsec-pl-oper-sub1 {

  belongs-to Cisco-IOS-XR-crypto-macsec-pl-oper {
    prefix Cisco-IOS-XR-crypto-macsec-pl-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR crypto-macsec-pl package operational data.

     Copyright (c) 2013-2016 by Cisco Systems, Inc.
     All rights reserved.";

  revision "2015-11-09" {
    description
      "IOS XR 6.0 revision.";
  }

  typedef Macsec-card {
    type enumeration {
      enum macsec-none {
        value 0;
        description "macsec none";
      }
      enum macsec-msfpga {
        value 1;
        description "macsec msfpga";
      }
      enum macsec-xlmsfpga {
        value 2;
        description "macsec xlmsfpga";
      }
      enum macsec-apm {
        value 3;
        description "macsec apm";
      }
    }
    description "Macsec card";
  }

  grouping PL-ES200-FLOW-INFO {
    description "Flow Information";
    leaf flow-no {
      type uint32;
      description "Flow Number";
    }
    leaf is-flow-enabled {
      type boolean;
      description "Is Flow Enabled";
    }
    leaf ethertype {
      type uint16;
      description
        "Parsed EtherType to match could be 0 if
        Ethertype should'nt                             
        be matched can be 0x88E5 for MACSec tag";
    }
    leaf outer-vlan-id {
      type uint16;
      description
        " VLAN ID for outer tag use this when            
        only one tag should be matched";
    }
    leaf outer-vlan-user-pri {
      type uint8;
      description
        "VLAN User Priority for outer tag  use           
        this when only one tag should be matched";
    }
    leaf inner-vlan-id {
      type uint16;
      description
        "VLAN ID for inner tag used when two             
        VLAN Tags should be matched";
    }
    leaf inner-vlan-user-pri {
      type uint8;
      description
        " VLAN User priority for inner tag use           
        when matching two VLAN tags";
    }
    leaf psci {
      type uint64;
      description
        " SCI to be matched value required for           
        ingress only, pass NULL for egress";
    }
    leaf match-priority {
      type uint8;
      description "priority for match 0-15(highest) ";
    }
    leaf tci-v {
      type uint8;
      description "value of 'v' in TCI to match (1bit) ";
    }
    leaf tci-e-xr {
      type uint8;
      description "value of 'es' in TCI to match (1bit) ";
    }
    leaf tci-sc {
      type uint8;
      description "value of 'sc' in TCI to match (1bit) ";
    }
    leaf tci-scb {
      type uint8;
      description "value of 'scb' in TCI to match (1bit) ";
    }
    leaf tci {
      type uint8;
      description "value of 'e' in TCI to match (1bit )";
    }
    leaf tci-c {
      type uint8;
      description "value of 'c' in TCI to match (1bit) ";
    }
    leaf tci-chk {
      type boolean;
      description
        "TCI bits will be checked only when this         
        bit is enabled. All the values of TCI bits      
        are mandatory when TCI check is used";
    }
    leaf pkt-type {
      type uint32;
      description "Type of packet. See ethMscCfyEPktType_e";
    }
    leaf tag-num {
      type uint32;
      description
        "No. of MPLS or VLAN tags See ethMscCfyETagNum_e ";
    }
    leaf inner-vlan-dei {
      type boolean;
      description "Dei to match for innner Vlan tag";
    }
    leaf outer-vlan-dei {
      type boolean;
      description "Dei to match for outer Vlan tag";
    }
    leaf pbb-sid {
      type uint32;
      description " Service Instance id ";
    }
    leaf pbb-bvid {
      type uint32;
      description " Backbone Vlan id ";
    }
    leaf pbb-pcp {
      type uint8;
      description " pcp ";
    }
    leaf pbb-dei {
      type uint8;
      description " dei ";
    }
    leaf vlan-id {
      type uint16;
      description " vlan id ";
    }
    leaf vlan-pcp {
      type uint8;
      description " pcp ";
    }
    leaf vlan-dei {
      type uint8;
      description " dei ";
    }
    leaf mpls1-label {
      type uint32;
      description " label ";
    }
    leaf mpls1-exp {
      type uint8;
      description " exp ";
    }
    leaf mpls1-bos {
      type uint8;
      description " botton of stack ";
    }
    leaf mpls2-label {
      type uint32;
      description " label ";
    }
    leaf mpls2-exp {
      type uint8;
      description " exp ";
    }
    leaf mpls2-bos {
      type uint8;
      description " botton of stack ";
    }
    leaf plain-bits {
      type uint64;
      units "bit";
      description
        "Plain bits to compare. Max values:              
        untagged pkt - 40 bits after EthType            
        1 VLAN tag - 24 bits after parsed EthType       
        2 VLAN tags- 8 bits after  parsed EthType       
        1 MPLS tag - 32 bits after 1st tag              
        2 MPLS tags- 8 bits following after 2nd         
        or atmost 5th MPLS tag                          
        PBB - 16 bits after C-SA                        
        PBB with VLAN tag - 16 bits of VLAN tag ";
    }
    leaf plain-bits-size {
      type uint8;
      description "No. of bits used in plainBits";
    }
    leaf force-ctrl {
      type boolean;
      description
        "Force the pkt as control pkt irrepective        
        of the results of control packet detector";
    }
    leaf drop {
      type boolean;
      description "Drop the packet";
    }
    leaf mask-da {
      type uint64;
      description "DA mask";
    }
    leaf mask-ethertype {
      type uint32;
      description "Parsed EtherType mask";
    }
    leaf mask-plain-bits {
      type uint64;
      description "Plain Bits mask";
    }
    leaf flow-hits {
      type uint64;
      description "Pkts matching the Flow";
    }
    leaf-list macda {
      type uint8;
      description "MAC DA";
    }
  }

  grouping PL-ES200-FLOW {
    description "Flow Details";

    container tx-flow {
      description "Tx Flow Details";
      uses PL-ES200-FLOW-INFO;
    }

    container rx-flow {
      description "Rx Flow Details";
      uses PL-ES200-FLOW-INFO;
    }
  }

  grouping PL-MSFPGA-FLOW-INFO {
    description "Flow Information";
    leaf flow-id {
      type uint8;
      description "Flow Index";
    }
    leaf valid {
      type boolean;
      description "Flow Validity";
    }
    leaf is-egress {
      type boolean;
      description "rx_tx direction";
    }
    leaf in-use {
      type boolean;
      description "In Use";
    }
    leaf action {
      type uint8;
      description "Action";
    }
    leaf smac-inuse {
      type boolean;
      description "If MAC SA in Use";
    }
    leaf dmac-inuse {
      type boolean;
      description "If MAC DA in Use";
    }
    leaf ethertype {
      type uint16;
      description "Ether Type";
    }
    leaf outer-vlan {
      type uint16;
      description "Outer VLAN ID";
    }
    leaf outer-vlan-up {
      type uint8;
      description "Outer Vlan UserPri";
    }
    leaf outer-vlan-tpid {
      type uint16;
      description "Outer Vlan TPID";
    }
    leaf inner-vlan {
      type uint16;
      description "Inner VLAN ID";
    }
    leaf inner-vlan-up {
      type uint8;
      description "Inner Vlan UserPri";
    }
    leaf inner-vlan-tpid {
      type uint16;
      description "Inner Vlan TPID";
    }
    leaf source-port {
      type uint32;
      description "Source Port";
    }
    leaf source-port-chk {
      type boolean;
      description "Source Port ChkEn";
    }
    leaf sci-inuse {
      type boolean;
      description "If SCI in use";
    }
    leaf sci {
      type uint64;
      description "SCI";
    }
    leaf match-pri {
      type uint8;
      description "Match Priority";
    }
    leaf is-ctrl-pkt {
      type boolean;
      description "Is Control Pkt";
    }
    leaf ctrl-check {
      type boolean;
      description "Ctrl Pkt ChkEn";
    }
    leaf match-untagged {
      type boolean;
      description "MatchUntagged";
    }
    leaf match-tagged {
      type boolean;
      description "MatchTagged";
    }
    leaf match-bad-tag {
      type boolean;
      description "Match Bad Tag";
    }
    leaf match-kay-tag {
      type boolean;
      description "MatchKaYTag";
    }
    leaf tci-v {
      type uint8;
      description "TCI V";
    }
    leaf tci-e-xr {
      type uint8;
      description "TCI ES";
    }
    leaf tci-sc {
      type uint8;
      description "TCI SC";
    }
    leaf tci-scb {
      type uint8;
      description "TCI SCB";
    }
    leaf tci {
      type uint8;
      description "TCI E";
    }
    leaf tci-c {
      type uint8;
      description "TCI C";
    }
    leaf tci-an {
      type uint8;
      description "TCI AN";
    }
    leaf tci-an-chk {
      type boolean;
      description "TciAnChkEn";
    }
    leaf tci-chk {
      type boolean;
      description "TciChkEn";
    }
    leaf sai {
      type uint32;
      description "SAI";
    }
    leaf-list macsa {
      type uint8;
      description "MAC SA";
    }
    leaf-list macda {
      type uint8;
      description "MAC DA";
    }
  }

  grouping PL-MSFPGA-FLOW {
    description "Flow Details";

    container tx-flow {
      description "Tx Flow Details";
      uses PL-MSFPGA-FLOW-INFO;
    }

    container rx-flow {
      description "Rx Flow Details";
      uses PL-MSFPGA-FLOW-INFO;
    }
  }

  grouping PL-MACSEC-FLOW-EXT {
    description "PL MACSEC FLOW EXT";

    container msfpga-flow {
      when "../type = 'macsec-msfpga'" {
        description "../type = 'MACSEC_MSFPGA'";
      }
      description "MSFPGA Flow Information";
      uses PL-MSFPGA-FLOW;
    }

    container es200-flow {
      when "../type = 'macsec-apm'" {
        description "../type = 'MACSEC_APM'";
      }
      description "ES200 Flow Information";
      uses PL-ES200-FLOW;
    }
    leaf type {
      type Macsec-card;
      description "type";
    }
  }

  grouping PL-MACSEC-FLOW {
    description "MACSec HW Flow Details";

    container ext {
      description "ext";
      uses PL-MACSEC-FLOW-EXT;
    }
  }

  grouping PL-ES200-RX-SA-INFO {
    description "RX SA specific information";

    container xform-params {
      description " Xform Params";
      uses PL-ES200-XFORM-PARAMS;
    }
    leaf is-valid {
      type boolean;
      description "Is structure valid";
    }
    leaf sa-id {
      type uint8;
      description "SA Index";
    }
    leaf sc-no {
      type uint32;
      description "SC Number";
    }
    leaf in-pkts-unchecked {
      type uint8;
      description "frame not valid & validateFrames disabled";
    }
    leaf in-pkts-delayed {
      type uint8;
      description
        "PN of packet outside replay window &
        validateFrames !strict";
    }
    leaf in-pkts-late {
      type uint8;
      description
        "PN of packet outside replay window &
        validateFrames strict";
    }
    leaf in-pkts-ok {
      type uint8;
      description "packets with no error";
    }
    leaf in-pkts-invalid {
      type uint8;
      description "packet not valid & validateFrames !strict";
    }
    leaf in-pkts-not-valid {
      type uint8;
      description "packet not valid & validateFrames strict";
    }
    leaf in-pkts-not-using-sa {
      type uint8;
      description
        "packet assigned to SA not in use &
        validateFrames strict";
    }
    leaf in-pkts-unused-sa {
      type uint8;
      description
        "packet assigned to SA not in use& validateFrames
        !strict";
    }
    leaf in-octets-decrypted-validated1 {
      type uint8;
      description "octets1 decrypted/validated";
    }
    leaf in-octets-validated {
      type uint8;
      description "octets validated";
    }
  }

  grouping PL-ES200-XFORM-PARAMS {
    description "SA Xform specific information";
    leaf replay-win-size {
      type uint32;
      description "range of pkt nos considered valid";
    }
    leaf crypt-algo {
      type uint32;
      description "Cryptographic algo used";
    }
    leaf is-egress-tr {
      type boolean;
      description
        "APM_TRUE if this is Egress Transform record,
        APM_FALSE otherwise";
    }
    leaf aes-key-len {
      type uint32;
      description "AES Key length";
    }
    leaf assoc-num {
      type uint8;
      description "Association Number for egress";
    }
    leaf is-seq-num64-bit {
      type boolean;
      description
        "TRUE if Seq Num is 64-bit, FALSE if it is 32-bit";
    }
    leaf bgen-auth-key {
      type boolean;
      description
        "TRUE to generate the authKey, so authKey in this
        struct not used                                 
        APM_FALSE to use provided authKey";
    }
  }

  grouping PL-ES200-TX-SA-INFO {
    description "TX SA specific information";

    container xform-params {
      description " Xform Params";
      uses PL-ES200-XFORM-PARAMS;
    }
    leaf is-valid {
      type boolean;
      description "Is structure valid";
    }
    leaf sa-id {
      type uint8;
      description "SA Index";
    }
    leaf sc-no {
      type uint32;
      description "SC Number";
    }
    leaf out-pkts-too-long {
      type uint8;
      description "packets exceeding egress MTU";
    }
    leaf out-pkts-encrypted-protected {
      type uint8;
      description "packets encrypted/protected";
    }
    leaf out-octets-encrypted-protected1 {
      type uint8;
      description "octets1 encrypted/protected";
    }
    leaf initial-pkt-number {
      type uint8;
      description "Initial Packet Number";
    }
    leaf current-pkt-number {
      type uint64;
      description "Current packet Number";
    }
    leaf max-pkt-number {
      type uint64;
      description "Maximum packet Number";
    }
  }

  grouping PL-ES200-SA {
    description "SA details";

    container tx-sa {
      description "Tx SA Details";
      uses PL-ES200-TX-SA-INFO;
    }

    container rx-sa {
      description "Rx SA Details";
      uses PL-ES200-RX-SA-INFO;
    }
  }

  grouping PL-XLFPGA-RX-SA-INFO {
    description "Rx SA specific information";
    leaf protection-enable {
      type boolean;
      description "Protection Enabled";
    }
    leaf secure-mode {
      type uint32;
      description "Secure Mode - Must/Should";
    }
    leaf replay-protect-mode {
      type boolean;
      description "Replay Protect Mode";
    }
    leaf validation-mode {
      type uint32;
      description "Validation Mode";
    }
    leaf replay-window {
      type uint32;
      description "Replay Window ";
    }
    leaf secure-channel-id {
      type uint64;
      description "Secure Channel ID";
    }
    leaf cipher-suite {
      type uint32;
      description "Cipher Suite Used";
    }
    leaf confidentiality-offset {
      type uint8;
      description "Confidentiality Offset";
    }
    leaf fcs-err-cfg {
      type uint32;
      description "FCS Error Config";
    }
    leaf auth-err-cfg {
      type uint32;
      description "Auth  Error Config";
    }
    leaf max-packet-num {
      type uint64;
      description "Max Packet Number";
    }
    leaf num-an-in-use {
      type uint32;
      description "Num of AN's in Use";
    }
    leaf an {
      type yang:hex-string;
      description "Association Number";
    }
    leaf recent-an {
      type uint8;
      description "Recent Association Num";
    }
    leaf pkt-untagged-detected {
      type boolean;
      description "Untagged Pkts Detected";
    }
    leaf pkt-tagged-detected {
      type boolean;
      description "Tagged Pkts Detected";
    }
    leaf pkt-tagged-validated {
      type boolean;
      description "Tagged Pkts Validated";
    }
    leaf current-packet-num {
      type uint64;
      description "Current Packet Number";
    }
    leaf lowest-acceptable-packet-num {
      type uint64;
      description "Lowest Acceptable Packet Number";
    }
    leaf next-expected-packet-num {
      type uint64;
      description "Next expected Packet Number";
    }
    leaf-list ssci {
      type uint32;
      max-elements "4";
      description "Short Secure Channel ID";
    }
    leaf-list crc-value {
      type uint32;
      max-elements "4";
      description "CRC Value";
    }
  }

  grouping PL-XLFPGA-TX-SA-INFO {
    description "Tx SA specific information";
    leaf protection-enable {
      type boolean;
      description "Protection Enabled";
    }
    leaf secure-mode {
      type uint8;
      description "Secure Mode - Must/Should";
    }
    leaf secure-channel-id {
      type uint64;
      description "Secure Channel ID";
    }
    leaf sectag-length {
      type uint32;
      units "byte";
      description "Sec Tag Length(bytes) ";
    }
    leaf cipher-suite {
      type uint32;
      description "Cipher Suite Used";
    }
    leaf confidentiality-offset {
      type uint8;
      description "Confidentiality Offset";
    }
    leaf fcs-err-cfg {
      type uint8;
      description "FCS Error Config";
    }
    leaf max-packet-num {
      type uint64;
      description "Max Packet Number";
    }
    leaf an {
      type uint8;
      description "Association Number";
    }
    leaf initial-packet-number {
      type uint64;
      description "Initial Packet Number";
    }
    leaf ssci {
      type uint32;
      description "Short Secure Channel ID";
    }
    leaf current-packet-num {
      type uint64;
      description "Current Packet Number";
    }
    leaf crc-value {
      type uint32;
      description "CRC Value";
    }
  }

  grouping PL-XLFPGA-SA {
    description "Xilinx FPGA SA Detail";

    container tx-sa {
      description "Tx SA Details";
      uses PL-XLFPGA-TX-SA-INFO;
    }

    container rx-sa {
      description "Rx SA Details";
      uses PL-XLFPGA-RX-SA-INFO;
    }
  }

  grouping PL-MSFPGA-SA-INFO {
    description "SA specific information";
    leaf sa-id {
      type uint8;
      description "SA Index";
    }
    leaf valid {
      type boolean;
      description "SA Validity";
    }
    leaf is-egress {
      type boolean;
      description "rx_tx direction";
    }
    leaf crypto-algo {
      type uint8;
      description "Crypto Algorithm";
    }
    leaf key-len {
      type uint8;
      description "Key Length";
    }
    leaf an {
      type uint8;
      description "Association Number";
    }
    leaf xpn {
      type uint8;
      description "XPN EN";
    }
    leaf sci {
      type uint64;
      description "SCI";
    }
    leaf in-use {
      type boolean;
      description "In Use";
    }
    leaf next-pn {
      type uint64;
      description "Next Packet Number";
    }
    leaf c-offset {
      type uint8;
      description "Conf offset";
    }
    leaf action {
      type uint8;
      description "Action";
    }
    leaf q-bit {
      type boolean;
      description "Q bit";
    }
    leaf qq-bit {
      type boolean;
      description "QQ bit";
    }
  }

  grouping PL-MSFPGA-SA {
    description "SA details";

    container tx-sa {
      description "Tx SA Details";
      uses PL-MSFPGA-SA-INFO;
    }

    container rx-sa {
      description "Rx SA Details";
      uses PL-MSFPGA-SA-INFO;
    }
  }

  grouping PL-MACSEC-SA-EXT {
    description "PL MACSEC SA EXT";

    container msfpga-sa {
      when "../type = 'macsec-msfpga'" {
        description "../type = 'MACSEC_MSFPGA'";
      }
      description "MSFPGA SA Information";
      uses PL-MSFPGA-SA;
    }

    container xlfpga-sa {
      when "../type = 'macsec-xlmsfpga'" {
        description "../type = 'MACSEC_XLMSFPGA'";
      }
      description "XLFPGA SA Information";
      uses PL-XLFPGA-SA;
    }

    container es200-sa {
      when "../type = 'macsec-apm'" {
        description "../type = 'MACSEC_APM'";
      }
      description "ES200 SA Information";
      uses PL-ES200-SA;
    }
    leaf type {
      type Macsec-card;
      description "type";
    }
  }

  grouping PL-MACSEC-SA {
    description "MACSec HW SA Details";

    container ext {
      description "ext";
      uses PL-MACSEC-SA-EXT;
    }
  }

  grouping PL-ES200-PORT-LEVEL-STATS {
    description "Port Level Stats";
    leaf multi-flow-match {
      type uint64;
      description "Pkts matching multiple flow entries";
    }
    leaf parser-dropped {
      type uint64;
      description "Pkts dropped by header parser as invalid";
    }
    leaf flow-miss {
      type uint64;
      description "Pkts matching none of flow entries";
    }
    leaf pkts-ctrl {
      type uint64;
      description "Control pkts forwarded";
    }
    leaf pkts-data {
      type uint64;
      description "Data pkts forwarded";
    }
    leaf pkts-dropped {
      type uint64;
      description "Pkts dropped by classifier";
    }
    leaf pkts-err-in {
      type uint64;
      description "Pkts received with an error indication";
    }
  }

  grouping PL-ES200-RX-INTERFACE-MACSEC-STATS {
    description "Per Interface Macsec Ingress Stats";
    leaf transform-error-pkts {
      type uint64;
      description
        "counter to count internal errors in the MACSec
        core";
    }
    leaf in-pkt-ctrl {
      type uint64;
      description
        "ingress packet that is classified as control
        packet";
    }
    leaf in-pkt-no-tag {
      type uint64;
      description
        "ingress packet untagged & validateFrames is
        strict";
    }
    leaf in-pkts-untagged {
      type uint64;
      description
        "ingress packet untagged & validateFrames is 
        !strict";
    }
    leaf in-pkt-bad-tag {
      type uint64;
      description
        "ingress frames received with an invalid MACSec
        tag or ICV                                      
        added with next one gives InPktsSCIMiss";
    }
    leaf in-pkt-no-sci {
      type uint64;
      description
        "correctly tagged ingress frames for which no
        valid SC found & \;                             
        validateFrames is strict";
    }
    leaf in-pkts-unknown-sci {
      type uint64;
      description
        "correctly tagged ingress frames for which no
        valid SC found &                                
        validateFrames is !strict";
    }
    leaf in-pkts-tagged-ctrl {
      type uint64;
      description "ingress packets that are control or KaY packets";
    }
    leaf in-octets-unctrl {
      type uint64;
      description "Octets rx on uncontrolled port";
    }
    leaf in-octets-ctrl {
      type uint64;
      description "Octets rx on controlled port";
    }
    leaf in-ucast-pkts-unctrl {
      type uint64;
      description "Unicast pkts rx on uncontrolled port";
    }
    leaf in-ucast-pkts-ctrl {
      type uint64;
      description "Unicast pkts rx on controlled port";
    }
    leaf in-mcast-pkts-unctrl {
      type uint64;
      description "Multicast pkts rx on uncontrolled port";
    }
    leaf in-mcast-pkts-ctrl {
      type uint64;
      description "Multicast pkts rx on controlled port";
    }
    leaf in-bcast-pkts-unctrl {
      type uint64;
      description "Broadcast pkts rx on uncontrolled port";
    }
    leaf in-bcast-pkts-ctrl {
      type uint64;
      description "Broadcast pkts rx on controlled port";
    }
    leaf in-rx-drop-pkts-unctrl {
      type uint64;
      description "Control pkts dropped due to overrun";
    }
    leaf in-rx-drop-pkts-ctrl {
      type uint64;
      description "Data pkts dropped due to overrun";
    }
    leaf in-rx-error-pkts-unctrl {
      type uint64;
      description "Control pkts error-terminated due to overrun";
    }
    leaf in-rx-error-pkts-ctrl {
      type uint64;
      description "Data pkts error-terminated due to overrun";
    }
    leaf in-drop-pkts-class {
      type uint64;
      description
        "Packets dropped due to overflow in
        classification pipeline";
    }
    leaf in-drop-pkts-data {
      type uint64;
      description
        "Packets dropped due to overflow in processing
        pipeline";
    }
  }

  grouping PL-ES200-TX-INTERFACE-MACSEC-STATS {
    description "Per Interface Macsec Egress Stats";
    leaf transform-error-pkts {
      type uint64;
      description
        "counter to count internal errors in the MACSec
        core";
    }
    leaf out-pkt-ctrl {
      type uint64;
      description
        "egress packet that is classified as control
        packet";
    }
    leaf out-pkts-untagged {
      type uint64;
      description
        "egress packet to go out untagged when
        protectFrames not set";
    }
    leaf out-octets-unctrl {
      type uint64;
      description "Octets tx on uncontrolled port";
    }
    leaf out-octets-ctrl {
      type uint64;
      description "Octets tx on controlled port";
    }
    leaf out-octets-common {
      type uint64;
      description "Octets tx on common port";
    }
    leaf out-ucast-pkts-unctrl {
      type uint64;
      description "Unicast pkts tx on uncontrolled port";
    }
    leaf out-ucast-pkts-ctrl {
      type uint64;
      description "Unicast pkts tx on controlled port";
    }
    leaf out-mcast-pkts-unctrl {
      type uint64;
      description "Multicast pkts tx on uncontrolled port";
    }
    leaf out-mcast-pkts-ctrl {
      type uint64;
      description "Multicast pkts tx on controlled port";
    }
    leaf out-bcast-pkts-unctrl {
      type uint64;
      description "Broadcast pkts tx on uncontrolled port";
    }
    leaf out-bcast-pkts-ctrl {
      type uint64;
      description "Broadcast pkts tx on controlled port";
    }
    leaf out-rx-drop-pkts-unctrl {
      type uint64;
      description "Control pkts dropped due to overrun";
    }
    leaf out-rx-drop-pkts-ctrl {
      type uint64;
      description "Data pkts dropped due to overrun";
    }
    leaf out-rx-err-pkts-unctrl {
      type uint64;
      description "Control pkts error-terminated due to overrun";
    }
    leaf out-rx-err-pkts-ctrl {
      type uint64;
      description "Data pkts error-terminated due to overrun";
    }
    leaf out-drop-pkts-class {
      type uint64;
      description
        "Packets dropped due to overflow in
        classification pipeline";
    }
    leaf out-drop-pkts-data {
      type uint64;
      description
        "Packets dropped due to overflow in  processing
        pipeline";
    }
  }

  grouping PL-ES200-RX-SA-STATS {
    description "Per SA Ingress Stats";
    leaf in-pkts-unchecked {
      type uint64;
      description "frame not valid & validateFrames disabled";
    }
    leaf in-pkts-delayed {
      type uint64;
      description
        "PN of packet outside replay window &
        validateFrames !strict";
    }
    leaf in-pkts-late {
      type uint64;
      description
        "PN of packet outside replay window &
        validateFrames strict";
    }
    leaf in-pkts-ok {
      type uint64;
      description "packets with no error";
    }
    leaf in-pkts-invalid {
      type uint64;
      description "packet not valid & validateFrames !strict";
    }
    leaf in-pkts-not-valid {
      type uint64;
      description "packet not valid & validateFrames strict";
    }
    leaf in-pkts-not-using-sa {
      type uint64;
      description
        "packet assigned to SA not in use &
        validateFrames strict";
    }
    leaf in-pkts-unused-sa {
      type uint64;
      description
        "packet assigned to SA not in use &
        validateFrames !strict";
    }
    leaf in-octets-decrypted-validated1 {
      type uint64;
      description "octets1 decrypted/validated";
    }
    leaf in-octets-validated {
      type uint64;
      description "octets validated";
    }
  }

  grouping PL-ES200-TX-SA-STATS {
    description "Per SA Egress Stats";
    leaf out-pkts-too-long {
      type uint64;
      description "packets exceeding egress MTU";
    }
    leaf out-pkts-encrypted-protected {
      type uint64;
      description "packets encrypted/protected";
    }
    leaf out-octets-encrypted-protected1 {
      type uint64;
      description "octets1 encrypted/protected ?";
    }
  }

  grouping PL-ES200-STATS {
    description "Stats Details";

    container tx-sa-stats {
      description "Tx SA Stats";
      uses PL-ES200-TX-SA-STATS;
    }

    container rx-sa-stats {
      description "Rx SA Stats";
      uses PL-ES200-RX-SA-STATS;
    }

    container tx-interface-macsec-stats {
      description "Tx interface Macsec Stats";
      uses PL-ES200-TX-INTERFACE-MACSEC-STATS;
    }

    container rx-interface-macsec-stats {
      description "Rx interface Macsec Stats";
      uses PL-ES200-RX-INTERFACE-MACSEC-STATS;
    }

    container tx-port-stats {
      description "Port level TX Stats";
      uses PL-ES200-PORT-LEVEL-STATS;
    }

    container rx-port-stats {
      description "Port level RX Stats";
      uses PL-ES200-PORT-LEVEL-STATS;
    }
  }

  grouping PL-XLFPGA-MACSEC-RX-SA-STATS {
    description "Rx SA Level Stats";
    leaf an {
      type uint64;
      description "Current Rx AN";
    }
    leaf sa-ok-pkts {
      type uint64;
      description "Rx Ok Pkts for Current AN";
    }
    leaf sa-not-using-pkts {
      type uint64;
      description "Rx Pkts not using SA for Current AN";
    }
    leaf sa-unused-pkts {
      type uint64;
      description "Rx Pkts Unused Pkts for Current AN";
    }
    leaf sa-not-valid-pkts {
      type uint64;
      description "Rx Not Valid Pkts for Current AN";
    }
    leaf sa-invalid-pkts {
      type uint64;
      description "Rx Invalid Pkts for current AN";
    }
  }

  grouping PL-XLFPGA-MACSEC-RX-STATS {
    description "Per SC and SA Level Rx Stats";
    leaf sc-decrypted-octets {
      type uint64;
      description "Rx Octets Decrypted";
    }
    leaf sc-no-tag-pkts {
      type uint64;
      description "Rx No Tag Packets";
    }
    leaf sc-untagged-pkts {
      type uint64;
      description "Rx Untagged Packets";
    }
    leaf sc-bad-tag-pkts {
      type uint64;
      description "Rx Bad Tag Packets";
    }
    leaf sc-late-pkts {
      type uint64;
      description "Rx Late Pkts";
    }
    leaf sc-delayed-pkts {
      type uint64;
      description "Rx Delayed Pkts";
    }
    leaf sc-unchecked-pkts {
      type uint64;
      description "Rx Unchecked Pkts";
    }
    leaf sc-no-sci-pkts {
      type uint64;
      description "Rx No SCI Pkts";
    }
    leaf sc-unknown-sci-pkts {
      type uint64;
      description "Rx Unknown SCI Pkts";
    }
    leaf sc-ok-pkts {
      type uint64;
      description "Rx Pkts Ok";
    }
    leaf sc-not-using-pkts {
      type uint64;
      description "Rx Pkts Not Using SA";
    }
    leaf sc-unused-pkts {
      type uint64;
      description "Rx Pkts Unused SA";
    }
    leaf sc-not-valid-pkts {
      type uint64;
      description "Rx Not Valid Pkts";
    }
    leaf sc-invalid-pkts {
      type uint64;
      description "Rx Pkts Invalid";
    }
    leaf sc-overrun-pkts {
      type uint64;
      description "Rx Overrun Pkts";
    }
    leaf sc-bypass-pkts {
      type uint64;
      description "Rx Bypass Packets";
    }
    leaf sc-eapol-pkts {
      type uint64;
      description "Rx Eapol Packets";
    }
    leaf sc-dropped-pkts {
      type uint64;
      description "Rx Dropped Packets";
    }

    list rx-sa-stat {
      description "Rx SA Level Stats";
      uses PL-XLFPGA-MACSEC-RX-SA-STATS;
    }
  }

  grouping PL-XLFPGA-MACSEC-TX-STATS {
    description "Per SC and SA Level Tx Stats";
    leaf sc-encrypted-octets {
      type uint64;
      description "Tx Octets Encrypted";
    }
    leaf sc-toolong-pkts {
      type uint64;
      description "Tx Pkts Too Long";
    }
    leaf sc-encrypted-pkts {
      type uint64;
      description "Tx packets Encrypted";
    }
    leaf sc-untagged-pkts {
      type uint64;
      description "Tx Untagged Packets";
    }
    leaf sc-overrun-pkts {
      type uint64;
      description "Tx Overrun Packets";
    }
    leaf sc-bypass-pkts {
      type uint64;
      description "Tx Bypass Packets";
    }
    leaf sc-eapol-pkts {
      type uint64;
      description "Tx Eapol Packets";
    }
    leaf sc-dropped-pkts {
      type uint64;
      description "Tx Dropped Packets";
    }
    leaf current-an {
      type uint64;
      description "Current Tx AN";
    }
    leaf sa-encrypted-pkts {
      type uint64;
      description "Current Tx SA Encrypted Packets";
    }
  }

  grouping PL-XLFPGA-STATS {
    description "XLFPGA Stats Details";

    container macsec-tx-stats {
      description "Tx SC and SA Level Stats";
      uses PL-XLFPGA-MACSEC-TX-STATS;
    }

    container macsec-rx-stats {
      description "Rx SC and SA Level Stats";
      uses PL-XLFPGA-MACSEC-RX-STATS;
    }
  }

  grouping PL-MSFPGA-RX-INTERFACE-MACSEC-STATS {
    description "Per Interface Macsec Ingress Stats";
    leaf in-pkt-untagged {
      type uint64;
      description "Rx Pkts Untagged";
    }
    leaf in-pkt-notag {
      type uint64;
      description "Rx Pkts Notag";
    }
    leaf in-pkt-bad-tag {
      type uint64;
      description "Rx Pkts Bad tag";
    }
    leaf in-pkt-no-sci {
      type uint64;
      description "Rx Pkts No Sci";
    }
    leaf in-pkt-unknown-sci {
      type uint64;
      description "Rx Pkts Unknown Sci";
    }
    leaf in-pkt-tagged {
      type uint64;
      description "Rx Pkts Tagged";
    }
    leaf in-pkt-overrun {
      type uint64;
      description "Rx Pkts Over Run";
    }
    leaf in-pkt-uncontrolled {
      type uint64;
      description "Rx Pkts Uncontrolled";
    }
  }

  grouping PL-MSFPGA-TX-INTERFACE-MACSEC-STATS {
    description "Per Interface Macsec Egress Stats";
    leaf out-pkt-uncontrolled {
      type uint64;
      description "Tx Pkts Uncontrolled";
    }
    leaf out-pkt-untagged {
      type uint64;
      description "Tx Pkts Untagged";
    }
    leaf out-pkt-too-long {
      type uint64;
      description "Tx Pkts Too Long";
    }
  }

  grouping PL-MSFPGA-RX-SA-STATS {
    description "Per SA Ingress Stats";
    leaf in-pkts-unused-sa {
      type uint64;
      description "Rx Pkts Unused SA";
    }
    leaf in-pkts-not-using-sa {
      type uint64;
      description "Rx Pkts Not Using SA";
    }
    leaf in-pkts-not-valid {
      type uint64;
      description "Rx Pkts Not Valid";
    }
    leaf in-pkts-invalid {
      type uint64;
      description "Rx Pkts Invalid";
    }
    leaf in-pkts-ok {
      type uint64;
      description "Rx Pkts OK";
    }
    leaf in-pkts-delayed {
      type uint64;
      description "Rx Pkts Delayed";
    }
    leaf in-pkts-late {
      type uint64;
      description "Rx Pkts Late";
    }
    leaf in-pkts-unchecked {
      type uint64;
      description "Rx Pkts Unchecked";
    }
    leaf in-octets-validated {
      type uint64;
      description "Rx Octets Validated";
    }
    leaf in-octets-decrypted {
      type uint64;
      description "Rx Octets Decrypted";
    }
  }

  grouping PL-MSFPGA-TX-SA-STATS {
    description "Per SA Egress Stats";
    leaf out-pkts-protected {
      type uint64;
      description "Tx Pkts Protected";
    }
    leaf out-pkts-encrypted {
      type uint64;
      description "Tx Pkts Encrypted";
    }
    leaf out-octets-protected {
      type uint64;
      description "Tx Octets Protected";
    }
    leaf out-octets-encrypted {
      type uint64;
      description "Tx Octets Encrypted";
    }
  }

  grouping PL-MSFPGA-STATS {
    description "Stats Details";

    container tx-sa-stats {
      description "Tx SA Stats";
      uses PL-MSFPGA-TX-SA-STATS;
    }

    container rx-sa-stats {
      description "Rx SA Stats";
      uses PL-MSFPGA-RX-SA-STATS;
    }

    container tx-interface-macsec-stats {
      description "Tx interface Macsec Stats";
      uses PL-MSFPGA-TX-INTERFACE-MACSEC-STATS;
    }

    container rx-interface-macsec-stats {
      description "Rx interface Macsec Stats";
      uses PL-MSFPGA-RX-INTERFACE-MACSEC-STATS;
    }
  }

  grouping PL-MACSEC-STATS-T-EXT {
    description "PL MACSEC STATS T EXT";

    container msfpga-stats {
      when "../type = 'macsec-msfpga'" {
        description "../type = 'MACSEC_MSFPGA'";
      }
      description "MSFPGA Stats";
      uses PL-MSFPGA-STATS;
    }

    container xlfpga-stats {
      when "../type = 'macsec-xlmsfpga'" {
        description "../type = 'MACSEC_XLMSFPGA'";
      }
      description "XLFPGA Stats";
      uses PL-XLFPGA-STATS;
    }

    container es200-stats {
      when "../type = 'macsec-apm'" {
        description "../type = 'MACSEC_APM'";
      }
      description "ES200 Stats";
      uses PL-ES200-STATS;
    }
    leaf type {
      type Macsec-card;
      description "type";
    }
  }

  grouping PL-MACSEC-STATS {
    description "Per SA Stats Counters";

    container ext {
      description "ext";
      uses PL-MACSEC-STATS-T-EXT;
    }
  }
}
