module Cisco-IOS-XR-asr9k-sc-invmgr-oper {

  /*** NAMESPACE / PREFIX DEFINITION ***/

  namespace "http://cisco.com/ns/yang"+
    "/Cisco-IOS-XR-asr9k-sc-invmgr-oper";


  prefix "asr9k-sc-invmgr-oper";

  /*** LINKAGE (IMPORTS / INCLUDES) ***/

  import Cisco-IOS-XR-types { prefix "xr"; }

  include Cisco-IOS-XR-asr9k-sc-invmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-sc-invmgr package operational data.

     This module contains definitions
     for the following management objects:
       inventory: Logical Router Inventory operational data

     Copyright (c) 2013-2016 by Cisco Systems, Inc.
     All rights reserved.";

  revision "2015-11-09" {
    description
      "IOS XR 6.0 revision.";
  }


  grouping PORT-SLOT-TABLE {
    description "Common node of module, card";

    container port-slots {
      description
        "PortSlotTable contains all optics ports in a
        SPA/PLIM.";

      list port-slot {
        key "number";
        description "PortSlot number in the SPA/PLIM";

        container port {
          description "Port string";
          uses BASIC-ATTRIBUTES;
        }
        leaf number {
          type int32;
          description "portslot number";
        }
        uses BASIC-ATTRIBUTES;
      }
    }
  }

  grouping SENSOR-TABLE {
    description "Common node of card, hw-component, module";

    container sensors {
      description
        "ModuleSensorTable contains all sensors in a
        Module.";

      list sensor {
        key "number";
        description "Sensor number in the Module";
        leaf number {
          type int32;
          description "sensor number";
        }
        uses BASIC-ATTRIBUTES;
      }
    }
  }

  grouping BASIC-ATTRIBUTES {
    description
      "Common node of slot, card, sub-slot, module,
      port-slot, port, hw-component, sensor";

    container basic-attributes {
      description "Attributes";

      container basic-info {
        description "Inventory information";
        uses INV-PHY-ENTITY-BASIC-INFO;
      }

      container fru-info {
        description
          "Field Replaceable Unit (FRU) inventory
          information";
        uses INV-CARD-FRU-INFO;
      }
    }
  }

  container inventory {
    config false;
    description "Logical Router Inventory operational data";

    container racks {
      description "Table of racks";

      list rack {
        key "number";
        description "Rack number";

        container slots {
          description "Slot table contains all slots in the rack";

          list slot {
            key "number";
            description "Slot number";

            container cards {
              description
                "Card table contains all cards in the slot";

              list card {
                key "number";
                description "Card number";

                container sub-slots {
                  description
                    "SubSlotTable contains all subslots in a
                    Slot";

                  list sub-slot {
                    key "number";
                    description "SubSlot number";

                    container module {
                      description "Module string";
                      uses SENSOR-TABLE;
                      uses PORT-SLOT-TABLE;
                      uses BASIC-ATTRIBUTES;
                    }
                    leaf number {
                      type int32;
                      description "subslot number";
                    }
                    uses BASIC-ATTRIBUTES;
                  }
                }

                container hw-components {
                  description
                    "HWComponent table contains all HW modules
                    within the card ";

                  list hw-component {
                    key "number";
                    description "HWComponent number";
                    leaf number {
                      type int32;
                      description "node number";
                    }
                    uses SENSOR-TABLE;
                    uses BASIC-ATTRIBUTES;
                  }
                }
                leaf number {
                  type int32;
                  description "card number";
                }
                uses SENSOR-TABLE;
                uses PORT-SLOT-TABLE;
                uses BASIC-ATTRIBUTES;
              }
            }
            leaf number {
              type int32;
              description "Slot number";
            }
            uses BASIC-ATTRIBUTES;
          }
        }
        leaf number {
          type int32;
          description "Rack number";
        }
      }
    }
  }
}
