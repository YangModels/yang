module Cisco-IOS-XR-openconfig-terminal-device-oper {

  /*** NAMESPACE / PREFIX DEFINITION ***/

  namespace "http://cisco.com/ns/yang"+
    "/Cisco-IOS-XR-openconfig-terminal-device-oper";


  prefix "openconfig-terminal-device-oper";

  /*** LINKAGE (IMPORTS / INCLUDES) ***/

  import Cisco-IOS-XR-types { prefix "xr"; }

  include Cisco-IOS-XR-openconfig-terminal-device-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR openconfig-terminal-device package operational data.

     This module contains definitions
     for the following management objects:
       optical-interface: System-wide view of interface operational
         data

     Copyright (c) 2013-2016 by Cisco Systems, Inc.
     All rights reserved.";

  revision "2015-11-09" {
    description
      "IOS XR 6.0 revision.";
  }


  container optical-interface {
    config false;
    description "System-wide view of interface operational data";

    container optical-client-interfaces {
      description
        "The operational attributes table for Client Port";

      list optical-client-interface {
        key "name";
        description "The operational attributes for Client Port";

        container optical-client-logical-channel-assignments {
          description
            "The operational attributes for a Underline
            Ether Interface";

          list optical-client-logical-channel-assignment {
            key "index";
            description
              "The operational attributes for a Underline
              Ether Interface";
            leaf index {
              type int32;
              description "The index of the interface";
            }
            uses LOGICAL-CHAN-ASSIGNMENT;
          }
        }
        leaf name {
          type xr:Interface-name;
          description "The name of the client interface";
        }
      }
    }

    container operational-modes {
      description "The Operational Mode Table";

      list operational-mode {
        key "mode-id";
        description "Mode supported on Device";

        container operational-mode-attributes {
          description
            "The operational attributes for mxp driver
            fec-mode";
          uses OPERATIONAL-MODE-ATTRIBUTES;
        }
        leaf mode-id {
          type int32;
          description "Mode-id for supported mode on Device";
        }
      }
    }

    container optical-logical-interfaces {
      description
        "The operational attributes for a particular
        interface";

      list optical-logical-interface {
        key "index";
        description
          "The operational attributes for a particular
          interface";

        container optical-logical-interface-attr {
          description
            "The operational attributes for a particular
            interface";
          uses LOGICAL-CHANNEL-ATTR;
        }

        container "optical-logical-interface-logical-channel"+
          "-assignments" {
          description
            "The operational attributes for a particular
            interface";

          list "optical-logical-interface-logical-channel"+
            "-assignment" {
            key "index";
            description
              "The operational attributes for a particular
              interface";
            leaf index {
              type int32;
              description "The index of the interface";
            }
            uses LOGICAL-CHAN-ASSIGNMENT;
          }
        }
        leaf index {
          type int32;
          description "The index of the logical-channel";
        }
      }
    }
  }
}
