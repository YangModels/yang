submodule Cisco-IOS-XR-iedge4710-oper-sub3 {

  belongs-to Cisco-IOS-XR-iedge4710-oper {
    prefix Cisco-IOS-XR-iedge4710-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR iedge4710 package operational data.

     Copyright (c) 2013-2016 by Cisco Systems, Inc.
     All rights reserved.";

  revision "2015-11-09" {
    description
      "IOS XR 6.0 revision.";
  }


  grouping IEDGE-STATS-SRG-DATA {
    description "Geo Redundancy statistics";
    leaf txlist-send-triggered {
      type uint32;
      description "Txlist Send Triggered";
    }
    leaf txlist-send-failed {
      type uint32;
      description "Txlist Send Failed";
    }
    leaf txlist-send-failed-notactive {
      type uint32;
      description "Txlist send failed due to not active";
    }
    leaf actual-txlist-sent {
      type uint32;
      description "Txlist Send Success";
    }
    leaf alreadyin-txlist {
      type uint32;
      description "Element already in Txlist";
    }
    leaf txlist-encode {
      type uint32;
      description "Txlist Encode";
    }
    leaf txlist-encode-fail {
      type uint32;
      description "Txlist encode Failed";
    }
    leaf create-update-encode {
      type uint32;
      description "Txlist Create Update Encode";
    }
    leaf delete-encode {
      type uint32;
      description "Txlist Delete Encode";
    }
    leaf create-upd-clean-callback {
      type uint32;
      description "Txlist Create/update clean callback";
    }
    leaf delete-clean-callback {
      type uint32;
      description "Txlist Delete clean callback";
    }
    leaf slave-recv-entry {
      type uint32;
      description "Slave Recieved Sync";
    }
    leaf slave-decode-fail {
      type uint32;
      description "Decode failed on Slave";
    }
    leaf slave-create-update {
      type uint32;
      description "Create Update received on slave";
    }
    leaf slave-delete {
      type uint32;
      description "Delete received on slave";
    }
    leaf srg-context-malloc {
      type uint32;
      description "SRG context allocated";
    }
    leaf srg-context-free {
      type uint32;
      description "SRG context freed";
    }
    leaf sod-count {
      type uint32;
      description "Number of SODs Received";
    }
    leaf eod-count {
      type uint32;
      description "Number of EODs Received";
    }
    leaf sod-eod-replay-req-count {
      type uint32;
      description "Number of Replay Requests Within SOD EOD Window";
    }
    leaf sod-eod-dirty-mark-count {
      type uint32;
      description
        "Number of Sessions Marked as Invalid Within SOD
        EOD Window";
    }
    leaf sod-eod-dirty-delete-count {
      type uint32;
      description
        "Number of Sessions Invalid Deletes Within SOD
        EOD Window";
    }
    leaf ack-to-srg {
      type uint32;
      description "Number of ACKs sent to Srg";
    }
    leaf nack-to-srg {
      type uint32;
      description "Number of NACKs sent to Srg";
    }
    leaf nack-to-srg-fail-cnt {
      type uint32;
      description "Number of NACKs Failed to send to Srg";
    }
    leaf txlist-remove-all {
      type uint32;
      description "Number of Txlist remove all calls";
    }
    leaf txlist-del-sync {
      type uint32;
      description "Number for Txlist delete for sync msg";
    }
    leaf txlist-del-sync-notlinked {
      type uint32;
      description
        "Number of Txlist delete for sync which are not
        linked";
    }
    leaf txlist-del-app {
      type uint32;
      description "Number of Txlist delete for App msg";
    }
    leaf txlist-del-app-notlinked {
      type uint32;
      description
        "Number of Txlist delete for App which are not
        linked";
    }
    leaf txlist-clean-invalid-state {
      type uint32;
      description
        "Number of Txlist Cleanup called on Invalid
        subscriber srg state";
    }
    leaf txlist-remove-all-internal-error {
      type uint32;
      description
        "Number of Internal errors upon Master Txlist
        remove all call";
    }
    leaf is-srg-flow-control-enabled {
      type boolean;
      description "Flag indicating SRG Flow control enabled or not";
    }
    leaf max-inflight-sessoin-count {
      type uint32;
      description "Maximum no.of inflight sessions allowed";
    }
    leaf flow-control-resume-threshold {
      type uint32;
      description "Threshold Limit to resume the flow control";
    }
    leaf inflight-session-count {
      type uint32;
      description "No.of Sessions inflight at given time";
    }
    leaf inflight-add-count {
      type uint32;
      description "No.of inflight sessions added";
    }
    leaf inflight-under-run-count {
      type uint32;
      description "Inflight Underrun Counter";
    }
    leaf inflight-alloc-fails {
      type uint32;
      description "Memory Alloc Failures for Inflight Entry";
    }
    leaf inflight-insert-failures {
      type uint32;
      description "Inflight Entry Insert Failures";
    }
    leaf inflight-deletes {
      type uint32;
      description "Inflight Deletes Count";
    }
    leaf inflight-not-found {
      type uint32;
      description "Inflight Entries not found during delete";
    }
    leaf inflight-delete-failures {
      type uint32;
      description "Inflight Entry Delete Failures";
    }
    leaf total-pause-count {
      type uint32;
      description "Total No.of times Pause is Enabled";
    }
    leaf total-resume-count {
      type uint32;
      description "Total No.of times Resume is triggered";
    }
    leaf total-dont-send-to-txlist {
      type uint32;
      description "Total No of times Dont send to Txlist";
    }
    leaf total-srg-not-master {
      type uint32;
      description "Total No of times SRG Not Master";
    }
    leaf total-master-eoms-pending {
      type uint32;
      description "Total No of times Master EOMS Pending";
    }
    leaf last-pause-period {
      type uint64;
      description
        "Amount of time paused during last flow control
        window";
    }
    leaf total-pause-time {
      type uint64;
      description
        "Total Amount of time paused during all flow
        control windows";
    }
    leaf last-pause-time {
      type uint64;
      description "Timestamp of recent Pause Event";
    }
    leaf last-resume-time {
      type uint64;
      description "Timestamp of recent Resume Event";
    }
  }

  grouping IEDGE-STATS-SUMMARY-DATA {
    description "Summary statistics";
    leaf no-subscriber-control-policy-on-interface {
      type uint64;
      description
        "Subscriber control policy not applied on
        interface";
    }
    leaf no-class-match-in-start-request {
      type uint64;
      description
        "No control policy class match during subscriber
        start";
    }
    leaf nas-port-attribute-format-warnings {
      type uint64;
      description "NAS port attribute format warnings";
    }
    leaf nas-port-id-attribute-format-warnings {
      type uint64;
      description "NAS port ID attribute format warnings";
    }
    leaf destination-station-id-attribute-format-warnings {
      type uint64;
      description
        "Destination station ID attribute format warnings";
    }
    leaf calling-station-id-attribute-format-warnings {
      type uint64;
      description "Calling station ID attribute format warnings";
    }
    leaf username-attribute-format-warnings {
      type uint64;
      description "Username attribute format warnings";
    }
    leaf install-user-profiles {
      type uint64;
      description "User profiles installed";
    }
    leaf user-profile-install-errors {
      type uint64;
      description "User profile install errors";
    }
    leaf user-profile-removals {
      type uint64;
      description "User profile removals";
    }
    leaf user-profile-errors {
      type uint64;
      description "User profile errors";
    }
    leaf sess-disc-quota-exhausts {
      type uint64;
      description "Session Disconnect Quota Exhausts";
    }
    leaf sess-disc-no-quota {
      type uint64;
      description "Session Disconnect Request Queued, no quota";
    }
    leaf sess-disc-quota-avail {
      type uint64;
      description
        "Session Disconnect Request Accepted, quota
        available";
    }
    leaf sess-disc-recon-ip {
      type uint64;
      description
        "Session Disconnect Requests not Dequeued,
        reconciliation in progress";
    }
    leaf sess-disc-none-started {
      type uint64;
      description
        "Session Disconnect Requests not Dequeued, no
        quota";
    }
    leaf sess-disc-quota {
      type uint32;
      description "Session Disconnect Quota";
    }
    leaf sess-disc-quota-remaining {
      type uint32;
      description "Session Disconnect Quota Remaining";
    }
    leaf sess-disc-q-count {
      type uint32;
      description "Session Disconnect Requests Queued";
    }
  }

  grouping IEDGE-STATS-CH-REQ-STATS {
    description "Change of authorization request statistics";
    leaf received-requests {
      type uint64;
      description "Received requests";
    }
    leaf acknowledged-requests {
      type uint64;
      description "Acknowledged requests";
    }
    leaf non-acknowledged-requests {
      type uint64;
      description "Non acknowledged requests";
    }
  }

  grouping IEDGE-STATS-CH-DATA {
    description "Change of authorization statistics";

    container account-logon {
      description "Account logon request statistics";
      uses IEDGE-STATS-CH-REQ-STATS;
    }

    container account-logoff {
      description "Account logoff request statistics";
      uses IEDGE-STATS-CH-REQ-STATS;
    }

    container account-update {
      description "Account update request statistics";
      uses IEDGE-STATS-CH-REQ-STATS;
    }

    container session-disconnect {
      description "Session disconnect request statistics";
      uses IEDGE-STATS-CH-REQ-STATS;
    }

    container single-service-logon {
      description "Service logon request statistics";
      uses IEDGE-STATS-CH-REQ-STATS;
    }

    container single-service-logoff {
      description "Single Service logoff request statistics";
      uses IEDGE-STATS-CH-REQ-STATS;
    }

    container single-service-modify {
      description "Single Service Modify request statistics";
      uses IEDGE-STATS-CH-REQ-STATS;
    }

    container service-multi {
      description "MA-CoA Service request statistics";
      uses IEDGE-STATS-CH-REQ-STATS;
    }
    leaf unknown-account-cmd-resps {
      type uint64;
      description "Responses to unknown account command";
    }
    leaf unknown-service-cmd-resps {
      type uint64;
      description "Responses to unknown service command";
    }
    leaf unknown-cmd-resps {
      type uint64;
      description "Responses to unknown command";
    }
    leaf attr-list-retrieve-failure-resps {
      type uint64;
      description "Responses to attribute list failure errors";
    }
    leaf resp-send-failure {
      type uint64;
      description "Response send failures";
    }
    leaf internal-err-resps {
      type uint64;
      description "Responses to internal error";
    }
    leaf service-profile-push-failure-resps {
      type uint64;
      description "Responses to service profile push failures";
    }
    leaf no-cmd-resps {
      type uint64;
      description "Responses empty (no command) COA request";
    }
    leaf no-session-found-resps {
      type uint64;
      description
        "Responses to COA with unknown session identifier";
    }
    leaf no-session-peer-resps {
      type uint64;
      description "Responses to session peer not found error";
    }
  }

  grouping IEDGE-STATS-MOB-DATA {
    description "Mobility statistics";
    leaf send-request-successes {
      type uint64;
      description "Request send success";
    }
    leaf send-request-failures {
      type uint64;
      description "Request send failures";
    }
    leaf receive-response-successes {
      type uint64;
      description "Response receive success";
    }
    leaf receive-response-failures {
      type uint64;
      description "Response receive failures";
    }
  }

  grouping IEDGE-STATS-COORD-AUTH-DATA {
    description "Authorization & authentication statistics";
    leaf sent-requests {
      type uint64;
      description "Requests sent to radius server";
    }
    leaf accepted-requests {
      type uint64;
      description "Request accepted by Radius server";
    }
    leaf successful-requests {
      type uint64;
      description "Requests which are successful";
    }
    leaf rejected-requests {
      type uint64;
      description "Requests rejected by radius server";
    }
    leaf unreachable-requests {
      type uint64;
      description "Radius server not available";
    }
    leaf errored-requests {
      type uint64;
      description "Unexpected errors";
    }
    leaf incomplete-requests {
      type uint64;
      description "Incomplete requests - missing attributes";
    }
    leaf terminated-requests {
      type uint64;
      description "Requests terminated by disconnect";
    }
  }

  grouping IEDGE-INTERIM-INFLIGHT-COORD-DATA {
    description "Interim inflight information";
    leaf quota-exhausts {
      type uint32;
      description "Quota exhausts";
    }
    leaf denied-requests {
      type uint32;
      description "Denied requests";
    }
    leaf accepted-requests {
      type uint32;
      description "Accepted requests";
    }
    leaf total-quota-of-requests {
      type uint32;
      description "Total quota of requests";
    }
    leaf remaining-quota-of-requests {
      type uint32;
      description "Remaining quota of requests";
    }
    leaf low-water-mark-quota-of-requests {
      type uint32;
      description "Low water mark quota of requests";
    }
  }

  grouping IEDGE-STATS-COORD-ACCT-REQ-STATS {
    description "AAA accounting request-response statistics";
    leaf received-requests {
      type uint64;
      description "Received requests";
    }
    leaf errored-requests {
      type uint64;
      description "Errored requests";
    }
    leaf aaa-errored-requests {
      type uint64;
      description "AAA errored requests";
    }
    leaf aaa-sent-requests {
      type uint64;
      description "AAA requests sent";
    }
    leaf aaa-succeeded-responses {
      type uint64;
      description "AAA succeeded responses";
    }
    leaf aaa-failed-responses {
      type uint64;
      description "AAA failed responses";
    }
  }

  grouping IEDGE-STATS-COORD-ACCT-DATA {
    description "AAA accounting statistics";

    container start {
      description "Start statistics";
      uses IEDGE-STATS-COORD-ACCT-REQ-STATS;
    }

    container stop {
      description "Stop statistics";
      uses IEDGE-STATS-COORD-ACCT-REQ-STATS;
    }

    container interim {
      description "Interim statistics";
      uses IEDGE-STATS-COORD-ACCT-REQ-STATS;
    }

    container pass-through {
      description "Pass-through statistics";
      uses IEDGE-STATS-COORD-ACCT-REQ-STATS;
    }

    container update {
      description "Update statistics";
      uses IEDGE-STATS-COORD-ACCT-REQ-STATS;
    }

    container interim-inflight {
      description "Interim inflight details";
      uses IEDGE-INTERIM-INFLIGHT-COORD-DATA;
    }
    leaf active-sessions {
      type uint32;
      description "Active sessions";
    }
    leaf started-sessions {
      type uint64;
      description "Started sessions";
    }
    leaf stopped-sessions {
      type uint64;
      description "Stopped sessions";
    }
    leaf policy-plane-errored-requests {
      type uint64;
      description "Policy plane errored requests";
    }
    leaf policy-plane-unknown-requests {
      type uint64;
      description "Policy plane unknown requests";
    }
  }
}
