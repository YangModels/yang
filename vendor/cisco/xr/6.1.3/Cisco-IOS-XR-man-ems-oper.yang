module Cisco-IOS-XR-man-ems-oper {

  /*** NAMESPACE / PREFIX DEFINITION ***/

  namespace "http://cisco.com/ns/yang/Cisco-IOS-XR-man-ems-oper";


  prefix "man-ems-oper";

  /*** LINKAGE (IMPORTS / INCLUDES) ***/

  import Cisco-IOS-XR-types { prefix "xr"; }

  include Cisco-IOS-XR-man-ems-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ems package operational data.

     This module contains definitions
     for the following management objects:
       grpc: grpc commands

     Copyright (c) 2013-2016 by Cisco Systems, Inc.
     All rights reserved.";

  revision "2015-11-09" {
    description
      "IOS XR 6.0 revision.";
  }


  container grpc {
    config false;
    description "grpc commands";

    container statistics {
      description "Grpc Statistics";
      uses GRPC-CONFIGURATION-INFO;
    }

    container status {
      description "Grpc Status";
      uses GRPC-CONFIGURATION-INFO;
    }
  }
}
