submodule Cisco-IOS-XR-nto-misc-shmem-oper-sub1 {

  belongs-to Cisco-IOS-XR-nto-misc-shmem-oper {
    prefix Cisco-IOS-XR-nto-misc-shmem-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR nto-misc-shmem package operational data.

     Copyright (c) 2013-2016 by Cisco Systems, Inc.
     All rights reserved.";

  revision "2015-11-09" {
    description
      "IOS XR 6.0 revision.";
  }


  grouping SHARED-WINDOW {
    description "Shared window information";
    leaf shared-window {
      type string;
      description "Name of shared window";
    }
    leaf window-size {
      type uint64;
      description "Size of shared window";
    }
  }

  grouping NODE-MEM-INFO-DETAIL {
    description "Detail Node memory information";
    leaf page-size {
      type uint32;
      units "byte";
      description "Page size in bytes";
    }
    leaf ram-memory {
      type uint64;
      units "byte";
      description "Physical memory size in bytes";
    }
    leaf free-physical-memory {
      type uint64;
      units "byte";
      description "Physical memory available in bytes";
    }
    leaf private-physical-memory {
      type uint64;
      units "byte";
      description "Private Physical memory in bytes";
    }
    leaf system-ram-memory {
      type uint64;
      units "byte";
      description "Application memory size in bytes";
    }
    leaf free-application-memory {
      type uint64;
      units "byte";
      description "Application memory available in bytes";
    }
    leaf image-memory {
      type uint64;
      units "byte";
      description "Image memory size in bytes";
    }
    leaf boot-ram-size {
      type uint64;
      units "byte";
      description "Boot RAM size in bytes";
    }
    leaf reserved-memory {
      type uint64;
      units "byte";
      description "Reserved memory size in bytes";
    }
    leaf io-memory {
      type uint64;
      units "byte";
      description "IO memory size in bytes";
    }
    leaf flash-system {
      type uint64;
      units "byte";
      description "Flash System size in bytes";
    }
    leaf total-shared-window {
      type uint64;
      description "Total Shared window";
    }
    leaf allocated-memory {
      type uint64;
      description "Allocated Memory Size";
    }
    leaf program-text {
      type uint64;
      description "Program Text Size";
    }
    leaf program-data {
      type uint64;
      description "Program Data Size";
    }
    leaf program-stack {
      type uint64;
      description "Program Stack Size";
    }

    list shared-window {
      description "Available Shared windows";
      uses SHARED-WINDOW;
    }
  }

  grouping NODE-MEM-INFO {
    description "Node memory information";
    leaf page-size {
      type uint32;
      units "byte";
      description "Page size in bytes";
    }
    leaf ram-memory {
      type uint64;
      units "byte";
      description "Physical memory size in bytes";
    }
    leaf free-physical-memory {
      type uint64;
      units "byte";
      description "Physical memory available in bytes";
    }
    leaf system-ram-memory {
      type uint64;
      units "byte";
      description "Application memory size in bytes";
    }
    leaf free-application-memory {
      type uint64;
      units "byte";
      description "Application memory available in bytes";
    }
    leaf image-memory {
      type uint64;
      units "byte";
      description "Image memory size in bytes";
    }
    leaf boot-ram-size {
      type uint64;
      units "byte";
      description "Boot RAM size in bytes";
    }
    leaf reserved-memory {
      type uint64;
      units "byte";
      description "Reserved memory size in bytes";
    }
    leaf io-memory {
      type uint64;
      units "byte";
      description "IO memory size in bytes";
    }
    leaf flash-system {
      type uint64;
      units "byte";
      description "Flash System size in bytes";
    }
  }
}
