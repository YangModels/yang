submodule Cisco-IOS-XR-infra-rsi-oper-sub1 {

  belongs-to Cisco-IOS-XR-infra-rsi-oper {
    prefix Cisco-IOS-XR-infra-rsi-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-rsi package operational data.

     Copyright (c) 2013-2015 by Cisco Systems, Inc.
     All rights reserved.";

  revision "2015-01-07" {
    description
      "IOS XR 5.3.1 revision.";
  }

  typedef String1 {
    type string;
    description "String1";
  }

  grouping RSI-MASTER-STATE {
    description "RSI MASTER STATE";
    leaf is-svd-enabled {
      xr:xr-xml-map "rsi_master:IsSVDEnabled";
      type boolean;
      description "Is SVD Enabled Operational";
    }
    leaf is-svd-enabled-cfg {
      xr:xr-xml-map "rsi_master:IsSVDEnabledCfg";
      type boolean;
      description "Is SVD Enabled Config";
    }
  }
}
