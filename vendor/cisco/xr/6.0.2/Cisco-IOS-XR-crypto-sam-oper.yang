module Cisco-IOS-XR-crypto-sam-oper {

  /*** NAMESPACE / PREFIX DEFINITION ***/

  namespace "http://cisco.com/ns/yang/Cisco-IOS-XR-crypto-sam-oper";


  prefix "crypto-sam-oper";

  /*** LINKAGE (IMPORTS / INCLUDES) ***/

  import Cisco-IOS-XR-types { prefix "xr"; }

  include Cisco-IOS-XR-crypto-sam-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-sam package operational data.

     This module contains definitions
     for the following management objects:
       sam: Software authentication manager certificate information

     Copyright (c) 2013-2015 by Cisco Systems, Inc.
     All rights reserved.";

  revision "2015-01-07" {
    description
      "IOS XR 5.3.1 revision.";
  }


  container sam {
    xr:xr-xml-map "crypto_sam_oper:SAM";
    config false;
    description
      "Software authentication manager certificate
      information";

    container system-information {
      xr:xr-xml-map "crypto_sam_oper:SystemInformation";
      description "SAM system information";
      uses CRYPTO-SAM-SYSINFO;
    }

    container log-contents {
      xr:xr-xml-map "crypto_sam_oper:LogContentTable";
      description "SAM log content table information";

      list log-content {
        xr:xr-xml-map "crypto_sam_oper:LogContent";
        key "number-of-lines";
        description "Number of lines for SAM log message";
        leaf number-of-lines {
          xr:xr-xml-map "crypto_sam_oper:NumberOfLines";
          type int32;
          description "Number of lines";
        }
        uses CRYPTO-LOG;
      }
    }

    container devices {
      xr:xr-xml-map "crypto_sam_oper:DeviceTable";
      description "Certificate device table information";

      list device {
        xr:xr-xml-map "crypto_sam_oper:Device";
        key "device-name";
        description "Certificate table device information";

        container certificate {
          xr:xr-xml-map "crypto_sam_oper:Certificate";
          description "Certificate table information";

          container brief {
            xr:xr-xml-map "crypto_sam_oper:Brief";
            description "Certificate table brief information";
            uses CRYPTO-SAM-CERTIFICATE-COMMON;
          }

          container certificate-indexes {
            xr:xr-xml-map "crypto_sam_oper:CertificateIndexTable";
            description
              "Certificate detail index table information";

            list certificate-index {
              xr:xr-xml-map "crypto_sam_oper:CertificateIndex";
              key "index";
              description "Certificate detail index information";

              container detail {
                xr:xr-xml-map "crypto_sam_oper:Detail";
                description "Certificate table detail information";
                uses CRYPTO-SAM-CERTIFICATE-COMMON;
              }
              leaf index {
                xr:xr-xml-map "crypto_sam_oper:Index";
                type int32;
                description "Specify certificate index";
              }
            }
          }
        }
        leaf device-name {
          xr:xr-xml-map "crypto_sam_oper:DeviceName";
          type xr:Cisco-ios-xr-string;
          description "Specify device name";
        }
      }
    }

    container packages {
      xr:xr-xml-map "crypto_sam_oper:PackageTable";
      description "SAM certificate information  package";

      list package {
        xr:xr-xml-map "crypto_sam_oper:Package";
        key "package-name";
        description
          "SAM certificate information for a specific
          package";
        leaf package-name {
          xr:xr-xml-map "crypto_sam_oper:PackageName";
          type string;
          description "Specify package name";
        }
        uses CRYPTO-SAM-CERTIFICATE-COMMON;
      }
    }

    container certificate-revocations {
      xr:xr-xml-map "crypto_sam_oper:CertificateRevocationListTable";
      description
        "Certificate revocation list index table
        information";

      list certificate-revocation {
        xr:xr-xml-map "crypto_sam_oper:CertificateRevocationList";
        key "crl-index";
        description "Certificate revocation list index information";

        container certificate-revocation-list-detail {
          xr:xr-xml-map "crypto_sam_oper:CertificateRevocationListD"+
            "etail";
          description
            "Certificate revocation list detail information";
          uses CRYPTO-SAM-CRL-INFO;
        }
        leaf crl-index {
          xr:xr-xml-map "crypto_sam_oper:CRLIndex";
          type int32;
          description "CRL index";
        }
      }
    }

    container certificate-revocation-list-summary {
      xr:xr-xml-map "crypto_sam_oper:CertificateRevocationListSumma"+
        "ry";
      description
        "Certificate revocation list summary information ";
      uses CRYPTO-SAM-CRL-INFO;
    }
  }
}
