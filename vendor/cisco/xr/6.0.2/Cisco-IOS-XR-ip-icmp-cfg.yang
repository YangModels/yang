module Cisco-IOS-XR-ip-icmp-cfg {

  /*** NAMESPACE / PREFIX DEFINITION ***/

  namespace "http://cisco.com/ns/yang/Cisco-IOS-XR-ip-icmp-cfg";


  prefix "ip-icmp-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-icmp package configuration.

     This module contains definitions
     for the following management objects:
       icmp: IP ICMP configuration data

     Copyright (c) 2013-2015 by Cisco Systems, Inc.
     All rights reserved.";

  revision "2015-11-09" {
    description
      "IOS XR 6.0 revision.";
  }

  typedef Source-policy {
    type enumeration {
      enum vrf {
        value 1;
        description "Set Source Selection Policy to vrf";
      }
      enum rfc {
        value 2;
        description "Set Source Selection Policy to rfc";
      }
    }
    description "Source policy";
  }

  container icmp {
    xr:xr-xml-map "ip_icmp_cfg:ICMP";
    description "IP ICMP configuration data";

    list ip-protocol {
      xr:xr-xml-map "ip_icmp_cfg:IPProtocol";
      key "protocol-type";
      description "IP Protocol Type";

      container rate-limit {
        xr:xr-xml-map "ip_icmp_cfg:RateLimit";
        description "Set ratelimit of ICMP packets";

        container unreachable {
          xr:xr-xml-map "ip_icmp_cfg:Unreachable";
          description "Set unreachable ICMP packets ratelimit";
          leaf rate {
            xr:xr-xml-map "ip_icmp_cfg:Rate";
            xr:xr-cli-map "icmp (ipv4)|(ipv6) rate-limit unreachabl"+
              "e [<number>|disable] ";
            type uint32 {
              range "0..4294967295";
            }
            description "Rate Limit of Unreachable ICMP paclets";
          }
          leaf fragmentation {
            xr:xr-xml-map "ip_icmp_cfg:Fragmentation";
            xr:xr-cli-map "icmp (ipv4)|(ipv6) rate-limit unreachabl"+
              "e DF (<number>)|(disable) ";
            type uint32 {
              range "0..4294967295";
            }
            description "Rate Limit of Unreachable DF paclets";
          }
        }
      }

      container source {
        xr:xr-xml-map "ip_icmp_cfg:Source";
        description "IP ICMP Source Address Selection Policy";
        leaf source-address-policy {
          xr:xr-xml-map "ip_icmp_cfg:SourceAddressPolicy";
          type Source-policy;
          description "Configure Source Address Policy";
        }
      }
      leaf protocol-type {
        xr:xr-xml-map "ip_icmp_cfg:ProtocolType";
        type xr:Cisco-ios-xr-string;
        description "IP Protocol Type; ipv4 or ipv6";
      }
    }
  }
}
