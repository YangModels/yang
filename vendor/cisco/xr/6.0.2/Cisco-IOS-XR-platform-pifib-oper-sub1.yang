submodule Cisco-IOS-XR-platform-pifib-oper-sub1 {

  belongs-to Cisco-IOS-XR-platform-pifib-oper {
    prefix Cisco-IOS-XR-platform-pifib-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR platform-pifib package operational data.

     Copyright (c) 2013-2015 by Cisco Systems, Inc.
     All rights reserved.";

  revision "2016-02-22" {
    description
      "Initial revision.";
  }

  revision "2015-11-09" {
    description
      "IOS XR 6.0 revision.";
  }


  grouping PL-PIFIB-SHOW-ENTRY {
    description "LPTS TCAM Pre-IFIB Entry Information";
    leaf l3protocol {
      xr:xr-xml-map "platform_pifib:l3protocol";
      type uint32;
      description "Layer 3 Protocol";
    }
    leaf l4protocol {
      xr:xr-xml-map "platform_pifib:l4protocol";
      type uint32;
      description "Layer 4 Protocol";
    }
    leaf intf-handle {
      xr:xr-xml-map "platform_pifib:intf_handle";
      type uint32;
      description "Interface Handle";
    }
    leaf intf-name {
      xr:xr-xml-map "platform_pifib:intf_name";
      type string;
      description "Interface Name";
    }
    leaf uidb-index {
      xr:xr-xml-map "platform_pifib:uidb_index";
      type uint32;
      description "Interface uidb index";
    }
    leaf local-addr {
      xr:xr-xml-map "platform_pifib:local_addr";
      type string;
      description "Local IP Address";
    }
    leaf local-prefix-len {
      xr:xr-xml-map "platform_pifib:local_prefix_len";
      type uint32;
      description "Local Prefix Length";
    }
    leaf remote-addr {
      xr:xr-xml-map "platform_pifib:remote_addr";
      type string;
      description "Remote IP Address";
    }
    leaf remote-prefix-len {
      xr:xr-xml-map "platform_pifib:remote_prefix_len";
      type uint32;
      description "Remote Prefix Length";
    }
    leaf vrf-id {
      xr:xr-xml-map "platform_pifib:vrf_id";
      type uint32;
      description "VRF ID";
    }
    leaf u-value {
      xr:xr-xml-map "platform_pifib:u_value";
      type uint32;
      description "Remote Port/ICMP Type/IGMP Type";
    }
    leaf u-len {
      xr:xr-xml-map "platform_pifib:u_len";
      type uint32;
      description "Union Key Length";
    }
    leaf local-port {
      xr:xr-xml-map "platform_pifib:local_port";
      type uint32;
      description "Local port";
    }
    leaf is-frag {
      xr:xr-xml-map "platform_pifib:is_frag";
      type uint8;
      description "Is Fragment";
    }
    leaf is-syn {
      xr:xr-xml-map "platform_pifib:is_syn";
      type uint8;
      description "Is SYN";
    }
    leaf action {
      xr:xr-xml-map "platform_pifib:action";
      type uint8;
      description "Action";
    }
    leaf action-string {
      xr:xr-xml-map "platform_pifib:action_string";
      type string;
      description "Action String";
    }
    leaf listener-tag {
      xr:xr-xml-map "platform_pifib:listener_tag";
      type uint8;
      description "Listener Tag";
    }
    leaf is-fgid {
      xr:xr-xml-map "platform_pifib:is_fgid";
      type uint8;
      description "Is FGID or not";
    }
    leaf is-vrf {
      xr:xr-xml-map "platform_pifib:is_vrf";
      type uint8;
      description "Is VRF or not";
    }
    leaf is-optimized {
      xr:xr-xml-map "platform_pifib:is_optimized";
      type uint8;
      description "Is optimized or not";
    }
    leaf is-uidb-opt-bit {
      xr:xr-xml-map "platform_pifib:is_uidb_opt_bit";
      type uint8;
      description "Is uidb set for optimized entry or not";
    }
    leaf fgid-or-sfp {
      xr:xr-xml-map "platform_pifib:fgid_or_sfp";
      type uint32;
      description "fabric group id or swith fabric port";
    }
    leaf remote-rack {
      xr:xr-xml-map "platform_pifib:remote_rack";
      type uint8;
      description "Is entry remote or not";
    }
    leaf rack-id {
      xr:xr-xml-map "platform_pifib:rack_id";
      type uint32;
      description "Remote racknum if remote";
    }
    leaf rslot {
      xr:xr-xml-map "platform_pifib:rslot";
      type uint32;
      description "Remote slotnum if remote";
    }
    leaf policer {
      xr:xr-xml-map "platform_pifib:policer";
      type uint32;
      description "Policer Pointer";
    }
    leaf stats-ptr {
      xr:xr-xml-map "platform_pifib:stats_ptr";
      type uint32;
      description "Stats Pointer";
    }
    leaf accepted {
      xr:xr-xml-map "platform_pifib:accepted";
      type uint64;
      description "Accepted Packets Counter";
    }
    leaf dropped {
      xr:xr-xml-map "platform_pifib:dropped";
      type uint64;
      description "Dropped Packets Counter";
    }
    leaf cir {
      xr:xr-xml-map "platform_pifib:cir";
      type uint64;
      description "Committed Information Rate";
    }
    leaf flow-type {
      xr:xr-xml-map "platform_pifib:flow_type";
      type uint32;
      description "Flow type";
    }
    leaf priority {
      xr:xr-xml-map "platform_pifib:priority";
      type uint32;
      description "Flow priority or COS";
    }
    leaf sid {
      xr:xr-xml-map "platform_pifib:sid";
      type uint32;
      description "Stream ID";
    }
    leaf policer-avgrate {
      xr:xr-xml-map "platform_pifib:policer_avgrate";
      type uint32;
      description "Policer avg. rate limit";
    }
    leaf policer-burst {
      xr:xr-xml-map "platform_pifib:policer_burst";
      type uint32;
      description "Policer burst";
    }
    leaf lookup-priority {
      xr:xr-xml-map "platform_pifib:lookup_priority";
      type int32;
      description "Lookup priority";
    }
    leaf storage-priority {
      xr:xr-xml-map "platform_pifib:storage_priority";
      type int32;
      description "Storage priority";
    }
    leaf num-tm-entries {
      xr:xr-xml-map "platform_pifib:num_tm_entries";
      type int32;
      description "Number of TCAM entries used";
    }
    leaf sort-start-offset {
      xr:xr-xml-map "platform_pifib:sort_start_offset";
      type int32;
      description "Relative position in sorting order";
    }
    leaf tm-start-offset {
      xr:xr-xml-map "platform_pifib:tm_start_offset";
      type int32;
      description "Relative position in TCAM";
    }
    leaf entry-ptr {
      xr:xr-xml-map "platform_pifib:entry_ptr";
      type uint32;
      description "ptr to ifib_entry_st";
    }
    leaf entry-shadow-ptr {
      xr:xr-xml-map "platform_pifib:entry_shadow_ptr";
      type uint32;
      description "ptr to ifib_entry_shadow_st";
    }
    leaf list-node-ptr {
      xr:xr-xml-map "platform_pifib:list_node_ptr";
      type uint32;
      description "ptr to dlqueue list node";
    }
    leaf state {
      xr:xr-xml-map "platform_pifib:state";
      type uint8;
      description "state of pifib entry";
    }
    leaf retry-fail-cause {
      xr:xr-xml-map "platform_pifib:retry_fail_cause";
      type uint8;
      description "failure cause";
    }
    leaf num-retries {
      xr:xr-xml-map "platform_pifib:num_retries";
      type uint8;
      description "retries count";
    }
    leaf min-ttl {
      xr:xr-xml-map "platform_pifib:min_ttl";
      type uint8;
      description "Minimum TTL";
    }
    leaf u-type {
      xr:xr-xml-map "platform_pifib:u_type";
      type uint8;
      description "Union Key Type";
    }
    leaf remote-fgid {
      xr:xr-xml-map "platform_pifib:remote_fgid";
      type uint32;
      description "Remote FGID";
    }
    leaf acl-str {
      xr:xr-xml-map "platform_pifib:acl_str";
      type yang:hex-string;
      description "Acl name";
    }
    leaf no-stats {
      xr:xr-xml-map "platform_pifib:no_stats";
      type uint8;
      description "Stats not available";
    }
  }

  grouping PL-PIFIB-SHOW-STATS {
    description "Pre-IFIB global statistics";
    leaf accepted {
      xr:xr-xml-map "platform_pifib:accepted";
      type uint64;
      description "Deleted-entry accepted packets counter";
    }
    leaf dropped {
      xr:xr-xml-map "platform_pifib:dropped";
      type uint64;
      description "Deleted-entry dropped packets counter";
    }
    leaf clear-ts {
      xr:xr-xml-map "platform_pifib:clear_ts";
      type uint64;
      description "Statistics clear timestamp";
    }
    leaf no-stats-mem-err {
      xr:xr-xml-map "platform_pifib:no_stats_mem_err";
      type uint64;
      description "No statistics memory error";
    }
  }

  grouping PL-PIFIB-SHOW-BFD-DISC-ENTRY-INFO {
    description "PL PIFIB SHOW BFD DISC ENTRY INFO";
    leaf index {
      xr:xr-xml-map "platform_pifib:index";
      type uint8;
      description "index";
    }
    leaf is-mcast {
      xr:xr-xml-map "platform_pifib:is_mcast";
      type uint8;
      description "is mcast";
    }
    leaf fgid-or-vqi {
      xr:xr-xml-map "platform_pifib:fgid_or_vqi";
      type uint32;
      description "fgid or vqi";
    }
    leaf is-valid {
      xr:xr-xml-map "platform_pifib:is_valid";
      type uint8;
      description "is valid";
    }
    leaf policer-id {
      xr:xr-xml-map "platform_pifib:policer_id";
      type uint32;
      description "policer id";
    }
  }

  grouping PL-PIFIB-SHOW-BFD-DISC-ENTRY {
    description
      "Pre-IFIB platform specific bfd discriminator
      table entry data structure";

    list bfd-entry-info {
      description "Per bfd disc entry info";
      uses PL-PIFIB-SHOW-BFD-DISC-ENTRY-INFO;
    }
  }

  grouping PL-PIFIB-SHOW-STATIC-POLICE-INFO {
    description "PL PIFIB SHOW STATIC POLICE INFO";
    leaf punt-reason {
      xr:xr-xml-map "platform_pifib:punt_reason";
      type uint32;
      description "punt reason";
    }
    leaf sid {
      xr:xr-xml-map "platform_pifib:sid";
      type uint32;
      description "sid";
    }
    leaf flow-rate {
      xr:xr-xml-map "platform_pifib:flow_rate";
      type uint32;
      description "flow rate";
    }
    leaf burst-rate {
      xr:xr-xml-map "platform_pifib:burst_rate";
      type uint32;
      description "burst rate";
    }
    leaf accepted {
      xr:xr-xml-map "platform_pifib:accepted";
      type uint64;
      description "accepted";
    }
    leaf dropped {
      xr:xr-xml-map "platform_pifib:dropped";
      type uint64;
      description "dropped";
    }
    leaf punt-reason-string {
      xr:xr-xml-map "platform_pifib:punt_reason_string";
      type yang:hex-string;
      description "punt reason string";
    }
    leaf change-type {
      xr:xr-xml-map "platform_pifib:change_type";
      type uint8;
      description "change type";
    }
  }

  grouping PL-PIFIB-SHOW-STATIC-POLICE {
    description
      "Pre-IFIB platform specific punt reason data
      structure";

    list static-info {
      description "Per punt reason info";
      uses PL-PIFIB-SHOW-STATIC-POLICE-INFO;
    }
  }

  grouping PL-PIFIB-POLICE-INFO {
    description "PL PIFIB POLICE INFO";
    leaf avgrate {
      xr:xr-xml-map "platform_pifib:avgrate";
      type uint32;
      description "avgrate";
    }
    leaf burst {
      xr:xr-xml-map "platform_pifib:burst";
      type uint32;
      description "burst";
    }
    leaf static-avgrate {
      xr:xr-xml-map "platform_pifib:static_avgrate";
      type uint32;
      description "static avgrate";
    }
    leaf avgrate-type {
      xr:xr-xml-map "platform_pifib:avgrate_type";
      type uint32;
      description "avgrate type";
    }
    leaf accepted-stats {
      xr:xr-xml-map "platform_pifib:accepted_stats";
      type uint64;
      description "accepted stats";
    }
    leaf dropped-stats {
      xr:xr-xml-map "platform_pifib:dropped_stats";
      type uint64;
      description "dropped stats";
    }
    leaf policer {
      xr:xr-xml-map "platform_pifib:policer";
      type uint32;
      description "policer";
    }
    leaf iptos-value {
      xr:xr-xml-map "platform_pifib:iptos_value";
      type uint8;
      description "iptos value";
    }
    leaf change-type {
      xr:xr-xml-map "platform_pifib:change_type";
      type uint8;
      description "change type";
    }
    leaf acl-config {
      xr:xr-xml-map "platform_pifib:acl_config";
      type uint8;
      description "acl config";
    }
    leaf acl-str {
      xr:xr-xml-map "platform_pifib:acl_str";
      type yang:hex-string;
      description "acl str";
    }
  }

  grouping PL-PIFIB-SHOW-POLICE {
    description "Pre-IFIB platform specific police data structure";

    list police-info {
      description "Per flow type police info";
      uses PL-PIFIB-POLICE-INFO;
    }
  }

  grouping PL-PIFIB-SHOW-USAGE {
    description "LPTS Pre-IFIB TCAM Usage Information";
    leaf region {
      xr:xr-xml-map "platform_pifib:region";
      type uint8;
      description "Region Type";
    }
    leaf region-id-xr {
      xr:xr-xml-map "platform_pifib:region-id-xr";
      type uint8;
      description "Region ID";
    }
    leaf size {
      xr:xr-xml-map "platform_pifib:size";
      type uint32;
      description "Maximum Number of Entries in the Region";
    }
    leaf used {
      xr:xr-xml-map "platform_pifib:used";
      type uint32;
      description "Used Number of Entries in the Region";
    }
  }
}
