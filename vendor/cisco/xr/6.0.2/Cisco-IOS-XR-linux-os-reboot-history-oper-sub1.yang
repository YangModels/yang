submodule Cisco-IOS-XR-linux-os-reboot-history-oper-sub1 {

  belongs-to Cisco-IOS-XR-linux-os-reboot-history-oper {
    prefix Cisco-IOS-XR-linux-os-reboot-history-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR linux-os-reboot-history package operational data.

     Copyright (c) 2013-2015 by Cisco Systems, Inc.
     All rights reserved.";

  revision "2015-11-09" {
    description
      "IOS XR 6.0 revision.";
  }


  grouping HISTORY-DETAIL {
    description "Reboot history details";
    leaf no {
      xr:xr-xml-map "linux_os_reboot_history:No";
      type uint32;
      description "Number count";
    }
    leaf time {
      xr:xr-xml-map "linux_os_reboot_history:Time";
      type string;
      description "Time of reboot";
    }
    leaf cause-code {
      xr:xr-xml-map "linux_os_reboot_history:CauseCode";
      type uint32;
      description "Cause code for reboot";
    }
    leaf reason {
      xr:xr-xml-map "linux_os_reboot_history:Reason";
      type string;
      description "Reason for reboot";
    }
  }

  grouping HISTORY {
    description "Reboot history information";

    list reboot-history {
      description "Last Reboots";
      uses HISTORY-DETAIL;
    }
  }
}
