submodule Cisco-IOS-XR-dnx-netflow-oper-sub1 {

  belongs-to Cisco-IOS-XR-dnx-netflow-oper {
    prefix Cisco-IOS-XR-dnx-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-netflow package operational data.

     Copyright (c) 2013-2015 by Cisco Systems, Inc.
     All rights reserved.";

  revision "2015-11-09" {
    description
      "IOS XR 6.0 revision.";
  }

  typedef Flow-monitor-name {
    type string;
    description "Flow monitor name";
  }

  grouping NFSVR-COLLECTOR-INFO {
    description "Per collector information";
    leaf exporter-state {
      xr:xr-xml-map "netflow_server_types:ExporterState";
      type string;
      description "Exporter state";
    }
    leaf destination-address {
      xr:xr-xml-map "netflow_server_types:DestinationAddress";
      type string;
      description
        "Destination IPv4 address in AAA.BBB.CCC.DDD
        format";
    }
    leaf source-address {
      xr:xr-xml-map "netflow_server_types:SourceAddress";
      type string;
      description "Source IPv4 address in AAA.BBB.CCC.DDD format";
    }
    leaf vrf-name {
      xr:xr-xml-map "netflow_server_types:VRFName";
      type string;
      description "VRF Name";
    }
    leaf destination-port {
      xr:xr-xml-map "netflow_server_types:DestinationPort";
      type uint16;
      description "Destination port number";
    }
    leaf souce-port {
      xr:xr-xml-map "netflow_server_types:SoucePort";
      type uint16;
      description "Source port number";
    }
    leaf transport-protocol {
      xr:xr-xml-map "netflow_server_types:TransportProtocol";
      type string;
      description "Transport protocol";
    }
    leaf packets-sent {
      xr:xr-xml-map "netflow_server_types:PacketsSent";
      type uint64;
      description "Packets sent";
    }
    leaf flows-sent {
      xr:xr-xml-map "netflow_server_types:FlowsSent";
      type uint64;
      description "Flows sent";
    }
    leaf templates-sent {
      xr:xr-xml-map "netflow_server_types:TemplatesSent";
      type uint64;
      description "Templates sent";
    }
    leaf option-templates-sent {
      xr:xr-xml-map "netflow_server_types:OptionTemplatesSent";
      type uint64;
      description "Option templates sent";
    }
    leaf option-data-sent {
      xr:xr-xml-map "netflow_server_types:OptionDataSent";
      type uint64;
      description "Option data sent";
    }
    leaf bytes-sent {
      xr:xr-xml-map "netflow_server_types:BytesSent";
      type uint64;
      units "byte";
      description "Bytes sent";
    }
    leaf flow-bytes-sent {
      xr:xr-xml-map "netflow_server_types:FlowBytesSent";
      type uint64;
      units "byte";
      description "Flow bytes sent";
    }
    leaf template-bytes-sent {
      xr:xr-xml-map "netflow_server_types:TemplateBytesSent";
      type uint64;
      units "byte";
      description "Template bytes sent";
    }
    leaf option-template-bytes-sent {
      xr:xr-xml-map "netflow_server_types:OptionTemplateBytesSent";
      type uint64;
      units "byte";
      description "Option template bytes sent";
    }
    leaf option-data-bytes-sent {
      xr:xr-xml-map "netflow_server_types:OptionDataBytesSent";
      type uint64;
      units "byte";
      description "Option data bytes sent";
    }
    leaf packets-dropped {
      xr:xr-xml-map "netflow_server_types:PacketsDropped";
      type uint64;
      description "Packets dropped";
    }
    leaf flows-dropped {
      xr:xr-xml-map "netflow_server_types:FlowsDropped";
      type uint64;
      description "Flows dropped";
    }
    leaf templates-dropped {
      xr:xr-xml-map "netflow_server_types:TemplatesDropped";
      type uint64;
      description "Templates dropped";
    }
    leaf option-templates-dropped {
      xr:xr-xml-map "netflow_server_types:OptionTemplatesDropped";
      type uint64;
      description "Option templates dropped";
    }
    leaf option-data-dropped {
      xr:xr-xml-map "netflow_server_types:OptionDataDropped";
      type uint64;
      description "Option data dropped";
    }
    leaf bytes-dropped {
      xr:xr-xml-map "netflow_server_types:BytesDropped";
      type uint64;
      units "byte";
      description "Bytes dropped";
    }
    leaf flow-bytes-dropped {
      xr:xr-xml-map "netflow_server_types:FlowBytesDropped";
      type uint64;
      units "byte";
      description "Flow bytes dropped";
    }
    leaf template-bytes-dropped {
      xr:xr-xml-map "netflow_server_types:TemplateBytesDropped";
      type uint64;
      units "byte";
      description "Template bytes dropped";
    }
    leaf option-template-bytes-dropped {
      xr:xr-xml-map "netflow_server_types:OptionTemplateBytesDroppe"+
        "d";
      type uint64;
      units "byte";
      description "Option template bytes dropped";
    }
    leaf option-data-bytes-dropped {
      xr:xr-xml-map "netflow_server_types:OptionDataBytesDropped";
      type uint64;
      description "Option data dropped";
    }
    leaf last-hour-packest-sent {
      xr:xr-xml-map "netflow_server_types:LastHourPackestSent";
      type uint64;
      description "Total packets exported over the last one hour";
    }
    leaf last-hour-bytes-sent {
      xr:xr-xml-map "netflow_server_types:LastHourBytesSent";
      type uint64;
      units "byte";
      description "Total bytes exported over the last one hour";
    }
    leaf last-hour-flows-sent {
      xr:xr-xml-map "netflow_server_types:LastHourFlowsSent";
      type uint64;
      description "Total flows exported over the of last one hour";
    }
    leaf last-minute-packets {
      xr:xr-xml-map "netflow_server_types:LastMinutePackets";
      type uint64;
      description "Total packets exported over the last one minute";
    }
    leaf last-minute-bytes-sent {
      xr:xr-xml-map "netflow_server_types:LastMinuteBytesSent";
      type uint64;
      units "byte";
      description "Total bytes exported over the last one minute";
    }
    leaf last-minute-flows-sent {
      xr:xr-xml-map "netflow_server_types:LastMinuteFlowsSent";
      type uint64;
      description "Total flows exported over the last one minute";
    }
    leaf last-second-packets-sent {
      xr:xr-xml-map "netflow_server_types:LastSecondPacketsSent";
      type uint64;
      description "Total packets exported over the last one second";
    }
    leaf last-second-bytes-sent {
      xr:xr-xml-map "netflow_server_types:LastSecondBytesSent";
      type uint64;
      units "byte";
      description "Total bytes exported over the last one second";
    }
    leaf last-second-flows-sent {
      xr:xr-xml-map "netflow_server_types:LastSecondFlowsSent";
      type uint64;
      description "Total flows exported over the last one second";
    }
  }

  grouping NFSVR-SHOW-FLOW-EXPORTER-RESP-STATS {
    description "Flow exporter information";
    leaf name {
      xr:xr-xml-map "netflow_server_types:Name";
      type string;
      description "Exporter name";
    }
    leaf memory-usage {
      xr:xr-xml-map "netflow_server_types:MemoryUsage";
      type uint32;
      description "Memory usage";
    }
    leaf-list used-by-flow-monitor {
      xr:xr-xml-map "netflow_server_types:UsedByFlowMonitor";
      type Flow-monitor-name;
      description "List of flow monitors that use the exporter";
    }

    list collector {
      description "Statistics of all collectors";
      uses NFSVR-COLLECTOR-INFO;
    }
  }

  grouping NFSVR-SHOW-FLOW-EXPORTER-RESP-ARRAY {
    description "Flow exporter information";

    list statistic {
      description "Array of flow exporters";
      uses NFSVR-SHOW-FLOW-EXPORTER-RESP-STATS;
    }
  }
}
