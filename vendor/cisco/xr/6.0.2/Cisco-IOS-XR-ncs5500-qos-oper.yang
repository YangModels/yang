module Cisco-IOS-XR-ncs5500-qos-oper {

  /*** NAMESPACE / PREFIX DEFINITION ***/

  namespace "http://cisco.com/ns/yang/Cisco-IOS-XR-ncs5500-qos-oper";


  prefix "ncs5500-qos-oper";

  /*** LINKAGE (IMPORTS / INCLUDES) ***/

  import Cisco-IOS-XR-types { prefix "xr"; }

  include Cisco-IOS-XR-ncs5500-qos-oper-sub2 {
    revision-date 2015-11-09;
  }

  include Cisco-IOS-XR-ncs5500-qos-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-qos package operational data.

     This module contains definitions
     for the following management objects:
       platform-qos: DNX QoS EA operational data

     Copyright (c) 2013-2015 by Cisco Systems, Inc.
     All rights reserved.";

  revision "2015-11-09" {
    description
      "IOS XR 6.0 revision.";
  }


  grouping POLICY-DETAILS {
    description
      "Common node of interface, bundle-interface,
      member-interface";

    container policy-details {
      xr:xr-xml-map "qos_ea_fretta_interface_oper:PolicyDetails";
      description "Policy Details";
      uses DNX-QOSEA-SHOW-IF-QOS-INFO-ST;
    }
  }

  grouping CLASS-TABLE {
    description
      "Common node of interface, bundle-interface,
      member-interface";

    container classes {
      xr:xr-xml-map "qos_ea_fretta_interface_oper:ClassTable";
      description "QoS list of class names";

      list class {
        xr:xr-xml-map "qos_ea_fretta_interface_oper:Class";
        key "level-one-class-name";
        description "QoS policy class";
        leaf level-one-class-name {
          xr:xr-xml-map "qos_ea_fretta_interface_oper:LevelOneClass"+
            "Name";
          type string;
          description "QoS policy class name at level 1";
        }
        leaf level-two-class-name {
          xr:xr-xml-map "qos_ea_fretta_interface_oper:LevelTwoClass"+
            "Name";
          type string;
          description "QoS policy child class name at level 2";
        }
        uses DNX-QOSEA-SHOW-CLASS-ST;
      }
    }
  }

  container platform-qos {
    xr:xr-xml-map "qos_ea_fretta_interface_oper:PlatformQoS";
    config false;
    description "DNX QoS EA operational data";

    container nodes {
      xr:xr-xml-map "qos_ea_fretta_interface_oper:NodeTable";
      description
        "List of nodes with platform specific QoS
        configuration";

      list node {
        xr:xr-xml-map "qos_ea_fretta_interface_oper:Node";
        key "node-name";
        description "Node with platform specific QoS configuration";

        container bundle-interfaces {
          xr:xr-xml-map "qos_ea_fretta_interface_oper:BundleInterfa"+
            "ceTable";
          description "QoS list of bundle interfaces";

          list bundle-interface {
            xr:xr-xml-map "qos_ea_fretta_interface_oper:BundleInter"+
              "face";
            key "interface-name";
            description "QoS interface names";

            container member-interfaces {
              xr:xr-xml-map "qos_ea_fretta_interface_oper:MemberInt"+
                "erfaceTable";
              description "QoS list of member interfaces";

              list member-interface {
                xr:xr-xml-map "qos_ea_fretta_interface_oper:MemberI"+
                  "nterface";
                key "interface-name";
                description "QoS interface names";
                leaf interface-name {
                  xr:xr-xml-map "qos_ea_fretta_interface_oper:Inter"+
                    "faceName";
                  type xr:Interface-name;
                  description "Member interface";
                }
                uses POLICY-DETAILS;
                uses CLASS-TABLE;
              }
            }
            leaf interface-name {
              xr:xr-xml-map "qos_ea_fretta_interface_oper:Interface"+
                "Name";
              type xr:Interface-name;
              description "Bundle interface name";
            }
            leaf npu-id {
              xr:xr-xml-map "qos_ea_fretta_interface_oper:NPU_ID";
              type int32;
              description "NPU ID";
            }
            leaf qos-direction {
              xr:xr-xml-map "qos_ea_fretta_interface_oper:QoSDirect"+
                "ion";
              type string;
              description
                "The interface direction on which QoS is
                applied to.";
            }
            uses POLICY-DETAILS;
            uses CLASS-TABLE;
          }
        }

        container interfaces {
          xr:xr-xml-map "qos_ea_fretta_interface_oper:InterfaceTabl"+
            "e";
          description "QoS list of interfaces";

          list interface {
            xr:xr-xml-map "qos_ea_fretta_interface_oper:Interface";
            key "interface-name";
            description "QoS interface names";
            leaf interface-name {
              xr:xr-xml-map "qos_ea_fretta_interface_oper:Interface"+
                "Name";
              type xr:Interface-name;
              description "The name of the interface";
            }
            leaf qos-direction {
              xr:xr-xml-map "qos_ea_fretta_interface_oper:QoSDirect"+
                "ion";
              type string;
              description
                "The interface direction on which QoS is
                applied to.";
            }
            uses POLICY-DETAILS;
            uses CLASS-TABLE;
          }
        }

        container remote-interfaces {
          xr:xr-xml-map "qos_ea_fretta_interface_oper:RemoteInterfa"+
            "ceTable";
          description "QoS list of remote interfaces";

          list remote-interface {
            xr:xr-xml-map "qos_ea_fretta_interface_oper:RemoteInter"+
              "face";
            key "interface-name";
            description "QoS remote interface names";
            leaf interface-name {
              xr:xr-xml-map "qos_ea_fretta_interface_oper:Interface"+
                "Name";
              type xr:Interface-name;
              description "The name of the remote interface";
            }
            uses DNX-QOSEA-SHOW-REMOTE-IF-INFO-ST;
          }
        }
        leaf node-name {
          xr:xr-xml-map "qos_ea_fretta_interface_oper:NodeName";
          type xr:Node-id;
          description "Node name";
        }
      }
    }
  }
}
