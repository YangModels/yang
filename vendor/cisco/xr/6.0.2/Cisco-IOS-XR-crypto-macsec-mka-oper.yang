module Cisco-IOS-XR-crypto-macsec-mka-oper {

  /*** NAMESPACE / PREFIX DEFINITION ***/

  namespace "http://cisco.com/ns/yang"+
    "/Cisco-IOS-XR-crypto-macsec-mka-oper";


  prefix "crypto-macsec-mka-oper";

  /*** LINKAGE (IMPORTS / INCLUDES) ***/

  import Cisco-IOS-XR-types { prefix "xr"; }

  include Cisco-IOS-XR-crypto-macsec-mka-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-mka package operational data.

     This module contains definitions
     for the following management objects:
       macsec: MACSec operational data

     Copyright (c) 2013-2015 by Cisco Systems, Inc.
     All rights reserved.";

  revision "2015-11-09" {
    description
      "IOS XR 6.0 revision.";
  }


  container macsec {
    xr:xr-xml-map "macsec_mka_oper:MACSEC";
    config false;
    description "MACSec operational data";

    container mka {
      xr:xr-xml-map "macsec_mka_oper:mka";
      description "MKA Data";

      container nodes {
        xr:xr-xml-map "macsec_mka_oper:NodeTable";
        description "NodeTable for all the nodes";

        list node {
          xr:xr-xml-map "macsec_mka_oper:Node";
          key "node-name";
          description "MACSec Data for a particular node";

          container interfaces {
            xr:xr-xml-map "macsec_mka_oper:session";
            description "Session data";

            list interface {
              xr:xr-xml-map "macsec_mka_oper:interface";
              key "name";
              description "Details value";
              leaf name {
                xr:xr-xml-map "macsec_mka_oper:Name";
                type xr:Interface-name;
                description "Value";
              }
              uses MKA-SESSION;
            }
          }
          leaf node-name {
            xr:xr-xml-map "macsec_mka_oper:NodeName";
            type xr:Node-id;
            description "Node";
          }
        }
      }
    }
  }
}
