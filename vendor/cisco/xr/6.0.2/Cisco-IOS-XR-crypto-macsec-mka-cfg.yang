module Cisco-IOS-XR-crypto-macsec-mka-cfg {

  /*** NAMESPACE / PREFIX DEFINITION ***/

  namespace "http://cisco.com/ns/yang"+
    "/Cisco-IOS-XR-crypto-macsec-mka-cfg";


  prefix "crypto-macsec-mka-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-mka package configuration.

     This module contains definitions
     for the following management objects:
       mac-sec: MACSec MKA

     Copyright (c) 2013-2015 by Cisco Systems, Inc.
     All rights reserved.";

  revision "2015-11-09" {
    description
      "IOS XR 6.0 revision.";
  }

  typedef Macsec-mka-window-size {
    type uint32 {
      range "0..1024";
    }
    description "Macsec mka window size";
  }
  typedef Macsec-mka-security-policy {
    type enumeration {
      enum should-secure {
        value 0;
        description "should secure";
      }
      enum must-secure {
        value 1;
        description "must secure";
      }
    }
    description "Macsec mka security policy";
  }
  typedef Macsec-mka-key-server-priority {
    type uint32 {
      range "0..255";
    }
    description "Macsec mka key server priority";
  }
  typedef Macsec-mka-cipher-suite {
    type enumeration {
      enum gcm-aes-128 {
        value 1;
        description "GCM AES 128";
      }
      enum gcm-aes-256 {
        value 2;
        description "GCM AES 256";
      }
      enum gcm-aes-xpn-128 {
        value 3;
        description "GCM AES XPN 128";
      }
      enum gcm-aes-xpn-256 {
        value 4;
        description "GCM AES XPN 256";
      }
    }
    description "Macsec mka cipher suite";
  }
  typedef Macsec-mka-conf-offset {
    type enumeration {
      enum conf-off-set-0 {
        value 0;
        description "CONF OFFSET 0";
      }
      enum conf-off-set-30 {
        value 30;
        description "CONF OFFSET 30";
      }
      enum conf-off-set-50 {
        value 50;
        description "CONF OFFSET 50";
      }
    }
    description "Macsec mka conf offset";
  }
  typedef Macsec-mka-vlan-tags-in-clear {
    type uint32 {
      range "1..2";
    }
    description "Macsec mka vlan tags in clear";
  }

  container mac-sec {
    xr:xr-xml-map "macsec_mka_cfg:MACSec";
    description "MACSec MKA";

    list policy {
      xr:xr-xml-map "macsec_mka_cfg:Policy";
      key "name";
      description "MACSec Policy";
      leaf security-policy {
        xr:xr-xml-map "macsec_mka_cfg:SecurityPolicy";
        xr:xr-cli-map "macsec-policy <string> security-policy <enum"+
          "> ";
        type Macsec-mka-security-policy;
        description "Security-Policy of Policy";
      }
      leaf key-server-priority {
        xr:xr-xml-map "macsec_mka_cfg:KeyServerPriority";
        xr:xr-cli-map "macsec-policy <string> key-server-priority <"+
          "number> ";
        type Macsec-mka-key-server-priority;
        description "Key-Server-Priority of Policy";
      }
      leaf conf-offset {
        xr:xr-xml-map "macsec_mka_cfg:ConfOffset";
        xr:xr-cli-map "macsec-policy <string> conf-offset <enum> ";
        type Macsec-mka-conf-offset;
        description "Conf-Offset of Policy";
      }
      leaf window-size {
        xr:xr-xml-map "macsec_mka_cfg:WindowSize";
        xr:xr-cli-map "macsec-policy <string> window-size <number> ";
        type Macsec-mka-window-size;
        description "Window-Size of Policy";
      }
      leaf cipher-suite {
        xr:xr-xml-map "macsec_mka_cfg:CipherSuite";
        xr:xr-cli-map "macsec-policy <string> cipher-suite <enum> ";
        type Macsec-mka-cipher-suite;
        description "Cipher-suite of Policy";
      }
      leaf vlan-tags-in-clear {
        xr:xr-xml-map "macsec_mka_cfg:VlanTagsInClear";
        xr:xr-cli-map "macsec-policy <string> vlan-tags-in-clear <n"+
          "umber> ";
        type Macsec-mka-vlan-tags-in-clear;
        description "VLAN-Tags-In-Clear of Policy";
      }
      leaf name {
        xr:xr-xml-map "macsec_mka_cfg:Name";
        type xr:Cisco-ios-xr-string;
        description "Name of the Policy";
      }
    }
  }
}
