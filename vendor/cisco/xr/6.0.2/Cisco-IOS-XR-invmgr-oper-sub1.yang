submodule Cisco-IOS-XR-invmgr-oper-sub1 {

  belongs-to Cisco-IOS-XR-invmgr-oper {
    prefix Cisco-IOS-XR-invmgr-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR invmgr package operational data.

     Copyright (c) 2013-2015 by Cisco Systems, Inc.
     All rights reserved.";

  revision "2015-11-09" {
    description
      "IOS XR 6.0 revision.";
  }


  grouping RMA-DETAIL {
    description "EEPROM RMA data content";
    leaf test-history {
      xr:xr-xml-map "invmgr_show_oper_data:TestHistory";
      type string {
        length "0..255";
      }
      description "Test history";
    }
    leaf rma-number {
      xr:xr-xml-map "invmgr_show_oper_data:RMANumber";
      type string {
        length "0..255";
      }
      description "RMA tracking number format is N-N-N";
    }
    leaf rma-history {
      xr:xr-xml-map "invmgr_show_oper_data:RMAHistory";
      type string {
        length "0..255";
      }
      description "RMA history";
    }
  }

  grouping DIAG-EEPROM {
    description "Diag EEPROM data content";

    container rma {
      description "RMA Data";
      uses RMA-DETAIL;
    }
    leaf description {
      xr:xr-xml-map "invmgr_show_oper_data:Description";
      type string {
        length "0..255";
      }
      description "A textual description of physical entity";
    }
    leaf idprom-format-rev {
      xr:xr-xml-map "invmgr_show_oper_data:IDPROMFormatRev";
      type string {
        length "0..255";
      }
      description "IDPROM Format Revision";
    }
    leaf controller-family {
      xr:xr-xml-map "invmgr_show_oper_data:ControllerFamily";
      type string {
        length "0..255";
      }
      description "Controller family";
    }
    leaf controller-type {
      xr:xr-xml-map "invmgr_show_oper_data:ControllerType";
      type string {
        length "0..255";
      }
      description "Controller type";
    }
    leaf vid {
      xr:xr-xml-map "invmgr_show_oper_data:VID";
      type string {
        length "0..255";
      }
      description "Version ID";
    }
    leaf hwid {
      xr:xr-xml-map "invmgr_show_oper_data:HWID";
      type string {
        length "0..255";
      }
      description "Hardware Revision";
    }
    leaf pid {
      xr:xr-xml-map "invmgr_show_oper_data:PID";
      type string {
        length "0..255";
      }
      description "Product ID";
    }
    leaf udi-description {
      xr:xr-xml-map "invmgr_show_oper_data:UDIDescription";
      type string {
        length "0..255";
      }
      description "UDI description";
    }
    leaf udi-name {
      xr:xr-xml-map "invmgr_show_oper_data:UDIName";
      type string {
        length "0..255";
      }
      description "UDI name";
    }
    leaf clei {
      xr:xr-xml-map "invmgr_show_oper_data:CLEI";
      type string {
        length "0..255";
      }
      description
        "Common Language Equipment Identifier (CLEI) code";
    }
    leaf eci {
      xr:xr-xml-map "invmgr_show_oper_data:ECI";
      type string {
        length "0..255";
      }
      description "Equipment Catalog Item (ECI) number";
    }
    leaf top-assem-part-num {
      xr:xr-xml-map "invmgr_show_oper_data:TopAssemPartNum";
      type string {
        length "0..255";
      }
      description "Top assembly part number";
    }
    leaf top-assem-vid {
      xr:xr-xml-map "invmgr_show_oper_data:TopAssemVID";
      type string {
        length "0..255";
      }
      description "Top assembly revision number";
    }
    leaf pca-num {
      xr:xr-xml-map "invmgr_show_oper_data:PCANum";
      type string {
        length "0..255";
      }
      description "PCA number";
    }
    leaf pcavid {
      xr:xr-xml-map "invmgr_show_oper_data:PCAVID";
      type string {
        length "0..255";
      }
      description "PCA revision ID";
    }
    leaf chassis-sid {
      xr:xr-xml-map "invmgr_show_oper_data:ChassisSID";
      type string {
        length "0..255";
      }
      description "Chassis serial number";
    }
    leaf dev-num1 {
      xr:xr-xml-map "invmgr_show_oper_data:DevNum1";
      type string {
        length "0..255";
      }
      description "Deviation Number # 1";
    }
    leaf dev-num2 {
      xr:xr-xml-map "invmgr_show_oper_data:DevNum2";
      type string {
        length "0..255";
      }
      description "Deviation Number # 2";
    }
    leaf dev-num3 {
      xr:xr-xml-map "invmgr_show_oper_data:DevNum3";
      type string {
        length "0..255";
      }
      description "Deviation Number # 3";
    }
    leaf dev-num4 {
      xr:xr-xml-map "invmgr_show_oper_data:DevNum4";
      type string {
        length "0..255";
      }
      description "Deviation Number # 4";
    }
    leaf dev-num5 {
      xr:xr-xml-map "invmgr_show_oper_data:DevNum5";
      type string {
        length "0..255";
      }
      description "Deviation Number # 5";
    }
    leaf dev-num6 {
      xr:xr-xml-map "invmgr_show_oper_data:DevNum6";
      type string {
        length "0..255";
      }
      description "Deviation Number # 6";
    }
    leaf dev-num7 {
      xr:xr-xml-map "invmgr_show_oper_data:DevNum7";
      type string {
        length "0..255";
      }
      description "Deviation Number # 7";
    }
    leaf manu-test-data {
      xr:xr-xml-map "invmgr_show_oper_data:ManuTest_Data";
      type string {
        length "0..255";
      }
      description "Manufacturing Test Data";
    }
    leaf asset-id {
      xr:xr-xml-map "invmgr_show_oper_data:AssetID";
      type string {
        length "0..255";
      }
      description "Asset ID";
    }
    leaf asset-alias {
      xr:xr-xml-map "invmgr_show_oper_data:AssetAlias";
      type string {
        length "0..255";
      }
      description "Asset Alias";
    }
    leaf base-mac-address1 {
      xr:xr-xml-map "invmgr_show_oper_data:BaseMacAddress1";
      type string {
        length "0..255";
      }
      description "Base Mac Address #1";
    }
    leaf mac-add-blk-size1 {
      xr:xr-xml-map "invmgr_show_oper_data:MacAddBlkSize1";
      type string {
        length "0..255";
      }
      description "Mac Address Block Size #1";
    }
    leaf base-mac-address2 {
      xr:xr-xml-map "invmgr_show_oper_data:BaseMacAddress2";
      type string {
        length "0..255";
      }
      description "Base Mac Address #2";
    }
    leaf mac-add-blk-size2 {
      xr:xr-xml-map "invmgr_show_oper_data:MacAddBlkSize2";
      type string {
        length "0..255";
      }
      description "Mac Address Block Size #2";
    }
    leaf base-mac-address3 {
      xr:xr-xml-map "invmgr_show_oper_data:BaseMacAddress3";
      type string {
        length "0..255";
      }
      description "Base Mac Address #3";
    }
    leaf mac-add-blk-size3 {
      xr:xr-xml-map "invmgr_show_oper_data:MacAddBlkSize3";
      type string {
        length "0..255";
      }
      description "Mac Address Block Size #3";
    }
    leaf base-mac-address4 {
      xr:xr-xml-map "invmgr_show_oper_data:BaseMacAddress4";
      type string {
        length "0..255";
      }
      description "Base Mac Address #4";
    }
    leaf mac-add-blk-size4 {
      xr:xr-xml-map "invmgr_show_oper_data:MacAddBlkSize4";
      type string {
        length "0..255";
      }
      description "Mac Address Block Size #4";
    }
    leaf pcb-serial-num {
      xr:xr-xml-map "invmgr_show_oper_data:PcbSerialNum";
      type string {
        length "0..255";
      }
      description "PCB Serial Number";
    }
    leaf power-supply-type {
      xr:xr-xml-map "invmgr_show_oper_data:PowerSupplyType";
      type string {
        length "0..255";
      }
      description "Power Supply Type";
    }
    leaf power-consumption {
      xr:xr-xml-map "invmgr_show_oper_data:PowerConsumption";
      type string {
        length "0..255";
      }
      description "Power Consumption";
    }
    leaf block-signature {
      xr:xr-xml-map "invmgr_show_oper_data:BlockSignature";
      type string {
        length "0..255";
      }
      description "Block Signature";
    }
    leaf block-version {
      xr:xr-xml-map "invmgr_show_oper_data:BlockVersion";
      type string {
        length "0..255";
      }
      description "Block Version";
    }
    leaf block-length {
      xr:xr-xml-map "invmgr_show_oper_data:BlockLength";
      type string {
        length "0..255";
      }
      description "Block Length";
    }
    leaf block-checksum {
      xr:xr-xml-map "invmgr_show_oper_data:BlockChecksum";
      type string {
        length "0..255";
      }
      description "Block Checksum";
    }
    leaf eeprom-size {
      xr:xr-xml-map "invmgr_show_oper_data:EEPROMSize";
      type string {
        length "0..255";
      }
      description "EEPROM Size";
    }
    leaf block-count {
      xr:xr-xml-map "invmgr_show_oper_data:BlockCount";
      type string {
        length "0..255";
      }
      description "Block Count";
    }
    leaf fru-major-type {
      xr:xr-xml-map "invmgr_show_oper_data:FRUMajorType";
      type string {
        length "0..255";
      }
      description "FRU Major Type";
    }
    leaf fru-minor-type {
      xr:xr-xml-map "invmgr_show_oper_data:FRUMinorType";
      type string {
        length "0..255";
      }
      description "FRU Minor Type";
    }
    leaf oem-string {
      xr:xr-xml-map "invmgr_show_oper_data:OEMString";
      type string {
        length "0..255";
      }
      description "OEM String";
    }
    leaf product-id {
      xr:xr-xml-map "invmgr_show_oper_data:ProductID";
      type string {
        length "0..255";
      }
      description "Product ID";
    }
    leaf serial-number {
      xr:xr-xml-map "invmgr_show_oper_data:SerialNumber";
      type string {
        length "0..255";
      }
      description "Serial Number";
    }
    leaf part-number {
      xr:xr-xml-map "invmgr_show_oper_data:PartNumber";
      type string {
        length "0..255";
      }
      description "Part Number";
    }
    leaf part-revision {
      xr:xr-xml-map "invmgr_show_oper_data:PartRevision";
      type string {
        length "0..255";
      }
      description "Part Revision";
    }
    leaf mfg-deviation {
      xr:xr-xml-map "invmgr_show_oper_data:MFGDeviation";
      type string {
        length "0..255";
      }
      description "MFG Deviation";
    }
    leaf hw-version {
      xr:xr-xml-map "invmgr_show_oper_data:HWVersion";
      type string {
        length "0..255";
      }
      description "Hardware Version";
    }
    leaf mfg-bits {
      xr:xr-xml-map "invmgr_show_oper_data:MFGBits";
      type string {
        length "0..255";
      }
      description "MFG Bits";
    }
    leaf engineer-use {
      xr:xr-xml-map "invmgr_show_oper_data:EngineerUse";
      type string {
        length "0..255";
      }
      description "Engineer Use";
    }
    leaf snmpoid {
      xr:xr-xml-map "invmgr_show_oper_data:SNMPOID";
      type string {
        length "0..255";
      }
      description "SNMP OID";
    }
    leaf rma-code {
      xr:xr-xml-map "invmgr_show_oper_data:RMACode";
      type string {
        length "0..255";
      }
      description "RMA Code";
    }
  }

  grouping INVMGR-EEPROM-OPAQUE-DATA {
    description "invmgr eeprom opaque data";

    container eeprom {
      description "EEPROM data not from hex data";
      uses DIAG-EEPROM;
    }
    leaf inv-card-type {
      xr:xr-xml-map "invmgr_show_oper_data:inv_card_type";
      type uint8;
      description "Inventory card type";
    }
    leaf opaque-data {
      xr:xr-xml-map "invmgr_show_oper_data:opaque_data";
      type yang:hex-string;
      description "EEPROM hex data";
    }
    leaf opaque-data-size {
      xr:xr-xml-map "invmgr_show_oper_data:opaque_data_size";
      type uint32;
      description "size of the EEPROM hex data";
    }
    leaf has-eeprom {
      xr:xr-xml-map "invmgr_show_oper_data:has_eeprom";
      type uint32;
      description "use eeprom instead of opaque data";
    }
    leaf description {
      xr:xr-xml-map "invmgr_show_oper_data:description";
      type string {
        length "0..255";
      }
      description "A textual description of physical entity";
    }
  }
}
