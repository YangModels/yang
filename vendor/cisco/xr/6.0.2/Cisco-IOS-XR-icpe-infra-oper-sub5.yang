submodule Cisco-IOS-XR-icpe-infra-oper-sub5 {

  belongs-to Cisco-IOS-XR-icpe-infra-oper {
    prefix Cisco-IOS-XR-icpe-infra-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2015 by Cisco Systems, Inc.
     All rights reserved.";

  revision "2015-11-09" {
    description
      "IOS XR 6.0 revision.";
  }

  typedef Icpe-oper-discd-link-state {
    type enumeration {
      enum icpe-oper-discd-link-state-stopped {
        description "Stopped";
      }
      enum icpe-oper-discd-link-state-probing {
        description "Probing";
      }
      enum icpe-oper-discd-link-state-configuring {
        description "Configuring";
      }
      enum icpe-oper-discd-link-state-ready {
        description "Ready";
      }
    }
    description "Icpe oper discd link state";
  }
  typedef Icpe-oper-port {
    type enumeration {
      enum icpe-oper-port-unknown {
        description "Unknown";
      }
      enum icpe-oper-port-gigabit-ethernet {
        description "Gigabit ethernet";
      }
      enum icpe-oper-port-ten-gig-e {
        description "Ten gig e";
      }
    }
    description "Icpe oper port";
  }
  typedef Icpe-oper-install-state {
    type enumeration {
      enum icpe-oper-install-state-stable {
        description "Stable";
      }
      enum icpe-oper-install-state-transferring {
        description "Transferring";
      }
      enum icpe-oper-install-state-transferred {
        description "Transferred";
      }
      enum icpe-oper-install-state-installing {
        description "Installing";
      }
    }
    description "Icpe oper install state";
  }
  typedef Icpe-gco-oper-control-reason {
    type enumeration {
      enum icpe-gco-oper-control-reason-unknown-error {
        description "Unknown error";
      }
      enum icpe-gco-oper-control-reason-wrong-chassis-type {
        description "Wrong chassis type";
      }
      enum icpe-gco-oper-control-reason-wrong-chassis-serial {
        description "Wrong chassis serial";
      }
      enum icpe-gco-oper-control-reason-needs-to-upgrade {
        description "Needs to upgrade";
      }
      enum icpe-gco-oper-control-reason-none {
        description "None";
      }
    }
    description "Icpe gco oper control reason";
  }
  typedef Icpe-oper-sdacp-sess-state {
    type enumeration {
      enum icpe-oper-sdacp-sess-state-not-created {
        description "Not created";
      }
      enum icpe-oper-sdacp-sess-state-created {
        description "Created";
      }
      enum icpe-oper-sdacp-sess-state-authentication-not-ok {
        description "Authentication not OK";
      }
      enum icpe-oper-sdacp-sess-state-authentication-ok {
        description "Authentication OK";
      }
      enum icpe-oper-sdacp-sess-state-version-not-ok {
        description "Version not OK";
      }
      enum icpe-oper-sdacp-sess-state-up {
        description "Up";
      }
      enum icpe-oper-sdacp-sess-state-issu {
        description "ISSU";
      }
    }
    description "Icpe oper sdacp sess state";
  }
  typedef Icpe-oper-conflict {
    type enumeration {
      enum icpe-oper-conflict-not-calculated {
        description "Not calculated";
      }
      enum icpe-oper-conflict-no-conflict {
        description "No conflict";
      }
      enum icpe-oper-conflict-satellite-not-configured {
        description "Satellite not configured";
      }
      enum icpe-oper-conflict-satellite-no-type {
        description "Satellite no type";
      }
      enum icpe-oper-conflict-satellite-id-invalid {
        description "Satellite id invalid";
      }
      enum icpe-oper-conflict-satellite-no-ipv4-addr {
        description "Satellite no ipv4 addr";
      }
      enum icpe-oper-conflict-satellite-conflicting-ipv4-addr {
        description "Satellite conflicting ipv4 addr";
      }
      enum icpe-oper-conflict-no-configured-links {
        description "No configured links";
      }
      enum icpe-oper-conflict-no-discovered-links {
        description "No discovered links";
      }
      enum icpe-oper-conflict-invalid-ports {
        description "Invalid ports";
      }
      enum icpe-oper-conflict-ports-overlap {
        description "Ports overlap";
      }
      enum icpe-oper-conflict-waiting-for-ipv4-addr {
        description "Waiting for ipv4 addr";
      }
      enum icpe-oper-conflict-waiting-for-vrf {
        description "Waiting for VRF";
      }
      enum icpe-oper-conflict-different-ipv4-addr {
        description "Different ipv4 addr";
      }
      enum icpe-oper-conflict-different-vrf {
        description "Different VRF";
      }
      enum icpe-oper-conflict-satellite-link-ipv4-overlap {
        description "Satellite link ipv4 overlap";
      }
      enum icpe-oper-conflict-waiting-for-ident {
        description "Waiting for ident";
      }
      enum icpe-oper-conflict-multiple-ids {
        description "Multiple ids";
      }
      enum icpe-oper-conflict-multiple-satellites {
        description "Multiple satellites";
      }
      enum icpe-oper-conflict-ident-rejected {
        description "Ident rejected";
      }
      enum icpe-oper-conflict-interface-down {
        description "Interface down";
      }
      enum icpe-oper-conflict-auto-ip-unavailable {
        description "Auto IP unavailable";
      }
      enum icpe-oper-conflict-satellite-auto-ip-link-manual-ip {
        description "Satellite auto IP link manual IP";
      }
      enum icpe-oper-conflict-link-auto-ip-satellite-manual-ip {
        description "Link auto IP satellite manual IP";
      }
      enum icpe-oper-conflict-serial-num-mismatch {
        description "Serial num mismatch";
      }
      enum icpe-oper-conflict-satellite-not-identified {
        description "Satellite not identified";
      }
      enum icpe-oper-conflict-satellite-unsupported-type {
        description "Satellite unsupported type";
      }
      enum icpe-oper-conflict-satellite-partition-unsupported {
        description "Satellite partition unsupported";
      }
      enum icpe-oper-conflict-satellite-no-serial-number {
        description "Satellite no serial number";
      }
      enum icpe-oper-conflict-satellite-conflicting-serial-number {
        description "Satellite conflicting serial number";
      }
      enum icpe-oper-conflict-satellite-link-waiting-for-arp {
        description "Satellite link waiting for arp";
      }
      enum icpe-oper-conflict-host-pe-isolated-split-brain {
        description "Host PE isolated split brain";
      }
      enum icpe-oper-conflict-fabric-iccp-group-inconsistent {
        description "Fabric ICCP group inconsistent";
      }
      enum icpe-oper-conflict-invalid-iccp-group {
        description "Invalid ICCP group";
      }
      enum icpe-oper-conflict-port-rejected {
        description "Port rejected";
      }
      enum icpe-oper-conflict-satellite-icl-not-supported {
        description "Satellite ICL not supported";
      }
      enum icpe-oper-conflict-multiple-serial-number {
        description "Multiple serial number";
      }
      enum icpe-oper-conflict-multiple-mac-address {
        description "Multiple MAC address";
      }
    }
    description "Icpe oper conflict";
  }
  typedef Icpe-optical-sync-state {
    type enumeration {
      enum icpe-optical-sync-state-unknown {
        description "Unknown";
      }
      enum icpe-optical-sync-state-syncing {
        description "Syncing";
      }
      enum icpe-optical-sync-state-synced {
        description "Synced";
      }
      enum icpe-optical-sync-state-not-connected {
        description "Not connected";
      }
    }
    description "Icpe optical sync state";
  }
  typedef Icpe-oper-ver-check-state {
    type enumeration {
      enum icpe-oper-ver-check-state-unknown {
        description "Unknown";
      }
      enum icpe-oper-ver-check-state-not-compatible {
        description "Not compatible";
      }
      enum icpe-oper-ver-check-state-current-version {
        description "Current version";
      }
      enum icpe-oper-ver-check-state-compatible-older {
        description "Compatible older";
      }
      enum icpe-oper-ver-check-state-compatible-newer {
        description "Compatible newer";
      }
    }
    description "Icpe oper ver check state";
  }
  typedef Icpe-oper-fabric-port {
    type enumeration {
      enum icpe-oper-fabric-port-unknown {
        description "Unknown";
      }
      enum icpe-oper-fabric-port-n-v-fabric-gig-e {
        description "n v fabric- gig e";
      }
      enum icpe-oper-fabric-port-n-v-fabric-ten-gig-e {
        description "n v fabric- ten gig e";
      }
      enum icpe-oper-fabric-port-n-v-fabric-hundred-gig-e {
        description "n v fabric- hundred gig e";
      }
    }
    description "Icpe oper fabric port";
  }
  typedef Xr-yang-string {
    type string;
    description "Xr yang string";
  }

  grouping ICPE-OPER-DISCD-LINK-TYPE {
    description "ICPE OPER DISCD LINK TYPE";
    leaf interface-handle {
      xr:xr-xml-map "icpe_oper_data_gen:InterfaceHandle";
      type xr:Interface-name;
      description "Interface handle";
    }
    leaf state {
      xr:xr-xml-map "icpe_oper_data_gen:State";
      type Icpe-oper-discd-link-state;
      description "State";
    }
    leaf conflict-reason {
      xr:xr-xml-map "icpe_oper_data_gen:ConflictReason";
      type Icpe-oper-conflict;
      description "Conflict reason";
    }
    leaf conflict-context {
      xr:xr-xml-map "icpe_oper_data_gen:ConflictContext";
      type Xr-yang-string;
      description "Conflict context";
    }
  }

  grouping ICPE-OPER-PORT-RANGE-TYPE {
    description "ICPE OPER PORT RANGE TYPE";
    leaf slot {
      xr:xr-xml-map "icpe_oper_data_gen:Slot";
      type uint32;
      description "Slot";
    }
    leaf subslot {
      xr:xr-xml-map "icpe_oper_data_gen:Subslot";
      type uint32;
      description "Subslot";
    }
    leaf low-port {
      xr:xr-xml-map "icpe_oper_data_gen:LowPort";
      type uint32;
      description "Low port";
    }
    leaf high-port {
      xr:xr-xml-map "icpe_oper_data_gen:HighPort";
      type uint32;
      description "High port";
    }
    leaf port-type {
      xr:xr-xml-map "icpe_oper_data_gen:PortType";
      type Icpe-oper-port;
      description "Port type";
    }
    leaf conflict-reason {
      xr:xr-xml-map "icpe_oper_data_gen:ConflictReason";
      type Icpe-oper-conflict;
      description "Conflict reason";
    }
    leaf conflict-context {
      xr:xr-xml-map "icpe_oper_data_gen:ConflictContext";
      type Xr-yang-string;
      description "Conflict context";
    }
  }

  grouping ICPE-OPER-CFGD-LINK-TYPE {
    description "ICPE OPER CFGD LINK TYPE";
    leaf interface-handle {
      xr:xr-xml-map "icpe_oper_data_gen:InterfaceHandle";
      type xr:Interface-name;
      description "Interface handle";
    }
    leaf ip-address {
      xr:xr-xml-map "icpe_oper_data_gen:IPAddress";
      type inet:ipv4-address;
      description "IP address";
    }
    leaf ip-address-auto {
      xr:xr-xml-map "icpe_oper_data_gen:IPAddressAuto";
      type boolean;
      description "IP address auto";
    }
    leaf vrf-id-present {
      xr:xr-xml-map "icpe_oper_data_gen:VRF_ID_Present";
      type boolean;
      description "VRF ID present";
    }
    leaf vrf-id {
      xr:xr-xml-map "icpe_oper_data_gen:VRF_ID";
      type uint32;
      description "VRF ID";
    }
    leaf minimum-preferred-links {
      xr:xr-xml-map "icpe_oper_data_gen:MinimumPreferredLinks";
      type uint32;
      description "Minimum preferred links";
    }
    leaf number-active-links {
      xr:xr-xml-map "icpe_oper_data_gen:NumberActiveLinks";
      type uint32;
      description "Number active links";
    }
    leaf min-links-satisfied {
      xr:xr-xml-map "icpe_oper_data_gen:MinLinksSatisfied";
      type boolean;
      description "Min links satisfied";
    }
    leaf conflict-reason {
      xr:xr-xml-map "icpe_oper_data_gen:ConflictReason";
      type Icpe-oper-conflict;
      description "Conflict reason";
    }
    leaf conflict-context {
      xr:xr-xml-map "icpe_oper_data_gen:ConflictContext";
      type Xr-yang-string;
      description "Conflict context";
    }

    list port-range {
      description "Port ranges table";
      uses ICPE-OPER-PORT-RANGE-TYPE;
    }

    list discovered-link {
      description "Discovered Links table";
      uses ICPE-OPER-DISCD-LINK-TYPE;
    }
  }

  grouping ICPE-OPTICAL-APPLICATION-STATE-TYPE {
    description "ICPE OPTICAL APPLICATION STATE TYPE";
    leaf name {
      xr:xr-xml-map "icpe_oper_data_gen:Name";
      type Xr-yang-string;
      description "Name";
    }
    leaf sync-state {
      xr:xr-xml-map "icpe_oper_data_gen:SyncState";
      type Icpe-optical-sync-state;
      description "Sync state";
    }
  }

  grouping ICPE-OPTICAL-STATUS-TYPE {
    description "ICPE OPTICAL STATUS TYPE";
    leaf chassis-sync-state {
      xr:xr-xml-map "icpe_oper_data_gen:ChassisSyncState";
      type Icpe-optical-sync-state;
      description "Chassis sync state";
    }

    list application {
      description "Application State table";
      uses ICPE-OPTICAL-APPLICATION-STATE-TYPE;
    }
  }

  grouping ICPE-OPER-CAND-FAB-PORTS-CURR-TYPE {
    description "ICPE OPER CAND FAB PORTS CURR TYPE";
    leaf port-type {
      xr:xr-xml-map "icpe_oper_data_gen:PortType";
      type Icpe-oper-fabric-port;
      description "Port type";
    }
    leaf slot {
      xr:xr-xml-map "icpe_oper_data_gen:Slot";
      type uint16;
      description "Slot";
    }
    leaf subslot {
      xr:xr-xml-map "icpe_oper_data_gen:Subslot";
      type uint16;
      description "Subslot";
    }
    leaf port {
      xr:xr-xml-map "icpe_oper_data_gen:Port";
      type uint16;
      description "Port";
    }
    leaf permanent {
      xr:xr-xml-map "icpe_oper_data_gen:Permanent";
      type boolean;
      description "Permanent";
    }
    leaf requested {
      xr:xr-xml-map "icpe_oper_data_gen:Requested";
      type boolean;
      description "Requested";
    }
  }

  grouping ICPE-OPER-CAND-FAB-PORTS-CFGD-TYPE {
    description "ICPE OPER CAND FAB PORTS CFGD TYPE";
    leaf port-type {
      xr:xr-xml-map "icpe_oper_data_gen:PortType";
      type Icpe-oper-fabric-port;
      description "Port type";
    }
    leaf slot {
      xr:xr-xml-map "icpe_oper_data_gen:Slot";
      type uint16;
      description "Slot";
    }
    leaf subslot {
      xr:xr-xml-map "icpe_oper_data_gen:Subslot";
      type uint16;
      description "Subslot";
    }
    leaf port {
      xr:xr-xml-map "icpe_oper_data_gen:Port";
      type uint16;
      description "Port";
    }
    leaf valid {
      xr:xr-xml-map "icpe_oper_data_gen:Valid";
      type boolean;
      description "Valid";
    }
  }

  grouping ICPE-OPER-CAND-FAB-PORTS-TYPE {
    description "ICPE OPER CAND FAB PORTS TYPE";
    leaf channel-up {
      xr:xr-xml-map "icpe_oper_data_gen:ChannelUp";
      type boolean;
      description "Channel up";
    }
    leaf out-of-sync {
      xr:xr-xml-map "icpe_oper_data_gen:OutOfSync";
      type boolean;
      description "Out of sync";
    }
    leaf error-string {
      xr:xr-xml-map "icpe_oper_data_gen:ErrorString";
      type Xr-yang-string;
      description "Error string";
    }

    list configured-port {
      description "Configured Candidate Fabric Ports table";
      uses ICPE-OPER-CAND-FAB-PORTS-CFGD-TYPE;
    }

    list current-port {
      description
        "Current Candidate Fabric Ports on this Satellite
        table";
      uses ICPE-OPER-CAND-FAB-PORTS-CURR-TYPE;
    }
  }

  grouping ICPE-OPER-SAT-STATUS {
    description "Satellite status information";

    container candidate-fabric-ports {
      description "Candidate Fabric Ports on this Satellite";
      uses ICPE-OPER-CAND-FAB-PORTS-TYPE;
    }

    container optical-status {
      description "Optical Satellite Status";
      uses ICPE-OPTICAL-STATUS-TYPE;
    }

    container redundancy-out-of-sync-timestamp {
      description "Timestamp";
      uses ICPE-TIMESTAMP-TYPE;
    }
    leaf satellite-id-xr {
      xr:xr-xml-map "icpe_oper_data_gen:satellite-id-xr";
      type uint32;
      description "Satellite ID";
    }
    leaf version-check-state {
      xr:xr-xml-map "icpe_oper_data_gen:VersionCheckState";
      type Icpe-oper-ver-check-state;
      description "Version check state";
    }
    leaf remote-version-present {
      xr:xr-xml-map "icpe_oper_data_gen:RemoteVersionPresent";
      type boolean;
      description "Remote version present";
    }
    leaf type {
      xr:xr-xml-map "icpe_oper_data_gen:Type";
      type Xr-yang-string;
      description "Type";
    }
    leaf ethernet-fabric-supported {
      xr:xr-xml-map "icpe_oper_data_gen:EthernetFabricSupported";
      type boolean;
      description "Ethernet fabric supported";
    }
    leaf optical-supported {
      xr:xr-xml-map "icpe_oper_data_gen:OpticalSupported";
      type boolean;
      description "Optical supported";
    }
    leaf ip-address {
      xr:xr-xml-map "icpe_oper_data_gen:IPAddress";
      type inet:ipv4-address;
      description "IP address";
    }
    leaf ip-address-present {
      xr:xr-xml-map "icpe_oper_data_gen:IPAddressPresent";
      type boolean;
      description "IP address present";
    }
    leaf ip-address-auto {
      xr:xr-xml-map "icpe_oper_data_gen:IPAddressAuto";
      type boolean;
      description "IP address auto";
    }
    leaf ipv6-address {
      xr:xr-xml-map "icpe_oper_data_gen:IPV6Address";
      type inet:ipv6-address;
      description "IPV6 address";
    }
    leaf ipv6-address-present {
      xr:xr-xml-map "icpe_oper_data_gen:IPV6AddressPresent";
      type boolean;
      description "IPV6 address present";
    }
    leaf vrf-name {
      xr:xr-xml-map "icpe_oper_data_gen:VRFName";
      type Xr-yang-string;
      description "VRF name";
    }
    leaf vrfid {
      xr:xr-xml-map "icpe_oper_data_gen:VRFID";
      type uint32;
      description "VRFID";
    }
    leaf description {
      xr:xr-xml-map "icpe_oper_data_gen:Description";
      type Xr-yang-string;
      description "Description";
    }
    leaf description-present {
      xr:xr-xml-map "icpe_oper_data_gen:DescriptionPresent";
      type boolean;
      description "Description present";
    }
    leaf mac-address {
      xr:xr-xml-map "icpe_oper_data_gen:MACAddress";
      type yang:mac-address;
      description "MAC address";
    }
    leaf mac-address-present {
      xr:xr-xml-map "icpe_oper_data_gen:MACAddressPresent";
      type boolean;
      description "MAC address present";
    }
    leaf configured-serial-number {
      xr:xr-xml-map "icpe_oper_data_gen:ConfiguredSerialNumber";
      type Xr-yang-string;
      description "Configured serial number";
    }
    leaf configured-serial-number-present {
      xr:xr-xml-map "icpe_oper_data_gen:ConfiguredSerialNumberPrese"+
        "nt";
      type boolean;
      description "Configured serial number present";
    }
    leaf received-serial-number {
      xr:xr-xml-map "icpe_oper_data_gen:ReceivedSerialNumber";
      type Xr-yang-string;
      description "Received serial number";
    }
    leaf received-serial-number-present {
      xr:xr-xml-map "icpe_oper_data_gen:ReceivedSerialNumberPresent";
      type boolean;
      description "Received serial number present";
    }
    leaf password {
      xr:xr-xml-map "icpe_oper_data_gen:Password";
      type Xr-yang-string;
      description "Password";
    }
    leaf password-error {
      xr:xr-xml-map "icpe_oper_data_gen:PasswordError";
      type Xr-yang-string;
      description "Password error";
    }
    leaf received-host-name {
      xr:xr-xml-map "icpe_oper_data_gen:ReceivedHostname";
      type Xr-yang-string;
      description "Received hostname";
    }
    leaf cfgd-timeout {
      xr:xr-xml-map "icpe_oper_data_gen:CfgdTimeout";
      type uint32;
      description "Cfgd timeout";
    }
    leaf timeout-warning {
      xr:xr-xml-map "icpe_oper_data_gen:TimeoutWarning";
      type uint32;
      description "Timeout warning";
    }
    leaf conflict-reason {
      xr:xr-xml-map "icpe_oper_data_gen:ConflictReason";
      type Icpe-oper-conflict;
      description "Conflict reason";
    }
    leaf conflict-context {
      xr:xr-xml-map "icpe_oper_data_gen:ConflictContext";
      type Xr-yang-string;
      description "Conflict context";
    }
    leaf redundancy-iccp-group {
      xr:xr-xml-map "icpe_oper_data_gen:RedundancyICCPGroup";
      type uint32;
      description "Redundancy ICCP group";
    }
    leaf recovery-delay-time-left {
      xr:xr-xml-map "icpe_oper_data_gen:RecoveryDelayTimeLeft";
      type uint16;
      description "Recovery delay time left";
    }
    leaf host-treating-as-active {
      xr:xr-xml-map "icpe_oper_data_gen:HostTreatingAsActive";
      type boolean;
      description "Host treating as active";
    }
    leaf satellite-treating-as-active {
      xr:xr-xml-map "icpe_oper_data_gen:SatelliteTreatingAsActive";
      type boolean;
      description "Satellite treating as active";
    }
    leaf sdacp-session-state {
      xr:xr-xml-map "icpe_oper_data_gen:SDACPSessionState";
      type Icpe-oper-sdacp-sess-state;
      description "SDACP session state";
    }
    leaf sdacp-session-failure-reason {
      xr:xr-xml-map "icpe_oper_data_gen:SDACPSessionFailureReason";
      type Icpe-gco-oper-control-reason;
      description "SDACP session failure reason";
    }
    leaf install-state {
      xr:xr-xml-map "icpe_oper_data_gen:InstallState";
      type Icpe-oper-install-state;
      description "Install state";
    }
    leaf-list remote-version {
      xr:xr-xml-map "icpe_oper_data_gen:RemoteVersion";
      type Xr-yang-string;
      description "Remote version";
    }

    list configured-link {
      description "Configured Links on this Satellite table";
      uses ICPE-OPER-CFGD-LINK-TYPE;
    }
  }

  grouping ICPE-TIMESTAMP-TYPE {
    description "ICPE TIMESTAMP TYPE";
    leaf seconds {
      xr:xr-xml-map "icpe_oper_data_gen:Seconds";
      type uint32;
      units "second";
      description "Seconds";
    }
    leaf nanoseconds {
      xr:xr-xml-map "icpe_oper_data_gen:Nanoseconds";
      type uint32;
      units "nanosecond";
      description "Nanoseconds";
    }
  }
}
