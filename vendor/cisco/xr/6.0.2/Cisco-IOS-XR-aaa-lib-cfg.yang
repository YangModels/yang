module Cisco-IOS-XR-aaa-lib-cfg {

  /*** NAMESPACE / PREFIX DEFINITION ***/

  namespace "http://cisco.com/ns/yang/Cisco-IOS-XR-aaa-lib-cfg";


  prefix "aaa-lib-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-lib package configuration.

     This module contains definitions
     for the following management objects:
       aaa: Authentication, Authorization and Accounting

     Copyright (c) 2013-2015 by Cisco Systems, Inc.
     All rights reserved.";

  revision "2015-11-09" {
    description
      "IOS XR 6.0 revision.";
  }

  typedef Aaa-accounting {
    type enumeration {
      enum not-set {
        value 0;
        description "Not Set";
      }
      enum start-stop {
        value 1;
        description "Start Stop";
      }
      enum stop-only {
        value 2;
        description "Stop Only";
      }
    }
    description "Aaa accounting";
  }
  typedef Aaa-accounting-rp-failover {
    type enumeration {
      enum not-set {
        value 0;
        description "Not Set";
      }
      enum set {
        value 1;
        description "rpfailover";
      }
    }
    description "Aaa accounting rp failover";
  }
  typedef Aaa-accounting-broadcast {
    type enumeration {
      enum not-set {
        value 0;
        description "Not Set";
      }
      enum set {
        value 1;
        description "broadcast";
      }
    }
    description "Aaa accounting broadcast";
  }
  typedef Aaa-method {
    type enumeration {
      enum not-set {
        value 0;
        description "Not Set";
      }
      enum none {
        value 1;
        description "None";
      }
      enum local {
        value 2;
        description "Local";
      }
      enum radius {
        value 3;
        description "Radius";
      }
      enum tacacs-plus {
        value 4;
        description "TACACS+";
      }
      enum dsmd {
        value 5;
        description "DSMD";
      }
      enum sgbp {
        value 6;
        description "SGBP";
      }
      enum acct-d {
        value 7;
        description "AcctD";
      }
      enum error {
        value 8;
        description "Error";
      }
      enum if-authenticated {
        value 9;
        description "If Authenticated";
      }
      enum server-group {
        value 10;
        description "Server Group";
      }
      enum server-group-not-defined {
        value 11;
        description "Server Group Not Defined";
      }
      enum line {
        value 12;
        description "Line";
      }
      enum enable {
        value 13;
        description "Enable";
      }
      enum kerberos {
        value 14;
        description "Kerberos";
      }
      enum diameter {
        value 15;
        description "Diameter";
      }
      enum last {
        value 16;
        description "Last";
      }
    }
    description "Aaa method";
  }
  typedef Aaa-accounting-update {
    type enumeration {
      enum none {
        value 0;
        description "Not Set";
      }
      enum newinfo {
        value 3;
        description
          "Update records for new accountable information
          only";
      }
      enum periodic {
        value 4;
        description "Update records at periodic intervals";
      }
    }
    description "Aaa accounting update";
  }

  container aaa {
    xr:xr-xml-map "aaa_lib_cfg:AAA";
    description "Authentication, Authorization and Accounting";

    container accountings {
      xr:xr-xml-map "aaa_lib_cfg:AccountingTable";
      description "AAA accounting";

      list accounting {
        xr:xr-xml-map "aaa_lib_cfg:Accounting";
        xr:xr-cli-map "aaa accounting (exec)|(commands)|(api)|(syst"+
          "em (rp-failover))|(network)|(onepk) (default)|(<string>)"+
          " <enum> (broadcast) (none)|(group (<enum>)|(<enum>)|(<st"+
          "ring>)) ";
        key "type listname";
        description "Configurations related to accounting";
        leaf type {
          xr:xr-xml-map "aaa_lib_cfg:Type";
          type xr:Cisco-ios-xr-string;
          description
            "exec:Account exec sessions, commands: Account
            CLI commands";
        }
        leaf listname {
          xr:xr-xml-map "aaa_lib_cfg:Listname";
          type xr:Cisco-ios-xr-string;
          description "Named accounting list";
        }
        leaf rp-failover {
          xr:xr-xml-map "aaa_lib_cfg:rp-failover";
          type Aaa-accounting-rp-failover;
          description "rpfailover";
        }
        leaf broadcast {
          xr:xr-xml-map "aaa_lib_cfg:Broadcast";
          type Aaa-accounting-broadcast;
          description "Broadcast";
        }
        leaf type-xr {
          xr:xr-xml-map "aaa_lib_cfg:Type";
          type Aaa-accounting;
          description "Stop only/Start Stop";
        }
        leaf-list method {
          xr:xr-xml-map "aaa_lib_cfg:Methods";
          type Aaa-method;
          max-elements "4";
          description "Method Types";
        }
        leaf-list server-group-name {
          xr:xr-xml-map "aaa_lib_cfg:ServerGroupNames";
          type string;
          max-elements "4";
          description "Server group names";
        }
      }
    }

    container authorizations {
      xr:xr-xml-map "aaa_lib_cfg:AuthorizationTable";
      description "AAA authorization";

      list authorization {
        xr:xr-xml-map "aaa_lib_cfg:Authorization";
        xr:xr-cli-map "aaa authorization network (default)|(<string"+
          ">) (none)|(local)|([group (<enum>)|(<enum>)|(<string>)])"+
          " ";
        key "type listname";
        description "Configurations related to authorization";
        leaf type {
          xr:xr-xml-map "aaa_lib_cfg:Type";
          type xr:Cisco-ios-xr-string;
          description
            "network: Authorize IKE requests, commands:
            Authorize CLI commands";
        }
        leaf listname {
          xr:xr-xml-map "aaa_lib_cfg:Listname";
          type xr:Cisco-ios-xr-string;
          description "List name for AAA authorization";
        }
        leaf-list method {
          xr:xr-xml-map "aaa_lib_cfg:Methods";
          type Aaa-method;
          min-elements "1";
          max-elements "4";
          description "Methods";
        }
        leaf-list server-group-name {
          xr:xr-xml-map "aaa_lib_cfg:ServerGroupNames";
          type string;
          max-elements "4";
          description "Server group names";
        }
      }
    }

    container accounting-update {
      xr:xr-xml-map "aaa_lib_cfg:AccountingUpdate";
      presence "Indicates a accounting-update node is configured.";
      description "Configuration related to 'update' accounting";
      leaf type {
        xr:xr-xml-map "aaa_lib_cfg:Type";
        type Aaa-accounting-update;
        mandatory true;
        description "newinfo/periodic";
      }
      leaf periodic-interval {
        xr:xr-xml-map "aaa_lib_cfg:PeriodicInterval";
        type uint32 {
          range "0..35791394";
        }
        units "minute";
        description "Periodic update interval in minutes";
      }
    }

    container authentications {
      xr:xr-xml-map "aaa_lib_cfg:AuthenticationTable";
      description "AAA authentication";

      list authentication {
        xr:xr-xml-map "aaa_lib_cfg:Authentication";
        xr:xr-cli-map "aaa authentication login (default)|(remote)|"+
          "(<string>) (local)|((line)|([group (<enum>)|(<enum>)|(<s"+
          "tring>)])) ";
        key "type listname";
        description "Configurations related to authentication";
        leaf type {
          xr:xr-xml-map "aaa_lib_cfg:Type";
          type xr:Cisco-ios-xr-string;
          description
            "login: Authenticate login sessions, ppp:
            Authenticate ppp sessions";
        }
        leaf listname {
          xr:xr-xml-map "aaa_lib_cfg:Listname";
          type xr:Cisco-ios-xr-string;
          description "List name for AAA authentication";
        }
        leaf-list method {
          xr:xr-xml-map "aaa_lib_cfg:Methods";
          type Aaa-method;
          min-elements "1";
          max-elements "4";
          description "Methods";
        }
        leaf-list server-group-name {
          xr:xr-xml-map "aaa_lib_cfg:ServerGroupNames";
          type string;
          max-elements "4";
          description "Server group names";
        }
      }
    }
  }
}
