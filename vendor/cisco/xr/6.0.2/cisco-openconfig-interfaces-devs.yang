//*************  DO-NOT EDIT  **************
//*********** Auto-generated file ********** 

 module cisco-openconfig-interfaces-devs {

  prefix  "ocifdevs";

  namespace "http://cisco.com/ns/yang/openconfig-interfaces-devs";

  import openconfig-interfaces { prefix ocif; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-interfaces.yang@2015-11-20 

     on Cisco IOS-XR devices.

     Copyright (c) 2015-2016 by Cisco Systems, Inc.
     All rights reserved.";

  revision "2016-05-16" {
    description
      "Initial revision applicable to IOS-XR 6.0.1";
  }


  deviation /ocif:interfaces/ocif:interface/ocif:subinterfaces/ocif:subinterface/ocif:config/ocif:unnumbered {
    deviate not-supported;
  }

  deviation /ocif:interfaces/ocif:interface/ocif:subinterfaces/ocif:subinterface/ocif:state/ocif:unnumbered {
    deviate not-supported;
  }


}
//total deviations:2
