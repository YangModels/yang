submodule Cisco-IOS-XR-install-augmented-oper-sub1 {
  belongs-to Cisco-IOS-XR-install-augmented-oper {
    prefix Cisco-IOS-XR-install-augmented-oper;
  }

  import Cisco-IOS-XR-types {
    prefix xr;
  }
  import cisco-semver {
    prefix semver;
  }
  include Cisco-IOS-XR-install-augmented-oper-sub2 {
    revision-date 2023-02-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR install-augmented package operational data.
     
     Copyright (c) 2013-2023 by Cisco Systems, Inc.
     All rights reserved.";

  revision 2023-02-10 {
    description
      "Add awaited unsolicited messages to internal data.
       2022-12-20
         Add username information.
       2022-11-17
         Add latest reimage bags.
       2022-05-05
         Add warning to inst_request_verbose_bag.
       2022-02-18
         Add detailed intervention event information.
       2021-10-27
         Add new bag for platform-specific disabled packages.
       2021-10-25
         Add source to package operation reporting.
       2021-10-01
         Add details in history for package verification failure reporting.";
    semver:module-version "2.3.0";
  }
  revision 2021-08-25 {
    description
      "7.5.1 release features.";
    semver:module-version "2.2.0";
  }
  revision 2021-03-22 {
    description
      "7.4.1 release features.
       2020-09-30
           7.3.1 release features.";
    semver:module-version "2.1.0";
  }
  revision 2020-05-12 {
    description
      "Removal of compound from enum naming conventions to avoid confusion.
       2019-12-11
         Obsoleted the nodes list for history items.
       2019-10-14
         Combined platform updates including updates to show install rollback list-ids";
    semver:module-version "2.0.0";
  }
  revision 2019-10-13 {
    description
      "NCS540L 7.1.1 release
       2019-10-12
       8000 series 7.0.11 release";
    semver:module-version "1.1.0";
  }
  revision 2019-04-05 {
    description
      "Establish semantic version baseline.";
    semver:module-version "1.0.0";
  }
  revision 2015-11-09 {
    description
      "IOS XR 6.0 revision.";
  }

  typedef Inst-recovery-action {
    type enumeration {
      enum "reload-to-new-version" {
        value 10;
        description
          "Reload to the new software version";
      }
      enum "reload-to-old-version" {
        value 11;
        description
          "Reload to the old software version";
      }
      enum "usb-boot" {
        value 12;
        description
          "Perform a USB Boot";
      }
      enum "pxe-boot" {
        value 13;
        description
          "Perform a PXE Boot";
      }
    }
    description
      "Inst recovery action";
  }

  typedef Inst-req-state {
    type enumeration {
      enum "in-progress" {
        value 0;
        description
          "In progress";
      }
      enum "success" {
        value 1;
        description
          "Success";
      }
      enum "failure" {
        value 2;
        description
          "Failure";
      }
    }
    description
      "Install request state type";
  }

  typedef Inst-action {
    type enumeration {
      enum "install-package-add" {
        value 10;
        description
          "Package add";
      }
      enum "install-package-remove" {
        value 11;
        description
          "Package remove";
      }
      enum "install-package-upgrade" {
        value 12;
        description
          "Package upgrade";
      }
      enum "install-package-downgrade" {
        value 13;
        description
          "Package downgrade";
      }
      enum "install-package-replace" {
        value 14;
        description
          "Package replace";
      }
      enum "install-package-rollback" {
        value 15;
        description
          "Rollback";
      }
      enum "install-package-abort-latest" {
        value 20;
        description
          "Package abort latest";
      }
      enum "install-package-abort-all-since-apply" {
        value 21;
        description
          "Package abort all since apply";
      }
      enum "install-package-abort-latest-force" {
        value 22;
        description
          "Package abort latest with force";
      }
      enum "install-package-abort-all-since-apply-force" {
        value 23;
        description
          "Package abort all since apply with force";
      }
      enum "install-apply-restart" {
        value 30;
        description
          "Apply by process restart";
      }
      enum "install-apply-reload" {
        value 31;
        description
          "Apply by reload";
      }
      enum "install-commit" {
        value 40;
        description
          "Commit";
      }
      enum "install-replace" {
        value 70;
        description
          "Replace and apply";
      }
      enum "install-rollback" {
        value 71;
        description
          "Rollback and apply";
      }
      enum "install-source" {
        value 72;
        description
          "Upgrade and apply packages from a source";
      }
      enum "install-reimage" {
        value 80;
        description
          "Reimage to given iso";
      }
      enum "install-label" {
        value 90;
        description
          "Label";
      }
    }
    description
      "Inst action";
  }

  typedef Inst-notif-phase {
    type enumeration {
      enum "veto" {
        value 0;
        description
          "Veto";
      }
      enum "prepare" {
        value 1;
        description
          "Prepare";
      }
      enum "pre-pre-apply" {
        value 2;
        description
          "Pre pre apply";
      }
      enum "pre-apply" {
        value 3;
        description
          "Pre apply";
      }
      enum "apply" {
        value 4;
        description
          "Apply";
      }
      enum "post-apply" {
        value 5;
        description
          "Post apply";
      }
      enum "post-post-apply" {
        value 6;
        description
          "Post post apply";
      }
    }
    description
      "Install notification phase type";
  }

  typedef Inst-pkg-op-stage {
    type enumeration {
      enum "not-started" {
        value 0;
        description
          "No operation has yet begun";
      }
      enum "preamble" {
        value 1;
        description
          "Preamble, including loading plugins";
      }
      enum "resolving-dependencies" {
        value 2;
        description
          "Resolving dependencies";
      }
      enum "transaction-check" {
        value 3;
        description
          "Package downloads and transaction check";
      }
      enum "package-operations" {
        value 4;
        description
          "Package operations - installations and removals";
      }
      enum "complete" {
        value 5;
        description
          "Operation has finished. This does not imply
           success";
      }
    }
    description
      "Inst pkg op stage";
  }

  typedef Inst-node-req {
    type enumeration {
      enum "veto-check" {
        value 0;
        description
          "Veto check";
      }
      enum "begin-trans" {
        value 1;
        description
          "Begin transaction";
      }
      enum "end-trans" {
        value 2;
        description
          "End transaction";
      }
      enum "abort-trans" {
        value 3;
        description
          "Abort transaction";
      }
      enum "begin-atomic" {
        value 4;
        description
          "Begin atomic operation";
      }
      enum "abort-atomic" {
        value 5;
        description
          "Abort atomic operation";
      }
      enum "pkg-install" {
        value 6;
        description
          "Package install operation";
      }
      enum "pkg-replace" {
        value 7;
        description
          "Package replace operation";
      }
      enum "undo-pkg-install" {
        value 8;
        description
          "Undo package install or undo other package
           operation";
      }
      enum "apply-reload" {
        value 9;
        description
          "Apply by reload";
      }
      enum "pre-pre-apply-restart" {
        value 10;
        description
          "Pre-pre-apply by restarting processes";
      }
      enum "pre-apply-restart" {
        value 11;
        description
          "Pre-apply by restarting processes";
      }
      enum "apply-and-post-apply-restart" {
        value 12;
        description
          "Apply and post-apply by restarting processes";
      }
      enum "post-post-apply-restart" {
        value 13;
        description
          "Post-post-apply by restarting processes";
      }
      enum "restart-infra" {
        value 14;
        description
          "Restart install infra";
      }
      enum "abort-op" {
        value 15;
        description
          "Abort current operation";
      }
      enum "node-idle" {
        value 16;
        description
          "Node is not handling a request";
      }
      enum "status-unknown" {
        value 17;
        description
          "The node did not respond to the operational
           data request";
      }
      enum "resync-remote-node" {
        value 18;
        description
          "Resyncing remote nodes with the active node";
      }
      enum "pre-commit-check" {
        value 19;
        description
          "Perform pre-commit checks";
      }
    }
    description
      "Install node request type";
  }

  typedef Inst-activity {
    type enumeration {
      enum "initiate-op" {
        value 0;
        description
          "Initiate operation";
      }
      enum "begin-trans" {
        value 1;
        description
          "Begin transaction";
      }
      enum "begin-atomic" {
        value 2;
        description
          "Begin atomic operation";
      }
      enum "veto-check" {
        value 3;
        description
          "Veto check";
      }
      enum "pkg-install" {
        value 4;
        description
          "Package add or other package operation";
      }
      enum "apply-reload" {
        value 5;
        description
          "Apply by reload";
      }
      enum "apply-restart" {
        value 6;
        description
          "Apply by restarting processes";
      }
      enum "restart-infra" {
        value 7;
        description
          "Restart install infra";
      }
      enum "commit-trans" {
        value 8;
        description
          "Commit transaction";
      }
      enum "abort-op" {
        value 9;
        description
          "Abort operation";
      }
      enum "abort-trans" {
        value 10;
        description
          "Abort transaction";
      }
      enum "abort-atomic" {
        value 11;
        description
          "Abort atomic operation";
      }
      enum "undo-pkg-inst" {
        value 12;
        description
          "Undo package install";
      }
      enum "await-user-input" {
        value 13;
        description
          "Await user input";
      }
      enum "await-recovery-input" {
        value 14;
        description
          "Failure, await user recovery input";
      }
      enum "trans-complete" {
        value 15;
        description
          "Transaction complete";
      }
      enum "no-op-in-progress" {
        value 16;
        description
          "No install operation in progress";
      }
      enum "apply-reload-awaiting-node-readiness" {
        value 17;
        description
          "Cleanup after apply by reload";
      }
      enum "automatic-recovery" {
        value 18;
        description
          "Automatic recovery";
      }
      enum "apply" {
        value 19;
        description
          "Apply by restarting processes or reload";
      }
      enum "begin-pkg-op" {
        value 20;
        description
          "Begin packaging operation";
      }
      enum "begin-apply-op" {
        value 21;
        description
          "Begin apply operation";
      }
      enum "apply-cleanup" {
        value 22;
        description
          "Post-apply operation cleanup";
      }
      enum "download" {
        value 23;
        description
          "Verify input and download to internal
           repository if needed";
      }
      enum "undo-download" {
        value 24;
        description
          "Undo download to internal repository if needed";
      }
      enum "bridging-download" {
        value 25;
        description
          "Download bridging bugfix RPMs to the internal
           repository";
      }
      enum "bridging-veto-check" {
        value 26;
        description
          "Veto check for bridging bugfix install";
      }
      enum "bridging-pkg-install" {
        value 27;
        description
          "Package upgrade of bridging bugfix RPMs";
      }
      enum "bridging-begin-apply-op" {
        value 28;
        description
          "Begin apply operation of bridging bugfixes";
      }
      enum "bridging-apply-reload" {
        value 29;
        description
          "Apply by reload of bridging bugfixes";
      }
      enum "bridging-apply-reload-awaiting-node-readiness" {
        value 30;
        description
          "Cleanup after apply by reload of bridging
           bugfixes";
      }
      enum "bridging-apply-restart" {
        value 31;
        description
          "Apply by restarting processes";
      }
      enum "bridging-restart-infra" {
        value 32;
        description
          "Restart install infra during apply of bridging
           bugfixes";
      }
      enum "bridging-apply-cleanup" {
        value 33;
        description
          "Post-apply of bridging bugfixes cleanup";
      }
      enum "bridging-apply" {
        value 34;
        description
          "Apply bridging bugfixes by restarting processes
           or reload";
      }
      enum "await-dnf-completion" {
        value 35;
        description
          "Wait for all DNF processes to complete after a
           packaging operation failure";
      }
      enum "iso-download" {
        value 36;
        description
          "Verify input and download ISO";
      }
      enum "extract-main-iso" {
        value 37;
        description
          "Extract main ISO contents to internal
           repository if needed";
      }
      enum "acquire-install-lock" {
        value 38;
        description
          "Acquire the install lock for the system";
      }
      enum "begin-reimage" {
        value 39;
        description
          "Prepare for a reimage from disk operation:
           downloading ISO and saving config";
      }
      enum "await-reimage" {
        value 40;
        description
          "Wait for reload during a reimage operation";
      }
      enum "undo-reimage-prep" {
        value 41;
        description
          "Undo actions taken to prepare for a reimage
           operation";
      }
    }
    description
      "Install activity type";
  }

  typedef Caveat {
    type string;
    description
      "Caveat";
  }

  typedef Fix {
    type string;
    description
      "DDTS or fix ID";
  }

  typedef Inst-fp-request-status {
    type enumeration {
      enum "generation-up-to-date" {
        value 0;
        description
          "Runtime fingerprint generation up to date.";
      }
      enum "generation-in-progress" {
        value 1;
        description
          "Runtime fingerprint generation in progress";
      }
      enum "to-be-regenerated-at-apply" {
        value 2;
        description
          "Runtime fingerprints will be regenerated on
           apply";
      }
    }
    description
      "package Fingerprint request status";
  }

  typedef Install-opt-string {
    type string;
    description
      "Install opt string";
  }

  typedef Inst-bridging-bugfix {
    type enumeration {
      enum "unknown" {
        value 0;
        description
          "Unknown bridging bugfix status";
      }
      enum "none-in-iso" {
        value 1;
        description
          "No bridging bugfixes in gISO";
      }
      enum "none-at-version" {
        value 2;
        description
          "No bridging bugfixes found for running XR
           version";
      }
      enum "already-installed" {
        value 3;
        description
          "Bridging bugfixes in gISO already installed";
      }
      enum "install-required" {
        value 4;
        description
          "Bridging bugfixes in gISO to be installed";
      }
    }
    description
      "Install bridging bugfix type";
  }

  typedef Inst-atomic-status {
    type enumeration {
      enum "in-progress" {
        value 0;
        description
          "In progress";
      }
      enum "apply-in-progress" {
        value 1;
        description
          "Apply in progress";
      }
      enum "success" {
        value 2;
        description
          "Success";
      }
      enum "failure" {
        value 3;
        description
          "Failure";
      }
      enum "aborting" {
        value 4;
        description
          "Aborting";
      }
      enum "aborted" {
        value 5;
        description
          "Aborted";
      }
      enum "skipped" {
        value 6;
        description
          "Skipped";
      }
    }
    description
      "Atomic change status type";
  }

  typedef Inst-cfg-replace-info {
    type enumeration {
      enum "iso-config-obtained" {
        value 0;
        description
          "Config successfully extracted from the ISO and
           user did not request to ignore config";
      }
      enum "iso-config-requested-but-not-present" {
        value 1;
        description
          "User requested to replace config, but no config
           present in ISO";
      }
      enum "ignored" {
        value 2;
        description
          "User requested to ignore config";
      }
      enum "iso-config-not-present" {
        value 3;
        description
          "No config present in ISO and user made no
           explicit request";
      }
      enum "iso-config-not-supported" {
        value 4;
        description
          "Config extraction is not supported for this ISO";
      }
    }
    description
      "Install ISO config outcome type";
  }

  typedef Inst-pkg-op-status {
    type enumeration {
      enum "in-progress" {
        value 0;
        description
          "In progress";
      }
      enum "success" {
        value 1;
        description
          "Success";
      }
      enum "failure" {
        value 2;
        description
          "Failure";
      }
      enum "aborted" {
        value 3;
        description
          "Aborted";
      }
      enum "skipped" {
        value 4;
        description
          "Skipped";
      }
    }
    description
      "Package operation status type";
  }

  typedef Inst-req-reason {
    type enumeration {
      enum "user" {
        value 0;
        description
          "User request";
      }
      enum "undoing-due-to-abort" {
        value 1;
        description
          "Undoing previous package operation due to user
           request";
      }
    }
    description
      "Install request reason type";
  }

  typedef Inst-pkg-verify-error {
    type enumeration {
      enum "unsigned" {
        value 0;
        description
          "Unsigned";
      }
      enum "pubkey-not-installed" {
        value 1;
        description
          "Public key is not installed";
      }
      enum "corrupt" {
        value 2;
        description
          "Corrupted";
      }
      enum "unknown" {
        value 99;
        description
          "Unknown error";
      }
    }
    description
      "Install package verification error failure types";
  }

  typedef Inst-disk-space-check-phase {
    type enumeration {
      enum "download" {
        value 0;
        description
          "Download";
      }
      enum "iso-unpack" {
        value 1;
        description
          "ISO unpack";
      }
      enum "tar-unpack" {
        value 2;
        description
          "Tar unpack";
      }
      enum "veto" {
        value 3;
        description
          "Veto";
      }
      enum "iso-copy" {
        value 4;
        description
          "This stage encompasses copying the ISO onto the
           router, and unpacking it, requiring 2x the size
           of the file";
      }
      enum "tar-copy" {
        value 5;
        description
          "This stage encompasses copying the tarball onto
           the router, and unpacking it, requiring 2.5x
           the size of the file";
      }
    }
    description
      "Install disk space check phase type";
  }

  typedef Inst-notif-res {
    type enumeration {
      enum "awaiting-response" {
        value 0;
        description
          "Awaiting response";
      }
      enum "success" {
        value 1;
        description
          "Success";
      }
      enum "veto-req" {
        value 2;
        description
          "Veto requested";
      }
      enum "reload-req" {
        value 3;
        description
          "Reload requested";
      }
      enum "extra-time" {
        value 4;
        description
          "Extra time requested";
      }
      enum "failure" {
        value 5;
        description
          "Client failed to process notification";
      }
    }
    description
      "Install client notification result type";
  }

  typedef Inst-feature-change {
    type enumeration {
      enum "removed" {
        value 0;
        description
          "Removed";
      }
      enum "added" {
        value 1;
        description
          "Added";
      }
    }
    description
      "Inst feature change";
  }

  typedef Inst-proc-change {
    type enumeration {
      enum "removed" {
        value 0;
        description
          "Removed";
      }
      enum "modified" {
        value 1;
        description
          "Modified";
      }
    }
    description
      "Inst proc change";
  }

  typedef Inst-file-change {
    type enumeration {
      enum "removed" {
        value 0;
        description
          "Removed";
      }
      enum "added" {
        value 1;
        description
          "Added";
      }
      enum "modified" {
        value 2;
        description
          "Modified";
      }
    }
    description
      "File change type";
  }

  typedef Inst-client {
    type enumeration {
      enum "default" {
        value 0;
        description
          "Default client";
      }
      enum "legacy" {
        value 1;
        description
          "Legacy client";
      }
    }
    description
      "Install client type";
  }

  typedef Inst-no-action-reason {
    type enumeration {
      enum "already-installed" {
        value 0;
        description
          "Package was already installed";
      }
      enum "nothing-to-remove" {
        value 1;
        description
          "No matching package found to remove";
      }
      enum "no-suitable-version" {
        value 2;
        description
          "No suitable package to upgrade to or downgrade
           to was found";
      }
    }
    description
      "Install no action reason type";
  }

  typedef Inst-pkg-op-act {
    type enumeration {
      enum "add" {
        value 0;
        description
          "Add";
      }
      enum "remove" {
        value 1;
        description
          "Remove";
      }
      enum "unknown" {
        value 255;
        description
          "Unknown";
      }
    }
    description
      "Install package operation action type";
  }

  typedef Inst-trans-status {
    type enumeration {
      enum "in-progress" {
        value 0;
        description
          "In progress";
      }
      enum "commit-in-progress" {
        value 1;
        description
          "Commit in progress";
      }
      enum "success" {
        value 2;
        description
          "Success";
      }
      enum "failure" {
        value 3;
        description
          "Failure";
      }
      enum "aborting" {
        value 4;
        description
          "Aborting";
      }
      enum "aborted" {
        value 5;
        description
          "Aborted";
      }
      enum "post-commit-cleanup" {
        value 6;
        description
          "Committed, cleaning up";
      }
      enum "error-retry" {
        value 7;
        description
          "Error encountered, retrying";
      }
      enum "commit-failure" {
        value 8;
        description
          "Commit failure";
      }
    }
    description
      "Transaction status type";
  }

  typedef Inst-request {
    type enumeration {
      enum "unknown" {
        value 0;
        description
          "Unknown, operation history not available";
      }
      enum "add" {
        value 1;
        description
          "Add";
      }
      enum "remove" {
        value 2;
        description
          "Remove";
      }
      enum "upgrade" {
        value 3;
        description
          "Upgrade";
      }
      enum "downgrade" {
        value 4;
        description
          "Downgrade";
      }
      enum "replace" {
        value 5;
        description
          "Replace";
      }
      enum "rollback" {
        value 6;
        description
          "Rollback";
      }
      enum "reimage" {
        value 7;
        description
          "Reimage";
      }
    }
    description
      "Install request type";
  }

  typedef Inst-node-event-reload-reason {
    type enumeration {
      enum "reloaded-to-continue" {
        value 0;
        description
          "The force keyword meant that in order for the
           install operation to continue best-effort
           despite this node event, this node was reloaded
           .";
      }
    }
    description
      "The reason a node was reloaded due to a node
       event";
  }

  typedef Inst-node-event {
    type enumeration {
      enum "node-unavailable" {
        value 0;
        description
          "Node became unavailable";
      }
      enum "node-available" {
        value 1;
        description
          "Node became available";
      }
      enum "error" {
        value 2;
        description
          "Per-node error";
      }
      enum "user-requested-reload" {
        value 3;
        description
          "User requested reload of this node to recover
           from a failure.";
      }
    }
    description
      "Install node event type";
  }

  typedef Inst-intervention-event-category {
    type enumeration {
      enum "retry" {
        value 0;
        description
          "Retrying the operation may resolve the issue";
      }
      enum "user" {
        value 1;
        description
          "The user has made an invalid request";
      }
      enum "manual" {
        value 2;
        description
          "Manual intervention is needed to resolve the
           issue";
      }
      enum "reload" {
        value 3;
        description
          "One or more nodes need to be reloaded to
           resolve the issue";
      }
      enum "warning" {
        value 4;
        description
          "The operation succeeded but an unexpected event
           may have occurred";
      }
      enum "support" {
        value 5;
        description
          "An error occurred with no recovery options,
           contact Cisco Support";
      }
    }
    description
      "Install intervention event category type";
  }

  grouping INST-AVAILABLE-FIX-TYPE {
    description
      "INST AVAILABLE FIX TYPE";
    leaf ddts {
      type string;
      description
        "DDTS id";
    }
    list package {
      description
        "Packages";
      uses INST-AVAILABLE-PKG-TYPE;
    }
  }

  grouping INST-AVAILABLE-FIXES-BAG {
    description
      "Install bag containing details of available fixes";
    leaf-list inaccessible-repository {
      type String1;
      description
        "List of repositories that the package manager
         was unable to access, likely due to
         configuration errors or network connectivity";
    }
    leaf-list repositories-metadata-failed {
      type String1;
      description
        "List of local repositories where automatic
         metadata generation failed. Information about
         packages in these repositories may not be up to
         date.";
    }
    list fixes {
      description
        "Fixes";
      uses INST-AVAILABLE-FIX-TYPE;
    }
  }

  grouping INST-DEACTIVATE-GROUP-FIX-TYPE {
    description
      "INST DEACTIVATE GROUP FIX TYPE";
    leaf-list requested-ddts {
      type String1;
      description
        "Requested DDTS ids to deactivate";
    }
    leaf-list ddt-ss-to-deactivate {
      type String1;
      description
        "The DDTS ids that would be deactivated by this
         change";
    }
    list packages-to-downgrade {
      description
        "The packages that would be downgraded from by
         this change";
      uses INST-PKG;
    }
    list packages-to-activate {
      description
        "The packages that would be activated by this
         change (ie. downgraded to)";
      uses INST-PKG;
    }
    list missing-mandatory-package {
      description
        "The mandatory packages that are missing and so
         preventing this downgrade";
      uses INST-PKG;
    }
    list missing-optional-package {
      description
        "The optional packages that are missing and so
         preventing this downgrade";
      uses INST-PKG;
    }
  }

  grouping INST-DEACTIVATE-DDTS-IDS-BAG {
    description
      "Install bag containing details of available
       groups of fixes";
    container combined-deactivate-info {
      description
        "The combined information for deactivating all
         specified DDTSs";
      uses INST-DEACTIVATE-GROUP-FIX-TYPE;
    }
    leaf-list not-installed-ddts {
      type String1;
      description
        "DDTSs specified for deactivation but not
         currently installed";
    }
    list group-deactivate-info {
      description
        "The groups of fixes for deactivating the
         specified DDTSs";
      uses INST-DEACTIVATE-GROUP-FIX-TYPE;
    }
  }

  grouping INST-QUERY-PKG-FIX-TYPE {
    description
      "Package and fix type";
    container package {
      description
        "Package";
      uses INST-PKG-TYPE;
    }
    container ddts-list {
      description
        "DDTSs associated with this package";
      uses INST-DDTS-LIST;
    }
  }

  grouping INST-ROLLBACK-POINT-BAG {
    description
      "Bag containing information for a specific
       rollback point";
    leaf id {
      type int32;
      description
        "Rollback point ID";
    }
    leaf label {
      type String1;
      description
        "Optional GISO label for rollback point";
    }
    leaf description {
      type String1;
      description
        "Optional user defined description of the
         rollback point";
    }
    list package {
      description
        "List of packages and fixes for the rollback
         point";
      uses INST-QUERY-PKG-FIX-TYPE;
    }
  }

  grouping INST-DDTS-LIST {
    description
      "DDTS List";
    leaf-list ddts {
      type String1;
      description
        "DDTS items in list";
    }
  }

  grouping INST-QUERY-PKG-CHANGE-TYPE {
    description
      "Package changes type";
    container package {
      description
        "Package";
      uses INST-PKG-TYPE;
    }
    container ddts-list {
      description
        "DDTSs associated with this package";
      uses INST-DDTS-LIST;
    }
    leaf action {
      type Inst-pkg-op-act;
      description
        "Action pending on package";
    }
  }

  grouping INST-CHANGES-BAG {
    description
      "Install pending changes bag";
    list package {
      description
        "List of packages and the action pending on each";
      uses INST-QUERY-PKG-CHANGE-TYPE;
    }
  }

  grouping INST-ROLLBACK-SUMMARY-BAG {
    description
      "Install bag containing summary information about
       a possible rollback transaction";
    leaf time-finished {
      type String1;
      description
        "Timestamp this transaction completed, in RFC3339
         internet date/time format";
    }
    leaf pkgs-to-add-count {
      type int32;
      description
        "Number of packages to be added";
    }
    leaf pkgs-to-modify-count {
      type int32;
      description
        "Number of packages to be modified";
    }
    leaf pkgs-to-remove-count {
      type int32;
      description
        "Number of packages to be removed";
    }
    leaf description {
      type string;
      description
        "The description of the transaction, if set";
    }
    leaf ddt-ss-to-add-count {
      type int32;
      description
        "Number of DDTSs to be added";
    }
    leaf ddt-ss-to-remove-count {
      type int32;
      description
        "Number of DDTSs to be removed";
    }
  }

  grouping INST-VER-PKG-TYPE {
    description
      "Install package type";
    leaf name {
      type string;
      description
        "Name";
    }
    leaf version {
      type string;
      description
        "Version";
    }
    leaf built-by {
      type string;
      description
        "User built by";
    }
    leaf built-on {
      type string;
      description
        "Time built";
    }
    leaf workspace {
      type string;
      description
        "Workspace built in";
    }
    leaf build-host {
      type string;
      description
        "Build host";
    }
  }

  grouping INST-VERSION-BAG {
    description
      "Install version bag";
    leaf label {
      type string;
      description
        "Added telemetry event on Label field";
      xr:event-telemetry "Subscribe Telemetry Event";
    }
    leaf copyright-info {
      type string;
      description
        "Copyright information";
    }
    leaf hardware-info {
      type string;
      description
        "Hardware information";
    }
    leaf uptime {
      type string;
      description
        "System uptime";
    }
    leaf location {
      type Install-opt-string;
      description
        "Prefix for the path where packages will be
         installed";
    }
    leaf processor {
      type Install-opt-string;
      description
        "Processor";
    }
    leaf chassis-pid {
      type Install-opt-string;
      description
        "Chassis PID";
    }
    leaf chassis-description {
      type Install-opt-string;
      description
        "Chassis Unique Device Identifier description";
    }
    leaf xr-host-name {
      type Install-opt-string;
      description
        "Configured XR hostname";
    }
    leaf total-ram {
      type uint64;
      description
        "Total physical memory in GB";
    }
    list package {
      description
        "Packages";
      uses INST-VER-PKG-TYPE;
    }
  }

  grouping INST-RECOVERY-ACTIONS {
    description
      "INST RECOVERY ACTIONS";
    leaf-list recovery-action {
      type Inst-recovery-action;
      description
        "Non install recovery actions, when install
         actions are not available.";
    }
  }

  grouping INST-AVAILABLE-ACTIONS {
    description
      "INST AVAILABLE ACTIONS";
    leaf-list available-action {
      type Inst-action;
      description
        "Action available to user. If there are no
         available actions, a system reload may be used
         to recover.";
    }
  }

  grouping INST-LOCK-REQ-CLIENT {
    description
      "Install lock details for during requests";
    leaf name {
      type string;
      description
        "Name of the client";
    }
    leaf held-since {
      type Install-opt-string;
      description
        "Timestamp when the lock was acquired, in RFC3339
         format";
    }
    leaf timeout {
      type uint32;
      description
        "Maximum length of time this client has hold the
         lock before timeout";
    }
    leaf reason {
      type Install-opt-string;
      description
        "Reason that the client holds the lock";
    }
  }

  grouping INST-LOCK-REQ-STATUS {
    description
      "Install lock details for during requests";
    leaf clients-holding-lock-count {
      type uint32;
      description
        "Count of clients holding the lock";
    }
    list clients-holding-lock {
      description
        "Details of any clients holding the lock";
      uses INST-LOCK-REQ-CLIENT;
    }
  }

  grouping INST-NOTIF-STATUS {
    description
      "Install client notification status information";
    leaf notification-phase {
      type Inst-notif-phase;
      description
        "Notification phase";
    }
    leaf time-sent {
      type string;
      description
        "Timestamp notifications were sent, in RFC3339
         internet date/time format";
    }
    leaf-list clients-responded {
      type String1;
      description
        "Clients that have responded to notifications";
    }
    leaf-list clients-waiting {
      type String1;
      description
        "Clients that have not yet responded to
         notifications";
    }
  }

  grouping INST-PKG-OP-INFO {
    description
      "Install packaging operation information";
    leaf stage {
      type Inst-pkg-op-stage;
      description
        "Package operation stage";
    }
    leaf percentage-progress {
      type uint32;
      units "percentage";
      description
        "Percentage complete";
    }
    leaf packages-complete {
      type uint32;
      description
        "Count of packages completed";
    }
    leaf packages-total {
      type uint32;
      description
        "Count of total packages";
    }
  }

  grouping INST-STATUS-NODE {
    description
      "Install per-node status data";
    container packaging-operation-status {
      description
        "Further information, if a packaging operation is
         in progress";
      uses INST-PKG-OP-INFO;
    }
    container client-notification-status {
      description
        "Further information, if client notifications are
         in progress";
      uses INST-NOTIF-STATUS;
    }
    leaf node {
      type string;
      description
        "Node name";
    }
    leaf current-request {
      type Inst-node-req;
      description
        "Node request currently being handled";
    }
    leaf time-started {
      type String1;
      description
        "Timestamp this node request was started, in
         RFC3339 internet date/time format";
    }
  }

  grouping INST-REQUEST-VERBOSE-BAG {
    description
      "Status of current install user request";
    container lock-status {
      description
        "Status of the install lock";
      uses INST-LOCK-REQ-STATUS;
    }
    container available-actions {
      description
        "Actions that are currently valid to start";
      uses INST-AVAILABLE-ACTIONS;
    }
    container recovery-actions {
      description
        "Non install recovery actions, if install actions
         are not available";
      uses INST-RECOVERY-ACTIONS;
    }
    leaf current-activity {
      type Inst-activity;
      description
        "Activity in progress";
    }
    leaf time-started {
      type String1;
      description
        "Timestamp this activity was started, in RFC3339
         internet date/time format";
    }
    leaf next-activity {
      type Inst-activity;
      description
        "Activity ";
    }
    leaf node-request {
      type Inst-node-req;
      description
        "Node request in progress, if any";
    }
    leaf node-request-time {
      type String1;
      description
        "Timestamp node request was sent, in RFC3339
         internet date/time format";
    }
    leaf node-request-time-left {
      type uint32;
      units "second";
      description
        "Seconds until the node request will time out";
    }
    leaf nodes-responded {
      type uint32;
      description
        "Count of nodes that have responded";
    }
    leaf nodes-total {
      type uint32;
      description
        "Total count of nodes the request was sent to";
    }
    leaf request {
      type String1;
      description
        "The last user request";
    }
    leaf state {
      type Inst-req-state;
      description
        "The state of the last user request";
    }
    leaf timestamp {
      type String1;
      description
        "The time the current state was entered";
    }
    leaf error {
      type String1;
      description
        "String describing the error, if any";
    }
    leaf operation-id {
      type String1;
      description
        "The operation ID of this request";
    }
    leaf warning {
      type String1;
      description
        "String describing a warning, if any";
    }
    list nodes-req-status {
      description
        "Status of per-node processing, if a node request
         is in progress";
      uses INST-STATUS-NODE;
    }
  }

  grouping INST-DISABLED-PKGS-BAG {
    description
      "Packages that are disabled by the platform";
    leaf-list package {
      type String1;
      description
        "List of packages that are disabled on this
         platform.";
    }
  }

  grouping INST-AVAILABLE-GROUP-FIX-TYPE {
    description
      "INST AVAILABLE GROUP FIX TYPE";
    leaf-list ddt-ss {
      type String1;
      description
        "All DDTS ids fixed by Packages";
    }
    list package {
      description
        "Packages";
      uses INST-PKG;
    }
  }

  grouping INST-AVAILABLE-GROUP-FIXES-BAG {
    description
      "Install bag containing details of available
       groups of fixes";
    leaf-list all-ddts {
      type String1;
      description
        "All DDTSs referenced in GroupFix";
    }
    list group-fix {
      description
        "The group fixes";
      uses INST-AVAILABLE-GROUP-FIX-TYPE;
    }
  }

  grouping INST-UPGRADE-MATRIX-RPM {
    description
      "Upgrade matrix RPM details";
    leaf name {
      type string;
      description
        "RPM name";
    }
    leaf version {
      type string;
      description
        "RPM version";
    }
  }

  grouping INST-UPGRADE-MATRIX-FIX {
    description
      "Upgrade matrix fix";
    leaf fix {
      type Fix;
      description
        "DDTS or fix ID";
    }
    list rpms {
      description
        "RPMs";
      uses INST-UPGRADE-MATRIX-RPM;
    }
  }

  grouping INST-REIMAGE-INFO {
    description
      "Reimage Info";
    leaf reimage-only {
      type boolean;
      description
        "Upgrade requires a reimage";
    }
  }

  grouping INST-UPGRADE-MATRIX-HW {
    description
      "Upgrade matrix hardware data";
    leaf pid {
      type Install-opt-string;
      description
        "PID";
    }
    leaf reason {
      type Install-opt-string;
      description
        "Reason for the hardware being unsupported";
    }
  }

  grouping INSTALL-UPGRADE-MATRIX-DETAILS {
    description
      "Upgrade matrix details";
    container reimage-info {
      description
        "Reimage info";
      uses INST-REIMAGE-INFO;
    }
    leaf-list bridging-fixe {
      type Fix;
      description
        "Bridging Fixes List";
    }
    leaf-list target-fixe {
      type Fix;
      description
        "Target Fixes List";
    }
    leaf-list caveats {
      type Caveat;
      description
        "Caveats list";
    }
    leaf-list blocklisted-fixe {
      type Fix;
      description
        "Blocklisted Fixes List";
    }
    list unsupported-hardware {
      description
        "Unsupported hardware list";
      uses INST-UPGRADE-MATRIX-HW;
    }
    list bridging-fixes-rpm {
      description
        "Bridging Fixes, list of DDTS (and associated
         RPMs)";
      uses INST-UPGRADE-MATRIX-FIX;
    }
    list target-fixes-rpm {
      description
        "Target Fixes, list of DDTS (and associated RPMs)";
      uses INST-UPGRADE-MATRIX-FIX;
    }
    list blocklisted-fixes-rpm {
      description
        "List of DDTS (and associated RPMs) which must
         not be installed";
      uses INST-UPGRADE-MATRIX-FIX;
    }
  }

  grouping INSTALL-UPGRADE-MATRIX-RELEASE-DATA {
    description
      "Upgrade matrix version data";
    leaf from {
      type string;
      description
        "From version";
    }
    leaf to {
      type string;
      description
        "To version";
    }
  }

  grouping INSTALL-UPGRADE-MATRIX-DATA {
    description
      "Upgrade matrix data";
    container versions {
      description
        "Versions";
      uses INSTALL-UPGRADE-MATRIX-RELEASE-DATA;
    }
    container details {
      description
        "Details";
      uses INSTALL-UPGRADE-MATRIX-DETAILS;
    }
  }

  grouping INSTALL-UPGRADE-MATRIX-ISO {
    description
      "Upgrade matrix info for the input ISO";
    leaf info {
      type Install-opt-string;
      description
        "Info";
    }
    leaf matrix-version {
      type Install-opt-string;
      description
        "Matrix file version";
    }
    list upgrade-matrix-info {
      description
        "Upgrade matrix table";
      uses INSTALL-UPGRADE-MATRIX-DATA;
    }
  }

  grouping INST-AVAILABLE-PKG-TYPE {
    description
      "Install package type";
    leaf name {
      type string;
      description
        "Package name";
    }
    leaf architecture {
      type string;
      description
        "Architecture";
    }
    leaf version {
      type string;
      description
        "Version";
    }
    leaf repository {
      type string;
      description
        "Repository";
    }
    leaf cached {
      type boolean;
      description
        "Cached in the internal repository";
    }
    leaf release {
      type Install-opt-string;
      description
        "Release";
    }
    leaf epoch {
      type Install-opt-string;
      description
        "Epoch";
    }
    leaf xr-package {
      type boolean;
      description
        "XR Package";
    }
  }

  grouping INST-AVAILABLE-PACKAGES-BAG {
    description
      "Available package result bag";
    leaf-list inaccessible-repository {
      type String1;
      description
        "List of repositories that the package manager
         was unable to access, likely due to
         configuration errors or network connectivity";
    }
    leaf-list repositories-metadata-failed {
      type String1;
      description
        "List of local repositories where automatic
         metadata generation failed. Information about
         packages in these repositories may not be up to
         date.";
    }
    list package {
      description
        "Packages";
      uses INST-AVAILABLE-PKG-TYPE;
    }
  }

  grouping INST-RPM-FINGER-PRINT {
    description
      "Install package fingerprint type";
    leaf rpm-fingerprint-install-time {
      type Install-opt-string;
      description
        "Package fingerprint at install time.";
    }
    leaf rpm-fingerprint-run-time {
      type Install-opt-string;
      description
        "Package fingerprint at run time. A runtime
         fingerprint of '0' indicates that the runtime
         fingerprint for this package has not yet been
         calculated.";
    }
  }

  grouping INST-PKG-TYPE {
    description
      "Install package type";
    container rpm-fingerprint {
      description
        "RPM Fingerprint at install and run time";
      uses INST-RPM-FINGER-PRINT;
    }
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
    leaf gpg-key-id {
      type Install-opt-string;
      description
        "The GPG key ID at install time. A key ID of '0'
         indicates a package with no GPG signature.";
    }
  }

  grouping INST-PACKAGES-BAG {
    description
      "Package result bag";
    leaf rpm-fingerprint-status {
      type Inst-fp-request-status;
      description
        "Package Fingerprint request status";
    }
    leaf rpm-fingerprint-timestamp {
      type Install-opt-string;
      description
        "Package run time fingerprint collection time";
    }
    leaf label {
      type Install-opt-string;
      description
        "Label of image";
    }
    leaf xr-packages-hash {
      type Install-opt-string;
      description
        "Hash of XR packages in this bag";
    }
    list package {
      description
        "Packages";
      uses INST-PKG-TYPE;
    }
  }

  grouping INST-ATOMIC-CHANGE-NODE-BAG {
    description
      "Node specific atomic change information";
    container changeset {
      description
        "Changeset information";
      uses INST-CHANGESET;
    }
    list pre-pre-apply-notification {
      description
        "Notifications sent for 'Pre-pre-apply' phase";
      uses INST-NOTIF;
    }
    list pre-apply-notification {
      description
        "Notifications sent for 'Pre-apply' phase";
      uses INST-NOTIF;
    }
    list apply-notification {
      description
        "Notifications sent for 'Apply' phase";
      uses INST-NOTIF;
    }
    list further-apply-notification {
      description
        "Further notifications sent for 'Apply' phase,
         after allowing for processes to restart";
      uses INST-NOTIF;
    }
    list post-apply-notification {
      description
        "Notifications sent for 'Post-apply' phase";
      uses INST-NOTIF;
    }
    list post-post-apply-notification {
      description
        "Notifications sent for 'Post-post-apply' phase";
      uses INST-NOTIF;
    }
    list event {
      description
        "Per node events";
      uses INST-NODE-EVENT;
    }
  }

  grouping INST-SYSTEM-RELOAD-REASON {
    description
      "Information about system reload reasons";
    leaf iso-config {
      type boolean;
      description
        "True if ISO config is being applied";
    }
  }

  grouping INST-ATOMIC-CHANGE-NODE {
    description
      "Install per-node atomic change data";
    container changeset {
      description
        "Changeset information";
      uses INST-CHANGESET;
    }
    leaf node {
      type string;
      description
        "Node name";
    }
    list pre-pre-apply-notification {
      description
        "Notifications sent for 'Pre-pre-apply' phase";
      uses INST-NOTIF;
    }
    list pre-apply-notification {
      description
        "Notifications sent for 'Pre-apply' phase";
      uses INST-NOTIF;
    }
    list apply-notification {
      description
        "Notifications sent for 'Apply' phase";
      uses INST-NOTIF;
    }
    list further-apply-notification {
      description
        "Further notifications sent for 'Apply' phase,
         after allowing for processes to restart";
      uses INST-NOTIF;
    }
    list post-apply-notification {
      description
        "Notifications sent for 'Post-apply' phase";
      uses INST-NOTIF;
    }
    list post-post-apply-notification {
      description
        "Notifications sent for 'Post-post-apply' phase";
      uses INST-NOTIF;
    }
    list event {
      description
        "Per node events";
      uses INST-NODE-EVENT;
    }
  }

  grouping INST-ATOMIC-STATUS {
    description
      "Atomic change status";
    leaf status {
      type Inst-atomic-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping INST-ATOMIC-CHANGE-BAG {
    description
      "Install atomic change entry";
    container reload-reasons {
      description
        "Reload reasons";
      uses INST-SYSTEM-RELOAD-REASON;
    }
    leaf index {
      type uint32;
      description
        "Atomic change index";
    }
    leaf requested-apply-method {
      type Inst-activation;
      description
        "Requested apply method";
    }
    leaf least-impactful-apply-method {
      type Inst-activation;
      description
        "Least impactful apply method required to apply
         packaging operations thus far.";
    }
    leaf install-restart {
      type boolean;
      description
        "Install infra restart during apply";
    }
    leaf previous-index {
      type uint32;
      description
        "Atomic change index of previous atomic operation";
    }
    leaf previous-bridging-status {
      type Inst-bridging-bugfix;
      description
        "Information about whether bridging bugfix RPMs
         were installed as part of the previous atomic
         change";
    }
    leaf username {
      type String1;
      description
        "The user who initiated the atomic operation";
    }
    leaf apply-username {
      type String1;
      description
        "If this operation has been applied, the user who
         applied it";
    }
    list status-history {
      description
        "Status history for this atomic change, in
         reverse chronological order";
      uses INST-ATOMIC-STATUS;
    }
    list nodes {
      status obsolete;
      description
        "Node-specific information";
      uses INST-ATOMIC-CHANGE-NODE;
    }
  }

  grouping INST-PKG-OP-NODE {
    description
      "Install per-node packaging operation data";
    container disk-space-check {
      description
        "Disk space pre-check information";
      uses INST-DISK-SPACE;
    }
    leaf node {
      type string;
      description
        "Node name";
    }
    leaf download-size {
      type uint64;
      units "byte";
      description
        "Download size in bytes (deprecated)";
    }
    leaf installed-size {
      type uint64;
      units "byte";
      description
        "Total installed size of packages in bytes
         (deprecated)";
    }
    list package {
      description
        "List of packages";
      uses INST-PKG-INFO;
    }
    list packages-no-action {
      description
        "List of input packages on which no action was
         taken, for example because there was no suitable
         version to upgrade or downgrade to";
      uses INST-PKG-NO-ACTION;
    }
    list veto-notification {
      description
        "List of notifications sent in 'Veto' phase";
      uses INST-NOTIF;
    }
    list prepare-veto-notification {
      description
        "List of veto notifications sent in 'Prepare'
         phase";
      uses INST-NOTIF;
    }
    list prepare-notification {
      description
        "List of prepare notifications sent in 'Prepare'
         phase";
      uses INST-NOTIF;
    }
    list event {
      description
        "Per node events";
      uses INST-NODE-EVENT;
    }
    list pkg-verify-failure {
      description
        "Signature check failures";
      uses INST-PKG-VERIFY-FAILURE;
    }
  }

  grouping INST-PKG-OP-STATUS {
    description
      "Package operation status";
    leaf status {
      type Inst-pkg-op-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping INST-UNDO-REQ {
    description
      "Install undo packaging operation request";
    leaf abort-type {
      type Inst-package-abort;
      description
        "Abort Type";
    }
    leaf-list packaging-operation {
      type uint32;
      description
        "Indices of packaging operations being undone";
    }
  }

  grouping INST-REQ {
    description
      "Install request";
    container operation {
      when "../reason = 'user'" {
        description
          "../Reason = 'User'";
      }
      description
        "Details of user request";
      uses INST-USER-REQ;
    }
    container abort-operation {
      when "../reason = 'undoing-due-to-abort'" {
        description
          "../Reason = 'UndoingDueToAbort'";
      }
      description
        "Details of packaging operation(s) being undone";
      uses INST-UNDO-REQ;
    }
    leaf reason {
      type Inst-req-reason;
      description
        "Reason";
    }
  }

  grouping INST-PKG-OP-BAG {
    description
      "Install package operation entry";
    container request {
      description
        "Requested operation";
      uses INST-REQ;
    }
    leaf index {
      type uint32;
      description
        "Packaging operation index";
    }
    leaf error-string {
      type String1;
      description
        "String pointing the user to any packaging
         manager error information";
    }
    leaf config-replace-info {
      type Inst-cfg-replace-info;
      description
        "Info about config handling in replace operations";
    }
    leaf package-source {
      type String1;
      description
        "Source used for the packaging operation";
    }
    leaf username {
      type String1;
      description
        "User who initiated this package operation";
    }
    list status-history {
      description
        "Status history for the package operation, in
         reverse chronological order";
      uses INST-PKG-OP-STATUS;
    }
    list nodes {
      status obsolete;
      description
        "Node-specific information";
      uses INST-PKG-OP-NODE;
    }
  }

  grouping INST-PKG-VERIFY-FAILURE {
    description
      "Install package verification check failure";
    container package {
      description
        "Package which failed the signature check";
      uses INST-PKG;
    }
    leaf error-type {
      type Inst-pkg-verify-error;
      description
        "The error causing the signature check failure";
    }
    leaf key-id {
      type String1;
      description
        "Fingerprint for the key used to sign the package";
    }
  }

  grouping INST-DISK-SPACE {
    description
      "Install disk space pre-check data";
    leaf phase {
      type Inst-disk-space-check-phase;
      description
        "Phase the disk space check failed at";
    }
    leaf required-space {
      type uint64;
      units "byte";
      description
        "Space required in the rootfs in bytes";
    }
    leaf available-space {
      type uint64;
      units "byte";
      description
        "Space available in the rootfs in bytes";
    }
  }

  grouping INST-NOTIF-TIME-REQ {
    description
      "Extra time request information";
    leaf time {
      type string;
      description
        "Timestamp of request, in RFC3339 internet
         date/time format";
    }
    leaf extra-time {
      type uint32;
      units "second";
      description
        "Amount of extra time requested in seconds";
    }
    leaf reason {
      type String1;
      description
        "Reason for the extra time being requested (if
         known)";
    }
  }

  grouping INST-NOTIF-RELOAD-TYPE {
    description
      "INST NOTIF RELOAD TYPE";
    leaf node {
      type string;
      description
        "Which node is to be reloaded";
    }
    leaf reason {
      type String1;
      description
        "Reason for requested reload";
    }
  }

  grouping INST-CLIENT-RELOAD {
    description
      "Information about client reload reasons";
    leaf name {
      type string;
      description
        "The name of the client";
    }
    leaf jid {
      type string;
      description
        "Job ID of the client";
    }
    leaf reason {
      type string;
      description
        "Reason to request a reload";
    }
  }

  grouping INST-RELOAD-REASON {
    description
      "Information about reload reasons";
    container packages {
      description
        "List of packages which has requested a reload";
      uses PACKAGE-NAMES;
    }
    leaf too-many-processes {
      type boolean;
      description
        "True if too many processes requested a restart";
    }
    list client {
      description
        "List of clients which have requested a reload";
      uses INST-CLIENT-RELOAD;
    }
  }

  grouping INST-FEATURE-CHANGE {
    description
      "Feature change information";
    leaf feature-name {
      type string;
      description
        "Name of feature";
    }
    leaf change {
      type Inst-feature-change;
      description
        "Change type";
    }
  }

  grouping INST-PROCESS-CHANGE {
    description
      "Impacted process information";
    leaf name {
      type string;
      description
        "Process name";
    }
    leaf change {
      type Inst-proc-change;
      description
        "Type of change";
    }
    leaf pid {
      type uint32;
      description
        "Process ID";
    }
  }

  grouping INST-FILE-CHANGE {
    description
      "File change information";
    leaf path {
      type string;
      description
        "File path, relative to /opt/cisco/iosxr";
    }
    leaf change {
      type Inst-file-change;
      description
        "Change type";
    }
  }

  grouping INST-CHANGESET {
    description
      "Changeset";
    container reload-reasons {
      description
        "Reload reasons";
      uses INST-RELOAD-REASON;
    }
    list changed-file {
      description
        "Changed files";
      uses INST-FILE-CHANGE;
    }
    list impacted-process {
      description
        "Impacted processes";
      uses INST-PROCESS-CHANGE;
    }
    list changed-feature {
      description
        "Changed features";
      uses INST-FEATURE-CHANGE;
    }
  }

  grouping NOTIFICATION-TRIGGER {
    description
      "Notification Trigger";
    container trigger-changeset {
      when "../client-type = 'default'" {
        description
          "../ClientType = 'Default'";
      }
      description
        "Trigger Changeset";
      uses INST-CHANGESET;
    }
    leaf client-type {
      type Inst-client;
      description
        "ClientType";
    }
    leaf legacy-client {
      when "../client-type = 'legacy'" {
        description
          "../ClientType = 'Legacy'";
      }
      type boolean;
      description
        "Legacy client - notifications are sent
         regardless of changeset";
    }
  }

  grouping INST-NOTIF {
    description
      "Install notification information";
    container notification-trigger {
      description
        "Notification trigger";
      uses NOTIFICATION-TRIGGER;
    }
    leaf client {
      type string;
      description
        "Client notification was sent to";
    }
    leaf description {
      type string;
      description
        "Description of the client";
    }
    leaf sent-time {
      type string;
      description
        "Time notification was sent, in RFC3339 internet
         date/time format";
    }
    leaf response-status {
      type Inst-notif-res;
      description
        "Status of response from client";
    }
    leaf error {
      type String1;
      description
        "Error, if any";
    }
    leaf response-time {
      type string;
      description
        "Time of clients response, in RFC3339 internet
         date/time format";
    }
    leaf veto-reason {
      type String1;
      description
        "Reason for requested veto";
    }
    list reload-reason {
      description
        "Reasons for reload, if any";
      uses INST-NOTIF-RELOAD-TYPE;
    }
    list extra-time-request {
      description
        "Requests for extra time, if any";
      uses INST-NOTIF-TIME-REQ;
    }
  }

  grouping INST-PKG-NO-ACTION {
    description
      "Information about a package on which no action
       was taken";
    container package {
      description
        "Package or user input on which no action was
         taken";
      uses INST-PKG;
    }
    leaf reason {
      type Inst-no-action-reason;
      description
        "Reason that no action was taken on this package";
    }
  }

  grouping INST-PKG {
    description
      "Package";
    leaf name {
      type string;
      description
        "Package name";
    }
    leaf version {
      type String1;
      description
        "Version";
    }
    leaf architecture {
      type String1;
      description
        "Package architecture";
    }
  }

  grouping INST-PKG-INFO {
    description
      "Install per package information";
    container package {
      description
        "Package";
      uses INST-PKG;
    }
    leaf action {
      type Inst-pkg-op-act;
      description
        "Action taken on this package";
    }
  }

  grouping INST-PKG-OP-NODE-BAG {
    description
      "Node specific packaging operation information";
    container disk-space-check {
      description
        "Disk space pre-check information";
      uses INST-DISK-SPACE;
    }
    leaf download-size {
      type uint64;
      units "byte";
      description
        "Download size in bytes (deprecated)";
    }
    leaf installed-size {
      type uint64;
      units "byte";
      description
        "Total installed size of packages in bytes
         (deprecated)";
    }
    list package {
      description
        "List of packages";
      uses INST-PKG-INFO;
    }
    list packages-no-action {
      description
        "List of input packages on which no action was
         taken, for example because there was no suitable
         version to upgrade or downgrade to";
      uses INST-PKG-NO-ACTION;
    }
    list veto-notification {
      description
        "List of notifications sent in 'Veto' phase";
      uses INST-NOTIF;
    }
    list prepare-veto-notification {
      description
        "List of veto notifications sent in 'Prepare'
         phase";
      uses INST-NOTIF;
    }
    list prepare-notification {
      description
        "List of prepare notifications sent in 'Prepare'
         phase";
      uses INST-NOTIF;
    }
    list event {
      description
        "Per node events";
      uses INST-NODE-EVENT;
    }
    list pkg-verify-failure {
      description
        "Signature check failures";
      uses INST-PKG-VERIFY-FAILURE;
    }
  }

  grouping INST-PKG-OP-ERRORS-BAG {
    description
      "DNF logs for any node where DNF has encountered
       errors in a packaging operation";
    leaf-list lines {
      type String1;
      description
        "Lines of the DNF output";
    }
  }

  grouping INST-TRANS-NODE {
    description
      "Install per-node transaction data";
    leaf node {
      type String1;
      description
        "Node name";
    }
    list event {
      description
        "Per-node events";
      uses INST-NODE-EVENT;
    }
  }

  grouping INST-TRANS-STATUS {
    description
      "Transaction status";
    leaf status {
      type Inst-trans-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping PACKAGE-NAMES {
    description
      "PACKAGE NAMES";
    leaf-list package-name {
      type String1;
      description
        "package name";
    }
  }

  grouping INST-USER-REQ {
    description
      "Install user packaging operation request";
    container unknown-packages {
      when "../request = 'unknown'" {
        description
          "../Request = 'Unknown'";
      }
      description
        "List of packages";
      uses PACKAGE-NAMES;
    }
    container install-packages {
      when "../request = 'add'" {
        description
          "../Request = 'Add'";
      }
      description
        "List of packages";
      uses PACKAGE-NAMES;
    }
    container remove-packages {
      when "../request = 'remove'" {
        description
          "../Request = 'Remove'";
      }
      description
        "List of packages";
      uses PACKAGE-NAMES;
    }
    container upgrade-packages {
      when "../request = 'upgrade'" {
        description
          "../Request = 'Upgrade'";
      }
      description
        "List of packages";
      uses PACKAGE-NAMES;
    }
    container downgrade-packages {
      when "../request = 'downgrade'" {
        description
          "../Request = 'Downgrade'";
      }
      description
        "List of packages";
      uses PACKAGE-NAMES;
    }
    leaf request {
      type Inst-request;
      description
        "Request";
    }
    leaf replace-iso {
      when "../request = 'replace'" {
        description
          "../Request = 'Replace'";
      }
      type String1;
      description
        "ISO";
    }
    leaf rollback-to-transaction {
      when "../request = 'rollback'" {
        description
          "../Request = 'Rollback'";
      }
      type uint32;
      description
        "Transaction ID";
    }
    leaf reimage-iso {
      when "../request = 'reimage'" {
        description
          "../Request = 'Reimage'";
      }
      type String1;
      description
        "ISO";
    }
  }

  grouping INST-TRANS-BAG {
    description
      "Install transaction entry";
    container started-by-user-request {
      description
        "Packaging operation that started this
         transaction";
      uses INST-USER-REQ;
    }
    leaf transaction-id {
      type uint32;
      description
        "Transaction ID";
    }
    leaf username {
      type String1;
      description
        "The user who initiated the transaction";
    }
    leaf commit-username {
      type String1;
      description
        "The this transaction has been committed, the
         usern who committed it";
    }
    list status-history {
      description
        "Status history for this transaction, in reverse
         chronological order";
      uses INST-TRANS-STATUS;
    }
    list nodes {
      status obsolete;
      description
        "Node-specific information";
      uses INST-TRANS-NODE;
    }
  }

  grouping INST-NODE-EVENT {
    description
      "Node events";
    leaf event {
      type Inst-node-event;
      description
        "Event";
    }
    leaf time {
      type string;
      description
        "Timestamp, in RFC3339 internet date/time format";
    }
    leaf reason {
      type String1;
      description
        "Reason for the event, for example an error
         string";
    }
    leaf event-id {
      type uint32;
      description
        "Transaction level identifier for this event";
    }
    leaf reload-reason {
      type Inst-node-event-reload-reason;
      description
        "If applicable, the reason the node was reloaded
         due to this node event";
    }
  }

  grouping INST-TRANS-NODE-BAG {
    description
      "Node specific transaction information";
    list event {
      description
        "Per-node events";
      uses INST-NODE-EVENT;
    }
  }

  grouping INST-TRIAGE-COMMAND {
    description
      "Install triage command";
    leaf cli-cmd {
      type String1;
      description
        "Command to run from the CLI";
    }
  }

  grouping INST-TRIAGE-COMMANDS {
    description
      "INST TRIAGE COMMANDS";
    list inst-triage-command {
      description
        "inst triage command";
      uses INST-TRIAGE-COMMAND;
    }
  }

  grouping INST-SUGGESTED-STEP {
    description
      "Install suggested step";
    leaf cli-cmd {
      type String1;
      description
        "Command to run from the CLI";
    }
    leaf cli-description {
      type String1;
      description
        "Description of a step to perform from the CLI";
    }
  }

  grouping INST-SUGGESTED-STEPS {
    description
      "INST SUGGESTED STEPS";
    list inst-suggested-step {
      description
        "inst suggested step";
      uses INST-SUGGESTED-STEP;
    }
  }

  grouping INST-INTERVENTION-EVENT-INFO {
    description
      "Information about Install event requiring
       intervention";
    container error {
      description
        "Description of the error";
      uses STRING-LIST-TYPE;
    }
    container warning {
      description
        "Description of the warning";
      uses STRING-LIST-TYPE;
    }
    container suggested-steps {
      description
        "Suggested steps to resolve the issue";
      uses INST-SUGGESTED-STEPS;
    }
    container triage-commands {
      description
        "Triage commands to run that collect information
         for Cisco Support";
      uses INST-TRIAGE-COMMANDS;
    }
    container internal-details {
      description
        "Details to pass on to Cisco Support";
      uses STRING-LIST-TYPE;
    }
  }

  grouping INST-INTERVENTION-EVENT {
    description
      "Install event requiring intervention";
    container intervention-event-info {
      description
        "Detailed information associated with the
         intervention event";
      uses INST-INTERVENTION-EVENT-INFO;
    }
    leaf category {
      type Inst-intervention-event-category;
      description
        "The intervention category";
    }
    leaf time {
      type string;
      description
        "Timestamp for when the intervention event
         occurred in RFC3339 internet date/time format";
    }
  }

  grouping INST-OP-INTERVENTION-EVENTS-BAG {
    description
      "Install events requiring intervention";
    list intervention-event {
      description
        "Intervention events";
      uses INST-INTERVENTION-EVENT;
    }
  }

  grouping INST-REIMAGE-HISTORY-BAG {
    description
      "Install Reimage history entry";
    leaf reimage-id {
      type uint32;
      description
        "Reimage ID";
    }
    leaf user-request {
      type String1;
      description
        "User request string that started this
         transaction";
    }
    leaf time-started {
      type String1;
      description
        "Timestamp this activity was started, in RFC3339
         internet date/time format";
    }
    leaf error-string {
      type String1;
      description
        "String describing the error during this
         operation";
    }
    leaf error-time {
      type String1;
      description
        "Timestamp the error was hit, in RFC3339 internet
         date/time format";
    }
  }

  grouping INST-PLATFORM-SUPPORT-BAG {
    description
      "Support for Install features on this platform";
    leaf max-rollback-space {
      type uint64;
      description
        "The maximum amount of space allowed for rollback
         points on this platform. A value of 0 indicates
         that rollback is not supported.";
    }
  }
}
