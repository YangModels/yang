submodule Cisco-IOS-XR-fib-common-oper-sub1 {
  belongs-to Cisco-IOS-XR-fib-common-oper {
    prefix Cisco-IOS-XR-fib-common-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2023 by Cisco Systems, Inc.
     All rights reserved.";

  revision 2023-06-01 {
    description
      "Added new field to ltep-nve-tunnels in order keep track of destination address protocol
       2023-04-24
         Combined separate evni tables for BGP and RTEP-ID to single evni table
       2023-04-14
         Added hardware ingress and egress path for evni
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  grouping SRV6-ACCT-PATH-INFO {
    description
      "SRV6 ACCT PATH INFO";
    leaf number-of-tx-packets {
      type uint64;
      description
        "Number of Tx packets per path";
    }
    leaf number-of-tx-bytes {
      type uint64;
      units "byte";
      description
        "Number of Tx bytes per path";
    }
    leaf path-index {
      type uint32;
      description
        "Path index";
    }
    leaf outgoing-interface {
      type xr:Interface-name;
      description
        "Output Interface in string format";
    }
    leaf nexthop-addr {
      type string {
        length "0..52";
      }
      description
        "Nexthop address";
    }
  }

  grouping SRV6-ACCT-PFX-INFO {
    description
      "SRV6 ACCT PFX INFO";
    leaf ipv6-prefix {
      type string {
        length "0..52";
      }
      description
        "IPV6 prefix";
    }
    leaf ipv6-prefix-length {
      type uint32;
      description
        "Prefix length";
    }
    leaf total-number-of-packets-switched {
      type uint64;
      description
        "Total number of packets switched";
    }
    leaf total-number-of-bytes-switched {
      type uint64;
      units "byte";
      description
        "Total number of Bytes switched";
    }
    list accounting-information {
      description
        "Accounting infos for each path";
      uses SRV6-ACCT-PATH-INFO;
    }
  }
}
