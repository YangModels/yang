module Cisco-IOS-XR-um-subscriber-cfg {
  namespace "http://cisco.com/ns/yang/Cisco-IOS-XR-um-subscriber-cfg";
  prefix um-subscriber-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber package configuration.
     
     This YANG module augments the
     modules with configuration data.
     
     Copyright (c) 2020, 2022-2023 by Cisco Systems, Inc.
     All rights reserved.";

  revision 2022-09-23 {
    description
      "Paltx support";
    semver:module-version "1.1.0";
  }
  revision 2020-08-11 {
    description
      "Initial release";
    semver:module-version "1.0.0";
  }

  container subscriber {
    description
      "Subscriber Configuration";
    container database {
      description
        "subdb batching configuration";
      leaf batch-control {
        type uint32 {
          range "0..4" {
            description
              "higher level, better batching, more delay. <0 - disable>";
          }
        }
        description
          "batching performance control";
      }
      leaf backpressure-level {
        type uint32 {
          range "0..3" {
            description
              "0 - disable, 1 - gentle, 3 - aggressive";
          }
        }
        description
          "backpressure level";
      }
    }
    container periodic-trace {
      description
        "periodic collection of ltraces";
      leaf cfg-file {
        type xr:Cisco-ios-xr-string {
          length "1..800" {
            description
              "name of file on the system. ex: /harddisk:/paltx/bng.cfg";
          }
        }
        description
          "configuration file [Restricted to development use only !!!]";
      }
      container iedge {
        presence "Indicates a iedge node is configured.";
        description
          "periodic tracing for iedge";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container ipsub {
        presence "Indicates a ipsub node is configured.";
        description
          "periodic tracing for ipsub";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container dhcpv4 {
        presence "Indicates a dhcpv4 node is configured.";
        description
          "periodic tracing for dhcpv4";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container dhcpv6 {
        presence "Indicates a dhcpv6 node is configured.";
        description
          "periodic tracing for dhcpv6";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container subdb {
        presence "Indicates a subdb node is configured.";
        description
          "periodic tracing for subdb";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container srg {
        presence "Indicates a srg node is configured.";
        description
          "periodic tracing for srg";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container acct {
        presence "Indicates a acct node is configured.";
        description
          "periodic tracing for accounting";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container diameter {
        presence "Indicates a diameter node is configured.";
        description
          "periodic tracing for diameter";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container cnbng-nal {
        presence "Indicates a cnbng-nal node is configured.";
        description
          "periodic tracing for cnbng-nal";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container pppoe {
        presence "Indicates a pppoe node is configured.";
        description
          "periodic tracing for pppoe";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
      container ppp {
        presence "Indicates a ppp node is configured.";
        description
          "periodic tracing for ppp";
        leaf delay {
          type xr:Cisco-ios-xr-string {
            length "1..800" {
              description
                "[1 - 99] default 10";
            }
            pattern "[1-9][0-9]{0,1}";
          }
          description
            "time between collections in minutes";
        }
        leaf quota {
          type xr:Cisco-ios-xr-string {
            length "1..800" {
              description
                "[10 - 999] default 100";
            }
            pattern "[1-9][0-9]{1,2}";
          }
          description
            "disk quota in MB";
        }
        leaf location {
          type string {
            length "1..900" {
              description
                "default /harddisk:/paltx/<comp>";
            }
          }
          description
            "custom storage location";
        }
        leaf offload {
          type string {
            length "1..900" {
              description
                "ftp://anonymous:anonymous@serverip/folder
                 tftp://serverip/folder";
            }
          }
          description
            "offload location";
        }
      }
    }
  }
}
