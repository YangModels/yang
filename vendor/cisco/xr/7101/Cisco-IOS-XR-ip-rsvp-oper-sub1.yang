submodule Cisco-IOS-XR-ip-rsvp-oper-sub1 {
  belongs-to Cisco-IOS-XR-ip-rsvp-oper {
    prefix Cisco-IOS-XR-ip-rsvp-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-rsvp package operational data.
     
     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef Igpte-lib-bw-model {
    type enumeration {
      enum "rdm" {
        value 0;
        description
          "Russian Dolls Model";
      }
      enum "mam" {
        value 1;
        description
          "Maximum Allocation Model";
      }
      enum "not-set" {
        value 2;
        description
          "No model set";
      }
    }
    description
      "Bandwidth model";
  }

  typedef Rsvp-mgmt-restart-state {
    type enumeration {
      enum "done" {
        description
          "Restart is done";
      }
      enum "recovery" {
        description
          "Neighbor is in recovery";
      }
      enum "abort" {
        description
          "Neighbor recovery aborted";
      }
    }
    description
      "RSVP GR (Graceful Restart) Restart states";
  }

  typedef Rsvp-mgmt-hello-down-reason {
    type enumeration {
      enum "not-applicable" {
        description
          "Not applicable. This means RSVP Hellos are up";
      }
      enum "wrong-destination-instance" {
        description
          "Incorrect destination instance in received
           Hellos";
      }
      enum "wrong-source-instance" {
        description
          "Incorrect source instance in received Hellos";
      }
      enum "hello-missed" {
        description
          "Hellos not being received";
      }
      enum "interface-down" {
        description
          "Interface went down";
      }
      enum "neighbor-disabled-hello" {
        description
          "Neighbor disabled Hellos";
      }
      enum "control-channel-down" {
        description
          "Control channel went down";
      }
    }
    description
      "Reasons why RSVP Hellos went down";
  }

  typedef Rsvp-mgmt-hello-instance-owner {
    type enumeration {
      enum "mpls-graceful-restart" {
        description
          "MPLS Graceful Restart";
      }
      enum "mpls-ouni" {
        description
          "MPLS OUNI";
      }
    }
    description
      "RSVP Hello instance owner";
  }

  typedef Rsvp-mgmt-association {
    type enumeration {
      enum "none" {
        value 0;
        description
          "No ASSOCIATION Object present";
      }
      enum "ipv4" {
        value 1;
        description
          "IPv4 ASSOCIATION Type";
      }
      enum "ipv6" {
        value 2;
        description
          "IPv6 ASSOCIATION Type";
      }
      enum "extended-ipv4" {
        value 3;
        description
          "EXTENDED IPv4 ASSOCIATION Type";
      }
      enum "extended-ipv6" {
        value 4;
        description
          "EXTENDED IPv6 ASSOCIATION Type";
      }
    }
    description
      "RSVP ASSOCIATION Types";
  }

  typedef Rsvp-mgmt-rro-subobj {
    type enumeration {
      enum "ipv4rro-type" {
        value 1;
        description
          "IPv4 RRO Type";
      }
      enum "label-rro-type" {
        value 3;
        description
          "Label RRO Type";
      }
      enum "unnumbered-rro-type" {
        value 4;
        description
          "Unnumbered RRO Type";
      }
      enum "srlg-rro-type" {
        value 34;
        description
          "SRLG RRO Type";
      }
    }
    description
      "RSVP RRO Types";
  }

  typedef Rsi-vrf-id {
    type uint32;
    description
      "Rsi vrf id";
  }

  typedef Rsvp-mgmt-frr-state-enum {
    type enumeration {
      enum "ready-state" {
        value 0;
        description
          "Ready State";
      }
      enum "pending-state" {
        value 1;
        description
          "Pending";
      }
      enum "active-state" {
        value 2;
        description
          "Active State";
      }
    }
    description
      "RSVP FRR States";
  }

  typedef Rsvp-proc-nsr-not-ready-reason {
    type enumeration {
      enum "collab-time-out" {
        description
          "Collab connection time out";
      }
      enum "collab-conntection-idt" {
        description
          "Collab connection down or IDT not done";
      }
      enum "nsr-peer-not-connected" {
        description
          "NSR peer not connected";
      }
      enum "nsr-peer-not-in-sync" {
        description
          "NSR peer not in sync";
      }
    }
    description
      "Rsvp proc nsr not ready reason";
  }

  typedef Rsvp-sync-status {
    type enumeration {
      enum "not-ready" {
        description
          "Not Ready";
      }
      enum "ready" {
        description
          "Ready";
      }
    }
    description
      "Rsvp sync status";
  }

  typedef Rsvp-mgmt-gr-app {
    type enumeration {
      enum "ouni" {
        description
          "Application is OUNI";
      }
      enum "gmpls" {
        description
          "Application is GMPLS";
      }
    }
    description
      "RSVP Graceful Restart application type";
  }

  typedef Rsvp-proc-role {
    type enumeration {
      enum "unknown" {
        description
          "Unknown";
      }
      enum "v1-active" {
        description
          "V1 Active";
      }
      enum "v1-standby" {
        description
          "V1 Standby";
      }
      enum "v2-active" {
        description
          "V2 Active";
      }
      enum "v2-standby" {
        description
          "V2 Standby";
      }
      enum "v1-active-post-big-bang" {
        description
          "V1 Active post big-bang";
      }
      enum "v1-standby-post-big-bang" {
        description
          "V1 Standbyi post big-bang";
      }
      enum "count" {
        description
          "Count";
      }
    }
    description
      "RSVP Process Role";
  }

  typedef Rsvp-mgmt-auth-challenge-status {
    type enumeration {
      enum "rsvp-mgmt-auth-cs-not-cfg" {
        description
          "Not configured";
      }
      enum "rsvp-mgmt-auth-cs-completed" {
        description
          "Complete";
      }
      enum "rsvp-mgmt-auth-cs-in-progress" {
        description
          "In Progress";
      }
      enum "rsvp-mgmt-auth-cs-failure" {
        description
          "Failed";
      }
      enum "rsvp-mgmt-auth-cs-not-supported" {
        description
          "Not supported";
      }
    }
    description
      "RSVP Authentication Challenge Status";
  }

  typedef Rsvp-mgmt-hello-instance {
    type enumeration {
      enum "active" {
        description
          "Hello requests and ACKs are sent";
      }
      enum "passive" {
        description
          "Hello ACKs only are sent";
      }
    }
    description
      "RSVP Hello instance types";
  }

  typedef Rsvp-mgmt-hello-state {
    type enumeration {
      enum "hello-state-init" {
        description
          "No Hello messages ever received from neighbor";
      }
      enum "hello-state-up" {
        description
          "Receiving expected Hello messages from neighbor";
      }
      enum "hello-state-down" {
        description
          "Stopped receiving expected Hello messages from
           neighbor";
      }
    }
    description
      "RSVP Hello instance states";
  }

  typedef Rsvp-mgmt-reservation-type-enum {
    type enumeration {
      enum "rsvp-mgmt-ff-option" {
        value 10;
        description
          "Single Reservation";
      }
      enum "rsvp-mgmt-wf-option" {
        value 17;
        description
          "Shared Reservation, Unlimited Scope";
      }
      enum "rsvp-mgmt-se-option" {
        value 18;
        description
          "Shared Reservation, Limited Scope";
      }
    }
    description
      "RSVP Reservation Types";
  }

  typedef Rsvp-mgmt-flow-spec {
    type enumeration {
      enum "g709otn" {
        value 5;
        description
          "G709 OTN FlowSpec Type";
      }
    }
    description
      "RSVP Generic FlowSpec Types";
  }

  typedef Rsvp-mgmt-qos-service-enum {
    type enumeration {
      enum "rsvp-mgmt-qos-unknown" {
        value 0;
        description
          "QOS Unknown";
      }
      enum "rsvp-mgmt-qos-guaranteed" {
        value 3;
        description
          "QOS Guaranteed";
      }
      enum "rsvp-mgmt-qos-controlled-load" {
        value 5;
        description
          "QOS Controlled Load";
      }
      enum "rsvp-mgmt-qos-qualitative" {
        value 6;
        description
          "QOS Qualitative";
      }
    }
    description
      "QOS Types";
  }

  typedef Rsvp-mgmt-messageid {
    type uint32;
    description
      "Rsvp mgmt messageid";
  }

  typedef Rsvp-timer-state {
    type enumeration {
      enum "rsvp-timer-running-and-sleeping" {
        value 1;
        description
          "RSVP timer running and sleeping";
      }
      enum "rsvp-timer-running" {
        value 2;
        description
          "RSVP timer running";
      }
      enum "rsvp-timer-not-running" {
        value 3;
        description
          "RSVP timer not running";
      }
    }
    description
      "RSVP Timer States";
  }

  typedef Rsvp-mgmt-ero-subobj-status {
    type enumeration {
      enum "rsvp-mgmt-ero-status-not-available" {
        value 0;
        description
          "ERO is not available in topology";
      }
      enum "rsvp-mgmt-ero-status-available" {
        value 1;
        description
          "ERO is available in topology";
      }
      enum "rsvp-mgmt-ero-status-bw-not-available" {
        value 2;
        description
          "ERO doesn't have bw available in topology";
      }
    }
    description
      "RSVP ERO Status";
  }

  typedef Rsvp-mgmt-ero-subobj {
    type enumeration {
      enum "rsvp-mgmt-ero-type-ipv4" {
        value 1;
        description
          "IPv4 ERO Type";
      }
      enum "rsvp-mgmt-ero-type-un-num" {
        value 4;
        description
          "Unnumbered ERO Type";
      }
    }
    description
      "RSVP ERO Types";
  }

  typedef Rsvp-mgmt-generic-label {
    type enumeration {
      enum "rsvp-mgmt-label-type-gmpls" {
        value 2;
        description
          "Generalized Label Type";
      }
    }
    description
      "RSVP Generic Label Types";
  }

  typedef Rsvp-mgmt-mpls-label {
    type uint32;
    description
      "Rsvp mgmt mpls label";
  }

  typedef Rsvp-mgmt-tspec {
    type enumeration {
      enum "g709otn" {
        value 5;
        description
          "G709 OTN Sender Tspec Type";
      }
      enum "intsrv" {
        value 12;
        description
          "Int-Serv Sender Tspec Type";
      }
    }
    description
      "RSVP Generic Sender Tspec Types";
  }

  typedef Rsvp-mgmt-filter {
    type enumeration {
      enum "rsvp-mgmt-filter-type-ipv4" {
        value 1;
        description
          "IPv4 FilterSpec Type";
      }
      enum "rsvp-mgmt-filter-type-p2mp-lsp-ipv4" {
        value 12;
        description
          "P2MP LSP IPv4 FilterSpec Type";
      }
    }
    description
      "RSVP Filter Types";
  }

  typedef Rsvp-mgmt-session {
    type enumeration {
      enum "rsvp-mgmt-session-type-udp-ipv4" {
        value 1;
        description
          "UDP IPv4 Session Type";
      }
      enum "rsvp-mgmt-session-type-lsp-ipv4" {
        value 7;
        description
          "LSP IPv4 Session Type";
      }
      enum "rsvp-mgmt-session-type-uni-ipv4" {
        value 9;
        description
          "UNI IPv4 Session Type";
      }
      enum "rsvp-mgmt-session-type-p2mp-lsp-ipv4" {
        value 13;
        description
          "P2MP LSP IPv4 Session Type";
      }
    }
    description
      "RSVP Session Types";
  }

  typedef Rsvp-mgmt-auth-ki {
    type enumeration {
      enum "rsvp-mgmt-auth-ki-type-none" {
        description
          "None";
      }
      enum "rsvp-mgmt-auth-ki-type-global" {
        description
          "Global";
      }
      enum "rsvp-mgmt-auth-ki-type-interface" {
        description
          "Interface";
      }
      enum "rsvp-mgmt-auth-ki-type-neighbor" {
        description
          "Neighbor";
      }
    }
    description
      "RSVP Authentication KeyInfo Type";
  }

  typedef Rsvp-mgmt-auth-direction {
    type enumeration {
      enum "rsvp-mgmt-auth-direction-send" {
        description
          "Send";
      }
      enum "rsvp-mgmt-auth-direction-recv" {
        description
          "Receive";
      }
    }
    description
      "RSVP Authentication Direction Types";
  }

  typedef Rsvp-mgmt-dste-modes {
    type enumeration {
      enum "pre-standard" {
        value 1;
        description
          "pre standard";
      }
      enum "standard" {
        value 3;
        description
          "standard";
      }
    }
    description
      "RSVP DSTE modes";
  }

  grouping RSVP-MGMT-RXSB-DETAIL {
    description
      "Detailed Form of RSVP Proxy Reservation";
    container session {
      description
        "RSVP Session Information";
      uses RSVP-MGMT-SESSION-INFO;
    }
    container s2l-sub-lsp {
      description
        "RSVP S2L Sub-LSP information";
      uses RSVP-MGMT-S2L-SUB-LSP-IPV4;
    }
    container style {
      description
        "RSVP Style";
      uses RSVP-MGMT-STYLE;
    }
    container filter {
      description
        "RSVP Filter";
      uses RSVP-MGMT-FILTER-INFO;
    }
    container flow-spec {
      description
        "Flow Spec Information";
      uses RSVP-MGMT-FLOW-SPEC;
    }
    container generic-flow-spec {
      description
        "Generic Flow Spec Information";
      uses RSVP-MGMT-GEN-FLOW-SPEC;
    }
    container hop {
      description
        "Path Hop Info";
      uses RSVP-MGMT-HOP-INFO;
    }
    container rsvp-header {
      description
        "RSVP Header";
      uses RSVP-MGMT-HEADER-INFO;
    }
    leaf input-interface {
      type string;
      description
        "Path Input Interface";
    }
    leaf dynamic-state {
      type uint32;
      description
        "Dynamic State Handle";
    }
  }

  grouping RSVP-MGMT-PXSB-DETAIL {
    description
      "Detailed Form of RSVP Proxy Path";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    container hop {
      description
        "Path Hop Info";
      uses RSVP-MGMT-HOP-INFO;
    }
    container rsvp-header {
      description
        "RSVP Header";
      uses RSVP-MGMT-HEADER-INFO;
    }
    leaf input-interface {
      type string;
      description
        "Path Input Interface";
    }
    leaf dynamic-state {
      type uint32;
      description
        "Dynamic State Handle";
    }
  }

  grouping RSVP-MGMT-GLBL-BW-POOL-INFO {
    description
      "Global B/W pool information";
    leaf max-res-pool-percent {
      type uint32;
      units "percentage";
      description
        "Maxium reservable I/F percent B/W";
    }
    leaf bc0-percent {
      type uint32;
      units "percentage";
      description
        "BC0 I/F percent B/W";
    }
    leaf bc1-percent {
      type uint32;
      units "percentage";
      description
        "BC1 I/F percent B/W";
    }
    leaf is-max-res-pool-percent-configured {
      type boolean;
      description
        "Is maximum reservable default I/F percent
         configured";
    }
    leaf is-bc0-percent-configured {
      type boolean;
      description
        "Is BC0 default I/F percent configured";
    }
    leaf is-bc1-percent-configured {
      type boolean;
      description
        "Is BC1 default I/F percent configured";
    }
    leaf bandwidth-configuration-model {
      type Igpte-lib-bw-model;
      description
        "Bandwith configuration model currently in use
         (MAM/RDM)";
    }
  }

  grouping RSVP-MGMT-GLBL-NBR-COMPACT {
    description
      "Compact Info for RSVP Global Neighbor";
    container global-neighbor-flags {
      description
        "Global Neighbor Flags";
      uses RSVP-MGMT-GLBL-NBR-FLAGS;
    }
    leaf is-gr-enabled {
      type boolean;
      description
        "Is GR enabled";
    }
    leaf node-address {
      type inet:ipv4-address;
      description
        "Neighbor node address";
    }
    leaf restart-state {
      type Rsvp-mgmt-restart-state;
      description
        "Restart state";
    }
    list local-node-address {
      description
        "Local node address";
      leaf entry {
        type inet:ipv4-address;
        description
          "Local node address";
      }
    }
    list neighbor-hello-state {
      description
        "Neighbor Hello state";
      leaf entry {
        type Rsvp-mgmt-hello-state;
        description
          "Neighbor Hello state";
      }
    }
    list lost-communication-reason {
      description
        "Reason why communication was lost";
      leaf entry {
        type Rsvp-mgmt-hello-down-reason;
        description
          "Reason why communication was lost";
      }
    }
    list lost-communication-total {
      description
        "Total number of times communication got lost";
      leaf entry {
        type uint16;
        description
          "Total number of times communication got lost";
      }
    }
    list up-time {
      description
        "Time hellos have been up";
      uses RSVP-MGMT-TIMESPEC;
    }
    list lost-communication-time {
      description
        "Time when communication was lost";
      uses RSVP-MGMT-TIMESPEC;
    }
  }

  grouping RSVP-MGMT-PATH-COMPACT {
    description
      "Compact Form of RSVP Path Info";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container session-attribute {
      description
        "RSVP Session Attribute";
      uses RSVP-MGMT-SESSION-ATTRIBUTE;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    leaf input-interface {
      type string;
      description
        "Path Input Interface";
    }
  }

  grouping RSVP-MGMT-GLBL-NBR-FLAGS {
    description
      "Global Neighbor Flags";
    leaf is-application-ouni {
      type boolean;
      description
        "OUNI Application";
    }
    leaf is-application-mpls {
      type boolean;
      description
        "MPLS Application";
    }
  }

  grouping RSVP-MGMT-GLBL-NBR-DETAIL {
    description
      "Detail Info for RSVP Global Neighbor";
    container global-neighbor-flags {
      description
        "Global Neighbor Flags";
      uses RSVP-MGMT-GLBL-NBR-FLAGS;
    }
    container restart-time-left {
      description
        "How much restart time remains";
      uses RSVP-MGMT-TIMESPEC;
    }
    container restart-timer-expiry-time {
      description
        "When will restart timer expire";
      uses RSVP-MGMT-TIMESPEC;
    }
    container recovery-time-left {
      description
        "How much recovery timer remains";
      uses RSVP-MGMT-TIMESPEC;
    }
    container recovery-timer-exp-time {
      description
        "Time at which recovery timer will expire";
      uses RSVP-MGMT-TIMESPEC;
    }
    leaf is-gr-enabled {
      type boolean;
      description
        "Is GR enabled";
    }
    leaf node-address {
      type inet:ipv4-address;
      description
        "Neighbor node address";
    }
    leaf restart-state {
      type Rsvp-mgmt-restart-state;
      description
        "Current restart state";
    }
    leaf restart-time {
      type uint32;
      units "millisecond";
      description
        "GR Restart Time (milliseconds)";
    }
    leaf is-restart-timer-running {
      type boolean;
      description
        "Is GR restart timer running";
    }
    leaf recovery-time {
      type uint32;
      units "millisecond";
      description
        "GR Recovery Time (milliseconds)";
    }
    leaf is-recovery-timer-running {
      type boolean;
      description
        "Is RSVP recovery timer running";
    }
    leaf hello-interval {
      type uint32;
      units "millisecond";
      description
        "Hello Interval (milliseconds)";
    }
    leaf missed-hellos {
      type uint8;
      description
        "Hello missed count";
    }
    leaf pending-states {
      type uint32;
      description
        "Number of pending states for this neighbor";
    }
    list local-node-address {
      description
        "Local node address";
      leaf entry {
        type inet:ipv4-address;
        description
          "Local node address";
      }
    }
    list interface-neighbor {
      description
        "Interface Neighbor List";
      leaf entry {
        type inet:ipv4-address;
        description
          "Interface Neighbor List";
      }
    }
    list neighbor-hello-state {
      description
        "Neighbor's hello state";
      leaf entry {
        type Rsvp-mgmt-hello-state;
        description
          "Neighbor's hello state";
      }
    }
    list lost-communication-reason {
      description
        "Reason why communication was lost";
      leaf entry {
        type Rsvp-mgmt-hello-down-reason;
        description
          "Reason why communication was lost";
      }
    }
    list lost-communication-total {
      description
        "Total number of times communication got lost";
      leaf entry {
        type uint16;
        description
          "Total number of times communication got lost";
      }
    }
    list up-time {
      description
        "Hello up time";
      uses RSVP-MGMT-TIMESPEC;
    }
    list lost-communication-time {
      description
        "Time when communication was lost";
      uses RSVP-MGMT-TIMESPEC;
    }
  }

  grouping RSVP-MGMT-HELLO-INSTANCE-DETAIL {
    description
      "Detail Info for RSVP Hello Instance";
    container up-time {
      description
        "Hello up time";
      uses RSVP-MGMT-TIMESPEC;
    }
    container communication-lost-time {
      description
        "Time when communication was lost";
      uses RSVP-MGMT-TIMESPEC;
    }
    leaf source-address-xr {
      type inet:ipv4-address;
      description
        "Source address";
    }
    leaf destination-address-xr {
      type inet:ipv4-address;
      description
        "Destination address";
    }
    leaf hello-instance-owner {
      type Rsvp-mgmt-hello-instance-owner;
      description
        "Hello instance owner";
    }
    leaf neighbor-hello-state {
      type Rsvp-mgmt-hello-state;
      description
        "Neighbor Hello state";
    }
    leaf instance-type {
      type Rsvp-mgmt-hello-instance;
      description
        "Hello instance type";
    }
    leaf hello-interface {
      type xr:Interface-name;
      description
        "Interface to use";
    }
    leaf hello-interval {
      type uint32;
      description
        "Hello Interval";
    }
    leaf missed-acks-allowed {
      type uint32;
      description
        "Number of missed Hello allowed";
    }
    leaf source-instance {
      type uint32;
      description
        "Source Instance";
    }
    leaf destination-instance {
      type uint32;
      description
        "Destination Instance";
    }
    leaf communication-lost-reason {
      type Rsvp-mgmt-hello-down-reason;
      description
        "Reason why communication was lost";
    }
    leaf total-communication-lost {
      type uint16;
      description
        "Total number of times communication got lost";
    }
    leaf communication-lost-hello-missed {
      type uint16;
      description
        "Lost Comm. Hello missed count";
    }
    leaf communication-lost-wrong-source-inst {
      type uint16;
      description
        "Count of lost comm. due to wrong Source Inst";
    }
    leaf communication-lost-wrong-destination-inst {
      type uint16;
      description
        "Count of lost comm. due to wrong Destination
         Inst";
    }
    leaf communication-lost-interface-down {
      type uint16;
      description
        "Count of lost comm. due to interface down";
    }
    leaf communication-lost-neighbor-disabled-hello {
      type uint16;
      description
        "Count of lost comm. due to nbor disabling Hellos";
    }
    leaf hello-messages-sent {
      type uint64;
      description
        "Number of hello messages sent";
    }
    leaf hello-messages-received {
      type uint64;
      description
        "Number of hello messages received";
    }
    leaf hello-request-suppressed {
      type uint64;
      description
        "Count of Hello Requests suppessed";
    }
  }

  grouping RSVP-SESSION-RSB-DETAIL {
    description
      "RSVP Detail Session Reservation Info";
    container generic-out-label {
      description
        "Generic Label for outbound traffic";
      uses RSVP-MGMT-GENERIC-LABEL;
    }
    container flow-spec {
      description
        "Flow spec object";
      uses RSVP-MGMT-FLOW-SPEC;
    }
    container generic-flow-spec {
      description
        "Generic Flow Spec object";
      uses RSVP-MGMT-GEN-FLOW-SPEC;
    }
    leaf is-valid {
      type boolean;
      description
        "Entry validity";
    }
    leaf destination-address {
      type inet:ipv4-address;
      description
        "Destination address";
    }
    leaf out-interface {
      type xr:Interface-name;
      description
        "Interface on which outbound message was sent";
    }
    leaf out-label {
      type Rsvp-mgmt-mpls-label;
      description
        "Label for outbound traffic";
    }
    leaf backup-interface {
      type xr:Interface-name;
      description
        "Backup tunnel interface";
    }
    leaf backup-label {
      type Rsvp-mgmt-mpls-label;
      description
        "Backup label";
    }
    leaf is-rro-valid {
      type boolean;
      description
        "RRO validity";
    }
    leaf is-flow-spec-valid {
      type boolean;
      description
        "FlowSpec validity";
    }
    list rro {
      description
        "Record route object";
      uses RSVP-MGMT-RRO-SUBOBJ;
    }
  }

  grouping RSVP-MGMT-REV-LSP-UNSUPPORTED-SUBOBJ {
    description
      "RSVP MGMT REV LSP UNSUPPORTED SUBOBJ";
    list rsvp-mgmt-rev-lsp-unsupported-subobj {
      description
        "rsvp mgmt rev lsp unsupported subobj";
      leaf entry {
        type uint8;
        description
          "rsvp mgmt rev lsp unsupported subobj";
      }
    }
  }

  grouping RSVP-MGMT-REVERSE-LSP {
    description
      "RSVP REVERSE_LSP Object";
    container generic-traffic-spec {
      description
        "Generic Traffic Spec object";
      uses RSVP-MGMT-GEN-TRAFFIC-SPEC;
    }
    list ero {
      description
        "Explicit Route Sub Objects";
      uses RSVP-MGMT-ERO-SUBOBJ;
    }
    list unsup-sub-object {
      description
        "Unsupported REVERSE_LSP Sub Objects";
      uses RSVP-MGMT-REV-LSP-UNSUPPORTED-SUBOBJ;
    }
  }

  grouping RSVP-MGMT-PROTECTION-LINK-FLAGS {
    description
      "RSVP PROTECTION Object Link Flags";
    leaf enhanced {
      type boolean;
      description
        "Indicates Enhanced Protection Scheme";
    }
    leaf ded1-plus1 {
      type boolean;
      description
        "Dedicated 1+1 Protection";
    }
    leaf ded1-to1 {
      type boolean;
      description
        "Dedicated 1:1 Protection";
    }
    leaf shared {
      type boolean;
      description
        "Shared Link Layer Protection";
    }
    leaf unprotected {
      type boolean;
      description
        "LSP should not use any Link Layer Protection";
    }
    leaf extra-traffic {
      type boolean;
      description
        "LSP should use Links that are protecting other
         (primary) traffic";
    }
    leaf reserved-bit1 {
      type boolean;
      description
        "Reserved Bit 1";
    }
    leaf reserved-bit2 {
      type boolean;
      description
        "Reserved Bit 2";
    }
  }

  grouping RSVP-MGMT-PROTECTION-LSP-FLAGS {
    description
      "RSVP PROTECTION Object LSP Flags";
    leaf rerouting {
      type boolean;
      description
        "Full Rerouting";
    }
    leaf rerouting-no-et {
      type boolean;
      description
        "Rerouting Without Extra-Traffic";
    }
    leaf one-to-n-protection-et {
      type boolean;
      description
        "1:N Protection with Extra-Traffic";
    }
    leaf one-plus-one-uni {
      type boolean;
      description
        "1+1 Unidirectional Protection";
    }
    leaf one-plus-one-bi {
      type boolean;
      description
        "1+1 Bidirectional Protection";
    }
  }

  grouping RSVP-MGMT-PROTECTION {
    description
      "RSVP PROTECTION Object Info";
    container lsp-flags {
      description
        "PROTECTION Object LSP Flags";
      uses RSVP-MGMT-PROTECTION-LSP-FLAGS;
    }
    container link-flags {
      description
        "PROTECTION Object Link Flags";
      uses RSVP-MGMT-PROTECTION-LINK-FLAGS;
    }
    leaf s {
      type boolean;
      description
        "Secondary Bit";
    }
    leaf p {
      type boolean;
      description
        "Protecting Bit";
    }
    leaf n {
      type boolean;
      description
        "Notification Bit";
    }
    leaf o {
      type boolean;
      description
        "Operational Bit";
    }
  }

  grouping RSVP-MGMT-ASSOCIATION-IPV6-EXT {
    description
      "RSVP EXTENDED ASSOCIATION IPv6 Object Info";
    leaf type {
      type uint16;
      description
        "Association Type (RFC 4872)";
    }
    leaf id {
      type uint16;
      description
        "Association ID";
    }
    leaf source {
      type inet:ipv6-address;
      description
        "Association IPV6 Source Address";
    }
    leaf global-source {
      type uint32;
      description
        "Global Association Source";
    }
    list extended-id {
      description
        "Extended Association ID";
      leaf entry {
        type uint32;
        description
          "Extended Association ID";
      }
    }
  }

  grouping RSVP-MGMT-ASSOCIATION-IPV4-EXT {
    description
      "RSVP EXTENDED ASSOCIATION IPv4 Object Info";
    leaf type {
      type uint16;
      description
        "Association Type (RFC 4872)";
    }
    leaf id {
      type uint16;
      description
        "Association ID";
    }
    leaf source {
      type inet:ipv4-address;
      description
        "Association IPV4 Source Address";
    }
    leaf global-source {
      type uint32;
      description
        "Global Association Source";
    }
    list extended-id {
      description
        "Extended Association ID";
      leaf entry {
        type uint32;
        description
          "Extended Association ID";
      }
    }
  }

  grouping RSVP-MGMT-ASSOCIATION-IPV6 {
    description
      "RSVP ASSOCIATION IPv6 Object Info";
    leaf type {
      type uint16;
      description
        "Association Type (RFC 4872)";
    }
    leaf id {
      type uint16;
      description
        "Association ID";
    }
    leaf source {
      type inet:ipv6-address;
      description
        "Association IPV6 Source Address";
    }
  }

  grouping RSVP-MGMT-ASSOCIATION-IPV4 {
    description
      "RSVP ASSOCIATION IPv4 Object Info";
    leaf type {
      type uint16;
      description
        "Association Type (RFC 4872)";
    }
    leaf id {
      type uint16;
      description
        "Association ID";
    }
    leaf source {
      type inet:ipv4-address;
      description
        "Association IPV4 Source Address";
    }
  }

  grouping RSVP-MGMT-ASSOCIATION {
    description
      "Union of the different ASSOCIATION types";
    container ipv4 {
      when "../association-type = 'ipv4'" {
        description
          "../AssociationType = 'IPv4'";
      }
      description
        "IPV4 ASSOCIATION Object";
      uses RSVP-MGMT-ASSOCIATION-IPV4;
    }
    container ipv6 {
      when "../association-type = 'ipv6'" {
        description
          "../AssociationType = 'IPv6'";
      }
      description
        "IPV6 ASSOCIATION Object";
      uses RSVP-MGMT-ASSOCIATION-IPV6;
    }
    container extended-ipv4 {
      when "../association-type = 'extended-ipv4'" {
        description
          "../AssociationType = 'ExtendedIPv4'";
      }
      description
        "EXTENDED IPV4 ASSOCIATION Object";
      uses RSVP-MGMT-ASSOCIATION-IPV4-EXT;
    }
    container extended-ipv6 {
      when "../association-type = 'extended-ipv6'" {
        description
          "../AssociationType = 'ExtendedIPv6'";
      }
      description
        "EXTENDED IPV6 ASSOCIATION Object";
      uses RSVP-MGMT-ASSOCIATION-IPV6-EXT;
    }
    leaf association-type {
      type Rsvp-mgmt-association;
      description
        "AssociationType";
    }
  }

  grouping RSVP-MGMT-RRO-SRLG-SUBOBJ {
    description
      "RSVP RRO SRLG subobject";
    list srl-gs {
      description
        "The RRO Subobject SRLGs";
      leaf entry {
        type uint32;
        description
          "The RRO Subobject SRLGs";
      }
    }
  }

  grouping RSVP-MGMT-RRO-UNNUMBERED-SUBOBJ-FLAGS {
    description
      "RSVP RRO UNNUMBERED Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping RSVP-MGMT-RRO-UNNUMBERED-SUBOBJ {
    description
      "RSVP RRO Unnumbered subobject";
    container flags {
      description
        "The RRO Subobject Unnumbered Flags";
      uses RSVP-MGMT-RRO-UNNUMBERED-SUBOBJ-FLAGS;
    }
    leaf interface-address {
      type inet:ipv4-address;
      description
        "The RRO Interface Address";
    }
    leaf interface-id {
      type uint32;
      description
        "The RRO Interface ID";
    }
  }

  grouping RSVP-MGMT-RRO-LABEL-SUBOBJ-FLAGS {
    description
      "RSVP RRO Label Subobject Flags";
    leaf is-global-label {
      type boolean;
      description
        "Label is Global across all interfaces";
    }
  }

  grouping RSVP-MGMT-RRO-LABEL-SUBOBJ {
    description
      "RSVP RRO Label subobject";
    container flags {
      description
        "The RRO Subobject Label Flags";
      uses RSVP-MGMT-RRO-LABEL-SUBOBJ-FLAGS;
    }
    leaf label {
      type uint32;
      description
        "The RRO Subobject Label Value";
    }
    leaf is-label-variable-length {
      type boolean;
      description
        "Is the RRO Subobject Label Variable Length";
    }
    list variable-length-label {
      description
        "The RRO Subobject Variable Length Label";
      leaf entry {
        type uint32;
        description
          "The RRO Subobject Variable Length Label";
      }
    }
  }

  grouping RSVP-MGMT-RRO-IPV4-SUBOBJ-FLAGS {
    description
      "RSVP RRO IPV4 Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping RSVP-MGMT-RRO-IPV4-SUBOBJ {
    description
      "RSVP RRO IPV4 subobject";
    container flags {
      description
        "The RRO IPV4 Subobject Flags";
      uses RSVP-MGMT-RRO-IPV4-SUBOBJ-FLAGS;
    }
    leaf rro-address {
      type inet:ipv4-address;
      description
        "The RRO IPV4 Address";
    }
  }

  grouping RSVP-MGMT-RRO-SUBOBJ {
    description
      "Union of the different RSVP RRO types";
    container ipv4rro-sub-object {
      when "../rro-type = 'ipv4rro-type'" {
        description
          "../RROType = 'IPv4RROType'";
      }
      description
        "IPV4 RRO Sub Object";
      uses RSVP-MGMT-RRO-IPV4-SUBOBJ;
    }
    container label-rro-sub-object {
      when "../rro-type = 'label-rro-type'" {
        description
          "../RROType = 'LabelRROType'";
      }
      description
        "Label RRO Sub Object";
      uses RSVP-MGMT-RRO-LABEL-SUBOBJ;
    }
    container unnumbered-rro-sub-object {
      when "../rro-type = 'unnumbered-rro-type'" {
        description
          "../RROType = 'UnnumberedRROType'";
      }
      description
        "Unnumbered RRO Sub Object";
      uses RSVP-MGMT-RRO-UNNUMBERED-SUBOBJ;
    }
    container srlg-rro-sub-object {
      when "../rro-type = 'srlg-rro-type'" {
        description
          "../RROType = 'SRLG_RROType'";
      }
      description
        "SRLG RRO Sub Object";
      uses RSVP-MGMT-RRO-SRLG-SUBOBJ;
    }
    leaf rro-type {
      type Rsvp-mgmt-rro-subobj;
      description
        "RROType";
    }
  }

  grouping RSVP-SESSION-PSB-DETAIL {
    description
      "RSVP Detail Session Path Info";
    container generic-in-label {
      description
        "Generic Label for inbound traffic";
      uses RSVP-MGMT-GENERIC-LABEL;
    }
    container traffic-spec {
      description
        "Traffic Spec object";
      uses RSVP-MGMT-TRAFFIC-SPEC;
    }
    container generic-traffic-spec {
      description
        "Generic Traffic Spec object";
      uses RSVP-MGMT-GEN-TRAFFIC-SPEC;
    }
    container association {
      description
        "Association object";
      uses RSVP-MGMT-ASSOCIATION;
    }
    container protection {
      description
        "Protection object";
      uses RSVP-MGMT-PROTECTION;
    }
    container reverse-lsp {
      description
        "Reverse LSP object";
      uses RSVP-MGMT-REVERSE-LSP;
    }
    leaf is-valid {
      type boolean;
      description
        "Entry validity";
    }
    leaf destination-address {
      type inet:ipv4-address;
      description
        "Destination address";
    }
    leaf lsp-id {
      type uint32;
      description
        "LSP ID";
    }
    leaf p2mp-sub-group-origin {
      type inet:ipv4-address;
      description
        "Point to Multipoint SubGroup Origin";
    }
    leaf sub-group-id {
      type uint16;
      description
        "Point to Multipoint Subgroup ID";
    }
    leaf in-interface {
      type xr:Interface-name;
      description
        "Interface on which inbound message was received";
    }
    leaf in-label {
      type Rsvp-mgmt-mpls-label;
      description
        "Label for inbound traffic";
    }
    leaf lsp-wrap-label {
      type Rsvp-mgmt-mpls-label;
      description
        "LSP Wrap Label";
    }
    leaf is-bad-address {
      type boolean;
      description
        "Address validity";
    }
    leaf incoming-interface-address {
      type inet:ipv4-address;
      description
        "IP address of Path's incoming interface";
    }
    leaf is-ero-valid {
      type boolean;
      description
        "ERO validity";
    }
    leaf is-rro-valid {
      type boolean;
      description
        "RRO validity";
    }
    leaf is-traffic-spec-valid {
      type boolean;
      description
        "Traffic Spec validity";
    }
    leaf tunnel-name {
      type string;
      description
        "Tunnel name";
    }
    list ero {
      description
        "Explicit Route Sub Objects";
      uses RSVP-MGMT-ERO-SUBOBJ;
    }
    list rro {
      description
        "Record Route Sub Objects";
      uses RSVP-MGMT-RRO-SUBOBJ;
    }
  }

  grouping RSVP-SESSION-PSB-RSB-DETAIL {
    description
      "List of Path and Reservation Info";
    list psb-info {
      description
        "Path Info";
      uses RSVP-SESSION-PSB-DETAIL;
    }
    list rsb-info {
      description
        "Reservation Info";
      uses RSVP-SESSION-RSB-DETAIL;
    }
  }

  grouping RSVP-MGMT-SESSION-DETAIL {
    description
      "RSVP Detail Session Info";
    container compact {
      description
        "Compact session data";
      uses RSVP-MGMT-SESSION-COMPACT;
    }
    container s2l-sub-lsp {
      description
        "RSVP S2L Sub-LSP information";
      uses RSVP-MGMT-S2L-SUB-LSP-IPV4;
    }
    list psb-rsb-info {
      description
        "Path and Reservation Info";
      uses RSVP-SESSION-PSB-RSB-DETAIL;
    }
  }

  grouping RSVP-MGMT-KEY {
    description
      "Key to uniquely identify some RSVP records";
    leaf p2mp-id {
      type uint32;
      description
        "Point-to-multipoint ID";
    }
    leaf destination-address {
      type inet:ipv4-address;
      description
        "Destination address";
    }
    leaf destination-port-or-tunnel-id {
      type uint32;
      description
        "Destination Port or Tunnel ID. For the LSP and
         OUNI session types this represents the Tunnel ID
         whereas for the UDP session type this represents
         the Destination Port";
    }
    leaf protocol {
      type uint32;
      description
        "Protocol. UDP session type this represents the
         Protocol (UDP not supported at present)";
    }
    leaf extended-tunnel-id {
      type inet:ipv4-address;
      description
        "Protocol or Extended Tunnel ID. For the LSP and
         OUNI sesion types this represents the Extended
         Tunnel ID";
    }
    leaf session-type {
      type Rsvp-mgmt-session;
      description
        "Session Type (e.g. LSP, OUNI or UDP)";
    }
    leaf source-address {
      type inet:ipv4-address;
      description
        "Source Address";
    }
    leaf source-port-or-lsp-id {
      type uint32;
      description
        "Source Port or LSP_ID. For the LSP and OUNI
         session types this represents the LSP_ID whereas
         for the UDP session type this represents the
         SourcePort";
    }
    leaf p2mp-sub-group-origin {
      type inet:ipv4-address;
      description
        "Point to Multipoint SubGroup Origin";
    }
    leaf sub-group-id {
      type uint16;
      description
        "Point to Multipoint Subgroup ID";
    }
    leaf vrfid {
      type Rsi-vrf-id;
      description
        "Signalling VRF ID";
    }
  }

  grouping RSVP-MGMT-REQUEST-FLAGS {
    description
      "Request state flags";
    leaf is-local-receiver {
      type boolean;
      description
        "Local Receiver";
    }
    leaf is-refreshing {
      type boolean;
      description
        "Is neighbor refreshing";
    }
    leaf is-send-confirm {
      type boolean;
      description
        "Send Confirm message";
    }
    leaf is-ack-outstanding {
      type boolean;
      description
        "Is ACK message outstanding";
    }
    leaf is-message-id-allocated {
      type boolean;
      description
        "Is MessageID allocated";
    }
    leaf is-nack-received {
      type boolean;
      description
        "A NACK message was received";
    }
    leaf is-retransmit {
      type boolean;
      description
        "Retransmit the message";
    }
    leaf is-paced {
      type boolean;
      description
        "Message is paced";
    }
    leaf is-label-request-in-path {
      type boolean;
      description
        "The Path message contains Label Request";
    }
    leaf is-rro-in-path {
      type boolean;
      description
        "The Path message contains RRO";
    }
    leaf is-record-label-in-path {
      type boolean;
      description
        "Path has Session-Attr object with Record Labels
         set";
    }
    leaf is-merge-point {
      type boolean;
      description
        "Is node a Merge Point";
    }
  }

  grouping RSVP-MGMT-REQUEST-DETAIL {
    description
      "Detailed Form of RSVP Request Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Information";
      uses RSVP-MGMT-GEN-FLOW-SPEC;
    }
    container filter {
      description
        "RSVP Filter";
      uses RSVP-MGMT-FILTER-INFO;
    }
    container style {
      description
        "RSVP Style";
      uses RSVP-MGMT-STYLE;
    }
    container req-flags {
      description
        "Request flags";
      uses RSVP-MGMT-REQUEST-FLAGS;
    }
    container hop {
      description
        "Hop Infomation";
      uses RSVP-MGMT-HOP-INFO;
    }
    container header {
      description
        "RSVP Header Information";
      uses RSVP-MGMT-HEADER-INFO;
    }
    container policy-sources {
      description
        "RSVP Policy Sources";
      uses RSVP-MGMT-POLICY-SOURCES;
    }
    container policy-flags {
      description
        "RSVP Policy Flags";
      uses RSVP-MGMT-POLICY-FLAGS;
    }
    container policy-query-flags {
      description
        "RSVP Query Flags";
      uses RSVP-MGMT-POLICY-QUERY-FLAGS;
    }
    leaf output-interface {
      type string;
      description
        "output Interface";
    }
    list psb-key {
      description
        "List of RSB keys";
      uses RSVP-MGMT-KEY;
    }
    list rsb-key {
      description
        "List of RSB keys";
      uses RSVP-MGMT-KEY;
    }
  }

  grouping RSVP-MGMT-REQUEST-COMPACT {
    description
      "Compact Form of RSVP Request Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Information";
      uses RSVP-MGMT-GEN-FLOW-SPEC;
    }
    container filter {
      description
        "RSVP Filter";
      uses RSVP-MGMT-FILTER-INFO;
    }
    container style {
      description
        "RSVP Style";
      uses RSVP-MGMT-STYLE;
    }
    leaf output-interface {
      type string;
      description
        "Output Interface";
    }
  }

  grouping RSVP-MGMT-FRR-STATES-DETAIL {
    description
      "RSVP states for one FRR LSP";
    container session {
      description
        "RSVP Session Information";
      uses RSVP-MGMT-SESSION-INFO;
    }
    container s2l-sub-lsp {
      description
        "RSVP S2L Sub-LSP information";
      uses RSVP-MGMT-S2L-SUB-LSP-IPV4;
    }
    leaf path-status {
      type Rsvp-mgmt-frr-state-enum;
      description
        "RSVP FRR Path States";
    }
    leaf reservation-status {
      type Rsvp-mgmt-frr-state-enum;
      description
        "RSVP FRR Reservation States";
    }
  }

  grouping RSVP-GLOBAL-INFO {
    description
      "RSVP global information";
    container issu-status {
      description
        "Issu status";
      uses RSVP-NSR-ISSU-STATUS-INFO;
    }
    container nsr-status {
      description
        "NSR status";
      uses RSVP-NSR-ISSU-STATUS-INFO;
    }
    container database-counters {
      description
        "All database counters";
      uses RSVP-MGMT-ALL-DB-COUNTERS;
    }
    leaf interfaces {
      type uint32;
      description
        "Total interfaces";
    }
    leaf ls-ps {
      type uint32;
      description
        "Total LSPs";
    }
  }

  grouping RSVP-IDT-STATUS {
    description
      "IDT status information";
    leaf sync-status {
      type Rsvp-sync-status;
      description
        "Sync status";
    }
    leaf not-ready-reason {
      type Rsvp-proc-nsr-not-ready-reason;
      description
        "Not ready reason";
    }
    leaf idt-start-time {
      type uint32;
      units "second";
      description
        "IDT start timestamp in seconds";
    }
    leaf idt-end-time {
      type uint32;
      units "second";
      description
        "IDT end timestamp in seconds";
    }
    leaf declare-time {
      type uint32;
      units "second";
      description
        "Declare ready timestamp in seconds";
    }
    leaf withdraw-time {
      type uint32;
      units "second";
      description
        "Withdraw ready timestamp in seconds";
    }
  }

  grouping RSVP-NSR-ISSU-STATUS-INFO {
    description
      "NSR/ISSU status information";
    container idt-status {
      description
        "IDT status";
      uses RSVP-IDT-STATUS;
    }
    container previous-idt-status {
      description
        "Previous IDT status";
      uses RSVP-IDT-STATUS;
    }
    leaf role {
      type Rsvp-proc-role;
      description
        "Process role";
    }
  }

  grouping RSVP-MGMT-IF-NBR-DETAIL {
    description
      "Detail Info for RSVP Interface Neighbor";
    leaf interface-neighbor-address {
      type inet:ipv4-address;
      description
        "Interface Neighbor address";
    }
    leaf neighbor-interface-name {
      type xr:Interface-name;
      description
        "Neighbor's Interface handle";
    }
    leaf is-rr-enabled {
      type boolean;
      description
        "Is Neighbor's RR enable";
    }
    leaf neighbor-epoch {
      type uint32;
      description
        "Neighbor's epoch value";
    }
    leaf out-of-order-messages {
      type uint32;
      description
        "Number of out of order msgs";
    }
    leaf retransmitted-messages {
      type uint32;
      description
        "Number of retransmitted msgs";
    }
  }

  grouping RSVP-MGMT-NBR-DETAIL {
    description
      "Detail Info for RSVP Neighbor";
    leaf node-address {
      type inet:ipv4-address;
      description
        "Neighbor node address";
    }
    list interface-neighbor-list-detail {
      description
        "Detail list of I/F Neighbors";
      uses RSVP-MGMT-IF-NBR-DETAIL;
    }
  }

  grouping RSVP-MGMT-HELLO-IF-INSTANCE-DETAIL {
    description
      "Detail Info for IF-based RSVP Hello Instance";
    container last-message-sent-time {
      description
        "Last Ack/msg sent time";
      uses RSVP-MGMT-TIMESPEC;
    }
    leaf source-address-xr {
      type inet:ipv4-address;
      description
        "Source address";
    }
    leaf destination-address-xr {
      type inet:ipv4-address;
      description
        "Destination address";
    }
    leaf hello-global-neighbor-id {
      type inet:ipv4-address;
      description
        "Global Neighbor ID";
    }
    leaf instance-type {
      type Rsvp-mgmt-hello-instance;
      description
        "Hello instance type";
    }
    leaf hello-interface {
      type xr:Interface-name;
      description
        "Interface to use";
    }
    leaf source-instance {
      type uint32;
      description
        "Source Instance";
    }
    leaf destination-instance {
      type uint32;
      description
        "Destination Instance";
    }
    leaf hello-messages-sent {
      type uint64;
      description
        "Number of hello messages sent";
    }
    leaf hello-messages-received {
      type uint64;
      description
        "Number of hello messages received";
    }
  }

  grouping RSVP-MGMT-HELLO-IF-INSTANCE-COMPACT {
    description
      "Compact Info for IF-based RSVP Hello Instance";
    leaf source-address-xr {
      type inet:ipv4-address;
      description
        "Source address";
    }
    leaf destination-address-xr {
      type inet:ipv4-address;
      description
        "Destination address";
    }
    leaf instance-type {
      type Rsvp-mgmt-hello-instance;
      description
        "Hello instance type";
    }
    leaf hello-interface {
      type xr:Interface-name;
      description
        "Interface to use";
    }
  }

  grouping RSVP-MGMT-LOCAL-NODE-ID-IPV4 {
    description
      "Local Node-id";
    leaf local-node-ip-address {
      type inet:ipv4-address;
      description
        "Local node address";
    }
    leaf application-type {
      type Rsvp-mgmt-gr-app;
      description
        "GR local node-id app type";
    }
  }

  grouping RSVP-MGMT-GRACEFUL-RESTART {
    description
      "RSVP Graceful Restart Info";
    container recovery-time-left {
      description
        "How much recovery timer remains";
      uses RSVP-MGMT-TIMESPEC;
    }
    container recovery-timer-exp-time {
      description
        "Time at which recovery timer will expire";
      uses RSVP-MGMT-TIMESPEC;
    }
    leaf is-gr-enabled {
      type boolean;
      description
        "Whether GR is enabled";
    }
    leaf global-neighbors {
      type uint32;
      description
        "Global neighbor count";
    }
    leaf restart-time {
      type uint32;
      units "millisecond";
      description
        "Restart time (milliseconds)";
    }
    leaf recovery-time {
      type uint32;
      units "millisecond";
      description
        "Recovery time (milliseconds)";
    }
    leaf is-recovery-timer-running {
      type boolean;
      description
        "Whether recovery timer is running";
    }
    leaf hello-interval {
      type uint32;
      description
        "Interval at which hello messages are sent";
    }
    leaf missed-hellos {
      type uint8;
      description
        "Max number of hellos missed before hellos
         declared down";
    }
    leaf pending-states {
      type uint32;
      description
        "Total number of pending states";
    }
    list local-node-address {
      description
        "Local node address";
      uses RSVP-MGMT-LOCAL-NODE-ID-IPV4;
    }
  }

  grouping RSVP-MGMT-INTERFACE-COMPACT {
    description
      "Compact Form of RSVP interface Info";
    container bandwidth-information {
      description
        "Interface bandwidth information";
      uses RSVP-MGMT-DSTE-MODE-INTERFACE-BW;
    }
    leaf interface-name-xr {
      type string;
      description
        "Interface Name";
    }
  }

  grouping RSVP-MGMT-ALL-DB-COUNTERS {
    description
      "All database counters";
    leaf sessions {
      type uint32;
      description
        "Number of sessions";
    }
    leaf incoming-paths {
      type uint32;
      description
        "Number of locally created and incoming path
         states";
    }
    leaf outgoing-paths {
      type uint32;
      description
        "Number of outgoing path states";
    }
    leaf incoming-reservations {
      type uint32;
      description
        "Number of locally created and incoming
         reservation states";
    }
    leaf outgoing-reservations {
      type uint32;
      description
        "Number of outgoing reservation states";
    }
    leaf interfaces {
      type uint32;
      description
        "Number of Interfaces";
    }
  }

  grouping RSVP-SYNC-COUNT-INFO {
    description
      "RSVP sync sent and received counters information";
    leaf last-cleared-timestamp {
      type uint32;
      units "second";
      description
        "The timestamp, in seconds, when these statistics
         are cleared              since 00:00:00 UTC,
         January 1, 1970";
    }
    leaf rsvp-process-role {
      type Rsvp-proc-role;
      description
        "Process role";
    }
    leaf last-idt-states {
      type uint32;
      description
        "Last IDT number of states";
    }
    leaf total-states {
      type uint32;
      description
        "Total number of states";
    }
    leaf total-deletions {
      type uint32;
      description
        "Total number of deletions";
    }
    leaf total-nacks {
      type uint64;
      description
        "Total number of NACKs";
    }
    leaf total-id-ts {
      type uint32;
      description
        "Total number of IDTs";
    }
  }

  grouping RSVP-MGMT-EVENT-COUNT-INFO {
    description
      "Count of events";
    leaf expired-paths {
      type uint32;
      description
        "Counter for Expired Path states";
    }
    leaf expired-reservations {
      type uint32;
      description
        "Counter for Expired Reservation states";
    }
    leaf nac-ks {
      type uint32;
      description
        "Counter for NACKs received";
    }
  }

  grouping RSVP-MGMT-COUNTERS-OOR {
    description
      "Counters for all messages dropped in OOR
       condition";
    leaf dropped-path-messages {
      type uint32;
      description
        "Count of Path messages dropped due to an out of
         resource condition";
    }
  }

  grouping RSVP-MGMT-COUNT-PREFIX-INTERFACE-INFO {
    description
      "Prefix filtering interface counters";
    container forwarded {
      description
        "Count of messages which got forwarded";
      uses RSVP-MGMT-COUNT-PREFIX-MSG;
    }
    container locally-destined {
      description
        "Count of locally destined messages";
      uses RSVP-MGMT-COUNT-PREFIX-MSG;
    }
    container dropped {
      description
        "Count of messages dropped";
      uses RSVP-MGMT-COUNT-PREFIX-MSG;
    }
    container default-action-dropped {
      description
        "Count of messages which got dropped due to
         default ACL action";
      uses RSVP-MGMT-COUNT-PREFIX-MSG;
    }
    container default-action-processed {
      description
        "Count of messages which were processed due to
         default ACL action";
      uses RSVP-MGMT-COUNT-PREFIX-MSG;
    }
    container total {
      description
        "Count of total messages";
      uses RSVP-MGMT-COUNT-PREFIX-MSG;
    }
  }

  grouping RSVP-MGMT-COUNT-PREFIX-MSG {
    description
      "Message types for prefix filtering";
    leaf path {
      type uint32;
      description
        "Count of Path messages";
    }
    leaf path-tear {
      type uint32;
      description
        "Count of PathTear messages";
    }
    leaf reservation-confirm {
      type uint32;
      description
        "Count of ReservationConfirm messages";
    }
    leaf total {
      type uint32;
      description
        "Total count of messages";
    }
  }

  grouping RSVP-MGMT-COUNT-PREFIX-ACL-INFO {
    description
      "Prefix filtering ACL counters";
    container forwarded {
      description
        "Count of messages which got forwarded";
      uses RSVP-MGMT-COUNT-PREFIX-MSG;
    }
    container locally-destined {
      description
        "Count of locally destined messages";
      uses RSVP-MGMT-COUNT-PREFIX-MSG;
    }
    container dropped {
      description
        "Count of messages dropped";
      uses RSVP-MGMT-COUNT-PREFIX-MSG;
    }
    container total {
      description
        "Count of total messages";
      uses RSVP-MGMT-COUNT-PREFIX-MSG;
    }
  }

  grouping RSVP-MGMT-COUNTS {
    description
      "Counters for all known RSVP message types";
    leaf path {
      type uint32;
      description
        "Count of Path messages";
    }
    leaf reservation {
      type uint32;
      description
        "Count of Reservation messages";
    }
    leaf path-error {
      type uint32;
      description
        "Count of PathError messages";
    }
    leaf reservation-error {
      type uint32;
      description
        "Count of ReservationError messages";
    }
    leaf path-tear {
      type uint32;
      description
        "Count of PathTear messages";
    }
    leaf reservation-tear {
      type uint32;
      description
        "Count of ReservationTear messages";
    }
    leaf reservation-confirm {
      type uint32;
      description
        "Count of ReservationConfirm messages";
    }
    leaf bundle {
      type uint32;
      description
        "Count of Bundle messages";
    }
    leaf ack {
      type uint32;
      description
        "Count of ACK messages";
    }
    leaf srefresh {
      type uint32;
      description
        "Count of Srefresh messages";
    }
    leaf hello {
      type uint32;
      description
        "Count of Hello messages";
    }
    leaf challenge {
      type uint32;
      description
        "Count of Integrity Challenge messages";
    }
    leaf response {
      type uint32;
      description
        "Count of Integrity Response messages";
    }
  }

  grouping RSVP-MGMT-COUNT-MESSAGE {
    description
      "Counters for all messages";
    container received-messages {
      description
        "Count of messages received";
      uses RSVP-MGMT-COUNTS;
    }
    container transmitted-messages {
      description
        "Count of messages transmitted";
      uses RSVP-MGMT-COUNTS;
    }
    container bundle-received-messages {
      description
        "Count of Bundle messages received";
      uses RSVP-MGMT-COUNTS;
    }
    container bundle-transmitted-messages {
      description
        "Count of Bundle messages transmitted";
      uses RSVP-MGMT-COUNTS;
    }
    leaf retransmitted-messages {
      type uint32;
      description
        "Count of messages retransmitted";
    }
    leaf out-of-order-messages {
      type uint32;
      description
        "Count of Out of Order messages";
    }
    leaf rate-limited-messages {
      type uint32;
      description
        "Count of Rate Limited messages";
    }
  }

  grouping RSVP-MGMT-RESERVATION-COMPACT {
    description
      "Compact Form of RSVP Reservation Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Info";
      uses RSVP-MGMT-GEN-FLOW-SPEC;
    }
    container style {
      description
        "RSVP Style";
      uses RSVP-MGMT-STYLE;
    }
    container filter {
      description
        "RSVP Filter";
      uses RSVP-MGMT-FILTER-INFO;
    }
    leaf input-interface {
      type string;
      description
        "Reservation Input Interface";
    }
  }

  grouping RSVP-MGMT-AUTH-RECV-TYPE-COUNTERS {
    description
      "RSVP Authentication Receive Type Counters";
    leaf authentication-received-valid-messages {
      type uint32;
      description
        "Valid messages";
    }
    leaf authentication-received-challenges-sent {
      type uint32;
      description
        "Challenges sent";
    }
    leaf authentication-received-challenge-response {
      type uint32;
      description
        "Challenge responses received";
    }
    leaf authentication-received-challenges-resent {
      type uint32;
      description
        "Challenges resent";
    }
    leaf authentication-received-challenge-timeouts {
      type uint32;
      description
        "Challenge timeouts";
    }
    leaf authentication-received-during-challenge {
      type uint32;
      description
        "Authentication received during challenge";
    }
    leaf authentication-received-incomplete {
      type uint32;
      description
        "Authentication received incomplete";
    }
    leaf authentication-received-no-integrity {
      type uint32;
      description
        "Authentication received with no integrity";
    }
    leaf authentication-received-bad-digest {
      type uint32;
      description
        "Authentication received with bad digest";
    }
    leaf authentication-received-wrong-digest-type {
      type uint32;
      description
        "Authentication received with wrong digest type";
    }
    leaf authentication-received-sequence-number-duplicate {
      type uint32;
      description
        "Authentication received with duplicate sequence
         number";
    }
    leaf authentication-received-sequence-number-outof-range {
      type uint32;
      description
        "Authentication received with sequence number out
         of range";
    }
    leaf authentication-received-wrong-challenges-response {
      type uint32;
      description
        "Incorect challenge responses received";
    }
    leaf authentication-received-challenges-response-duplicate {
      type uint32;
      description
        "Duplicate challenge responses received";
    }
    leaf authentication-received-response-late {
      type uint32;
      description
        "Challenge responses received late";
    }
    leaf authentication-received-bad-message-format {
      type uint32;
      description
        "Authentication received with bad mesage format";
    }
  }

  grouping RSVP-MGMT-AUTH-DIRECTION-RECV {
    description
      "RSVP Authentication Recieve Type Information";
    container counters {
      description
        "Counters";
      uses RSVP-MGMT-AUTH-RECV-TYPE-COUNTERS;
    }
    leaf sequence {
      type uint64;
      description
        "Sequence number";
    }
    leaf sequence-window-size {
      type uint32;
      description
        "Sequence window size";
    }
    leaf sequence-window-count {
      type uint32;
      description
        "Sequence window count";
    }
    list sequence-window {
      max-elements "64";
      description
        "Sequence window";
      leaf entry {
        type uint64;
        description
          "Sequence window";
      }
    }
  }

  grouping RSVP-MGMT-AUTH-SEND-TYPE-COUNTERS {
    description
      "RSVP Authentication Send Type Counters";
    leaf authentication-sent {
      type uint32;
      description
        "Messages sent";
    }
    leaf authentication-failures {
      type uint32;
      description
        "Failures";
    }
    leaf authentication-send-challenges-received {
      type uint32;
      description
        "Challenges received";
    }
    leaf authentication-challenge-responses-sent {
      type uint32;
      description
        "Challenge responses sent";
    }
  }

  grouping RSVP-MGMT-AUTH-DIRECTION-SEND {
    description
      "RSVP Authentication Send Type Information";
    container counters {
      description
        "Counters";
      uses RSVP-MGMT-AUTH-SEND-TYPE-COUNTERS;
    }
    leaf sequence {
      type uint64;
      description
        "Sequence number";
    }
  }

  grouping RSVP-MGMT-AUTH-DIRECTION {
    description
      "Union of the different RSVP Authentication
       Direction types";
    container send-info {
      when "../auth-direction = 'rsvp-mgmt-auth-direction-send'" {
        description
          "../AuthDirection = 'RSVPMgmtAuthDirectionSend'";
      }
      description
        "send info";
      uses RSVP-MGMT-AUTH-DIRECTION-SEND;
    }
    container receive-info {
      when "../auth-direction = 'rsvp-mgmt-auth-direction-recv'" {
        description
          "../AuthDirection = 'RSVPMgmtAuthDirectionRecv'";
      }
      description
        "receive info";
      uses RSVP-MGMT-AUTH-DIRECTION-RECV;
    }
    leaf auth-direction {
      type Rsvp-mgmt-auth-direction;
      description
        "AuthDirection";
    }
  }

  grouping RSVP-MGMT-AUTHENTICATION-DETAIL {
    description
      "Authentication Detail Information";
    container auth-compact {
      description
        "Basic authentication data";
      uses RSVP-MGMT-AUTHENTICATION-COMPACT;
    }
    container direction-info {
      description
        "direction info";
      uses RSVP-MGMT-AUTH-DIRECTION;
    }
    leaf key-status {
      type uint32;
      description
        "Key status";
    }
    leaf key-digest-info {
      type uint32;
      description
        "Direction";
    }
    leaf lifetime {
      type uint32;
      units "second";
      description
        "Lifetime (seconds)";
    }
    leaf lifetime-left {
      type uint32;
      units "second";
      description
        "Remaining lifetime (seconds)";
    }
    leaf challenge-status {
      type Rsvp-mgmt-auth-challenge-status;
      description
        "Challenge status";
    }
  }

  grouping RSVP-MGMT-HELLO-INSTANCE-COMPACT {
    description
      "Compact Info for RSVP Hello Instance";
    leaf source-address-xr {
      type inet:ipv4-address;
      description
        "Source address";
    }
    leaf destination-address-xr {
      type inet:ipv4-address;
      description
        "Destination address";
    }
    leaf neighbor-hello-state {
      type Rsvp-mgmt-hello-state;
      description
        "Neighbor Hello state";
    }
    leaf instance-type {
      type Rsvp-mgmt-hello-instance;
      description
        "Hello instance type";
    }
    leaf hello-interface {
      type xr:Interface-name;
      description
        "Interface to use";
    }
    leaf lost-communication-total {
      type uint16;
      description
        "Total number of times communication got lost";
    }
  }

  grouping RSVP-MGMT-RSB-FLAGS {
    description
      "Reservation State Block Flags";
    leaf is-local-receiver {
      type boolean;
      description
        "Local Receiver";
    }
    leaf is-message-id-valid {
      type boolean;
      description
        "MessageID Valid";
    }
    leaf is-local-repair {
      type boolean;
      description
        "Rerouted";
    }
    leaf is-merge-point {
      type boolean;
      description
        "Is node a Merge Point";
    }
    leaf is-lockout {
      type boolean;
      description
        "Locked Out";
    }
  }

  grouping RSVP-MGMT-STYLE {
    description
      "RSVP Reservation Style";
    leaf reservation-type {
      type Rsvp-mgmt-reservation-type-enum;
      description
        "The Reservation Type: WF, SE or FF";
    }
  }

  grouping RSVP-MGMT-FLOW-SPEC-G709-OTN {
    description
      "RSVP G709 OTN FlowSpec Info";
    leaf flow-signal-type {
      type uint8;
      description
        "G709 OTN Flow Signal Type (Refer G709 v3)";
    }
    leaf flow-nvc {
      type uint16;
      description
        "G709 OTN Flow NVC";
    }
    leaf flow-multiplier {
      type uint16;
      description
        "G709 OTN Flow Multiplier";
    }
    leaf flow-bit-rate {
      type uint64;
      description
        "G709 OTN Flow Bit Rate";
    }
  }

  grouping RSVP-MGMT-GEN-FLOW-SPEC {
    description
      "Union of different RSVP Generic FlowSpec types";
    container g709otn-flow-spec {
      when "../flow-spec-type = 'g709otn'" {
        description
          "../FlowSpecType = 'G709OTN'";
      }
      description
        "G709 OTN FlowSpec";
      uses RSVP-MGMT-FLOW-SPEC-G709-OTN;
    }
    leaf flow-spec-type {
      type Rsvp-mgmt-flow-spec;
      description
        "FlowSpecType";
    }
  }

  grouping RSVP-MGMT-FLOW-SPEC {
    description
      "RSVP Flow Spec";
    leaf flow-average-rate {
      type uint64;
      units "byte/s";
      description
        "The Flow Average Rate in bytes per second";
    }
    leaf flow-max-burst {
      type uint64;
      description
        "The Flow Maximum Burst";
    }
    leaf flow-peak-rate {
      type uint64;
      units "byte/s";
      description
        "The Flow Peak Rate in bytes per second";
    }
    leaf flow-min-unit {
      type uint32;
      description
        "The Flow Minimum Unit";
    }
    leaf flow-max-unit {
      type uint32;
      description
        "The Flow Maximum Unit";
    }
    leaf flow-requested-rate {
      type uint64;
      units "byte/s";
      description
        "The Flow Requested Rate in bytes per second";
    }
    leaf flow-slack {
      type uint32;
      description
        "The Flow Slack";
    }
    leaf flow-qos {
      type Rsvp-mgmt-qos-service-enum;
      description
        "The Flow Quality of Service";
    }
  }

  grouping RSVP-MGMT-RESERVATION-DETAIL {
    description
      "Detailed Form of RSVP Reservation Info";
    container flow-spec {
      description
        "Flow Spec Information";
      uses RSVP-MGMT-FLOW-SPEC;
    }
    container generic-flow-spec {
      description
        "Generic Flow Spec Information";
      uses RSVP-MGMT-GEN-FLOW-SPEC;
    }
    container session {
      description
        "RSVP Session Information";
      uses RSVP-MGMT-SESSION-INFO;
    }
    container s2l-sub-lsp {
      description
        "RSVP S2L Sub-LSP information";
      uses RSVP-MGMT-S2L-SUB-LSP-IPV4;
    }
    container style {
      description
        "RSVP Style";
      uses RSVP-MGMT-STYLE;
    }
    container filter {
      description
        "RSVP Filter";
      uses RSVP-MGMT-FILTER-INFO;
    }
    container rsb-flags {
      description
        "Reservation State Block Flags";
      uses RSVP-MGMT-RSB-FLAGS;
    }
    container hop {
      description
        "Hop Infomation";
      uses RSVP-MGMT-HOP-INFO;
    }
    container policy-sources {
      description
        "RSVP Policy Sources";
      uses RSVP-MGMT-POLICY-SOURCES;
    }
    container header {
      description
        "RSVP Header Information";
      uses RSVP-MGMT-HEADER-INFO;
    }
    container policy-flags {
      description
        "RSVP Policy Flags";
      uses RSVP-MGMT-POLICY-FLAGS;
    }
    container expiry-time {
      description
        "Expiry Time";
      uses RSVP-MGMT-TIMESPEC;
    }
    container policy-query-flags {
      description
        "RSVP Query Flags";
      uses RSVP-MGMT-POLICY-QUERY-FLAGS;
    }
    container label-info {
      description
        "Label Information";
      uses RSVP-MGMT-LABEL-INFO;
    }
    leaf input-adjusted-interface {
      type string;
      description
        "Input Adjusted Interface";
    }
    leaf input-physical-interface {
      type string;
      description
        "Input Physical Interface";
    }
  }

  grouping RSVP-MGMT-FRR-STATE-STATUS-COUNTERS {
    description
      "FRR state counters";
    leaf total {
      type uint32;
      description
        "Total number of instances of this state";
    }
    leaf active-instances {
      type uint32;
      description
        "Number of active instances of this state";
    }
    leaf ready-instances {
      type uint32;
      description
        "Number of ready instances of this state";
    }
    leaf active-wait-instances {
      type uint32;
      description
        "Number of instances of this state awaiting Path
         messages to be sent out or Resv messages to be
         received";
    }
  }

  grouping RSVP-MGMT-FRR-STATES-COMPACT {
    description
      "Count of RSVP FRR States";
    container path-states {
      description
        "Path state counters";
      uses RSVP-MGMT-FRR-STATE-STATUS-COUNTERS;
    }
    container reservation-states {
      description
        "Rerservation state counters";
      uses RSVP-MGMT-FRR-STATE-STATUS-COUNTERS;
    }
  }

  grouping RSVP-MGMT-MESSAGEID {
    description
      "RSVP Message ID";
    leaf message-id {
      type Rsvp-mgmt-messageid;
      description
        "Message ID";
    }
  }

  grouping RSVP-MGMT-NBOR {
    description
      "Neighbor";
    container expiry-time {
      description
        "Expiry time";
      uses RSVP-MGMT-TIMESPEC;
    }
    leaf is-neighbor-refresh-reduction-capable {
      type boolean;
      description
        "Is neighbor capable of Refresh Reduction";
    }
    leaf neighbor-address {
      type inet:ipv4-address;
      description
        "IP address of the neighbor";
    }
    leaf message-ids {
      type uint32;
      description
        "Number of MessageIDs";
    }
    leaf outgoing-states {
      type int32;
      description
        "Number of outgoing states to the neighbour";
    }
    list neighbor-message-id {
      max-elements "6";
      description
        "List of Neighbor MessageIDs";
      uses RSVP-MGMT-MESSAGEID;
    }
  }

  grouping RSVP-MGMT-INTERFACE-FLAGS {
    description
      "Interface related flags";
    leaf is-mpls-enabled {
      type boolean;
      description
        "MPLS enabled on interface";
    }
    leaf is-refresh-reduction-enabled {
      type boolean;
      description
        "Refresh Reduction enabled";
    }
    leaf is-pacing-enabled {
      type boolean;
      description
        "Message pacing enabled";
    }
    leaf is-refresh-enabled {
      type boolean;
      description
        "Refresh enabled";
    }
    leaf is-s-refresh-enabled {
      type boolean;
      description
        "Summary Refresh enabled";
    }
    leaf is-interface-down {
      type boolean;
      description
        "Interface is DOWN";
    }
    leaf is-interface-created {
      type boolean;
      description
        "Interface is created";
    }
    leaf is-rel-s-refresh-enabled {
      type boolean;
      description
        "Use reliable xmt for SRefresh";
    }
    leaf is-backup-tunnel {
      type boolean;
      description
        "This is backup tunnel";
    }
    leaf is-rsvp-configured {
      type boolean;
      description
        "RSVP explicitly configured";
    }
    leaf is-non-default-vrf {
      type boolean;
      description
        "Interface is defined in non-Default VRF";
    }
    leaf is-message-bundling-enabled {
      type boolean;
      description
        "Use bundling for outgoing RSVP messages.";
    }
  }

  grouping RSVP-MGMT-INTERFACE-DETAIL {
    description
      "Detail Form of RSVP interface Info";
    container bandwidth-information {
      description
        "Interface bandwidth information";
      uses RSVP-MGMT-DSTE-MODE-INTERFACE-BW;
    }
    container flags {
      description
        "Interface flags";
      uses RSVP-MGMT-INTERFACE-FLAGS;
    }
    leaf interface-name-xr {
      type string;
      description
        "Interface Name";
    }
    leaf signalling-ip-tos {
      type uint8;
      description
        "IP TOS (precedence/DSCP) to use in signalling
         messages";
    }
    leaf integrity-send-password {
      type string {
        length "0..40";
      }
      description
        "Integrity send password";
    }
    leaf integrity-receive-password {
      type string {
        length "0..40";
      }
      description
        "Integrity receive password";
    }
    leaf integrity-receive-password-optional {
      type uint8;
      description
        "Integrity recv password optional";
    }
    leaf refresh-timer-state {
      type Rsvp-timer-state;
      description
        "Refresh timer state";
    }
    leaf summary-refresh-timer-state {
      type Rsvp-timer-state;
      description
        "Summary refresh timer state";
    }
    leaf refresh-interval {
      type int32;
      units "millisecond";
      description
        "Refresh interval in msecs";
    }
    leaf out-of-band-refresh-interval {
      type uint32;
      units "millisecond";
      description
        "Out-of-band Refresh interval in msecs";
    }
    leaf summary-refresh-max-size {
      type uint32;
      units "byte";
      description
        "Max size in bytes of a single SRefresh";
    }
    leaf bundle-message-max-size {
      type uint32;
      units "byte";
      description
        "Max size in bytes of a single Bundle message";
    }
    leaf expiry-timer-state {
      type Rsvp-timer-state;
      description
        "Expiry timer state";
    }
    leaf expiry-states {
      type int32;
      description
        "Number of states for expiry check";
    }
    leaf expiry-interval {
      type int32;
      units "millisecond";
      description
        "Expiry interval in msecs";
    }
    leaf expiry-drops-tolerated {
      type int32;
      description
        "Number of missed messages tolerated";
    }
    leaf out-of-band-expiry-drops-tolerated {
      type uint32;
      description
        "Number of out-of-band missed messages tolerated";
    }
    leaf ack-hold-time {
      type uint32;
      description
        "ACK hold time in msec";
    }
    leaf ack-max-size {
      type uint32;
      description
        "Max size for ACK message";
    }
    leaf retransmit-time {
      type uint32;
      description
        "Retransmit time in msec";
    }
    leaf pacing-interval {
      type uint32;
      units "millisecond";
      description
        "Pacing interval in msecs";
    }
    leaf pacing-message-rate {
      type uint32;
      description
        "No. of messages per interval";
    }
    leaf pacing-timer-state {
      type Rsvp-timer-state;
      description
        "State of pacing timer";
    }
    leaf pacing-messages {
      type int32;
      description
        "Number of messages deferred for pacing";
    }
    list neighbor-array {
      max-elements "6";
      description
        "Neighbor array";
      uses RSVP-MGMT-NBOR;
    }
  }

  grouping RSVP-MGMT-ERO-UNNUM-SUBOBJ {
    description
      "RSVP ERO UNNUM subobject";
    leaf is-strict-route {
      type boolean;
      description
        "ERO Entry Is Strict";
    }
    leaf ero-interface-id {
      type uint32;
      description
        "The Interface ID in ERO";
    }
    leaf ero-router-id {
      type inet:ipv4-address;
      description
        "The Router ID in ERO";
    }
    leaf status {
      type Rsvp-mgmt-ero-subobj-status;
      description
        "Status of ERO";
    }
  }

  grouping RSVP-MGMT-ERO-IPV4-SUBOBJ {
    description
      "RSVP ERO IPV4 subobject";
    leaf is-strict-route {
      type boolean;
      description
        "ERO Entry Is Strict";
    }
    leaf ero-address {
      type inet:ipv4-address;
      description
        "The ERO IPV4 Address";
    }
    leaf prefix-length {
      type uint8;
      description
        "ERO Prefix Length";
    }
  }

  grouping RSVP-MGMT-ERO-SUBOBJ {
    description
      "Union of the different RSVP ERO types";
    container ipv4ero-sub-object {
      when "../ero-type = 'rsvp-mgmt-ero-type-ipv4'" {
        description
          "../EROType = 'RSVP_MGMT_ERO_TYPE_IPv4'";
      }
      description
        "IPV4 ERO Sub Object";
      uses RSVP-MGMT-ERO-IPV4-SUBOBJ;
    }
    container unnumbered-ero-sub-object {
      when "../ero-type = 'rsvp-mgmt-ero-type-un-num'" {
        description
          "../EROType = 'RSVP_MGMT_ERO_TYPE_UNNUM'";
      }
      description
        "Unnumbered ERO Sub Object";
      uses RSVP-MGMT-ERO-UNNUM-SUBOBJ;
    }
    leaf ero-type {
      type Rsvp-mgmt-ero-subobj;
      description
        "EROType";
    }
  }

  grouping RSVP-MGMT-CT-INFO {
    description
      "Class-Type Information";
    leaf is-class-type-info-valid {
      type boolean;
      description
        "Is the Class-Type information valid";
    }
    leaf class-type {
      type uint8;
      description
        "DS-TE Class-Type";
    }
  }

  grouping RSVP-MGMT-GENERALIZED-LABEL {
    description
      "RSVP Generalized Label";
    list value {
      description
        "Generalized Label Value";
      leaf entry {
        type uint32;
        description
          "Generalized Label Value";
      }
    }
  }

  grouping RSVP-MGMT-GENERIC-LABEL {
    description
      "Union of different RSVP Generic Label types";
    container generalized-label {
      when "../generic-label-type = 'rsvp-mgmt-label-type-gmpls'" {
        description
          "../GenericLabelType =
           'RSVP_MGMT_LABEL_TYPE_GMPLS'";
      }
      description
        "Generalized Label";
      uses RSVP-MGMT-GENERALIZED-LABEL;
    }
    leaf generic-label-type {
      type Rsvp-mgmt-generic-label;
      description
        "GenericLabelType";
    }
  }

  grouping RSVP-MGMT-LABEL-INFO {
    description
      "Label Information";
    container generic-local-downstream-label {
      description
        "Generic Local Downstream Label";
      uses RSVP-MGMT-GENERIC-LABEL;
    }
    container generic-outgoing-downstream-label {
      description
        "Generic Outgoing Downstream Label";
      uses RSVP-MGMT-GENERIC-LABEL;
    }
    container generic-merge-point-label {
      description
        "Generic MergePoint Label";
      uses RSVP-MGMT-GENERIC-LABEL;
    }
    container generic-outgoing-upstream-label {
      description
        "Generic Outgoing Upstream Label";
      uses RSVP-MGMT-GENERIC-LABEL;
    }
    container generic-local-upstream-label {
      description
        "Generic Local Upstream Label";
      uses RSVP-MGMT-GENERIC-LABEL;
    }
    container generic-recovery-label {
      description
        "Generic Recovery Label";
      uses RSVP-MGMT-GENERIC-LABEL;
    }
    leaf is-valid {
      type boolean;
      description
        "Is the label information valid";
    }
    leaf local-downstream-label {
      type Rsvp-mgmt-mpls-label;
      description
        "Local Downstream Label";
    }
    leaf outgoing-downstream-label {
      type Rsvp-mgmt-mpls-label;
      description
        "Outgoing Downstream Label";
    }
    leaf merge-point-label {
      type Rsvp-mgmt-mpls-label;
      description
        "MergePoint Label";
    }
    leaf outgoing-upstream-label {
      type Rsvp-mgmt-mpls-label;
      description
        "Outgoing Upstream Label";
    }
    leaf local-upstream-label {
      type Rsvp-mgmt-mpls-label;
      description
        "Local Upstream Label";
    }
    leaf recovery-label {
      type Rsvp-mgmt-mpls-label;
      description
        "Recovery Label";
    }
    leaf lsp-wrap-label {
      type Rsvp-mgmt-mpls-label;
      description
        "LSP Wrap Label";
    }
  }

  grouping RSVP-PATH-FORWARDING-CONTEXT {
    description
      "RSVP Path Forwarding Context";
    container policy-flags {
      description
        "Policy Flags";
      uses RSVP-MGMT-POLICY-FLAGS;
    }
    container policy-query-flags {
      description
        "Policy Query Flags";
      uses RSVP-MGMT-POLICY-QUERY-FLAGS;
    }
    leaf output-interface {
      type string;
      description
        "Output interface";
    }
  }

  grouping RSVP-MGMT-POLICY-QUERY-FLAGS {
    description
      "RSVP Policy Query Flags";
    leaf is-needed {
      type boolean;
      description
        "Needed";
    }
    leaf is-report-required {
      type boolean;
      description
        "Report Required";
    }
    leaf is-resync {
      type boolean;
      description
        "Resynchronization";
    }
    leaf is-bypass {
      type boolean;
      description
        "Bypass";
    }
  }

  grouping RSVP-MGMT-POLICY-FLAGS {
    description
      "RSVP Policy Flags";
    leaf is-accepted {
      type boolean;
      description
        "Accepted";
    }
    leaf is-installed {
      type boolean;
      description
        "Installed";
    }
    leaf is-forwarding {
      type boolean;
      description
        "Forwarding";
    }
  }

  grouping RSVP-MGMT-TIMESPEC {
    description
      "RSVP Time Spec";
    leaf seconds {
      type int32;
      units "second";
      description
        "Time Value in Seconds";
    }
    leaf nanoseconds {
      type int32;
      units "nanosecond";
      description
        "Time Value in Nano-seconds";
    }
  }

  grouping RSVP-MGMT-HEADER-INFO {
    description
      "RSVP/IP Header Info";
    leaf rsvp-version {
      type uint8;
      description
        "RSVP Version";
    }
    leaf rsvp-header-flags {
      type uint8;
      description
        "RSVP Header Flags (defined in RFC2205 Section 3
         .1.1)";
    }
    leaf rsvp-ttl {
      type uint8;
      description
        "RSVP TTL";
    }
    leaf rsvp-message-type {
      type uint8;
      description
        "RSVP Message Type";
    }
    leaf ip-tos {
      type uint8;
      description
        "IP Type of Service";
    }
    leaf ip-ttl {
      type uint8;
      description
        "IP TTL";
    }
    leaf ip-source-address {
      type inet:ipv4-address;
      description
        "IP Source Address";
    }
  }

  grouping RSVP-MGMT-POLICY-SOURCES {
    description
      "RSVP Policy Sources";
    leaf is-te-link {
      type boolean;
      description
        "Policy Source is TE Link";
    }
    leaf is-local {
      type boolean;
      description
        "Policy Source is Local";
    }
    leaf is-cops {
      type boolean;
      description
        "Policy Source is COPS";
    }
    leaf is-default {
      type boolean;
      description
        "Policy Source is Default";
    }
    leaf is-cable {
      type boolean;
      description
        "Policy Source is Cable";
    }
  }

  grouping RSVP-MGMT-HOP-INFO {
    description
      "Hop Info";
    leaf neighbor-address {
      type inet:ipv4-address;
      description
        "IP address of the neighbor";
    }
    leaf neighbor-logical-interface-handle {
      type uint32;
      description
        "Neighbor Logical Interface Handle";
    }
  }

  grouping RSVP-MGMT-PATH-FLAGS {
    description
      "RSVP Path Flags";
    leaf is-non-rsvp-hop-upstream {
      type boolean;
      description
        "Non-RSVP Hop Upstream";
    }
    leaf is-local-sender {
      type boolean;
      description
        "Local Sender";
    }
    leaf is-message-id-valid {
      type boolean;
      description
        "MessageID Valid";
    }
    leaf is-local-repair {
      type boolean;
      description
        "Rerouted";
    }
    leaf is-bidirectional {
      type boolean;
      description
        "Bidirectional";
    }
    leaf is-lockout {
      type boolean;
      description
        "Locked Out";
    }
  }

  grouping RSVP-MGMT-TSPEC-G709-OTN {
    description
      "RSVP G709 OTN Sender Tspec Info";
    leaf traffic-signal-type {
      type uint8;
      description
        "G709 OTN Traffic Signal Type (Refer G709 v3)";
    }
    leaf traffic-nvc {
      type uint16;
      description
        "G709 OTN Traffic NVC";
    }
    leaf traffic-multiplier {
      type uint16;
      description
        "G709 OTN Traffic Multiplier";
    }
    leaf traffic-bit-rate {
      type uint64;
      description
        "G709 OTN Traffic Bit Rate";
    }
  }

  grouping RSVP-MGMT-GEN-TRAFFIC-SPEC {
    description
      "Union of different RSVP Generic Sender Tspec
       types";
    container g709otn-tspec {
      when "../tspec-type = 'g709otn'" {
        description
          "../TspecType = 'G709OTN'";
      }
      description
        "G709 OTN Sender Tspec";
      uses RSVP-MGMT-TSPEC-G709-OTN;
    }
    container intsrv-tspec {
      when "../tspec-type = 'intsrv'" {
        description
          "../TspecType = 'INTSRV'";
      }
      description
        "Integrated Services Sender Tspec";
      uses RSVP-MGMT-TRAFFIC-SPEC;
    }
    leaf tspec-type {
      type Rsvp-mgmt-tspec;
      description
        "TspecType";
    }
  }

  grouping RSVP-MGMT-TRAFFIC-SPEC {
    description
      "RSVP Traffic Spec Info";
    leaf traffic-average-rate {
      type uint64;
      units "byte/s";
      description
        "Traffic Average Rate in bytes per second";
    }
    leaf traffic-max-burst {
      type uint64;
      description
        "Traffic Maximum Burst";
    }
    leaf traffic-peak-rate {
      type uint64;
      units "byte/s";
      description
        "Traffic Peak Rate in bytes per second";
    }
    leaf traffic-min-unit {
      type uint32;
      description
        "Traffic Minimum Unit";
    }
    leaf traffic-max-unit {
      type uint32;
      description
        "Traffic Maximum Unit";
    }
  }

  grouping RSVP-MGMT-SESSION-ATTRIBUTE-FLAGS {
    description
      "RSVP Session Attribute Flags";
    leaf is-local-protect {
      type boolean;
      description
        "Local Protection";
    }
    leaf is-node-protect {
      type boolean;
      description
        "Node Protection";
    }
    leaf is-bandwidth-protect {
      type boolean;
      description
        "Bandwidth Protection";
    }
    leaf is-record-labels {
      type boolean;
      description
        "Records Labels";
    }
    leaf is-shared-explicit-requested {
      type boolean;
      description
        "Shared Explicit Requested";
    }
  }

  grouping RSVP-MGMT-SESSION-ATTRIBUTE {
    description
      "RSVP Session Attributes";
    container sess-attribute-flags {
      description
        "Session Attributes";
      uses RSVP-MGMT-SESSION-ATTRIBUTE-FLAGS;
    }
    leaf setup-priority {
      type uint8;
      description
        "Setup Priority";
    }
    leaf reservation-priority {
      type uint8;
      description
        "Reservation Priority";
    }
  }

  grouping RSVP-MGMT-FILTER-P2MP-IPV4 {
    description
      "RSVP P2MP IPv4 FilterSpec";
    leaf source-address {
      type inet:ipv4-address;
      description
        "Source Address";
    }
    leaf source-port {
      type uint16;
      description
        "Source Port";
    }
    leaf p2mp-sub-group-origin {
      type inet:ipv4-address;
      description
        "Point to Multipoint SubGroup Origin";
    }
    leaf sub-group-id {
      type uint16;
      description
        "Point to Multipoint Subgroup ID";
    }
  }

  grouping RSVP-MGMT-FILTER-IPV4 {
    description
      "RSVP Filter";
    leaf source-address {
      type inet:ipv4-address;
      description
        "Source Address";
    }
    leaf source-port {
      type uint16;
      description
        "Source Port";
    }
  }

  grouping RSVP-FILTER-UNION {
    description
      "Union of the different RSVP filterspec types";
    container udp-ipv4-session {
      when "../filter-type = 'rsvp-mgmt-filter-type-ipv4'" {
        description
          "../FilterType = 'RSVPMgmtFilterTypeIPv4'";
      }
      description
        "UDP IPV4 FilterSpec";
      uses RSVP-MGMT-FILTER-IPV4;
    }
    container p2mp-ipv4-session {
      when "../filter-type = 'rsvp-mgmt-filter-type-p2mp-lsp-ipv4'" {
        description
          "../FilterType =
           'RSVPMgmtFilterTypeP2MP_LSP_IPv4'";
      }
      description
        "IPv4 P2MP LSP FilterSpec";
      uses RSVP-MGMT-FILTER-P2MP-IPV4;
    }
    leaf filter-type {
      type Rsvp-mgmt-filter;
      description
        "FilterType";
    }
  }

  grouping RSVP-MGMT-FILTER-INFO {
    description
      "RSVP FilterSpec Info";
    container rsvp-filter {
      description
        "RSVP Filter";
      uses RSVP-FILTER-UNION;
    }
  }

  grouping RSVP-MGMT-S2L-SUB-LSP-IPV4 {
    description
      "RSVP S2L Sub-LSP";
    leaf s2l-destination-address {
      type inet:ipv4-address;
      description
        "S2L Sub-LSP Destination Address";
    }
  }

  grouping RSVP-MGMT-PATH-DETAIL {
    description
      "Detailed Form of RSVP Path Info";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container session-attribute {
      description
        "RSVP Session Attribute";
      uses RSVP-MGMT-SESSION-ATTRIBUTE;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    container path-flags {
      description
        "Path Flags";
      uses RSVP-MGMT-PATH-FLAGS;
    }
    container hop {
      description
        "Path Hop Info";
      uses RSVP-MGMT-HOP-INFO;
    }
    container policy-source-info {
      description
        "Policy Sources Info";
      uses RSVP-MGMT-POLICY-SOURCES;
    }
    container header {
      description
        "RSVP Header Info";
      uses RSVP-MGMT-HEADER-INFO;
    }
    container expiry-time {
      description
        "Expiry Time";
      uses RSVP-MGMT-TIMESPEC;
    }
    container policy-flags {
      description
        "Policy Flags";
      uses RSVP-MGMT-POLICY-FLAGS;
    }
    container policy-query-flags {
      description
        "Policy Query Flags";
      uses RSVP-MGMT-POLICY-QUERY-FLAGS;
    }
    container label-info {
      description
        "Label Information";
      uses RSVP-MGMT-LABEL-INFO;
    }
    container class-type {
      description
        "DS-TE Class-Type";
      uses RSVP-MGMT-CT-INFO;
    }
    leaf input-interface {
      type string;
      description
        "Path Input Interface";
    }
    leaf backup-tunnel-name {
      type string;
      description
        "Path Backup Tunnel";
    }
    leaf is-in-ero-valid {
      type boolean;
      description
        "Incoming ERO validity";
    }
    leaf is-out-ero-valid {
      type boolean;
      description
        "Outgoing ERO validity";
    }
    list pfc {
      description
        "Path Forwarding Contexts";
      uses RSVP-PATH-FORWARDING-CONTEXT;
    }
    list in-ero {
      description
        "Incoming Explicit Route Sub Objects";
      uses RSVP-MGMT-ERO-SUBOBJ;
    }
    list out-ero {
      description
        "Outgoing Explicit Route Sub Objects";
      uses RSVP-MGMT-ERO-SUBOBJ;
    }
  }

  grouping RSVP-MGMT-SESSION-P2MP-LSP-TUNNEL-IPV4 {
    description
      "RSVP P2MP-LSP-Tunnel-IPv4 Session";
    leaf p2mp-id {
      type uint32;
      description
        "The Point to Multipoint ID";
    }
    leaf tunnel-id {
      type uint16;
      description
        "The Session Tunnel ID";
    }
    leaf extended-tunnel-id {
      type inet:ipv4-address;
      description
        "The Session Extended Tunnel ID";
    }
  }

  grouping RSVP-MGMT-SESSION-UNI-IPV4 {
    description
      "RSVP UNI IPv4 Session";
    leaf destination-address {
      type inet:ipv4-address;
      description
        "Destination address";
    }
    leaf tunnel-id {
      type uint16;
      description
        "The Session Tunnel ID";
    }
    leaf extended-address {
      type inet:ipv4-address;
      description
        "The Session Extended Address";
    }
  }

  grouping RSVP-MGMT-SESSION-LSP-TUNNEL-IPV4 {
    description
      "RSVP LSP-Tunnel-IPv4 Session";
    leaf destination-address {
      type inet:ipv4-address;
      description
        "Destination address";
    }
    leaf tunnel-id {
      type uint16;
      description
        "The Session Tunnel ID";
    }
    leaf extended-tunnel-id {
      type inet:ipv4-address;
      description
        "The Session Extended Tunnel ID";
    }
  }

  grouping RSVP-MGMT-SESSION-UDP-IPV4 {
    description
      "RSVP UDP IPv4 Session";
    leaf destination-address {
      type inet:ipv4-address;
      description
        "Destination address";
    }
    leaf protocol {
      type uint8;
      description
        "Protocol type (originally defined in RFC 790,
         further values in subsequent RFCs)";
    }
    leaf destination-port {
      type uint16;
      description
        "The Session Destination Port";
    }
  }

  grouping RSVP-SESSION-UNION {
    description
      "Union of the different RSVP session types";
    container ipv4 {
      when "../session-type = 'rsvp-mgmt-session-type-udp-ipv4'" {
        description
          "../SessionType = 'RSVPMgmtSessionTypeUDP_IPv4'";
      }
      description
        "UDP IPv4 session";
      uses RSVP-MGMT-SESSION-UDP-IPV4;
    }
    container ipv4-lsp-session {
      when "../session-type = 'rsvp-mgmt-session-type-lsp-ipv4'" {
        description
          "../SessionType = 'RSVPMgmtSessionTypeLSP_IPv4'";
      }
      description
        "IPv4 LSP session";
      uses RSVP-MGMT-SESSION-LSP-TUNNEL-IPV4;
    }
    container ipv4-uni-session {
      when "../session-type = 'rsvp-mgmt-session-type-uni-ipv4'" {
        description
          "../SessionType = 'RSVPMgmtSessionTypeUNI_IPv4'";
      }
      description
        "IPv4 UNI session";
      uses RSVP-MGMT-SESSION-UNI-IPV4;
    }
    container ipv4-p2mp-lsp-session {
      when "../session-type = 'rsvp-mgmt-session-type-p2mp-lsp-ipv4'" {
        description
          "../SessionType =
           'RSVPMgmtSessionTypeP2MP_LSP_IPv4'";
      }
      description
        "IPv4 P2MP LSP session";
      uses RSVP-MGMT-SESSION-P2MP-LSP-TUNNEL-IPV4;
    }
    leaf session-type {
      type Rsvp-mgmt-session;
      description
        "SessionType";
    }
  }

  grouping RSVP-MGMT-SESSION-INFO {
    description
      "RSVP Session Info";
    container rsvp-session {
      description
        "RSVP Session";
      uses RSVP-SESSION-UNION;
    }
  }

  grouping RSVP-MGMT-SESSION-COMPACT {
    description
      "RSVP Compact Session Info";
    container session {
      description
        "RSVP Session Information";
      uses RSVP-MGMT-SESSION-INFO;
    }
    leaf ps-bs {
      type uint32;
      description
        "Number of path state block states";
    }
    leaf rs-bs {
      type uint32;
      description
        "Number of reservation state block states";
    }
    leaf requests {
      type uint32;
      description
        "Number of request states";
    }
    leaf detail-list-size {
      type uint32;
      description
        "Number of elements in detail list";
    }
  }

  grouping RSVP-MGMT-AUTHENTICATION-COMPACT {
    description
      "Authentication Compact Information";
    leaf source-address-xr {
      type inet:ipv4-address;
      description
        "Source address";
    }
    leaf destination-address-xr {
      type inet:ipv4-address;
      description
        "Destination address";
    }
    leaf neighbor-address {
      type inet:ipv4-address;
      description
        "Neighbor address";
    }
    leaf direction {
      type Rsvp-mgmt-auth-direction;
      description
        "Direction";
    }
    leaf key-type {
      type Rsvp-mgmt-auth-ki;
      description
        "Key type";
    }
    leaf key-source {
      type string;
      description
        "Key source";
    }
    leaf key-id {
      type uint64;
      description
        "Key ID";
    }
    leaf key-id-valid {
      type uint32;
      description
        "Key validity";
    }
  }

  grouping RSVP-MGMT-INTERFACE-BW-STD-DSTE {
    description
      "RSVP interface bandwidth info with standard based
       DSTE enabled";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-pool0-bandwidth {
      type uint64;
      units "bit/s";
      description
        "Max bandwidth (bits per second) allowed in BC0
         pool";
    }
    leaf max-pool1-bandwidth {
      type uint64;
      units "bit/s";
      description
        "Max bandwidth (bits per second) allowed in BC1
         pool";
    }
    leaf is-max-bandwidth-absolute {
      type boolean;
      description
        "True if the Max B/W is an absolute value and
         false if its a percentage";
    }
    leaf is-max-bc0-bandwidth-absolute {
      type boolean;
      description
        "True if the Max BC0 B/W is an absolute value and
         false if its a percentage";
    }
    leaf is-max-bc1-bandwidth-absolute {
      type boolean;
      description
        "True if the Max BC1 sub-pool B/W is an absolute
         value and false if its a percentage";
    }
  }

  grouping RSVP-MGMT-INTERFACE-BW-PRESTD-DSTE {
    description
      "Prestandard DSTE interface bandwidth information";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-subpool-bandwidth {
      type uint64;
      units "bit/s";
      description
        "Max bandwidth (bits per second) allowed in
         subpool";
    }
    leaf is-max-bandwidth-absolute {
      type boolean;
      description
        "True if the Max B/W is an absolute value and
         false if its a percentage";
    }
    leaf is-max-subpool-bandwidth-absolute {
      type boolean;
      description
        "True if the Max sub-pool B/W is an absolute
         value and false if its a percentage";
    }
  }

  grouping RSVP-MGMT-DSTE-MODE-INTERFACE-BW {
    description
      "Union of the different RSVP interface bandwidth
       types";
    container pre-standard-dste-interface {
      when "../dste-mode = 'pre-standard'" {
        description
          "../DSTEMode = 'PreStandard'";
      }
      description
        "Prestandard DSTE interface information";
      uses RSVP-MGMT-INTERFACE-BW-PRESTD-DSTE;
    }
    container standard-dste-interface {
      when "../dste-mode = 'standard'" {
        description
          "../DSTEMode = 'Standard'";
      }
      description
        "Standard DSTE interface information";
      uses RSVP-MGMT-INTERFACE-BW-STD-DSTE;
    }
    leaf dste-mode {
      type Rsvp-mgmt-dste-modes;
      description
        "DSTEMode";
    }
  }

  grouping RSVP-MGMT-INTERFACE-SUMMARY {
    description
      "Summary Form of RSVP interface Info";
    container bandwidth-information {
      description
        "Interface bandwidth information";
      uses RSVP-MGMT-DSTE-MODE-INTERFACE-BW;
    }
    leaf interface-name-xr {
      type string;
      description
        "Interface Name";
    }
    leaf paths-in {
      type uint32;
      description
        "Number of locally created and incoming path
         states";
    }
    leaf paths-out {
      type uint32;
      description
        "Number of outgoing path states";
    }
    leaf reservations-in {
      type uint32;
      description
        "Number of locally created and incoming
         reservation states";
    }
    leaf reservations-out {
      type uint32;
      description
        "Number of outgoing reservation states";
    }
  }

  grouping RSVP-MGMT-IF-NBR-COMPACT {
    description
      "Compact Info for RSVP Interface Neighbor";
    leaf interface-neighbor-address {
      type inet:ipv4-address;
      description
        "Interface Neighbor address";
    }
    leaf neighbor-interface-name {
      type xr:Interface-name;
      description
        "Neighbor's Interface handle";
    }
  }

  grouping RSVP-MGMT-NBR-COMPACT {
    description
      "Compact Info for RSVP Neighbor";
    leaf node-address {
      type inet:ipv4-address;
      description
        "Neighbor node address";
    }
    list interface-neighbor-list-compact {
      description
        "Compact list of I/F Neighbors";
      uses RSVP-MGMT-IF-NBR-COMPACT;
    }
  }
}
