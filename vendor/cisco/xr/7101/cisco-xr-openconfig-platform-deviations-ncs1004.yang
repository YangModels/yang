//*************  DO-NOT EDIT  **************
//*********** Auto-generated file ********** 

 module cisco-xr-openconfig-platform-deviations {

  namespace "http://cisco.com/ns/yang/cisco-xr-openconfig-platform-deviations";
  prefix  "oc-platformdevs";

  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform.yang@2021-08-13 

     on Cisco IOS-XR devices.

     Copyright (c) 2017 by Cisco Systems, Inc.
     All rights reserved.";

  revision "2022-03-24" {
    description
      "Initial revision applicable to IOS-XR 6.4.1";
  }


  deviation /oc-platform:components/oc-platform:component/oc-platform:state/oc-platform:mfg-date {
    deviate not-supported;
  }

  deviation /oc-platform:components/oc-platform:component/oc-platform:state/oc-platform:pcie {
    deviate not-supported;
  }

  deviation /oc-platform:components/oc-platform:component/oc-platform:state/oc-platform:redundant-role {
    deviate not-supported;
  }

  deviation /oc-platform:components/oc-platform:component/oc-platform:state/oc-platform:last-switchover-reason {
    deviate not-supported;
  }

  deviation /oc-platform:components/oc-platform:component/oc-platform:state/oc-platform:last-switchover-time {
    deviate not-supported;
  }

  deviation /oc-platform:components/oc-platform:component/oc-platform:state/oc-platform:last-reboot-reason {
    deviate not-supported;
  }

  deviation /oc-platform:components/oc-platform:component/oc-platform:state/oc-platform:last-reboot-time {
    deviate not-supported;
  }

  deviation /oc-platform:components/oc-platform:component/oc-platform:state/oc-platform:switchover-ready {
    deviate not-supported;
  }

  deviation /oc-platform:components/oc-platform:component/oc-platform:chassis/oc-platform:utilization {
    deviate not-supported;
  }

  deviation /oc-platform:components/oc-platform:component/oc-platform:integrated-circuit/oc-platform:utilization {
    deviate not-supported;
  }

}
//total deviations:10
