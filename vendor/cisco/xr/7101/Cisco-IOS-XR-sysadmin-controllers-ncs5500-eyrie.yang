module Cisco-IOS-XR-sysadmin-controllers-ncs5500-eyrie {
  namespace "http://www.cisco.com/ns/yang/Cisco-IOS-XR-sysadmin-controllers-ncs5500-eyrie";
  prefix calvados_controllers;

  import Cisco-IOS-XR-sysadmin-fabric-ncs5501 {
    prefix fabric;
  }
  import Cisco-IOS-XR-sysadmin-ethsw-esdma-cli-ncs5500 {
    prefix esdma;
  }
  import Cisco-IOS-XR-sysadmin-card-mgr {
    prefix card_mgr;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright (c) 2021-2020 by Cisco Systems, Inc.
     All rights reserved.";

  revision 2021-01-29 {
    description
      "Changed the implementation to not to have SFE and to have Switch";
    semver:module-version "1.0.0";
  }

  container controller {
    uses fabric:fabric;
    container switch {
      uses esdma:switch;
    }
    uses card_mgr:card_mgr-group;
  }
}
