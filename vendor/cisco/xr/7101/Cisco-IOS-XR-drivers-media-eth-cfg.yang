module Cisco-IOS-XR-drivers-media-eth-cfg {
  namespace "http://cisco.com/ns/yang/Cisco-IOS-XR-drivers-media-eth-cfg";
  prefix drivers-media-eth-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-media-eth package configuration.
     
     This model is deprecated and is replaced by
     Cisco-IOS-XR-um-if-ethernet-cfg.yang which will provide the
     compatible functionalities.
     
     This YANG module augments the
       Cisco-IOS-XR-ifmgr-cfg
     module with configuration data.
     
     Copyright (c) 2013-2022 by Cisco Systems, Inc.
     All rights reserved.";

  revision 2022-07-12 {
    description
      "Support added for forwarding unviable configuration.";
    semver:module-version "2.1.0";
  }
  revision 2019-12-03 {
    description
      "Adding priority flow-control mode configuration.";
    semver:module-version "2.0.0";
  }
  revision 2019-05-21 {
    description
      "Added new leaf for frame preemption configuration.";
    semver:module-version "1.1.0";
  }
  revision 2019-05-12 {
    description
      "Deprecated the native model, replaced by UM model.";
    semver:module-version "1.0.0";
  }
  revision 2019-04-05 {
    description
      "Establish semantic version baseline.";
  }
  revision 2019-01-18 {
    description
      "Makig carrier delay tuple items optional.";
  }
  revision 2017-05-01 {
    description
      "Fixing backward compatibility error in module.";
  }
  revision 2015-07-30 {
    description
      "Descriptions updated.";
  }
  revision 2015-01-07 {
    description
      "IOS XR 5.3.1 revision.";
  }

  typedef Ethernet-auto-negotiation {
    type enumeration {
      enum "true" {
        value 1;
        description
          "IEEE Standard auto-negotiation";
      }
      enum "override" {
        value 2;
        description
          "Auto-negotiation with configuration override";
      }
    }
    description
      "Ethernet auto negotiation";
  }

  typedef Ethernet-fec {
    type enumeration {
      enum "none" {
        value 0;
        description
          "Disable any FEC enabled on the interface";
      }
      enum "standard" {
        value 1;
        description
          "Enable standard (Reed-Solomon) FEC";
      }
    }
    description
      "Ethernet fec";
  }

  typedef Ethernet-flow-ctrl {
    type enumeration {
      enum "ingress" {
        value 0;
        description
          "Ingress flow control (sending pause frames)";
      }
      enum "egress" {
        value 1;
        description
          "Egress flow control (received pause frames)";
      }
      enum "bidirectional" {
        value 2;
        description
          "Bi-direction flow control";
      }
    }
    description
      "Ethernet flow ctrl";
  }

  typedef Ethernet-duplex {
    type enumeration {
      enum "full" {
        value 0;
        description
          "Full duplex";
      }
      enum "half" {
        value 1;
        description
          "Half duplex";
      }
    }
    description
      "Ethernet duplex";
  }

  typedef Ethernet-pfcwd {
    type enumeration {
      enum "off" {
        value 0;
        description
          "Disable priority flow control watchdog";
      }
      enum "on" {
        value 1;
        description
          "Enable priority flow control 1atchdog";
      }
    }
    description
      "Ethernet pfcwd";
  }

  typedef Ethernet-loopback {
    type enumeration {
      enum "external" {
        value 0;
        description
          "External loopback (using loopback connector)";
      }
      enum "internal" {
        value 1;
        description
          "Internal loopback";
      }
      enum "line" {
        value 2;
        description
          "Line loopback";
      }
    }
    description
      "Ethernet loopback";
  }

  typedef Ethernet-speed {
    type enumeration {
      enum "10" {
        value 10;
        description
          "10Mbits/s";
      }
      enum "100" {
        value 100;
        description
          "100Mbits/s";
      }
      enum "1000" {
        value 1000;
        description
          "1Gbits/s";
      }
    }
    description
      "Ethernet speed";
  }

  typedef Ethernet-ipg {
    type enumeration {
      enum "non-standard" {
        value 16;
        description
          "Non standard IPG";
      }
    }
    description
      "Ethernet ipg";
  }

  typedef Ethernet-pfc {
    type enumeration {
      enum "off" {
        value 0;
        description
          "Disable priority flow control";
      }
      enum "on" {
        value 1;
        description
          "Enable priority flow control";
      }
    }
    description
      "Ethernet pfc";
  }

  augment "/a1:interface-configurations/a1:interface-configuration" {
    description
      "This augment extends the configuration data of
       'Cisco-IOS-XR-ifmgr-cfg'";
    container ethernet {
      status deprecated;
      description
        "This model is deprecated and is replaced by
         Cisco-IOS-XR-um-if-ethernet-cfg.yang which will
         provide the compatible functionalities.  Ether
         specific interface configuration";
      container priority-flow-control-watchdog {
        description
          "Priority Flow Control Watchdog options";
        leaf shutdown-multiplier {
          type uint32 {
            range "1..10";
          }
          description
            "Configure priority flow-control watchdog
             interval multiplier";
        }
        leaf mode {
          type Ethernet-pfcwd;
          description
            "Configure priority flow-control watchdog mode";
        }
        leaf auto-restore-multiplier {
          type uint32 {
            range "0..100";
          }
          description
            "Configure priority flow-control watchdog Auto
             Restore Multiplier";
        }
        leaf interval {
          type uint32 {
            range "100..1000";
          }
          description
            "Configure priority flow-control watchdog
             interval";
        }
      }
      container signal-fail-bit-error-rate {
        description
          "Signal Fail Bit Error Rate handling options";
        leaf signal-remote-fault {
          type empty;
          description
            "Signal a remote fault to the peer device
             whenever the link is taken down due to
             crossing the SF-BER threshold";
        }
        leaf signal-fail-threshold {
          type uint32 {
            range "4..15";
          }
          default "4";
          description
            "Set the Signal Fail bit error rate threshold
             on an interface to a value of 10e-x, where x
             is the value passed in here";
        }
        leaf signal-fail-report-disable {
          type empty;
          description
            "Disable generation of an alarm whenever the
             SF-BER threshold is crossed for this interface";
        }
      }
      container optical-power-degrade {
        description
          "Optical power degrade handling options";
        leaf rx-alarm-threshold {
          type int32 {
            range "-300..50";
          }
          description
            "Set the value of the received optical power
             degrade alarm threshold on an interface";
        }
      }
      container signal-degrade-bit-error-rate {
        description
          "Signal Degrade Bit Error Rate handling options";
        leaf signal-degrade-threshold {
          type uint32 {
            range "3..15";
          }
          default "6";
          description
            "Set the Signal Degrade bit error rate
             threshold on an interface to a value of 10e-x,
             where x is the value passed in here";
        }
        leaf signal-degrade-report {
          type empty;
          description
            "Generate an alarm whenever the SD-BER
             threshold is crossed for this interface";
        }
      }
      container priority-flow-control {
        description
          "Priority Flow Control options";
        leaf mode {
          type Ethernet-pfc;
          description
            "Configure priority flow-control mode";
        }
      }
      container carrier-delay {
        description
          "Set the carrier transition delay on an
           interface in msecs";
        leaf carrier-delay-up {
          type uint32 {
            range "0..2147483647";
          }
          description
            "Carrier Delay (up) in msecs";
        }
        leaf carrier-delay-down {
          type uint32 {
            range "0..2147483647";
          }
          description
            "Carrier Delay (down) in msecs";
        }
      }
      leaf frame-preemption {
        type empty;
        description
          "Enable frame preemption";
      }
      leaf duplex {
        type Ethernet-duplex;
        description
          "Configure duplex operational mode";
      }
      leaf forwarding-unviable {
        type empty;
        description
          "Disable traffic forwarding on the ethernet port
           . This port is already part of a Link
           Aggregation(LAG) or can be part of one.";
      }
      leaf auto-negotiation {
        type Ethernet-auto-negotiation;
        description
          "Link auto-negotiation";
      }
      leaf flow-control {
        type Ethernet-flow-ctrl;
        description
          "Configure flow-control mode";
      }
      leaf forward-error-correction {
        type Ethernet-fec;
        description
          "Forward Error Correction";
      }
      leaf loopback {
        type Ethernet-loopback;
        description
          "Configure loopback mode";
      }
      leaf speed {
        type Ethernet-speed;
        description
          "Set the ethernet speed on an interface";
      }
      leaf inter-packet-gap {
        type Ethernet-ipg;
        description
          "Inter-packet gap";
      }
    }
  }
}
