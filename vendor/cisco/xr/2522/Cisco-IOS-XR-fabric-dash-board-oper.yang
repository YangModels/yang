module Cisco-IOS-XR-fabric-dash-board-oper {
  namespace "http://cisco.com/ns/yang/Cisco-IOS-XR-fabric-dash-board-oper";
  prefix fabric-dash-board-oper;

  import Cisco-IOS-XR-types {
    prefix xr;
  }
  import cisco-semver {
    prefix semver;
  }
  include Cisco-IOS-XR-fabric-dash-board-oper-sub1 {
    revision-date 2024-07-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fabric-dash-board package operational data.
     
     This module contains definitions
     for the following management objects:
       fabric-dash-board: Fabric Data
     
     Copyright (c) 2013-2024 by Cisco Systems, Inc.
     All rights reserved.";

  revision 2024-07-10 {
    description
      "Yang Schema for fabric dash-board";
    semver:module-version "1.0.0";
  }
  revision 2019-04-05 {
    description
      "Establish semantic version baseline.";
  }
  revision 2015-11-09 {
    description
      "IOS XR 6.0 revision.";
  }

  typedef Fabric-max-asic-instances {
    type uint32 {
      range "0..255";
    }
    description
      "Fabric max asic instances";
  }

  container fabric-dash-board {
    config false;
    description
      "Fabric Data";
    list fabric-node {
      key "node-name";
      description
        "Data for particular node";
      container dash-board {
        description
          "Fabric Dash-Board";
        container dash-board-asic-instances {
          description
            "Asic Instance table for Fabric Dash Board";
          list dash-board-asic-instance {
            key "instance";
            description
              "Instance Number";
            container dash-board-output {
              description
                "Fabric Dash Board output";
              uses NPU-EDM-FABRIC-DATAPATH-INFO;
            }
            leaf instance {
              type Fabric-max-asic-instances;
              description
                "Instance Number";
            }
          }
        }
      }
      leaf node-name {
        type xr:Node-id;
        description
          "Node ID";
      }
    }
  }
}
