submodule Cisco-IOS-XR-dot1x-portauth-oper-sub1 {
  belongs-to Cisco-IOS-XR-dot1x-portauth-oper {
    prefix Cisco-IOS-XR-dot1x-portauth-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR dot1x-portauth package operational data.
     
     Copyright (c) 2013-2024 by Cisco Systems, Inc.
     All rights reserved.";

  revision 2024-12-12 {
    description
      "Addition of dot1x portauth oper model";
    semver:module-version "1.0.0";
  }
  revision 2019-04-05 {
    description
      "Establish semantic version baseline.";
  }
  revision 2015-11-09 {
    description
      "IOS XR 6.0 revision.";
  }

  grouping DOT1X-PORT-AUTH-CLIENT-INFO {
    description
      "DOT1X PORT AUTH CLIENT INFO";
    leaf client-mac {
      type string;
      description
        "Formatted Client MAC Address";
    }
    list auth-method {
      description
        "Port Authentication method, dot1x(EAPOL) or MAB";
      uses DOT1X-PORT-AUTH-METHOD;
    }
  }

  grouping DOT1X-PORT-AUTH-SUMMARY {
    description
      "DOT1X PORT AUTH SUMMARY";
    leaf interface-short-name {
      type string;
      description
        "Interface short name";
    }
    list client-info {
      description
        "Information on Dot1x and MAB Clients";
      uses DOT1X-PORT-AUTH-CLIENT-INFO;
    }
  }

  grouping DOT1X-PORT-AUTH-METHOD {
    description
      "DOT1X PORT AUTH METHOD";
    leaf method {
      type string;
      description
        "Authentication method dot1x or MAB";
    }
    leaf status {
      type string;
      description
        "Authentication method status";
    }
  }

  grouping DOT1X-PORT-AUTH-CLIENT-INFO-DETAIL {
    description
      "DOT1X PORT AUTH CLIENT INFO DETAIL";
    leaf client-mac {
      type string;
      description
        "Formatted Client MAC Address";
    }
    leaf status {
      type string;
      description
        "Client Authentication status";
    }
    leaf programming-status {
      type string;
      description
        "Programming Status";
    }
    leaf unauthorized-timeout {
      type uint32;
      units "second";
      description
        "Authentication Lockout Timer duration in seconds";
    }
    leaf unauthorized-timer {
      type string;
      description
        "Authentication Lockout Timer Status";
    }
    list auth-method {
      description
        "Port Authentication method, dot1x(EAPOL) or MAB";
      uses DOT1X-PORT-AUTH-METHOD;
    }
  }

  grouping DOT1X-PORT-AUTH-DETAIL {
    description
      "DOT1X PORT AUTH DETAIL";
    leaf interface-short-name {
      type string;
      description
        "Interface short name";
    }
    leaf interface-handle {
      type xr:Hex-integer;
      description
        "Interface Handle";
    }
    leaf interface-state {
      type string;
      description
        "Interface State, Up or Down";
    }
    leaf port-status {
      type string;
      description
        "Authorization Status for clients on this Port";
    }
    leaf dot1x-profile {
      type string;
      description
        "Dot1x Profile";
    }
    leaf method-list {
      type string;
      description
        "Authentication Method List";
    }
    list client-info {
      description
        "Detailed Information on Dot1x and MAB Clients";
      uses DOT1X-PORT-AUTH-CLIENT-INFO-DETAIL;
    }
  }
}
