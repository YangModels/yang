module Cisco-IOS-XR-osa-hwmod-linesys-oper {
  namespace "http://cisco.com/ns/yang/Cisco-IOS-XR-osa-hwmod-linesys-oper";
  prefix osa-hwmod-linesys-oper;

  import Cisco-IOS-XR-types {
    prefix xr;
  }
  import cisco-semver {
    prefix semver;
  }
  include Cisco-IOS-XR-osa-hwmod-linesys-oper-sub1 {
    revision-date 2022-06-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa-hwmod-linesys package operational data.
     
     This module contains definitions
     for the following management objects:
       osa: Show hw-module location
     
     Copyright (c) 2013-2022 by Cisco Systems, Inc.
     All rights reserved.";

  revision 2022-06-08 {
    description
      "Show Hwmod Enhancement.";
    semver:module-version "1.0.0";
  }
  revision 2019-04-05 {
    description
      "Establish semantic version baseline.";
  }
  revision 2015-11-09 {
    description
      "IOS XR 6.0 revision.";
  }

  container osa {
    config false;
    description
      "Show hw-module location";
    container node-ids {
      description
        "Per-node OSA operational data";
      list node-id {
        key "node-name";
        description
          "Node ID of LC";
        container terminal-ampli {
          description
            "Display Terminal Amplifier Information";
          uses OSA-HWMOD-TERMINAL-AMPLI-INFO-B;
        }
        container inline-ampli {
          description
            "Display Inline Amplifier Information";
          uses OSA-HWMOD-INLINE-AMPLI-INFO-B;
        }
        leaf node-name {
          type xr:Node-id;
          description
            "The identifier for the node";
        }
      }
    }
  }
}
