module Cisco-IOS-XR-Ots-Och-cfg {
  namespace "http://cisco.com/ns/yang/Cisco-IOS-XR-Ots-Och-cfg";
  prefix ots-och-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Ots-Och package configuration.
     
     This YANG module augments the
       Cisco-IOS-XR-ifmgr-cfg
     module with configuration data.
     
     Copyright (c) 2013-2021 by Cisco Systems, Inc.
     All rights reserved.";

  revision 2021-03-16 {
    description
      "Channel Attenuation Parameter added for Ots-Och Controller";
    semver:module-version "1.0.0";
  }
  revision 2020-07-09 {
    description
      "New Cfg Model Added for Ots-Och Controller";
  }
  revision 2019-04-05 {
    description
      "Establish semantic version baseline.";
  }
  revision 2015-11-09 {
    description
      "IOS XR 6.0 revision.";
  }

  augment "/a1:interface-configurations/a1:interface-configuration" {
    description
      "This augment extends the configuration data of
       'Cisco-IOS-XR-ifmgr-cfg'";
    container ots-och {
      description
        "Ots-Och controller configuration";
      leaf channel-attenuation {
        type uint32 {
          range "0..250";
        }
        description
          "Select Channel Attenuation(in units of 0.1dB)";
      }
      leaf add-drop-channel {
        type xr:Interface-name;
        description
          "configures optical cross connect";
      }
    }
  }
}
