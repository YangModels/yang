module Cisco-IOS-XR-sfi-ma-oper {
  namespace "http://cisco.com/ns/yang/Cisco-IOS-XR-sfi-ma-oper";
  prefix sfi-ma-oper;

  import Cisco-IOS-XR-types {
    prefix xr;
  }
  import cisco-semver {
    prefix semver;
  }
  include Cisco-IOS-XR-sfi-ma-oper-sub1 {
    revision-date 2021-08-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sfi-ma package operational data.
     
     This module contains definitions
     for the following management objects:
       sfi: SFI operational data
     
     Copyright (c) 2013-2021 by Cisco Systems, Inc.
     All rights reserved.";

  revision 2021-08-25 {
    description
      "Added registered-table-id and registered-proto-id leafs to SFI VRF RIB AFI registration information";
    semver:module-version "1.1.0";
  }
  revision 2021-08-12 {
    description
      "Added MPLS v4/v6 label leaves to SFI-DETAIL";
    semver:module-version "1.0.0";
  }
  revision 2020-12-08 {
    description
      "Added SFI VRF Bag and respective oper commands";
  }
  revision 2020-01-06 {
    description
      "Initial version";
  }
  revision 2019-04-05 {
    description
      "Establish semantic version baseline.";
  }
  revision 2015-11-09 {
    description
      "IOS XR 6.0 revision.";
  }

  container sfi {
    config false;
    description
      "SFI operational data";
    container sfi-vrfs {
      description
        "SFI VRFs";
      list sfi-vrf {
        key "name";
        description
          "SFI VRF detail";
        leaf name {
          type xr:Cisco-ios-xr-string {
            length "1..32";
          }
          description
            "VRF name";
        }
        uses SFI-VRF-INFO;
      }
    }
    container detail-interfaces {
      description
        "SFI Interfaces";
      list detail-interface {
        key "interface-name";
        description
          "SFI Interface detail";
        leaf interface-name {
          type xr:Interface-name;
          description
            "SFI Interface name";
        }
        uses SFI-DETAIL;
      }
    }
  }
}
