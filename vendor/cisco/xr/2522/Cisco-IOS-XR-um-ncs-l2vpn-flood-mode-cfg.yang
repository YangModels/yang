module Cisco-IOS-XR-um-ncs-l2vpn-flood-mode-cfg {
  namespace "http://cisco.com/ns/yang/Cisco-IOS-XR-um-ncs-l2vpn-flood-mode-cfg";
  prefix um-ncs-l2vpn-flood-mode-cfg;

  import Cisco-IOS-XR-um-l2vpn-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs-l2vpn-flood-mode package configuration.
     
     This YANG module augments the
     modules with configuration data.
     
     Copyright (c) 2021-2022 by Cisco Systems, Inc.
     All rights reserved.";

  revision 2022-07-11 {
    description
      "Added missing description statement to nodes";
    semver:module-version "1.0.0";
  }
  revision 2021-04-13 {
    description
      "Initial release";
    semver:module-version "1.0.0";
  }

  augment "/a1:l2vpn/a1:bridge/a1:groups/a1:group/a1:bridge-domains/a1:bridge-domain" {
    description
      "This augment extends l2vpn bridge group bridge-domain nodes
       configuration";
    container flood {
      description
        "Flooding Capability";
      container mode {
        description
          "Choose Flooding Mode";
        container ac-ingress-replication {
          presence "Indicates a ac-ingress-replication node is configured.";
          description
            "Ingress replication of Atachment circuits";
        }
      }
    }
  }
}
