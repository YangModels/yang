module Cisco-IOS-XR-um-ncs560-cont-portmode-cfg {
  namespace "http://cisco.com/ns/yang/Cisco-IOS-XR-um-ncs560-cont-portmode-cfg";
  prefix um-ncs560-cont-portmode-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs560-cont-portmode package configuration.
     
     This YANG module augments the
     modules with configuration data.
     
     Copyright (c) 2020, 2022 by Cisco Systems, Inc.
     All rights reserved.";

  revision 2022-07-11 {
    description
      "Added missing description statement to nodes
       2022-06-01
         Adjusted controller augmentation hierarchy";
    semver:module-version "1.1.0";
  }
  revision 2020-12-07 {
    description
      "Initial release";
    semver:module-version "1.0.0";
  }

  feature optics {
    description
      "optics";
  }

  grouping CONT-BODY {
    description
      "Grouping for controller";
    container port-mode {
      when "../a1:controller-name[starts-with(text(),'Optics')]" {
        tailf:dependency "../a1:controller-name";
      }
      if-feature "optics";
      description
        "Configure through port-mode";
      leaf speed {
        type enumeration {
          enum "100G" {
            value 100000000;
            description
              "Speed 100";
          }
          enum "200G" {
            value 200000000;
            description
              "Speed 200";
          }
        }
        must "../mod";
        description
          "optics speed";
      }
      leaf mod {
        type enumeration {
          enum "qpsk" {
            value 1;
            description
              "select qpsk for modulation";
          }
          enum "8qam" {
            value 2;
            description
              "select 8qam for modulation";
          }
          enum "16qam" {
            value 3;
            description
              "select 16qam for modulation";
          }
        }
        must "../speed and ../fec";
        description
          "modulation value";
      }
      leaf fec {
        type enumeration {
          enum "15sdfec" {
            value 0;
            description
              "15%-SD Forward Error Correction";
          }
          enum "25sdfec" {
            value 1;
            description
              "25%-SD Forward Error Correction";
          }
          enum "15sdfecde" {
            value 2;
            description
              "15%-SD Forward Error Correction with Diff";
          }
          enum "otu7staircase" {
            value 3;
            description
              "7%-STAIRCASE Forward Error Correction";
          }
        }
        must "../mod and ../diff";
        description
          "optics fec";
      }
      leaf diff {
        type enumeration {
          enum "disable" {
            value 0;
            description
              "disable differential";
          }
          enum "enable" {
            value 1;
            description
              "enable differential";
          }
        }
        must "../fec";
        description
          "differential value";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
