module Cisco-IOS-XR-um-router-eigrp-cfg {
  namespace "http://cisco.com/ns/yang/Cisco-IOS-XR-um-router-eigrp-cfg";
  prefix um-router-eigrp-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR router-eigrp package configuration.
     
     This YANG module augments the
     modules with configuration data.
     
     Copyright (c) 2021-2023 by Cisco Systems, Inc.
     All rights reserved.";

  revision 2023-05-18 {
    description
      "Added rip under IPv6 redistribute container";
    semver:module-version "1.1.0";
  }
  revision 2021-06-29 {
    description
      "Initial release";
    semver:module-version "1.0.0";
  }

  container router {
    description
      "Enable a routing process";
    container eigrp {
      description
        "EIGRP configuration subcommands";
      container processes {
        description
          "AS number (1 - 65535) or Virtual instance name of the EIGRP process";
        list process {
          key "process-name";
          description
            "AS number (1 - 65535) or Virtual instance name of the EIGRP process";
          leaf process-name {
            type xr:Cisco-ios-xr-string {
              length "1..32" {
                description
                  "AS number (1 - 65535) or Virtual instance name of the EIGRP process";
              }
            }
            description
              "AS number (1 - 65535) or Virtual instance name of the EIGRP process";
          }
          container nsf {
            description
              "Global NSF related configuration";
            container disable {
              presence "Indicates a disable node is configured.";
              description
                "Disable NSF for all address families under all VRF's";
            }
          }
          container address-family {
            description
              "EIGRP address-family configuration submode";
            container ipv4 {
              presence "Indicates a ipv4 node is configured.";
              description
                "IPv4 Address Family";
              container auto-summary {
                presence "Indicates a auto-summary node is configured.";
                description
                  "Auto summarisation";
              }
              leaf autonomous-system {
                type uint32 {
                  range "1..65535" {
                    description
                      "Autonomous system number";
                  }
                }
                description
                  "Set the autonomous system of VRF";
              }
              container default-information {
                description
                  "Handling of default route";
                container allowed {
                  description
                    "Accept/Advertise a candidate default route";
                  container in {
                    presence "Indicates a in node is configured.";
                    description
                      "Accept candidate default information inbound";
                    leaf route-policy {
                      type xr:Route-policy-name;
                      description
                        "Filter with an RPL policy";
                    }
                  }
                  container out {
                    presence "Indicates a out node is configured.";
                    description
                      "Advertise candidate default information outbound";
                    leaf route-policy {
                      type xr:Route-policy-name;
                      description
                        "Filter with an RPL policy";
                    }
                  }
                }
              }
              leaf default-metric {
                type uint32 {
                  range "1..4294967295" {
                    description
                      "Bandwidth in Kbits per second";
                  }
                }
                must "../delay-metric-in-10-microsecond";
                description
                  "Set metric of redistributed routes";
              }
              leaf delay-metric-in-10-microsecond {
                type uint32 {
                  range "1..4294967295" {
                    description
                      "Delay metric, in 10 microsecond units";
                  }
                }
                must "../default-metric";
                must "../reliability-metric";
                description
                  "Delay metric, in 10 microsecond units";
              }
              leaf reliability-metric {
                type uint32 {
                  range "0..255" {
                    description
                      "Reliability metric where 255 is 100% reliable";
                  }
                }
                must "../delay-metric-in-10-microsecond";
                must "../effective-bandwidth-metric";
                description
                  "Reliability metric where 255 is 100% reliable";
              }
              leaf effective-bandwidth-metric {
                type uint32 {
                  range "1..255" {
                    description
                      "Effective bandwidth metric (Loading) where 255 is 100% loaded";
                  }
                }
                must "../reliability-metric";
                must "../maximum-transmission-unit";
                description
                  "Effective bandwidth metric (Loading) where 255 is 100% loaded";
              }
              leaf maximum-transmission-unit {
                type uint32 {
                  range "1..65535" {
                    description
                      "Maximum Transmission Unit metric of the path";
                  }
                }
                must "../effective-bandwidth-metric";
                description
                  "Maximum Transmission Unit metric of the path";
              }
              leaf distance {
                type uint32 {
                  range "1..255" {
                    description
                      "Internal routes' distance";
                  }
                }
                must "../external-routes-distance";
                description
                  "Set distance for EIGRP routes";
              }
              leaf external-routes-distance {
                type uint32 {
                  range "1..255" {
                    description
                      "External routes' distance";
                  }
                }
                must "../distance";
                description
                  "External routes' distance";
              }
              container log-neighbor-changes {
                presence "Indicates a log-neighbor-changes node is configured.";
                description
                  "Enable/Disable EIGRP neighbor logging";
              }
              container log-neighbor-warnings {
                presence "Indicates a log-neighbor-warnings node is configured.";
                description
                  "Enable/Disable EIGRP neighbor warnings";
              }
              leaf maximum-paths {
                type uint32 {
                  range "1..32" {
                    description
                      "number of paths";
                  }
                }
                description
                  "Maximum paths";
              }
              container metric {
                description
                  "Modify EIGRP routing metrics and parameters";
                leaf maximum-hops {
                  type uint32 {
                    range "1..255" {
                      description
                        "Hop count";
                    }
                  }
                  description
                    "Advertise EIGRP routes greater than <hops> as unreachable";
                }
                leaf rib-scale {
                  type uint32 {
                    range "1..255" {
                      description
                        "RIB metric scale-down value ";
                    }
                  }
                  description
                    "Change the value by which the RIB metric is to be scaled down";
                }
                leaf weights {
                  type uint32 {
                    range "0" {
                      description
                        "Type of Service (Only TOS 0 supported)";
                    }
                  }
                  description
                    "EIGRP metric coefficients";
                }
                leaf k1 {
                  type uint32 {
                    range "0..255" {
                      description
                        "K1";
                    }
                  }
                  must "../weights";
                  description
                    "K1";
                }
                leaf k2 {
                  type uint32 {
                    range "0..255" {
                      description
                        "K2";
                    }
                  }
                  must "../k1";
                  description
                    "K2";
                }
                leaf k3 {
                  type uint32 {
                    range "0..255" {
                      description
                        "K3";
                    }
                  }
                  must "../k2";
                  description
                    "K3";
                }
                leaf k4 {
                  type uint32 {
                    range "0..255" {
                      description
                        "K4";
                    }
                  }
                  must "../k3";
                  description
                    "K4";
                }
                leaf k5 {
                  type uint32 {
                    range "0..255" {
                      description
                        "K5";
                    }
                  }
                  must "../k4";
                  description
                    "K5";
                }
                leaf k6 {
                  type uint32 {
                    range "0..255" {
                      description
                        "K6";
                    }
                  }
                  must "../k5";
                  description
                    "K6";
                }
                container version {
                  description
                    "Change the EIGRP metric version";
                  container thirty-two-bit {
                    presence "Indicates a thirty-two-bit node is configured.";
                    description
                      "Change to 32-bit metric version";
                  }
                }
              }
              container nsf {
                description
                  "Address family specific NSF related configuration";
                container disable {
                  presence "Indicates a disable node is configured.";
                  description
                    "Disable NSF for this address family under this VRF";
                }
              }
              container redistribute {
                description
                  "Redistribute another protocol";
                container bgp {
                  description
                    "Border Gateway Protocol (BGP) routes";
                  container ases {
                    description
                      "bgp as-number";
                    list as {
                      key "as-number";
                      description
                        "bgp as-number";
                      leaf as-number {
                        type xr:Bgp-as-number;
                        description
                          "bgp as-number";
                      }
                      leaf route-policy {
                        type xr:Route-policy-name;
                        description
                          "Filter using an RPL policy";
                      }
                    }
                  }
                }
                container connected {
                  presence "Indicates a connected node is configured.";
                  description
                    "Connected routes";
                  leaf route-policy {
                    type xr:Route-policy-name;
                    description
                      "Filter using an RPL policy";
                  }
                }
                container mobile {
                  presence "Indicates a mobile node is configured.";
                  description
                    "Mobile routes";
                  leaf route-policy {
                    type xr:Route-policy-name;
                    description
                      "Filter using an RPL policy";
                  }
                }
                container eigrps {
                  description
                    "EIGRP routes";
                  list eigrp {
                    key "as-number";
                    description
                      "EIGRP routes";
                    leaf as-number {
                      type uint32 {
                        range "1..65535" {
                          description
                            "AS number of the redistributed EIGRP process";
                        }
                      }
                      description
                        "EIGRP routes";
                    }
                    leaf route-policy {
                      type xr:Route-policy-name;
                      description
                        "Filter using an RPL policy";
                    }
                  }
                }
                container isises {
                  description
                    "Intermediate System-to-Intermediate System (IS-IS) routes";
                  list isis {
                    key "instance-name";
                    description
                      "Intermediate System-to-Intermediate System (IS-IS) routes";
                    leaf instance-name {
                      type xr:Cisco-ios-xr-string {
                        length "1..800" {
                          description
                            "ISIS instance name";
                        }
                      }
                      description
                        "Intermediate System-to-Intermediate System (IS-IS) routes";
                    }
                    leaf route-policy {
                      type xr:Route-policy-name;
                      description
                        "Filter using an RPL policy";
                    }
                  }
                }
                container static {
                  presence "Indicates a static node is configured.";
                  description
                    "Static routes";
                  leaf route-policy {
                    type xr:Route-policy-name;
                    description
                      "Filter using an RPL policy";
                  }
                }
                container subscriber {
                  presence "Indicates a subscriber node is configured.";
                  description
                    "Subscriber routes";
                  leaf route-policy {
                    type xr:Route-policy-name;
                    description
                      "Filter using an RPL policy";
                  }
                }
                container applications {
                  description
                    "OnePK application routes";
                  list application {
                    key "application-name";
                    description
                      "OnePK application routes";
                    leaf application-name {
                      type xr:Cisco-ios-xr-string {
                        length "1..800" {
                          description
                            "OnePK application name";
                        }
                      }
                      description
                        "OnePK application routes";
                    }
                    leaf route-policy {
                      type xr:Route-policy-name;
                      description
                        "Filter using an RPL policy";
                    }
                  }
                }
                container ospfs {
                  description
                    "Open Shortest Path First (OSPF) routes";
                  list ospf {
                    key "ospf-name";
                    description
                      "Open Shortest Path First (OSPF) routes";
                    leaf ospf-name {
                      type xr:Cisco-ios-xr-string {
                        length "1..800" {
                          description
                            "OSPF instance name";
                        }
                      }
                      description
                        "Open Shortest Path First (OSPF) routes";
                    }
                    leaf route-policy {
                      type xr:Route-policy-name;
                      description
                        "Filter using an RPL policy";
                    }
                  }
                }
                container rip {
                  presence "Indicates a rip node is configured.";
                  description
                    "Routing Information Protocol (RIP) routes";
                  leaf route-policy {
                    type xr:Route-policy-name;
                    description
                      "Filter using an RPL policy";
                  }
                }
              }
              container passive-interface {
                description
                  "Suppress routing updates on all interfaces";
                container default {
                  presence "Indicates a default node is configured.";
                  description
                    "Interfaces passive by default";
                }
              }
              container route-policy {
                description
                  "Configure inbound/outbound policies";
                leaf in {
                  type xr:Route-policy-name;
                  description
                    "Filter inbound routes";
                }
                leaf out {
                  type xr:Route-policy-name;
                  description
                    "Filter outbound routes";
                }
              }
              leaf router-id {
                type inet:ipv4-address-no-zone;
                description
                  "Set router ID";
              }
              container stub {
                presence "Indicates a stub node is configured.";
                description
                  "EIGRP stub";
                container receive-only {
                  presence "Indicates a receive-only node is configured.";
                  description
                    "Set EIGRP as receive only neighbor";
                }
                container connected {
                  presence "Indicates a connected node is configured.";
                  description
                    "Do advertise connected routes";
                }
                container redistributed {
                  presence "Indicates a redistributed node is configured.";
                  description
                    "Do advertise redistributed routes";
                }
                container static {
                  presence "Indicates a static node is configured.";
                  description
                    "Do advertise static routes";
                }
                container summary {
                  presence "Indicates a summary node is configured.";
                  description
                    "Do advertise summary routes";
                }
              }
              container timers {
                description
                  "Configure EIGRP timers";
                container active-time {
                  description
                    "Configure active time";
                  leaf active-time-limit {
                    type uint32 {
                      range "1..4294967295" {
                        description
                          "Active time limit (in seconds)";
                      }
                    }
                    must "not(../disabled)";
                    description
                      "Active time limit (in seconds)";
                  }
                  container disabled {
                    must "not(../active-time-limit)";
                    presence "Indicates a disabled node is configured.";
                    description
                      "Disable active timer";
                  }
                }
                container nsf {
                  description
                    "Configure NSF timers";
                  leaf route-hold {
                    type uint32 {
                      range "20..6000" {
                        description
                          "Hold time (in seconds)";
                      }
                    }
                    description
                      "Route hold time for inactive peer";
                  }
                  leaf signal {
                    type uint32 {
                      range "10..30" {
                        description
                          "Signal time (in seconds)";
                      }
                    }
                    description
                      "Route signal time";
                  }
                  leaf converge {
                    type uint32 {
                      range "60..5000" {
                        description
                          "Converge time (in seconds)";
                      }
                    }
                    description
                      "Route converge time";
                  }
                }
              }
              leaf variance {
                type uint32 {
                  range "1..128" {
                    description
                      "Metric variance multiplier";
                  }
                }
                description
                  "Control load balancing variance";
              }
              container interfaces {
                description
                  "EIGRP interface configuration submode";
                list interface {
                  key "interface-name";
                  description
                    "EIGRP interface configuration submode";
                  leaf interface-name {
                    type xr:Interface-name;
                    description
                      "EIGRP interface configuration submode";
                  }
                  container authentication {
                    description
                      "Authentication configuration";
                    leaf keychain {
                      type xr:Cisco-ios-xr-string {
                        length "1..800" {
                          description
                            "Authentication keychain name";
                        }
                        pattern "[a-zA-Z0-9@#;:$._-]*";
                      }
                      description
                        "Authentication keychain configuration";
                    }
                  }
                  leaf bandwidth-percent {
                    type uint32 {
                      range "1..999999" {
                        description
                          "Percent";
                      }
                    }
                    description
                      "Bandwidth limit";
                  }
                  container bfd {
                    description
                      "Configure BFD parameters";
                    container fast-detect {
                      presence "Indicates a fast-detect node is configured.";
                      description
                        "Enable BFD fast detection";
                    }
                    leaf minimum-interval {
                      type uint32 {
                        range "15..3000" {
                          description
                            "BFD interval (in milliseconds)";
                        }
                      }
                      description
                        "BFD minimum-interval configuration";
                    }
                    leaf multiplier {
                      type uint32 {
                        range "2..50" {
                          description
                            "BFD multiplier";
                        }
                      }
                      description
                        "BFD multiplier configuration";
                    }
                  }
                  leaf hello-interval {
                    type uint32 {
                      range "1..65535" {
                        description
                          "Interval (in seconds)";
                      }
                    }
                    description
                      "Hello interval";
                  }
                  leaf hold-time {
                    type uint32 {
                      range "1..65535" {
                        description
                          "Neighbor hold time (in seconds)";
                      }
                    }
                    description
                      "Hold Time";
                  }
                  container metric {
                    description
                      "Metric";
                    leaf bandwidth {
                      type uint32 {
                        range "1..4294967295" {
                          description
                            "Bandwidth in Kbits per second";
                        }
                      }
                      description
                        "Interface bandwidth";
                    }
                    leaf delay {
                      type uint32 {
                        range "1..4294967295" {
                          description
                            "Delay metric, in 10 microsecond units";
                        }
                      }
                      description
                        "Interface delay";
                    }
                    container picoseconds {
                      must "../delay";
                      presence "Indicates a picoseconds node is configured.";
                      description
                        "Interpret configured delay to be in picosecond units";
                    }
                    leaf reliability {
                      type uint32 {
                        range "0..255" {
                          description
                            "Reliability metric where 255 is 100% reliable";
                        }
                      }
                      description
                        "Interface reliability";
                    }
                    leaf load {
                      type uint32 {
                        range "1..255" {
                          description
                            "Load metric where 255 is 100% loaded";
                        }
                      }
                      description
                        "Interface load";
                    }
                  }
                  container neighbors {
                    description
                      "Configure Neighbor";
                    list neighbor {
                      key "address";
                      description
                        "Neighbor IPv4 address";
                      leaf address {
                        type inet:ipv4-address-no-zone;
                        description
                          "Neighbor IPv4 address";
                      }
                      leaf remote {
                        type uint32 {
                          range "2..99" {
                            description
                              "Maxhops range";
                          }
                        }
                        description
                          "Configure max-hop count";
                      }
                    }
                  }
                  container remote-neighbor {
                    description
                      "Configure Remote-Neighbor";
                    container unicast-listen {
                      presence "Indicates a unicast-listen node is configured.";
                      description
                        "Configure unicast-listen";
                      leaf allow-list {
                        type xr:Route-policy-name;
                        description
                          "Policy list for allowing neighbors";
                      }
                      leaf max-neighbors {
                        type uint32 {
                          range "1..65535" {
                            description
                              "Max number of neighbors";
                          }
                        }
                        description
                          "Max count of the neighbors allowed";
                      }
                    }
                  }
                  container next-hop-self {
                    description
                      "Configure next-hop-self";
                    container disable {
                      presence "Indicates a disable node is configured.";
                      description
                        "Disable next-hop-self";
                    }
                  }
                  container passive-interface {
                    presence "Indicates a passive-interface node is configured.";
                    description
                      "Suppress routing updates on an interface";
                    container disable {
                      presence "Indicates a disable node is configured.";
                      description
                        "disable";
                    }
                  }
                  container route-policy {
                    description
                      "Configure inbound/outbound policies";
                    leaf in {
                      type xr:Route-policy-name;
                      description
                        "Filter inbound routes";
                    }
                    leaf out {
                      type xr:Route-policy-name;
                      description
                        "Filter outbound routes";
                    }
                  }
                  container site-of-origin {
                    description
                      "Configure Site-of-origin";
                    leaf two-byte-as-number {
                      type uint32 {
                        range "1..65535" {
                          description
                            "2-byte AS number";
                        }
                      }
                      must
                        "../two-byte-as-index and
                         not(../four-byte-as-number-asplain or
                            ../four-byte-as-number-asdot-x or
                             ../ipv4-address)";
                      description
                        "2-byte AS number";
                    }
                    leaf two-byte-as-index {
                      type uint32 {
                        range "0..4294967295" {
                          description
                            "ASN2:index (hex or decimal format)";
                        }
                      }
                      must "../two-byte-as-number";
                      description
                        "ASN2:index (hex or decimal format)";
                    }
                    leaf four-byte-as-number-asplain {
                      type uint32 {
                        range "65536..4294967295" {
                          description
                            "4-byte AS number";
                        }
                      }
                      must
                        "../four-byte-as-index and
                         not(../two-byte-as-number or
                             ../four-byte-as-number-asdot-x or
                             ../ipv4-address)";
                      description
                        "4-byte AS number in asplain format";
                    }
                    leaf four-byte-as-number-asdot-x {
                      type uint32 {
                        range "1..65535" {
                          description
                            "4-byte AS number in asdot x";
                        }
                      }
                      must
                        "../four-byte-as-index and
                         ../four-byte-as-number-asdot-y and
                         not(../four-byte-as-number-asplain or
                             ../two-byte-as-number or
                             ../ipv4-address)";
                      description
                        "4-byte AS number in asdot (X.Y) format";
                    }
                    leaf four-byte-as-number-asdot-y {
                      type uint32 {
                        range "0..65535" {
                          description
                            "4-byte AS number in asdot y";
                        }
                      }
                      must
                        "../four-byte-as-index and
                         ../four-byte-as-number-asdot-x and
                         not(../four-byte-as-number-asplain or
                             ../two-byte-as-number or
                             ../ipv4-address)";
                      description
                        "4-byte AS number in asdot (X.Y) format";
                    }
                    leaf four-byte-as-index {
                      type uint32 {
                        range "0..65535" {
                          description
                            "ASN4:index (hex or decimal format)";
                        }
                      }
                      must
                        "../four-byte-as-number-asplain or
                         ../four-byte-as-number-asdot-x";
                      description
                        "ASN4:index (hex or decimal format)";
                    }
                    leaf ipv4-address {
                      type inet:ipv4-address-no-zone;
                      must
                        "../ipv4-address-index and
                         not(../two-byte-as-number or
                             ../four-byte-as-number-asplain or
                             ../four-byte-as-number-asdot-x)";
                      description
                        "IPv4 address";
                    }
                    leaf ipv4-address-index {
                      type uint32 {
                        range "0..65535" {
                          description
                            "IPv4Address:index (hex or decimal format)";
                        }
                      }
                      must "../ipv4-address";
                      description
                        "IPv4Address:index (hex or decimal format)";
                    }
                  }
                  container split-horizon {
                    description
                      "Configure split horizon behaviour";
                    container disable {
                      presence "Indicates a disable node is configured.";
                      description
                        "Disable split horizon";
                    }
                  }
                  container summary-address {
                    description
                      "Summary address";
                    list ip-address {
                      key "address length";
                      description
                        "IPv4 Prefix/length or Prefix and Mask";
                      leaf address {
                        type inet:ipv4-address-no-zone;
                        description
                          "IPv4 Prefix/length or Prefix and Mask";
                      }
                      leaf length {
                        type uint32 {
                          range "0..32";
                        }
                        description
                          "IPv4 Prefix/length or Prefix and Mask";
                      }
                      leaf administrative-distance {
                        type uint32 {
                          range "1..255" {
                            description
                              "Administrative distance";
                          }
                        }
                        mandatory true;
                        description
                          "Administrative distance";
                      }
                    }
                  }
                }
              }
            }
            container ipv6 {
              presence "Indicates a ipv6 node is configured.";
              description
                "IPv6 Address Family";
              leaf autonomous-system {
                type uint32 {
                  range "1..65535" {
                    description
                      "Autonomous system number";
                  }
                }
                description
                  "Set the autonomous system of VRF";
              }
              leaf default-metric {
                type uint32 {
                  range "1..4294967295" {
                    description
                      "Bandwidth in Kbits per second";
                  }
                }
                must "../delay-metric-in-10-microsecond";
                description
                  "Set metric of redistributed routes";
              }
              leaf delay-metric-in-10-microsecond {
                type uint32 {
                  range "1..4294967295" {
                    description
                      "Delay metric, in 10 microsecond units";
                  }
                }
                must "../default-metric";
                must "../reliability-metric";
                description
                  "Delay metric, in 10 microsecond units";
              }
              leaf reliability-metric {
                type uint32 {
                  range "0..255" {
                    description
                      "Reliability metric where 255 is 100% reliable";
                  }
                }
                must "../delay-metric-in-10-microsecond";
                must "../effective-bandwidth-metric";
                description
                  "Reliability metric where 255 is 100% reliable";
              }
              leaf effective-bandwidth-metric {
                type uint32 {
                  range "1..255" {
                    description
                      "Effective bandwidth metric (Loading) where 255 is 100% loaded";
                  }
                }
                must "../reliability-metric";
                must "../maximum-transmission-unit";
                description
                  "Effective bandwidth metric (Loading) where 255 is 100% loaded";
              }
              leaf maximum-transmission-unit {
                type uint32 {
                  range "1..65535" {
                    description
                      "Maximum Transmission Unit metric of the path";
                  }
                }
                must "../effective-bandwidth-metric";
                description
                  "Maximum Transmission Unit metric of the path";
              }
              leaf distance {
                type uint32 {
                  range "1..255" {
                    description
                      "Internal routes' distance";
                  }
                }
                must "../external-routes-distance";
                description
                  "Set distance for EIGRP routes";
              }
              leaf external-routes-distance {
                type uint32 {
                  range "1..255" {
                    description
                      "External routes' distance";
                  }
                }
                must "../distance";
                description
                  "External routes' distance";
              }
              container log-neighbor-changes {
                presence "Indicates a log-neighbor-changes node is configured.";
                description
                  "Enable/Disable EIGRP neighbor logging";
              }
              container log-neighbor-warnings {
                presence "Indicates a log-neighbor-warnings node is configured.";
                description
                  "Enable/Disable EIGRP neighbor warnings";
              }
              leaf maximum-paths {
                type uint32 {
                  range "1..32" {
                    description
                      "number of paths";
                  }
                }
                description
                  "Maximum paths";
              }
              container metric {
                description
                  "Modify EIGRP routing metrics and parameters";
                leaf maximum-hops {
                  type uint32 {
                    range "1..255" {
                      description
                        "Hop count";
                    }
                  }
                  description
                    "Advertise EIGRP routes greater than <hops> as unreachable";
                }
                leaf rib-scale {
                  type uint32 {
                    range "1..255" {
                      description
                        "RIB metric scale-down value ";
                    }
                  }
                  description
                    "Change the value by which the RIB metric is to be scaled down";
                }
                leaf weights {
                  type uint32 {
                    range "0" {
                      description
                        "Type of Service (Only TOS 0 supported)";
                    }
                  }
                  description
                    "EIGRP metric coefficients";
                }
                leaf k1 {
                  type uint32 {
                    range "0..255" {
                      description
                        "K1";
                    }
                  }
                  must "../weights";
                  description
                    "K1";
                }
                leaf k2 {
                  type uint32 {
                    range "0..255" {
                      description
                        "K2";
                    }
                  }
                  must "../k1";
                  description
                    "K2";
                }
                leaf k3 {
                  type uint32 {
                    range "0..255" {
                      description
                        "K3";
                    }
                  }
                  must "../k2";
                  description
                    "K3";
                }
                leaf k4 {
                  type uint32 {
                    range "0..255" {
                      description
                        "K4";
                    }
                  }
                  must "../k3";
                  description
                    "K4";
                }
                leaf k5 {
                  type uint32 {
                    range "0..255" {
                      description
                        "K5";
                    }
                  }
                  must "../k4";
                  description
                    "K5";
                }
                leaf k6 {
                  type uint32 {
                    range "0..255" {
                      description
                        "K6";
                    }
                  }
                  must "../k5";
                  description
                    "K6";
                }
                container version {
                  description
                    "Change the EIGRP metric version";
                  container thirty-two-bit {
                    presence "Indicates a thirty-two-bit node is configured.";
                    description
                      "Change to 32-bit metric version";
                  }
                }
              }
              container nsf {
                description
                  "Address family specific NSF related configuration";
                container disable {
                  presence "Indicates a disable node is configured.";
                  description
                    "Disable NSF for this address family under this VRF";
                }
              }
              container redistribute {
                description
                  "Redistribute another protocol";
                container bgp {
                  description
                    "Border Gateway Protocol (BGP) routes";
                  container ases {
                    description
                      "bgp as-number";
                    list as {
                      key "as-number";
                      description
                        "bgp as-number";
                      leaf as-number {
                        type xr:Bgp-as-number;
                        description
                          "bgp as-number";
                      }
                      leaf route-policy {
                        type xr:Route-policy-name;
                        description
                          "Filter using an RPL policy";
                      }
                    }
                  }
                }
                container connected {
                  presence "Indicates a connected node is configured.";
                  description
                    "Connected routes";
                  leaf route-policy {
                    type xr:Route-policy-name;
                    description
                      "Filter using an RPL policy";
                  }
                }
                container mobile {
                  presence "Indicates a mobile node is configured.";
                  description
                    "Mobile routes";
                  leaf route-policy {
                    type xr:Route-policy-name;
                    description
                      "Filter using an RPL policy";
                  }
                }
                container eigrps {
                  description
                    "EIGRP routes";
                  list eigrp {
                    key "as-number";
                    description
                      "EIGRP routes";
                    leaf as-number {
                      type uint32 {
                        range "1..65535" {
                          description
                            "AS number of the redistributed EIGRP process";
                        }
                      }
                      description
                        "EIGRP routes";
                    }
                    leaf route-policy {
                      type xr:Route-policy-name;
                      description
                        "Filter using an RPL policy";
                    }
                  }
                }
                container isises {
                  description
                    "Intermediate System-to-Intermediate System (IS-IS) routes";
                  list isis {
                    key "instance-name";
                    description
                      "Intermediate System-to-Intermediate System (IS-IS) routes";
                    leaf instance-name {
                      type xr:Cisco-ios-xr-string {
                        length "1..800" {
                          description
                            "ISIS instance name";
                        }
                      }
                      description
                        "Intermediate System-to-Intermediate System (IS-IS) routes";
                    }
                    leaf route-policy {
                      type xr:Route-policy-name;
                      description
                        "Filter using an RPL policy";
                    }
                  }
                }
                container static {
                  presence "Indicates a static node is configured.";
                  description
                    "Static routes";
                  leaf route-policy {
                    type xr:Route-policy-name;
                    description
                      "Filter using an RPL policy";
                  }
                }
                container subscriber {
                  presence "Indicates a subscriber node is configured.";
                  description
                    "Subscriber routes";
                  leaf route-policy {
                    type xr:Route-policy-name;
                    description
                      "Filter using an RPL policy";
                  }
                }
                container applications {
                  description
                    "OnePK application routes";
                  list application {
                    key "application-name";
                    description
                      "OnePK application routes";
                    leaf application-name {
                      type xr:Cisco-ios-xr-string {
                        length "1..800" {
                          description
                            "OnePK application name";
                        }
                      }
                      description
                        "OnePK application routes";
                    }
                    leaf route-policy {
                      type xr:Route-policy-name;
                      description
                        "Filter using an RPL policy";
                    }
                  }
                }
                container ospfv3s {
                  description
                    "IPv6 Open Shortest Path First (OSPFv3) routes";
                  list ospfv3 {
                    key "ospfv3-name";
                    description
                      "IPv6 Open Shortest Path First (OSPFv3) routes";
                    leaf ospfv3-name {
                      type xr:Cisco-ios-xr-string {
                        length "1..800" {
                          description
                            "OSPFv3 instance name";
                        }
                      }
                      description
                        "IPv6 Open Shortest Path First (OSPFv3) routes";
                    }
                    leaf route-policy {
                      type xr:Route-policy-name;
                      description
                        "Filter using an RPL policy";
                    }
                  }
                }
                container rip {
                  presence "Indicates a rip node is configured.";
                  description
                    "Routing Information Protocol (RIP) routes";
                  leaf route-policy {
                    type xr:Route-policy-name;
                    description
                      "Filter using an RPL policy";
                  }
                }
              }
              container passive-interface {
                description
                  "Suppress routing updates on all interfaces";
                container default {
                  presence "Indicates a default node is configured.";
                  description
                    "Interfaces passive by default";
                }
              }
              container route-policy {
                description
                  "Configure inbound/outbound policies";
                leaf in {
                  type xr:Route-policy-name;
                  description
                    "Filter inbound routes";
                }
                leaf out {
                  type xr:Route-policy-name;
                  description
                    "Filter outbound routes";
                }
              }
              leaf router-id {
                type inet:ipv4-address-no-zone;
                description
                  "Set router ID";
              }
              container stub {
                presence "Indicates a stub node is configured.";
                description
                  "EIGRP stub";
                container receive-only {
                  presence "Indicates a receive-only node is configured.";
                  description
                    "Set EIGRP as receive only neighbor";
                }
                container connected {
                  presence "Indicates a connected node is configured.";
                  description
                    "Do advertise connected routes";
                }
                container redistributed {
                  presence "Indicates a redistributed node is configured.";
                  description
                    "Do advertise redistributed routes";
                }
                container static {
                  presence "Indicates a static node is configured.";
                  description
                    "Do advertise static routes";
                }
                container summary {
                  presence "Indicates a summary node is configured.";
                  description
                    "Do advertise summary routes";
                }
              }
              container timers {
                description
                  "Configure EIGRP timers";
                container active-time {
                  description
                    "Configure active time";
                  leaf active-time-limit {
                    type uint32 {
                      range "1..4294967295" {
                        description
                          "Active time limit (in seconds)";
                      }
                    }
                    must "not(../disabled)";
                    description
                      "Active time limit (in seconds)";
                  }
                  container disabled {
                    must "not(../active-time-limit)";
                    presence "Indicates a disabled node is configured.";
                    description
                      "Disable active timer";
                  }
                }
                container nsf {
                  description
                    "Configure NSF timers";
                  leaf route-hold {
                    type uint32 {
                      range "20..6000" {
                        description
                          "Hold time (in seconds)";
                      }
                    }
                    description
                      "Route hold time for inactive peer";
                  }
                  leaf signal {
                    type uint32 {
                      range "10..30" {
                        description
                          "Signal time (in seconds)";
                      }
                    }
                    description
                      "Route signal time";
                  }
                  leaf converge {
                    type uint32 {
                      range "60..5000" {
                        description
                          "Converge time (in seconds)";
                      }
                    }
                    description
                      "Route converge time";
                  }
                }
              }
              leaf variance {
                type uint32 {
                  range "1..128" {
                    description
                      "Metric variance multiplier";
                  }
                }
                description
                  "Control load balancing variance";
              }
              container interfaces {
                description
                  "EIGRP interface configuration submode";
                list interface {
                  key "interface-name";
                  description
                    "EIGRP interface configuration submode";
                  leaf interface-name {
                    type xr:Interface-name;
                    description
                      "EIGRP interface configuration submode";
                  }
                  container authentication {
                    description
                      "Authentication configuration";
                    leaf keychain {
                      type xr:Cisco-ios-xr-string {
                        length "1..800" {
                          description
                            "Authentication keychain name";
                        }
                        pattern "[a-zA-Z0-9@#;:$._-]*";
                      }
                      description
                        "Authentication keychain configuration";
                    }
                  }
                  leaf bandwidth-percent {
                    type uint32 {
                      range "1..999999" {
                        description
                          "Percent";
                      }
                    }
                    description
                      "Bandwidth limit";
                  }
                  container bfd {
                    description
                      "Configure BFD parameters";
                    container fast-detect {
                      presence "Indicates a fast-detect node is configured.";
                      description
                        "Enable BFD fast detection";
                    }
                    leaf minimum-interval {
                      type uint32 {
                        range "15..3000" {
                          description
                            "BFD interval (in milliseconds)";
                        }
                      }
                      description
                        "BFD minimum-interval configuration";
                    }
                    leaf multiplier {
                      type uint32 {
                        range "2..50" {
                          description
                            "BFD multiplier";
                        }
                      }
                      description
                        "BFD multiplier configuration";
                    }
                  }
                  leaf hello-interval {
                    type uint32 {
                      range "1..65535" {
                        description
                          "Interval (in seconds)";
                      }
                    }
                    description
                      "Hello interval";
                  }
                  leaf hold-time {
                    type uint32 {
                      range "1..65535" {
                        description
                          "Neighbor hold time (in seconds)";
                      }
                    }
                    description
                      "Hold Time";
                  }
                  container metric {
                    description
                      "Metric";
                    leaf bandwidth {
                      type uint32 {
                        range "1..4294967295" {
                          description
                            "Bandwidth in Kbits per second";
                        }
                      }
                      description
                        "Interface bandwidth";
                    }
                    leaf delay {
                      type uint32 {
                        range "1..4294967295" {
                          description
                            "Delay metric, in 10 microsecond units";
                        }
                      }
                      description
                        "Interface delay";
                    }
                    container picoseconds {
                      must "../delay";
                      presence "Indicates a picoseconds node is configured.";
                      description
                        "Interpret configured delay to be in picosecond units";
                    }
                    leaf reliability {
                      type uint32 {
                        range "0..255" {
                          description
                            "Reliability metric where 255 is 100% reliable";
                        }
                      }
                      description
                        "Interface reliability";
                    }
                    leaf load {
                      type uint32 {
                        range "1..255" {
                          description
                            "Load metric where 255 is 100% loaded";
                        }
                      }
                      description
                        "Interface load";
                    }
                  }
                  container neighbors {
                    description
                      "Configure Neighbor";
                    list neighbor {
                      key "address";
                      description
                        "Neighbor IPv4 address";
                      leaf address {
                        type inet:ipv6-address-no-zone;
                        description
                          "Neighbor IPv6 address";
                      }
                      leaf remote {
                        type uint32 {
                          range "2..99" {
                            description
                              "Maxhops range";
                          }
                        }
                        description
                          "Configure max-hop count";
                      }
                    }
                  }
                  container remote-neighbor {
                    description
                      "Configure Remote-Neighbor";
                    container unicast-listen {
                      presence "Indicates a unicast-listen node is configured.";
                      description
                        "Configure unicast-listen";
                      leaf allow-list {
                        type xr:Route-policy-name;
                        description
                          "Policy list for allowing neighbors";
                      }
                      leaf max-neighbors {
                        type uint32 {
                          range "1..65535" {
                            description
                              "Max number of neighbors";
                          }
                        }
                        description
                          "Max count of the neighbors allowed";
                      }
                    }
                  }
                  container next-hop-self {
                    description
                      "Configure next-hop-self";
                    container disable {
                      presence "Indicates a disable node is configured.";
                      description
                        "Disable next-hop-self";
                    }
                  }
                  container passive-interface {
                    presence "Indicates a passive-interface node is configured.";
                    description
                      "Suppress routing updates on an interface";
                    container disable {
                      presence "Indicates a disable node is configured.";
                      description
                        "disable";
                    }
                  }
                  container route-policy {
                    description
                      "Configure inbound/outbound policies";
                    leaf in {
                      type xr:Route-policy-name;
                      description
                        "Filter inbound routes";
                    }
                    leaf out {
                      type xr:Route-policy-name;
                      description
                        "Filter outbound routes";
                    }
                  }
                  container site-of-origin {
                    description
                      "Configure Site-of-origin";
                    leaf two-byte-as-number {
                      type uint32 {
                        range "1..65535" {
                          description
                            "2-byte AS number";
                        }
                      }
                      must
                        "../two-byte-as-index and
                         not(../four-byte-as-number-asplain or
                            ../four-byte-as-number-asdot-x or
                             ../ipv4-address)";
                      description
                        "2-byte AS number";
                    }
                    leaf two-byte-as-index {
                      type uint32 {
                        range "0..4294967295" {
                          description
                            "ASN2:index (hex or decimal format)";
                        }
                      }
                      must "../two-byte-as-number";
                      description
                        "ASN2:index (hex or decimal format)";
                    }
                    leaf four-byte-as-number-asplain {
                      type uint32 {
                        range "65536..4294967295" {
                          description
                            "4-byte AS number";
                        }
                      }
                      must
                        "../four-byte-as-index and
                         not(../two-byte-as-number or
                             ../four-byte-as-number-asdot-x or
                             ../ipv4-address)";
                      description
                        "4-byte AS number in asplain format";
                    }
                    leaf four-byte-as-number-asdot-x {
                      type uint32 {
                        range "1..65535" {
                          description
                            "4-byte AS number in asdot x";
                        }
                      }
                      must
                        "../four-byte-as-index and
                         ../four-byte-as-number-asdot-y and
                         not(../four-byte-as-number-asplain or
                             ../two-byte-as-number or
                             ../ipv4-address)";
                      description
                        "4-byte AS number in asdot (X.Y) format";
                    }
                    leaf four-byte-as-number-asdot-y {
                      type uint32 {
                        range "0..65535" {
                          description
                            "4-byte AS number in asdot y";
                        }
                      }
                      must
                        "../four-byte-as-index and
                         ../four-byte-as-number-asdot-x and
                         not(../four-byte-as-number-asplain or
                             ../two-byte-as-number or
                             ../ipv4-address)";
                      description
                        "4-byte AS number in asdot (X.Y) format";
                    }
                    leaf four-byte-as-index {
                      type uint32 {
                        range "0..65535" {
                          description
                            "ASN4:index (hex or decimal format)";
                        }
                      }
                      must
                        "../four-byte-as-number-asplain or
                         ../four-byte-as-number-asdot-x";
                      description
                        "ASN4:index (hex or decimal format)";
                    }
                    leaf ipv4-address {
                      type inet:ipv4-address-no-zone;
                      must
                        "../ipv4-address-index and
                         not(../two-byte-as-number or
                             ../four-byte-as-number-asplain or
                             ../four-byte-as-number-asdot-x)";
                      description
                        "IPv4 address";
                    }
                    leaf ipv4-address-index {
                      type uint32 {
                        range "0..65535" {
                          description
                            "IPv4Address:index (hex or decimal format)";
                        }
                      }
                      must "../ipv4-address";
                      description
                        "IPv4Address:index (hex or decimal format)";
                    }
                  }
                  container split-horizon {
                    description
                      "Configure split horizon behaviour";
                    container disable {
                      presence "Indicates a disable node is configured.";
                      description
                        "Disable split horizon";
                    }
                  }
                  container summary-address {
                    description
                      "Summary address";
                    list ip-address {
                      key "address length";
                      description
                        "IPv6 Prefix/length or Prefix and Mask";
                      leaf address {
                        type inet:ipv6-address-no-zone;
                        description
                          "IPv6 Prefix/length or Prefix and Mask";
                      }
                      leaf length {
                        type uint32 {
                          range "0..128";
                        }
                        description
                          "IPv4 Prefix/length or Prefix and Mask";
                      }
                      leaf administrative-distance {
                        type uint32 {
                          range "1..255" {
                            description
                              "Administrative distance";
                          }
                        }
                        mandatory true;
                        description
                          "Administrative distance";
                      }
                    }
                  }
                }
              }
            }
          }
          container vrfs {
            description
              "EIGRP VRF configuration submode";
            list vrf {
              key "vrf-name";
              description
                "EIGRP VRF configuration submode";
              leaf vrf-name {
                type xr:Cisco-ios-xr-string {
                  length "1..800" {
                    description
                      "VRF name";
                  }
                }
                description
                  "EIGRP VRF configuration submode";
              }
              container address-family {
                description
                  "EIGRP VRF address-family configuration submode";
                container ipv4 {
                  presence "Indicates a ipv4 node is configured.";
                  description
                    "IPv4 Address Family";
                  container auto-summary {
                    presence "Indicates a auto-summary node is configured.";
                    description
                      "Auto summarisation";
                  }
                  leaf autonomous-system {
                    type uint32 {
                      range "1..65535" {
                        description
                          "Autonomous system number";
                      }
                    }
                    description
                      "Set the autonomous system of VRF";
                  }
                  container default-information {
                    description
                      "Handling of default route";
                    container allowed {
                      description
                        "Accept/Advertise a candidate default route";
                      container in {
                        presence "Indicates a in node is configured.";
                        description
                          "Accept candidate default information inbound";
                        leaf route-policy {
                          type xr:Route-policy-name;
                          description
                            "Filter with an RPL policy";
                        }
                      }
                      container out {
                        presence "Indicates a out node is configured.";
                        description
                          "Advertise candidate default information outbound";
                        leaf route-policy {
                          type xr:Route-policy-name;
                          description
                            "Filter with an RPL policy";
                        }
                      }
                    }
                  }
                  leaf default-metric {
                    type uint32 {
                      range "1..4294967295" {
                        description
                          "Bandwidth in Kbits per second";
                      }
                    }
                    must "../delay-metric-in-10-microsecond";
                    description
                      "Set metric of redistributed routes";
                  }
                  leaf delay-metric-in-10-microsecond {
                    type uint32 {
                      range "1..4294967295" {
                        description
                          "Delay metric, in 10 microsecond units";
                      }
                    }
                    must "../default-metric";
                    must "../reliability-metric";
                    description
                      "Delay metric, in 10 microsecond units";
                  }
                  leaf reliability-metric {
                    type uint32 {
                      range "0..255" {
                        description
                          "Reliability metric where 255 is 100% reliable";
                      }
                    }
                    must "../delay-metric-in-10-microsecond";
                    must "../effective-bandwidth-metric";
                    description
                      "Reliability metric where 255 is 100% reliable";
                  }
                  leaf effective-bandwidth-metric {
                    type uint32 {
                      range "1..255" {
                        description
                          "Effective bandwidth metric (Loading) where 255 is 100% loaded";
                      }
                    }
                    must "../reliability-metric";
                    must "../maximum-transmission-unit";
                    description
                      "Effective bandwidth metric (Loading) where 255 is 100% loaded";
                  }
                  leaf maximum-transmission-unit {
                    type uint32 {
                      range "1..65535" {
                        description
                          "Maximum Transmission Unit metric of the path";
                      }
                    }
                    must "../effective-bandwidth-metric";
                    description
                      "Maximum Transmission Unit metric of the path";
                  }
                  leaf distance {
                    type uint32 {
                      range "1..255" {
                        description
                          "Internal routes' distance";
                      }
                    }
                    must "../external-routes-distance";
                    description
                      "Set distance for EIGRP routes";
                  }
                  leaf external-routes-distance {
                    type uint32 {
                      range "1..255" {
                        description
                          "External routes' distance";
                      }
                    }
                    must "../distance";
                    description
                      "External routes' distance";
                  }
                  container log-neighbor-changes {
                    presence "Indicates a log-neighbor-changes node is configured.";
                    description
                      "Enable/Disable EIGRP neighbor logging";
                  }
                  container log-neighbor-warnings {
                    presence "Indicates a log-neighbor-warnings node is configured.";
                    description
                      "Enable/Disable EIGRP neighbor warnings";
                  }
                  leaf maximum-paths {
                    type uint32 {
                      range "1..32" {
                        description
                          "number of paths";
                      }
                    }
                    description
                      "Maximum paths";
                  }
                  container metric {
                    description
                      "Modify EIGRP routing metrics and parameters";
                    leaf maximum-hops {
                      type uint32 {
                        range "1..255" {
                          description
                            "Hop count";
                        }
                      }
                      description
                        "Advertise EIGRP routes greater than <hops> as unreachable";
                    }
                    leaf rib-scale {
                      type uint32 {
                        range "1..255" {
                          description
                            "RIB metric scale-down value ";
                        }
                      }
                      description
                        "Change the value by which the RIB metric is to be scaled down";
                    }
                    leaf weights {
                      type uint32 {
                        range "0" {
                          description
                            "Type of Service (Only TOS 0 supported)";
                        }
                      }
                      description
                        "EIGRP metric coefficients";
                    }
                    leaf k1 {
                      type uint32 {
                        range "0..255" {
                          description
                            "K1";
                        }
                      }
                      must "../weights";
                      description
                        "K1";
                    }
                    leaf k2 {
                      type uint32 {
                        range "0..255" {
                          description
                            "K2";
                        }
                      }
                      must "../k1";
                      description
                        "K2";
                    }
                    leaf k3 {
                      type uint32 {
                        range "0..255" {
                          description
                            "K3";
                        }
                      }
                      must "../k2";
                      description
                        "K3";
                    }
                    leaf k4 {
                      type uint32 {
                        range "0..255" {
                          description
                            "K4";
                        }
                      }
                      must "../k3";
                      description
                        "K4";
                    }
                    leaf k5 {
                      type uint32 {
                        range "0..255" {
                          description
                            "K5";
                        }
                      }
                      must "../k4";
                      description
                        "K5";
                    }
                    leaf k6 {
                      type uint32 {
                        range "0..255" {
                          description
                            "K6";
                        }
                      }
                      must "../k5";
                      description
                        "K6";
                    }
                    container version {
                      description
                        "Change the EIGRP metric version";
                      container thirty-two-bit {
                        presence "Indicates a thirty-two-bit node is configured.";
                        description
                          "Change to 32-bit metric version";
                      }
                    }
                  }
                  container nsf {
                    description
                      "Address family specific NSF related configuration";
                    container disable {
                      presence "Indicates a disable node is configured.";
                      description
                        "Disable NSF for this address family under this VRF";
                    }
                  }
                  container redistribute {
                    description
                      "Redistribute another protocol";
                    container bgp {
                      description
                        "Border Gateway Protocol (BGP) routes";
                      container ases {
                        description
                          "bgp as-number";
                        list as {
                          key "as-number";
                          description
                            "bgp as-number";
                          leaf as-number {
                            type xr:Bgp-as-number;
                            description
                              "bgp as-number";
                          }
                          leaf route-policy {
                            type xr:Route-policy-name;
                            description
                              "Filter using an RPL policy";
                          }
                        }
                      }
                    }
                    container connected {
                      presence "Indicates a connected node is configured.";
                      description
                        "Connected routes";
                      leaf route-policy {
                        type xr:Route-policy-name;
                        description
                          "Filter using an RPL policy";
                      }
                    }
                    container mobile {
                      presence "Indicates a mobile node is configured.";
                      description
                        "Mobile routes";
                      leaf route-policy {
                        type xr:Route-policy-name;
                        description
                          "Filter using an RPL policy";
                      }
                    }
                    container eigrps {
                      description
                        "EIGRP routes";
                      list eigrp {
                        key "as-number";
                        description
                          "EIGRP routes";
                        leaf as-number {
                          type uint32 {
                            range "1..65535" {
                              description
                                "AS number of the redistributed EIGRP process";
                            }
                          }
                          description
                            "EIGRP routes";
                        }
                        leaf route-policy {
                          type xr:Route-policy-name;
                          description
                            "Filter using an RPL policy";
                        }
                      }
                    }
                    container isises {
                      description
                        "Intermediate System-to-Intermediate System (IS-IS) routes";
                      list isis {
                        key "instance-name";
                        description
                          "Intermediate System-to-Intermediate System (IS-IS) routes";
                        leaf instance-name {
                          type xr:Cisco-ios-xr-string {
                            length "1..800" {
                              description
                                "ISIS instance name";
                            }
                          }
                          description
                            "Intermediate System-to-Intermediate System (IS-IS) routes";
                        }
                        leaf route-policy {
                          type xr:Route-policy-name;
                          description
                            "Filter using an RPL policy";
                        }
                      }
                    }
                    container static {
                      presence "Indicates a static node is configured.";
                      description
                        "Static routes";
                      leaf route-policy {
                        type xr:Route-policy-name;
                        description
                          "Filter using an RPL policy";
                      }
                    }
                    container subscriber {
                      presence "Indicates a subscriber node is configured.";
                      description
                        "Subscriber routes";
                      leaf route-policy {
                        type xr:Route-policy-name;
                        description
                          "Filter using an RPL policy";
                      }
                    }
                    container applications {
                      description
                        "OnePK application routes";
                      list application {
                        key "application-name";
                        description
                          "OnePK application routes";
                        leaf application-name {
                          type xr:Cisco-ios-xr-string {
                            length "1..800" {
                              description
                                "OnePK application name";
                            }
                          }
                          description
                            "OnePK application routes";
                        }
                        leaf route-policy {
                          type xr:Route-policy-name;
                          description
                            "Filter using an RPL policy";
                        }
                      }
                    }
                    container ospfs {
                      description
                        "Open Shortest Path First (OSPF) routes";
                      list ospf {
                        key "ospf-name";
                        description
                          "Open Shortest Path First (OSPF) routes";
                        leaf ospf-name {
                          type xr:Cisco-ios-xr-string {
                            length "1..800" {
                              description
                                "OSPF instance name";
                            }
                          }
                          description
                            "Open Shortest Path First (OSPF) routes";
                        }
                        leaf route-policy {
                          type xr:Route-policy-name;
                          description
                            "Filter using an RPL policy";
                        }
                      }
                    }
                    container rip {
                      presence "Indicates a rip node is configured.";
                      description
                        "Routing Information Protocol (RIP) routes";
                      leaf route-policy {
                        type xr:Route-policy-name;
                        description
                          "Filter using an RPL policy";
                      }
                    }
                    leaf maximum-prefix {
                      type uint32 {
                        range "1..4294967295" {
                          description
                            "Number of IP prefixes for maximum-prefix limit";
                        }
                      }
                      description
                        "Maximum number of prefixes redistributed to protocol";
                    }
                    leaf threshold-percentage {
                      type uint32 {
                        range "1..100" {
                          description
                            "Configure threshold percentage for warnings";
                        }
                      }
                      description
                        "Configure threshold percentage for warnings";
                    }
                    container warning-only {
                      must "../threshold-percentage";
                      presence "Indicates a warning-only node is configured.";
                      description
                        "Only a warning is logged when prefix limit is reached";
                      container dampened {
                        presence "Indicates a dampened node is configured.";
                        description
                          "Enable decay penalty to be applied to time period";
                      }
                      leaf reset-time {
                        type uint32 {
                          range "0..4294967295" {
                            description
                              "Reset period (in minutes)";
                          }
                        }
                        description
                          "Time to reset restart count";
                      }
                      leaf restart {
                        type uint32 {
                          range "0..4294967295" {
                            description
                              "Restart period (in minutes)";
                          }
                        }
                        description
                          "Shutdown time after hitting max-prefix limit";
                      }
                      leaf restart-count {
                        type uint32 {
                          range "0..4294967295" {
                            description
                              "Restart count";
                          }
                        }
                        description
                          "Restart count after hitting max-prefix limit";
                      }
                    }
                  }
                  container passive-interface {
                    description
                      "Suppress routing updates on all interfaces";
                    container default {
                      presence "Indicates a default node is configured.";
                      description
                        "Interfaces passive by default";
                    }
                  }
                  container route-policy {
                    description
                      "Configure inbound/outbound policies";
                    leaf in {
                      type xr:Route-policy-name;
                      description
                        "Filter inbound routes";
                    }
                    leaf out {
                      type xr:Route-policy-name;
                      description
                        "Filter outbound routes";
                    }
                  }
                  leaf router-id {
                    type inet:ipv4-address-no-zone;
                    description
                      "Set router ID";
                  }
                  container stub {
                    presence "Indicates a stub node is configured.";
                    description
                      "EIGRP stub";
                    container receive-only {
                      presence "Indicates a receive-only node is configured.";
                      description
                        "Set EIGRP as receive only neighbor";
                    }
                    container connected {
                      presence "Indicates a connected node is configured.";
                      description
                        "Do advertise connected routes";
                    }
                    container redistributed {
                      presence "Indicates a redistributed node is configured.";
                      description
                        "Do advertise redistributed routes";
                    }
                    container static {
                      presence "Indicates a static node is configured.";
                      description
                        "Do advertise static routes";
                    }
                    container summary {
                      presence "Indicates a summary node is configured.";
                      description
                        "Do advertise summary routes";
                    }
                  }
                  container timers {
                    description
                      "Configure EIGRP timers";
                    container active-time {
                      description
                        "Configure active time";
                      leaf active-time-limit {
                        type uint32 {
                          range "1..4294967295" {
                            description
                              "Active time limit (in seconds)";
                          }
                        }
                        must "not(../disabled)";
                        description
                          "Active time limit (in seconds)";
                      }
                      container disabled {
                        must "not(../active-time-limit)";
                        presence "Indicates a disabled node is configured.";
                        description
                          "Disable active timer";
                      }
                    }
                    container nsf {
                      description
                        "Configure NSF timers";
                      leaf route-hold {
                        type uint32 {
                          range "20..6000" {
                            description
                              "Hold time (in seconds)";
                          }
                        }
                        description
                          "Route hold time for inactive peer";
                      }
                      leaf signal {
                        type uint32 {
                          range "10..30" {
                            description
                              "Signal time (in seconds)";
                          }
                        }
                        description
                          "Route signal time";
                      }
                      leaf converge {
                        type uint32 {
                          range "60..5000" {
                            description
                              "Converge time (in seconds)";
                          }
                        }
                        description
                          "Route converge time";
                      }
                    }
                  }
                  leaf variance {
                    type uint32 {
                      range "1..128" {
                        description
                          "Metric variance multiplier";
                      }
                    }
                    description
                      "Control load balancing variance";
                  }
                  leaf maximum-prefix {
                    type uint32 {
                      range "1..4294967295" {
                        description
                          "Number of IP prefixes for maximum-prefix limit";
                      }
                    }
                    description
                      "Maximum number of IP prefixes acceptable in aggregate";
                  }
                  leaf threshold-percentage {
                    type uint32 {
                      range "1..100" {
                        description
                          "Configure threshold percentage for warnings";
                      }
                    }
                    description
                      "Configure threshold percentage for warnings";
                  }
                  container warning-only {
                    must "../threshold-percentage";
                    presence "Indicates a warning-only node is configured.";
                    description
                      "Only a warning is logged when prefix limit is reached";
                    container dampened {
                      presence "Indicates a dampened node is configured.";
                      description
                        "Enable decay penalty to be applied to time period";
                    }
                    leaf reset-time {
                      type uint32 {
                        range "0..4294967295" {
                          description
                            "Reset period (in minutes)";
                        }
                      }
                      description
                        "Time to reset restart count";
                    }
                    leaf restart {
                      type uint32 {
                        range "0..4294967295" {
                          description
                            "Restart period (in minutes)";
                        }
                      }
                      description
                        "Shutdown time after hitting max-prefix limit";
                    }
                    leaf restart-count {
                      type uint32 {
                        range "0..4294967295" {
                          description
                            "Restart count";
                        }
                      }
                      description
                        "Restart count after hitting max-prefix limit";
                    }
                  }
                  container neighbors {
                    description
                      "Neighbor prefix limits configuration";
                    list neighbor {
                      key "address";
                      description
                        "Neighbor IPv4 address";
                      leaf address {
                        type inet:ipv4-address-no-zone;
                        description
                          "Neighbor IPv4 address";
                      }
                      leaf maximum-prefix {
                        type uint32 {
                          range "0..4294967295" {
                            description
                              "Number of IP prefixes for maximum-prefix limit";
                          }
                        }
                        mandatory true;
                        description
                          "Maximum prefixes from this neighbor";
                      }
                      leaf threshold-percentage {
                        type uint32 {
                          range "1..100" {
                            description
                              "Configure threshold percentage for warnings";
                          }
                        }
                        description
                          "Configure threshold percentage for warnings";
                      }
                      container warning-only {
                        presence "Indicates a warning-only node is configured.";
                        description
                          "Only a warning is logged when prefix limit is reached";
                      }
                    }
                    leaf maximum-prefix {
                      type uint32 {
                        range "1..4294967295" {
                          description
                            "Number of IP prefixes for maximum-prefix limit";
                        }
                      }
                      description
                        "Configure maximum prefixes for all neighbors in VRF";
                    }
                    leaf threshold-percentage {
                      type uint32 {
                        range "1..100" {
                          description
                            "Configure threshold percentage for warnings";
                        }
                      }
                      description
                        "Configure threshold percentage for warnings";
                    }
                    container warning-only {
                      must "../threshold-percentage";
                      presence "Indicates a warning-only node is configured.";
                      description
                        "Only a warning is logged when prefix limit is reached";
                      container dampened {
                        presence "Indicates a dampened node is configured.";
                        description
                          "Enable decay penalty to be applied to time period";
                      }
                      leaf reset-time {
                        type uint32 {
                          range "0..4294967295" {
                            description
                              "Reset period (in minutes)";
                          }
                        }
                        description
                          "Time to reset restart count";
                      }
                      leaf restart {
                        type uint32 {
                          range "0..4294967295" {
                            description
                              "Restart period (in minutes)";
                          }
                        }
                        description
                          "Shutdown time after hitting max-prefix limit";
                      }
                      leaf restart-count {
                        type uint32 {
                          range "0..4294967295" {
                            description
                              "Restart count";
                          }
                        }
                        description
                          "Restart count after hitting max-prefix limit";
                      }
                    }
                  }
                  container interfaces {
                    description
                      "EIGRP interface configuration submode";
                    list interface {
                      key "interface-name";
                      description
                        "EIGRP interface configuration submode";
                      leaf interface-name {
                        type xr:Interface-name;
                        description
                          "EIGRP interface configuration submode";
                      }
                      container authentication {
                        description
                          "Authentication configuration";
                        leaf keychain {
                          type xr:Cisco-ios-xr-string {
                            length "1..800" {
                              description
                                "Authentication keychain name";
                            }
                            pattern "[a-zA-Z0-9@#;:$._-]*";
                          }
                          description
                            "Authentication keychain configuration";
                        }
                      }
                      leaf bandwidth-percent {
                        type uint32 {
                          range "1..999999" {
                            description
                              "Percent";
                          }
                        }
                        description
                          "Bandwidth limit";
                      }
                      container bfd {
                        description
                          "Configure BFD parameters";
                        container fast-detect {
                          presence "Indicates a fast-detect node is configured.";
                          description
                            "Enable BFD fast detection";
                        }
                        leaf minimum-interval {
                          type uint32 {
                            range "15..3000" {
                              description
                                "BFD interval (in milliseconds)";
                            }
                          }
                          description
                            "BFD minimum-interval configuration";
                        }
                        leaf multiplier {
                          type uint32 {
                            range "2..50" {
                              description
                                "BFD multiplier";
                            }
                          }
                          description
                            "BFD multiplier configuration";
                        }
                      }
                      leaf hello-interval {
                        type uint32 {
                          range "1..65535" {
                            description
                              "Interval (in seconds)";
                          }
                        }
                        description
                          "Hello interval";
                      }
                      leaf hold-time {
                        type uint32 {
                          range "1..65535" {
                            description
                              "Neighbor hold time (in seconds)";
                          }
                        }
                        description
                          "Hold Time";
                      }
                      container metric {
                        description
                          "Metric";
                        leaf bandwidth {
                          type uint32 {
                            range "1..4294967295" {
                              description
                                "Bandwidth in Kbits per second";
                            }
                          }
                          description
                            "Interface bandwidth";
                        }
                        leaf delay {
                          type uint32 {
                            range "1..4294967295" {
                              description
                                "Delay metric, in 10 microsecond units";
                            }
                          }
                          description
                            "Interface delay";
                        }
                        container picoseconds {
                          must "../delay";
                          presence "Indicates a picoseconds node is configured.";
                          description
                            "Interpret configured delay to be in picosecond units";
                        }
                        leaf reliability {
                          type uint32 {
                            range "0..255" {
                              description
                                "Reliability metric where 255 is 100% reliable";
                            }
                          }
                          description
                            "Interface reliability";
                        }
                        leaf load {
                          type uint32 {
                            range "1..255" {
                              description
                                "Load metric where 255 is 100% loaded";
                            }
                          }
                          description
                            "Interface load";
                        }
                      }
                      container neighbors {
                        description
                          "Configure Neighbor";
                        list neighbor {
                          key "address";
                          description
                            "Neighbor IPv4 address";
                          leaf address {
                            type inet:ipv4-address-no-zone;
                            description
                              "Neighbor IPv4 address";
                          }
                          leaf remote {
                            type uint32 {
                              range "2..99" {
                                description
                                  "Maxhops range";
                              }
                            }
                            description
                              "Configure max-hop count";
                          }
                        }
                      }
                      container remote-neighbor {
                        description
                          "Configure Remote-Neighbor";
                        container unicast-listen {
                          presence "Indicates a unicast-listen node is configured.";
                          description
                            "Configure unicast-listen";
                          leaf allow-list {
                            type xr:Route-policy-name;
                            description
                              "Policy list for allowing neighbors";
                          }
                          leaf max-neighbors {
                            type uint32 {
                              range "1..65535" {
                                description
                                  "Max number of neighbors";
                              }
                            }
                            description
                              "Max count of the neighbors allowed";
                          }
                        }
                      }
                      container next-hop-self {
                        description
                          "Configure next-hop-self";
                        container disable {
                          presence "Indicates a disable node is configured.";
                          description
                            "Disable next-hop-self";
                        }
                      }
                      container passive-interface {
                        presence "Indicates a passive-interface node is configured.";
                        description
                          "Suppress routing updates on an interface";
                        container disable {
                          presence "Indicates a disable node is configured.";
                          description
                            "disable";
                        }
                      }
                      container route-policy {
                        description
                          "Configure inbound/outbound policies";
                        leaf in {
                          type xr:Route-policy-name;
                          description
                            "Filter inbound routes";
                        }
                        leaf out {
                          type xr:Route-policy-name;
                          description
                            "Filter outbound routes";
                        }
                      }
                      container site-of-origin {
                        description
                          "Configure Site-of-origin";
                        leaf two-byte-as-number {
                          type uint32 {
                            range "1..65535" {
                              description
                                "2-byte AS number";
                            }
                          }
                          must
                            "../two-byte-as-index and
                             not(../four-byte-as-number-asplain or
                                ../four-byte-as-number-asdot-x or
                                 ../ipv4-address)";
                          description
                            "2-byte AS number";
                        }
                        leaf two-byte-as-index {
                          type uint32 {
                            range "0..4294967295" {
                              description
                                "ASN2:index (hex or decimal format)";
                            }
                          }
                          must "../two-byte-as-number";
                          description
                            "ASN2:index (hex or decimal format)";
                        }
                        leaf four-byte-as-number-asplain {
                          type uint32 {
                            range "65536..4294967295" {
                              description
                                "4-byte AS number";
                            }
                          }
                          must
                            "../four-byte-as-index and
                             not(../two-byte-as-number or
                                 ../four-byte-as-number-asdot-x or
                                 ../ipv4-address)";
                          description
                            "4-byte AS number in asplain format";
                        }
                        leaf four-byte-as-number-asdot-x {
                          type uint32 {
                            range "1..65535" {
                              description
                                "4-byte AS number in asdot x";
                            }
                          }
                          must
                            "../four-byte-as-index and
                             ../four-byte-as-number-asdot-y and
                             not(../four-byte-as-number-asplain or
                                 ../two-byte-as-number or
                                 ../ipv4-address)";
                          description
                            "4-byte AS number in asdot (X.Y) format";
                        }
                        leaf four-byte-as-number-asdot-y {
                          type uint32 {
                            range "0..65535" {
                              description
                                "4-byte AS number in asdot y";
                            }
                          }
                          must
                            "../four-byte-as-index and
                             ../four-byte-as-number-asdot-x and
                             not(../four-byte-as-number-asplain or
                                 ../two-byte-as-number or
                                 ../ipv4-address)";
                          description
                            "4-byte AS number in asdot (X.Y) format";
                        }
                        leaf four-byte-as-index {
                          type uint32 {
                            range "0..65535" {
                              description
                                "ASN4:index (hex or decimal format)";
                            }
                          }
                          must
                            "../four-byte-as-number-asplain or
                             ../four-byte-as-number-asdot-x";
                          description
                            "ASN4:index (hex or decimal format)";
                        }
                        leaf ipv4-address {
                          type inet:ipv4-address-no-zone;
                          must
                            "../ipv4-address-index and
                             not(../two-byte-as-number or
                                 ../four-byte-as-number-asplain or
                                 ../four-byte-as-number-asdot-x)";
                          description
                            "IPv4 address";
                        }
                        leaf ipv4-address-index {
                          type uint32 {
                            range "0..65535" {
                              description
                                "IPv4Address:index (hex or decimal format)";
                            }
                          }
                          must "../ipv4-address";
                          description
                            "IPv4Address:index (hex or decimal format)";
                        }
                      }
                      container split-horizon {
                        description
                          "Configure split horizon behaviour";
                        container disable {
                          presence "Indicates a disable node is configured.";
                          description
                            "Disable split horizon";
                        }
                      }
                      container summary-address {
                        description
                          "Summary address";
                        list ip-address {
                          key "address length";
                          description
                            "IPv4 Prefix/length or Prefix and Mask";
                          leaf address {
                            type inet:ipv4-address-no-zone;
                            description
                              "IPv4 Prefix/length or Prefix and Mask";
                          }
                          leaf length {
                            type uint32 {
                              range "0..32";
                            }
                            description
                              "IPv4 Prefix/length or Prefix and Mask";
                          }
                          leaf administrative-distance {
                            type uint32 {
                              range "1..255" {
                                description
                                  "Administrative distance";
                              }
                            }
                            mandatory true;
                            description
                              "Administrative distance";
                          }
                        }
                      }
                    }
                  }
                }
                container ipv6 {
                  presence "Indicates a ipv6 node is configured.";
                  description
                    "IPv6 Address Family";
                  leaf autonomous-system {
                    type uint32 {
                      range "1..65535" {
                        description
                          "Autonomous system number";
                      }
                    }
                    description
                      "Set the autonomous system of VRF";
                  }
                  leaf default-metric {
                    type uint32 {
                      range "1..4294967295" {
                        description
                          "Bandwidth in Kbits per second";
                      }
                    }
                    must "../delay-metric-in-10-microsecond";
                    description
                      "Set metric of redistributed routes";
                  }
                  leaf delay-metric-in-10-microsecond {
                    type uint32 {
                      range "1..4294967295" {
                        description
                          "Delay metric, in 10 microsecond units";
                      }
                    }
                    must "../default-metric";
                    must "../reliability-metric";
                    description
                      "Delay metric, in 10 microsecond units";
                  }
                  leaf reliability-metric {
                    type uint32 {
                      range "0..255" {
                        description
                          "Reliability metric where 255 is 100% reliable";
                      }
                    }
                    must "../delay-metric-in-10-microsecond";
                    must "../effective-bandwidth-metric";
                    description
                      "Reliability metric where 255 is 100% reliable";
                  }
                  leaf effective-bandwidth-metric {
                    type uint32 {
                      range "1..255" {
                        description
                          "Effective bandwidth metric (Loading) where 255 is 100% loaded";
                      }
                    }
                    must "../reliability-metric";
                    must "../maximum-transmission-unit";
                    description
                      "Effective bandwidth metric (Loading) where 255 is 100% loaded";
                  }
                  leaf maximum-transmission-unit {
                    type uint32 {
                      range "1..65535" {
                        description
                          "Maximum Transmission Unit metric of the path";
                      }
                    }
                    must "../effective-bandwidth-metric";
                    description
                      "Maximum Transmission Unit metric of the path";
                  }
                  leaf distance {
                    type uint32 {
                      range "1..255" {
                        description
                          "Internal routes' distance";
                      }
                    }
                    must "../external-routes-distance";
                    description
                      "Set distance for EIGRP routes";
                  }
                  leaf external-routes-distance {
                    type uint32 {
                      range "1..255" {
                        description
                          "External routes' distance";
                      }
                    }
                    must "../distance";
                    description
                      "External routes' distance";
                  }
                  container log-neighbor-changes {
                    presence "Indicates a log-neighbor-changes node is configured.";
                    description
                      "Enable/Disable EIGRP neighbor logging";
                  }
                  container log-neighbor-warnings {
                    presence "Indicates a log-neighbor-warnings node is configured.";
                    description
                      "Enable/Disable EIGRP neighbor warnings";
                  }
                  leaf maximum-paths {
                    type uint32 {
                      range "1..32" {
                        description
                          "number of paths";
                      }
                    }
                    description
                      "Maximum paths";
                  }
                  container metric {
                    description
                      "Modify EIGRP routing metrics and parameters";
                    leaf maximum-hops {
                      type uint32 {
                        range "1..255" {
                          description
                            "Hop count";
                        }
                      }
                      description
                        "Advertise EIGRP routes greater than <hops> as unreachable";
                    }
                    leaf rib-scale {
                      type uint32 {
                        range "1..255" {
                          description
                            "RIB metric scale-down value ";
                        }
                      }
                      description
                        "Change the value by which the RIB metric is to be scaled down";
                    }
                    leaf weights {
                      type uint32 {
                        range "0" {
                          description
                            "Type of Service (Only TOS 0 supported)";
                        }
                      }
                      description
                        "EIGRP metric coefficients";
                    }
                    leaf k1 {
                      type uint32 {
                        range "0..255" {
                          description
                            "K1";
                        }
                      }
                      must "../weights";
                      description
                        "K1";
                    }
                    leaf k2 {
                      type uint32 {
                        range "0..255" {
                          description
                            "K2";
                        }
                      }
                      must "../k1";
                      description
                        "K2";
                    }
                    leaf k3 {
                      type uint32 {
                        range "0..255" {
                          description
                            "K3";
                        }
                      }
                      must "../k2";
                      description
                        "K3";
                    }
                    leaf k4 {
                      type uint32 {
                        range "0..255" {
                          description
                            "K4";
                        }
                      }
                      must "../k3";
                      description
                        "K4";
                    }
                    leaf k5 {
                      type uint32 {
                        range "0..255" {
                          description
                            "K5";
                        }
                      }
                      must "../k4";
                      description
                        "K5";
                    }
                    leaf k6 {
                      type uint32 {
                        range "0..255" {
                          description
                            "K6";
                        }
                      }
                      must "../k5";
                      description
                        "K6";
                    }
                    container version {
                      description
                        "Change the EIGRP metric version";
                      container thirty-two-bit {
                        presence "Indicates a thirty-two-bit node is configured.";
                        description
                          "Change to 32-bit metric version";
                      }
                    }
                  }
                  container nsf {
                    description
                      "Address family specific NSF related configuration";
                    container disable {
                      presence "Indicates a disable node is configured.";
                      description
                        "Disable NSF for this address family under this VRF";
                    }
                  }
                  container redistribute {
                    description
                      "Redistribute another protocol";
                    container bgp {
                      description
                        "Border Gateway Protocol (BGP) routes";
                      container ases {
                        description
                          "bgp as-number";
                        list as {
                          key "as-number";
                          description
                            "bgp as-number";
                          leaf as-number {
                            type xr:Bgp-as-number;
                            description
                              "bgp as-number";
                          }
                          leaf route-policy {
                            type xr:Route-policy-name;
                            description
                              "Filter using an RPL policy";
                          }
                        }
                      }
                    }
                    container connected {
                      presence "Indicates a connected node is configured.";
                      description
                        "Connected routes";
                      leaf route-policy {
                        type xr:Route-policy-name;
                        description
                          "Filter using an RPL policy";
                      }
                    }
                    container mobile {
                      presence "Indicates a mobile node is configured.";
                      description
                        "Mobile routes";
                      leaf route-policy {
                        type xr:Route-policy-name;
                        description
                          "Filter using an RPL policy";
                      }
                    }
                    container eigrps {
                      description
                        "EIGRP routes";
                      list eigrp {
                        key "as-number";
                        description
                          "EIGRP routes";
                        leaf as-number {
                          type uint32 {
                            range "1..65535" {
                              description
                                "AS number of the redistributed EIGRP process";
                            }
                          }
                          description
                            "EIGRP routes";
                        }
                        leaf route-policy {
                          type xr:Route-policy-name;
                          description
                            "Filter using an RPL policy";
                        }
                      }
                    }
                    container isises {
                      description
                        "Intermediate System-to-Intermediate System (IS-IS) routes";
                      list isis {
                        key "instance-name";
                        description
                          "Intermediate System-to-Intermediate System (IS-IS) routes";
                        leaf instance-name {
                          type xr:Cisco-ios-xr-string {
                            length "1..800" {
                              description
                                "ISIS instance name";
                            }
                          }
                          description
                            "Intermediate System-to-Intermediate System (IS-IS) routes";
                        }
                        leaf route-policy {
                          type xr:Route-policy-name;
                          description
                            "Filter using an RPL policy";
                        }
                      }
                    }
                    container static {
                      presence "Indicates a static node is configured.";
                      description
                        "Static routes";
                      leaf route-policy {
                        type xr:Route-policy-name;
                        description
                          "Filter using an RPL policy";
                      }
                    }
                    container subscriber {
                      presence "Indicates a subscriber node is configured.";
                      description
                        "Subscriber routes";
                      leaf route-policy {
                        type xr:Route-policy-name;
                        description
                          "Filter using an RPL policy";
                      }
                    }
                    container applications {
                      description
                        "OnePK application routes";
                      list application {
                        key "application-name";
                        description
                          "OnePK application routes";
                        leaf application-name {
                          type xr:Cisco-ios-xr-string {
                            length "1..800" {
                              description
                                "OnePK application name";
                            }
                          }
                          description
                            "OnePK application routes";
                        }
                        leaf route-policy {
                          type xr:Route-policy-name;
                          description
                            "Filter using an RPL policy";
                        }
                      }
                    }
                    container ospfv3s {
                      description
                        "IPv6 Open Shortest Path First (OSPFv3) routes";
                      list ospfv3 {
                        key "ospfv3-name";
                        description
                          "IPv6 Open Shortest Path First (OSPFv3) routes";
                        leaf ospfv3-name {
                          type xr:Cisco-ios-xr-string {
                            length "1..800" {
                              description
                                "OSPFv3 instance name";
                            }
                          }
                          description
                            "IPv6 Open Shortest Path First (OSPFv3) routes";
                        }
                        leaf route-policy {
                          type xr:Route-policy-name;
                          description
                            "Filter using an RPL policy";
                        }
                      }
                    }
                    container rip {
                      presence "Indicates a rip node is configured.";
                      description
                        "Routing Information Protocol (RIP) routes";
                      leaf route-policy {
                        type xr:Route-policy-name;
                        description
                          "Filter using an RPL policy";
                      }
                    }
                    leaf maximum-prefix {
                      type uint32 {
                        range "1..4294967295" {
                          description
                            "Number of IP prefixes for maximum-prefix limit";
                        }
                      }
                      description
                        "Maximum number of prefixes redistributed to protocol";
                    }
                    leaf threshold-percentage {
                      type uint32 {
                        range "1..100" {
                          description
                            "Configure threshold percentage for warnings";
                        }
                      }
                      description
                        "Configure threshold percentage for warnings";
                    }
                    container warning-only {
                      must "../threshold-percentage";
                      presence "Indicates a warning-only node is configured.";
                      description
                        "Only a warning is logged when prefix limit is reached";
                      container dampened {
                        presence "Indicates a dampened node is configured.";
                        description
                          "Enable decay penalty to be applied to time period";
                      }
                      leaf reset-time {
                        type uint32 {
                          range "0..4294967295" {
                            description
                              "Reset period (in minutes)";
                          }
                        }
                        description
                          "Time to reset restart count";
                      }
                      leaf restart {
                        type uint32 {
                          range "0..4294967295" {
                            description
                              "Restart period (in minutes)";
                          }
                        }
                        description
                          "Shutdown time after hitting max-prefix limit";
                      }
                      leaf restart-count {
                        type uint32 {
                          range "0..4294967295" {
                            description
                              "Restart count";
                          }
                        }
                        description
                          "Restart count after hitting max-prefix limit";
                      }
                    }
                  }
                  container passive-interface {
                    description
                      "Suppress routing updates on all interfaces";
                    container default {
                      presence "Indicates a default node is configured.";
                      description
                        "Interfaces passive by default";
                    }
                  }
                  container route-policy {
                    description
                      "Configure inbound/outbound policies";
                    leaf in {
                      type xr:Route-policy-name;
                      description
                        "Filter inbound routes";
                    }
                    leaf out {
                      type xr:Route-policy-name;
                      description
                        "Filter outbound routes";
                    }
                  }
                  leaf router-id {
                    type inet:ipv4-address-no-zone;
                    description
                      "Set router ID";
                  }
                  container stub {
                    presence "Indicates a stub node is configured.";
                    description
                      "EIGRP stub";
                    container receive-only {
                      presence "Indicates a receive-only node is configured.";
                      description
                        "Set EIGRP as receive only neighbor";
                    }
                    container connected {
                      presence "Indicates a connected node is configured.";
                      description
                        "Do advertise connected routes";
                    }
                    container redistributed {
                      presence "Indicates a redistributed node is configured.";
                      description
                        "Do advertise redistributed routes";
                    }
                    container static {
                      presence "Indicates a static node is configured.";
                      description
                        "Do advertise static routes";
                    }
                    container summary {
                      presence "Indicates a summary node is configured.";
                      description
                        "Do advertise summary routes";
                    }
                  }
                  container timers {
                    description
                      "Configure EIGRP timers";
                    container active-time {
                      description
                        "Configure active time";
                      leaf active-time-limit {
                        type uint32 {
                          range "1..4294967295" {
                            description
                              "Active time limit (in seconds)";
                          }
                        }
                        must "not(../disabled)";
                        description
                          "Active time limit (in seconds)";
                      }
                      container disabled {
                        must "not(../active-time-limit)";
                        presence "Indicates a disabled node is configured.";
                        description
                          "Disable active timer";
                      }
                    }
                    container nsf {
                      description
                        "Configure NSF timers";
                      leaf route-hold {
                        type uint32 {
                          range "20..6000" {
                            description
                              "Hold time (in seconds)";
                          }
                        }
                        description
                          "Route hold time for inactive peer";
                      }
                      leaf signal {
                        type uint32 {
                          range "10..30" {
                            description
                              "Signal time (in seconds)";
                          }
                        }
                        description
                          "Route signal time";
                      }
                      leaf converge {
                        type uint32 {
                          range "60..5000" {
                            description
                              "Converge time (in seconds)";
                          }
                        }
                        description
                          "Route converge time";
                      }
                    }
                  }
                  leaf variance {
                    type uint32 {
                      range "1..128" {
                        description
                          "Metric variance multiplier";
                      }
                    }
                    description
                      "Control load balancing variance";
                  }
                  leaf maximum-prefix {
                    type uint32 {
                      range "1..4294967295" {
                        description
                          "Number of IP prefixes for maximum-prefix limit";
                      }
                    }
                    description
                      "Maximum number of IP prefixes acceptable in aggregate";
                  }
                  leaf threshold-percentage {
                    type uint32 {
                      range "1..100" {
                        description
                          "Configure threshold percentage for warnings";
                      }
                    }
                    description
                      "Configure threshold percentage for warnings";
                  }
                  container warning-only {
                    must "../threshold-percentage";
                    presence "Indicates a warning-only node is configured.";
                    description
                      "Only a warning is logged when prefix limit is reached";
                    container dampened {
                      presence "Indicates a dampened node is configured.";
                      description
                        "Enable decay penalty to be applied to time period";
                    }
                    leaf reset-time {
                      type uint32 {
                        range "0..4294967295" {
                          description
                            "Reset period (in minutes)";
                        }
                      }
                      description
                        "Time to reset restart count";
                    }
                    leaf restart {
                      type uint32 {
                        range "0..4294967295" {
                          description
                            "Restart period (in minutes)";
                        }
                      }
                      description
                        "Shutdown time after hitting max-prefix limit";
                    }
                    leaf restart-count {
                      type uint32 {
                        range "0..4294967295" {
                          description
                            "Restart count";
                        }
                      }
                      description
                        "Restart count after hitting max-prefix limit";
                    }
                  }
                  container neighbors {
                    description
                      "Neighbor prefix limits configuration";
                    list neighbor {
                      key "address";
                      description
                        "Neighbor IPv6 address";
                      leaf address {
                        type inet:ipv6-address-no-zone;
                        description
                          "Neighbor IPv6 address";
                      }
                      leaf maximum-prefix {
                        type uint32 {
                          range "0..4294967295" {
                            description
                              "Number of IP prefixes for maximum-prefix limit";
                          }
                        }
                        mandatory true;
                        description
                          "Maximum prefixes from this neighbor";
                      }
                      leaf threshold-percentage {
                        type uint32 {
                          range "1..100" {
                            description
                              "Configure threshold percentage for warnings";
                          }
                        }
                        description
                          "Configure threshold percentage for warnings";
                      }
                      container warning-only {
                        presence "Indicates a warning-only node is configured.";
                        description
                          "Only a warning is logged when prefix limit is reached";
                      }
                    }
                    leaf maximum-prefix {
                      type uint32 {
                        range "1..4294967295" {
                          description
                            "Number of IP prefixes for maximum-prefix limit";
                        }
                      }
                      description
                        "Configure maximum prefixes for all neighbors in VRF";
                    }
                    leaf threshold-percentage {
                      type uint32 {
                        range "1..100" {
                          description
                            "Configure threshold percentage for warnings";
                        }
                      }
                      description
                        "Configure threshold percentage for warnings";
                    }
                    container warning-only {
                      must "../threshold-percentage";
                      presence "Indicates a warning-only node is configured.";
                      description
                        "Only a warning is logged when prefix limit is reached";
                      container dampened {
                        presence "Indicates a dampened node is configured.";
                        description
                          "Enable decay penalty to be applied to time period";
                      }
                      leaf reset-time {
                        type uint32 {
                          range "0..4294967295" {
                            description
                              "Reset period (in minutes)";
                          }
                        }
                        description
                          "Time to reset restart count";
                      }
                      leaf restart {
                        type uint32 {
                          range "0..4294967295" {
                            description
                              "Restart period (in minutes)";
                          }
                        }
                        description
                          "Shutdown time after hitting max-prefix limit";
                      }
                      leaf restart-count {
                        type uint32 {
                          range "0..4294967295" {
                            description
                              "Restart count";
                          }
                        }
                        description
                          "Restart count after hitting max-prefix limit";
                      }
                    }
                  }
                  container interfaces {
                    description
                      "EIGRP interface configuration submode";
                    list interface {
                      key "interface-name";
                      description
                        "EIGRP interface configuration submode";
                      leaf interface-name {
                        type xr:Interface-name;
                        description
                          "EIGRP interface configuration submode";
                      }
                      container authentication {
                        description
                          "Authentication configuration";
                        leaf keychain {
                          type xr:Cisco-ios-xr-string {
                            length "1..800" {
                              description
                                "Authentication keychain name";
                            }
                            pattern "[a-zA-Z0-9@#;:$._-]*";
                          }
                          description
                            "Authentication keychain configuration";
                        }
                      }
                      leaf bandwidth-percent {
                        type uint32 {
                          range "1..999999" {
                            description
                              "Percent";
                          }
                        }
                        description
                          "Bandwidth limit";
                      }
                      container bfd {
                        description
                          "Configure BFD parameters";
                        container fast-detect {
                          presence "Indicates a fast-detect node is configured.";
                          description
                            "Enable BFD fast detection";
                        }
                        leaf minimum-interval {
                          type uint32 {
                            range "15..3000" {
                              description
                                "BFD interval (in milliseconds)";
                            }
                          }
                          description
                            "BFD minimum-interval configuration";
                        }
                        leaf multiplier {
                          type uint32 {
                            range "2..50" {
                              description
                                "BFD multiplier";
                            }
                          }
                          description
                            "BFD multiplier configuration";
                        }
                      }
                      leaf hello-interval {
                        type uint32 {
                          range "1..65535" {
                            description
                              "Interval (in seconds)";
                          }
                        }
                        description
                          "Hello interval";
                      }
                      leaf hold-time {
                        type uint32 {
                          range "1..65535" {
                            description
                              "Neighbor hold time (in seconds)";
                          }
                        }
                        description
                          "Hold Time";
                      }
                      container metric {
                        description
                          "Metric";
                        leaf bandwidth {
                          type uint32 {
                            range "1..4294967295" {
                              description
                                "Bandwidth in Kbits per second";
                            }
                          }
                          description
                            "Interface bandwidth";
                        }
                        leaf delay {
                          type uint32 {
                            range "1..4294967295" {
                              description
                                "Delay metric, in 10 microsecond units";
                            }
                          }
                          description
                            "Interface delay";
                        }
                        container picoseconds {
                          must "../delay";
                          presence "Indicates a picoseconds node is configured.";
                          description
                            "Interpret configured delay to be in picosecond units";
                        }
                        leaf reliability {
                          type uint32 {
                            range "0..255" {
                              description
                                "Reliability metric where 255 is 100% reliable";
                            }
                          }
                          description
                            "Interface reliability";
                        }
                        leaf load {
                          type uint32 {
                            range "1..255" {
                              description
                                "Load metric where 255 is 100% loaded";
                            }
                          }
                          description
                            "Interface load";
                        }
                      }
                      container neighbors {
                        description
                          "Configure Neighbor";
                        list neighbor {
                          key "address";
                          description
                            "Neighbor IPv4 address";
                          leaf address {
                            type inet:ipv6-address-no-zone;
                            description
                              "Neighbor IPv6 address";
                          }
                          leaf remote {
                            type uint32 {
                              range "2..99" {
                                description
                                  "Maxhops range";
                              }
                            }
                            description
                              "Configure max-hop count";
                          }
                        }
                      }
                      container remote-neighbor {
                        description
                          "Configure Remote-Neighbor";
                        container unicast-listen {
                          presence "Indicates a unicast-listen node is configured.";
                          description
                            "Configure unicast-listen";
                          leaf allow-list {
                            type xr:Route-policy-name;
                            description
                              "Policy list for allowing neighbors";
                          }
                          leaf max-neighbors {
                            type uint32 {
                              range "1..65535" {
                                description
                                  "Max number of neighbors";
                              }
                            }
                            description
                              "Max count of the neighbors allowed";
                          }
                        }
                      }
                      container next-hop-self {
                        description
                          "Configure next-hop-self";
                        container disable {
                          presence "Indicates a disable node is configured.";
                          description
                            "Disable next-hop-self";
                        }
                      }
                      container passive-interface {
                        presence "Indicates a passive-interface node is configured.";
                        description
                          "Suppress routing updates on an interface";
                        container disable {
                          presence "Indicates a disable node is configured.";
                          description
                            "disable";
                        }
                      }
                      container route-policy {
                        description
                          "Configure inbound/outbound policies";
                        leaf in {
                          type xr:Route-policy-name;
                          description
                            "Filter inbound routes";
                        }
                        leaf out {
                          type xr:Route-policy-name;
                          description
                            "Filter outbound routes";
                        }
                      }
                      container site-of-origin {
                        description
                          "Configure Site-of-origin";
                        leaf two-byte-as-number {
                          type uint32 {
                            range "1..65535" {
                              description
                                "2-byte AS number";
                            }
                          }
                          must
                            "../two-byte-as-index and
                             not(../four-byte-as-number-asplain or
                                ../four-byte-as-number-asdot-x or
                                 ../ipv4-address)";
                          description
                            "2-byte AS number";
                        }
                        leaf two-byte-as-index {
                          type uint32 {
                            range "0..4294967295" {
                              description
                                "ASN2:index (hex or decimal format)";
                            }
                          }
                          must "../two-byte-as-number";
                          description
                            "ASN2:index (hex or decimal format)";
                        }
                        leaf four-byte-as-number-asplain {
                          type uint32 {
                            range "65536..4294967295" {
                              description
                                "4-byte AS number";
                            }
                          }
                          must
                            "../four-byte-as-index and
                             not(../two-byte-as-number or
                                 ../four-byte-as-number-asdot-x or
                                 ../ipv4-address)";
                          description
                            "4-byte AS number in asplain format";
                        }
                        leaf four-byte-as-number-asdot-x {
                          type uint32 {
                            range "1..65535" {
                              description
                                "4-byte AS number in asdot x";
                            }
                          }
                          must
                            "../four-byte-as-index and
                             ../four-byte-as-number-asdot-y and
                             not(../four-byte-as-number-asplain or
                                 ../two-byte-as-number or
                                 ../ipv4-address)";
                          description
                            "4-byte AS number in asdot (X.Y) format";
                        }
                        leaf four-byte-as-number-asdot-y {
                          type uint32 {
                            range "0..65535" {
                              description
                                "4-byte AS number in asdot y";
                            }
                          }
                          must
                            "../four-byte-as-index and
                             ../four-byte-as-number-asdot-x and
                             not(../four-byte-as-number-asplain or
                                 ../two-byte-as-number or
                                 ../ipv4-address)";
                          description
                            "4-byte AS number in asdot (X.Y) format";
                        }
                        leaf four-byte-as-index {
                          type uint32 {
                            range "0..65535" {
                              description
                                "ASN4:index (hex or decimal format)";
                            }
                          }
                          must
                            "../four-byte-as-number-asplain or
                             ../four-byte-as-number-asdot-x";
                          description
                            "ASN4:index (hex or decimal format)";
                        }
                        leaf ipv4-address {
                          type inet:ipv4-address-no-zone;
                          must
                            "../ipv4-address-index and
                             not(../two-byte-as-number or
                                 ../four-byte-as-number-asplain or
                                 ../four-byte-as-number-asdot-x)";
                          description
                            "IPv4 address";
                        }
                        leaf ipv4-address-index {
                          type uint32 {
                            range "0..65535" {
                              description
                                "IPv4Address:index (hex or decimal format)";
                            }
                          }
                          must "../ipv4-address";
                          description
                            "IPv4Address:index (hex or decimal format)";
                        }
                      }
                      container split-horizon {
                        description
                          "Configure split horizon behaviour";
                        container disable {
                          presence "Indicates a disable node is configured.";
                          description
                            "Disable split horizon";
                        }
                      }
                      container summary-address {
                        description
                          "Summary address";
                        list ip-address {
                          key "address length";
                          description
                            "IPv6 Prefix/length or Prefix and Mask";
                          leaf address {
                            type inet:ipv6-address-no-zone;
                            description
                              "IPv6 Prefix/length or Prefix and Mask";
                          }
                          leaf length {
                            type uint32 {
                              range "0..128";
                            }
                            description
                              "IPv4 Prefix/length or Prefix and Mask";
                          }
                          leaf administrative-distance {
                            type uint32 {
                              range "1..255" {
                                description
                                  "Administrative distance";
                              }
                            }
                            mandatory true;
                            description
                              "Administrative distance";
                          }
                        }
                      }
                    }
                  }
                }
              }
            }
          }
        }
      }
    }
  }
}
