module Cisco-IOS-XR-um-traps-selective-vrf-download-cfg {
  namespace "http://cisco.com/ns/yang/Cisco-IOS-XR-um-traps-selective-vrf-download-cfg";
  prefix um-traps-selective-vrf-download-cfg;

  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps-selective-vrf-download package configuration.
     
     This YANG module augments the
     modules with configuration data.
     
     Copyright (c) 2020-2022 by Cisco Systems, Inc.
     All rights reserved.";

  revision 2022-07-11 {
    description
      "Added missing description statement to nodes";
    semver:module-version "1.0.0";
  }
  revision 2020-09-17 {
    description
      "Initial release";
    semver:module-version "1.0.0";
  }

  augment "/a1:snmp-server/a1:traps" {
    description
      "This augment extends snmp-server traps nodes
       configuration";
    container selective-vrf-download {
      description
        "Enable selective VRF download traps";
      container role-change {
        presence "Indicates a role-change node is configured.";
        description
          "Enable selective VRF download role change traps";
      }
    }
  }
}
