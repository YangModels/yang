module Cisco-IOS-XR-um-if-arp-cfg {
  namespace "http://cisco.com/ns/yang/Cisco-IOS-XR-um-if-arp-cfg";
  prefix um-if-arp-cfg;

  import cisco-semver {
    prefix semver;
  }
  import Cisco-IOS-XR-um-interface-cfg {
    prefix a1;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if arp package configuration.
     
     This YANG module augments the
     modules with configuration data.
     
     Copyright (c) 2019-2024 by Cisco Systems, Inc.
     All rights reserved.";

  revision 2024-09-09 {
    description
      "Added support for ARP EVPN Proxy Partial suppression
       2024-01-11
         Added support for ARP EVPN Proxy Full suppression
       2023-10-11
         Added support for ARP BFD Host Tracking
       2022-09-26
         Added support for ARP DAGR and Cache Limit
       2022-07-11
         Added missing description statement to nodes";
    semver:module-version "1.1.0";
  }
  revision 2019-10-10 {
    description
      "Initial version";
    semver:module-version "1.0.0";
  }

  feature drop-adjacency {
    description
      "Set ARP drop adjacency timeout";
  }

  grouping IF-ARP {
    description
      "Grouping for if-arp";
    container arp {
      description
        "Configure Address Resolution Protocol";
      leaf timeout {
        type uint32 {
          range "30..2144448000" {
            description
              "Seconds";
          }
        }
        description
          "Set ARP cache timeout";
      }
      leaf probe-retries {
        type uint32 {
          range "2..10" {
            description
              "count";
          }
        }
        description
          "Set ARP probe retries on BFD down event";
      }
      leaf probe-interval {
        type uint32 {
          range "30..300" {
            description
              "Time interval in seconds";
          }
        }
        description
          "Set ARP probe retry interval on BFD down event";
      }
      leaf purge-delay {
        type uint32 {
          range "1..65535" {
            description
              "Purge delay in seconds";
          }
        }
        description
          "Delay purging ARP entries when the interface goes down";
      }
      container learning {
        description
          "Configuration for dynamic learning of ARP entries";
        container disable {
          presence "Indicates a disable node is configured.";
          description
            "Disable dynamic learning of ARP entries";
        }
        container local {
          presence "Indicates a local node is configured.";
          description
            "Enable dynamic learning only for local subnet only";
        }
        container solicited {
          presence "Indicates a solicited node is configured.";
          description
            "Enable dynamic learning only for solicited ARP packets";
        }
      }
      container gratuitous {
        description
          "Configure the handling of Gratuitous ARP packets";
        container ignore {
          presence "Indicates a ignore node is configured.";
          description
            "Ignore the receipt of Gratuitous ARP packets";
        }
      }
      container drop-adjacency {
        if-feature "drop-adjacency";
        description
          "Set ARP drop adjacency timeout";
        leaf timeout {
          type uint32 {
            range "900..7200" {
              description
                "Seconds";
            }
          }
          default "3600";
          description
            "Specify timeout";
        }
      }
      leaf cache-limit {
        type uint32 {
          range "0..127999" {
            description
              "Cache Limit value";
          }
        }
        description
          "Set cache limit for ARP entries";
      }
      container evpn-proxy {
        description
          "Proxy ARP for EVPN Remote entries";
        leaf mode {
          type enumeration {
            enum "full-suppression" {
              value 1;
              description
                "Full suppression of ARP with no flooding";
            }
            enum "partial-suppression" {
              value 2;
              description
                "Partial suppression of ARP with flooding";
            }
          }
          description
            "EVPN Proxy mode";
        }
      }
      container dagr {
        description
          "ARP Direct Attached Gateway Redundancy Configuration";
        container peer {
          description
            "Configure DAGR peer";
          container ipv4s {
            description
              "Configure DAGR Peer IPv4 address";
            list ipv4 {
              key "address";
              description
                "Configure DAGR Peer IPv4 address";
              leaf address {
                type inet:ipv4-address-no-zone;
                description
                  "Configure DAGR Peer IPv4 address";
              }
              container route {
                description
                  "Configure DAGR route options";
                container distance {
                  description
                    "Route Distance options";
                  leaf normal {
                    type uint32 {
                      range "0..256" {
                        description
                          "Normal Route distance";
                      }
                    }
                    must "../priority";
                    description
                      "Set normal route distance";
                  }
                  leaf priority {
                    type uint32 {
                      range "0..256" {
                        description
                          "Priority Route distance";
                      }
                    }
                    must "../normal";
                    description
                      "Set priority route distance";
                  }
                }
                container metric {
                  description
                    "Route Metric Options";
                  leaf normal {
                    type uint32 {
                      range "0..256" {
                        description
                          "Normal Route metric";
                      }
                    }
                    must "../priority";
                    description
                      "Set normal route metric";
                  }
                  leaf priority {
                    type uint32 {
                      range "0..256" {
                        description
                          "Priority Route metric";
                      }
                    }
                    must "../normal";
                    description
                      "Set priority route metric";
                  }
                }
              }
              container timers {
                description
                  "DAGR Timer configuration";
                leaf query {
                  type uint32 {
                    range "1..10000" {
                      description
                        "Query timer";
                    }
                  }
                  must "../standby";
                  description
                    "Set query timer value";
                }
                leaf standby {
                  type uint32 {
                    range "1..10000" {
                      description
                        "Standby Query timer";
                    }
                  }
                  must "../query";
                  description
                    "Set Standby Query timer";
                }
              }
              leaf priority-timeout {
                type uint32 {
                  range "1..10000" {
                    description
                      "Query timer";
                  }
                }
                description
                  "DAGR Priority Timeout";
              }
            }
          }
        }
      }
    }
    container proxy-arp {
      presence "Indicates a proxy-arp node is configured.";
      description
        "Enable proxy ARP";
    }
    container local-proxy-arp {
      presence "Indicates a local-proxy-arp node is configured.";
      description
        "Enable local proxy ARP";
    }
    container host-tracking {
      description
        "Enable host-tracking on this BVI";
      container arp {
        presence "Indicates a arp node is configured.";
        description
          "Configure arp host tracking";
        container bfd {
          description
            "Configure BFD parameters";
          container fast-detect {
            presence "Indicates a fast-detect node is configured.";
            description
              "Enable Fast detection";
          }
          leaf minimum-interval {
            type uint32 {
              range "3..30000" {
                description
                  "hello interval in milli-seconds";
              }
            }
            description
              "Hello interval";
          }
          leaf multiplier {
            type uint32 {
              range "2..50" {
                description
                  "Detect multiplier";
              }
            }
            description
              "Detect multiplier";
          }
          leaf source-ip {
            type inet:ipv4-address-no-zone;
            description
              "Set source ip for BFD";
          }
        }
      }
    }
  }

  augment "/a1:interfaces/a1:interface" {
    description
      "This augment extends active nodes configuration";
    uses IF-ARP;
  }
  augment "/a1:interfaces/a1:interface-preconfigure" {
    description
      "This augment extends preconfigured nodes
       configuration";
    uses IF-ARP;
  }
}
