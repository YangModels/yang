submodule Cisco-IOS-XR-ipv4-arp-oper-sub3 {
  belongs-to Cisco-IOS-XR-ipv4-arp-oper {
    prefix Cisco-IOS-XR-ipv4-arp-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-arp package operational data.
     
     Copyright (c) 2013-2025 by Cisco Systems, Inc.
     All rights reserved.";

  revision 2025-02-21 {
    description
      "Added Master Node ID leaf for ARP IDB information
       2024-08-21
         Updated ARP ext-flag enum for EVPN-Sync Immutable flag
       2024-05-30
         Statistics for ARP EVPN Proxy reinjected requests
       2024-01-18
         Statistics for ARP EVPN Proxy responses
       2024-01-08
         Updated ARP state enum / ARP ext-flag enum for EVPN-Remote entry + Immutable flag
       2023-10-03
         Increase in interface name length
       2023-10-01
         Adding support for ARP Host tracking entries
       2022-06-10
         Adding support for displaying counters related to ARP Cache Limit
       2022-06-09
         Adding support for ARP Policer";
    semver:module-version "3.0.0";
  }
  revision 2021-08-17 {
    description
      "Adding support for displaying Last pulse time for Punt and input queue from XIPC";
    semver:module-version "2.1.0";
  }
  revision 2021-02-11 {
    description
      "IOS XR 6.2.3 revision.
       2021-02-04
           IOS XR 6.2.2 revision.
       2020-12-03
           Adding support for displaying client resync time
       2020-04-22
           adding oper schema support, clinet stats update with cnbng.";
    semver:module-version "2.0.0";
  }
  revision 2019-12-11 {
    description
      "adding oper schema support.";
    semver:module-version "1.1.0";
  }
  revision 2019-04-05 {
    description
      "Establish semantic version baseline.";
    semver:module-version "1.0.1";
  }
  revision 2018-11-21 {
    description
      "Fixing backward compatibility error in module.";
  }
  revision 2017-05-01 {
    description
      "Fixing backward compatibility error in module.";
  }
  revision 2016-12-19 {
    description
      "IOS XR 6.2.1 revision.";
  }
  revision 2015-11-09 {
    description
      "IOS XR 6.0 revision.";
  }

  typedef Arp-gmp-bag-entry {
    type enumeration {
      enum "null" {
        value 0;
        description
          "No state";
      }
      enum "static" {
        value 1;
        description
          "Static";
      }
      enum "alias" {
        value 2;
        description
          "Alias";
      }
    }
    description
      "ARP Entry type";
  }

  typedef Arp-gmp-bag-encap {
    type enumeration {
      enum "none" {
        value 0;
        description
          "No encapsulation";
      }
      enum "arpa" {
        value 1;
        description
          "ARPA";
      }
      enum "snap" {
        value 2;
        description
          "SNAP";
      }
      enum "ieee802-1q" {
        value 3;
        description
          "802 1Q";
      }
      enum "srp" {
        value 4;
        description
          "SRP";
      }
      enum "srpa" {
        value 5;
        description
          "SRPA";
      }
      enum "srpb" {
        value 6;
        description
          "SRPB";
      }
    }
    description
      "ARP encapsulation";
  }

  grouping ARP-GMP-INTF-ENTRY {
    description
      "ARP GMP entries associated with an interface";
    container associated-configuration-entry {
      description
        "Configuration entry associated";
      uses ARP-GMP-CONFIG-ENTRY;
    }
    leaf interface-name-xr {
      type xr:Interface-name;
      description
        "Source Interface";
    }
    leaf reference-count {
      type uint32;
      description
        "Number of Route reference";
    }
  }

  grouping ARP-GMP-ROUTE-ENTRY {
    description
      "ARP GMP route entry";
    leaf ip-address {
      type inet:ipv4-address;
      description
        "IP address";
    }
    leaf prefix-length-xr {
      type uint8;
      description
        "IP address length";
    }
    leaf interface-name-xr {
      type xr:Interface-name;
      description
        "Source Interface";
    }
    list interface-name {
      description
        "Interface list";
      leaf entry {
        type xr:Interface-name;
        description
          "Interface list";
      }
    }
  }

  grouping ARP-GMP-CONFIG-ENTRY {
    description
      "ARP GMP configuration entry";
    leaf ip-address {
      type inet:ipv4-address;
      description
        "IP address";
    }
    leaf hardware-address {
      type yang:mac-address;
      description
        "MAC address ";
    }
    leaf encapsulation-type {
      type Arp-gmp-bag-encap;
      description
        "Encap type";
    }
    leaf entry-type {
      type Arp-gmp-bag-entry;
      description
        "Entry type static/alias";
    }
  }

  grouping ARP-GMP-VRF-ENTRY {
    description
      "ARP GMP VRF entry";
    leaf vrf-name-xr {
      type string;
      description
        "VRF Name";
    }
    leaf vrf-id-number {
      type uint32;
      description
        "VRF ID";
    }
    leaf table-id {
      type uint32;
      description
        "IPv4 unicast table ID";
    }
    leaf rsi-handle {
      type uint32;
      description
        "RSI registration handle";
    }
    leaf rsi-handle-high {
      type uint32;
      description
        "RSI registration handle (top 32-bits)";
    }
  }
}
