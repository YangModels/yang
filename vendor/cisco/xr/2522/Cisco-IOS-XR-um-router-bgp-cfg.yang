module Cisco-IOS-XR-um-router-bgp-cfg {
  namespace "http://cisco.com/ns/yang/Cisco-IOS-XR-um-router-bgp-cfg";
  prefix um-router-bgp-cfg;

  import ietf-inet-types {
    prefix inet;
  }
  import Cisco-IOS-XR-um-snmp-server-cfg {
    prefix snmp-server-cfg;
  }
  import Cisco-IOS-XR-um-vrf-cfg {
    prefix vrf-cfg;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco bgp package configuration.
     This YANG module augments and other modules configuration data.
     
     Copyright (c) 2025 by Cisco Systems, Inc., and/or its affiliates.
     All rights reserved.";

  revision 2025-02-17 {
    description
      "Changed rpki server length to 255
       2024-10-17
         Added new ecmp-delay support
       2024-09-18
         Updated with tailf dependency for when statements
       Added support for route-mirroring under bmp
       Added support for default-policy-action-in
       2024-09-04
         Updated model for bgp typedef
       2024-08-06
         Updated model for UM2
       2024-03-10
         Changed prefix-download-delay leaf to prefix-ecmp-delay
       Changed oor-delay leaf to oor-threshold
       2024-02-21
         Update help section of description for neighbor
       2024-02-10
         Added tcp ip-only-preferred
       2024-01-31
         Removed deprecated policy container under route-monitoring
       2024-01-23
         Updated containers for export to vrf allow-imported-vpn
       disable-adv-source-vrf-vni allow backup best-external
       2024-01-18
         BGP neighbor level fast-fallover for both IBGP and EBGP
       2024-01-16
         Added prefix-download-delay
       2023-12-21
         Addpath support to limit additional-paths with additional-paths advertise-limit
       2023-12-13
         Added leaf route-policy under global non-afi container optimal-route-reflection
       2023-12-08
         Updated containers for import from vrf advertise-as-vpn allow backup best-external
       2023-12-03
         Updated sch-pathnames for next-hop-self
       2023-08-04
         Added MPLS-VPN label mode per-vrf-46 option
       2023-07-12
         Support for allocate-secondary-label
       2023-06-05
         Support for local aggregates OC
       2023-05-01
         Added per-vrf-46 segment-routing srv6 alloc mode
       2023-04-18
         1. Added allowconfedas-in leaf
       2. Added nexthop route-policy under vrf leafs
       2023-03-15
         Added segment-routing SRv6 uSID allocate from
       WLIB
       2023-02-27
         Added maximum-paths route-policy and eibgp equal-cost leaf
       2023-02-06
         Added LPTS secure binding leaf
       2023-01-25
         Support for update in error-handling
       2022-12-13
         Support for evpn-link-bandwidth
       2022-12-09
         Added OC-BGP neighbor logging and addpath
       2022-12-08
         1. Added OC-BGP restart timer
       2. Added EVPN host import knobs under AF v4/v6 of
       global VRF.
       2022-11-05
         Updated slow-peer static and dynamic leafs
       2022-10-04
         Added OC-BGP replace-private-as
       2022-09-23
         Added BMP route-monitoring suport for L3VPN inbound post-policy
       and Local RIB,
       Deprecated container policy under route-monitoring
       2022-09-19
         Added EVPN Gateway IP disable
       2022-08-16
         Updated slow-peer feature
       2022-07-14
         Added OC-BGP mtu-discovery
       2022-07-11
         Added missing description statement to nodes
       2022-06-20
         Added delay/startup support under wait-install
       2022-03-03
         Added leaf percentage-threshold-high under bandwidth-aware
       2022-02-18
         Updated maximum-paths ebgp/eibgp and ibgp to remove unused container 'order' and fix pack format
       2021-10-20
         Added force node under sr-policy";
    semver:module-version "5.0.0";
  }
  revision 2021-10-19 {
    description
      "Added leaf flex-algo under container optimal-route-reflection
       2021-09-21
          Added retention under route-policy
       2021-08-27
          Increase maximum-paths ebgp range to 1024,
        Added preference  under rpki/server,
        Added datafile under rpki,
        Added unique-nexthop-check-disable under maximum-paths,
        Added table-version under address-family
       2021-08-23
          Added epe-bgp/labeled-unicast under advertise and epe/backup/enable
        Added deterministic under unequal-cost of maximum-paths
        Added container export under address family
        Added leaf route-policy under srv6/alloc
        Added container bandwidth-aware
        Added leaf route-policy under srv6/alloc of vrfs
        Added node deterministic under unequal-cost of maximum-paths/address family
       2021-07-29
          Removed duplicate enforce-first-as-disable which serve same as enforce-first-as/disable";
    semver:module-version "4.0.0";
  }
  revision 2021-05-31 {
    description
      "Added must statement under list instances router->bgp
       2021-03-15
           Added sr-policy under router-bgp->bgp->bestpath and
         router-bgp->vrf->bgp->bestpath
       2021-02-25
           Added multipath container under vrf->neighbors->address-family
       2021-02-17
           Added must constraints in af-group list
       2021-02-11
           Removed presence statement from match node under eigrp container
       2021-02-10
           Added labeled-unicast under best-external
       2021-02-04
           Added sr-policy under nexthop & igp-metric
       2021-02-03
           Added container option-b-asbr-only
       2020-11-16
           Added srte-metric and validation under nexthop
       2020-11-10
           Added mask-length under local-address-subnet as needed
       2020-10-22
           Added rpki-dropped-only/rpki-tested-only under
         soft-reconfiguration/inbound. Updated must statements accordingly
         to define proper constraints with new nodes.
       2020-09-30
           Added multipath under neighbor address-family
       2020-08-12
           Added route-target container under retain.
         Added per-nexthop-received-label under mode.
         Added appropriate when statements under retain/mode containers.
         Removed per-prefix under vrf as it's not supported.
       2020-08-05
           Added some must statements as needed
       2020-07-30
           Added when statement to local-labeled-route under address-family
         hierarchy and removed one presence statement as needed";
    semver:module-version "3.0.0";
  }
  revision 2020-07-24 {
    description
      "Added internal under remove-private-as. Also added must statements
         under remove-private-as as appropriate.
       2020-06-05
         Removed unused nodes from vrf address-family
         Added constraint to nodes under as-format
       2020-05-17
         (1) Added enable/label-mode under as
         (2) Added srv6 under encapsulation-type
         (3) Added vpnv4/vpnv6/l2vpn nodes under advertise
         (4) Added segment-routing node under neighbors/neighbor/address-family
         (5) Changed integer range of multipath, message-log-buffer-size, purge-time
         (6) Added minimum-ipv6 node under nexthop/resolution/prefix-length
         (7) Changed sysdb path of log node and its chilren
         (8) Changed sysdb path of suppress node and its children
         (9) Added extended-nexthop-encoding node under suppress
         (10) Added update node under neighbor-group/address-families/address-family
         (11) Added retain-nbr-routes under graceful-restart
       
       2020-04-14
         Added rd augment to vrf model
       2020-03-13
         Added corresponding nodes for peer-set-id, adjacencies,
         peer-set and peer-node-sid";
    semver:module-version "2.0.0";
  }
  revision 2019-06-10 {
    description
      "Establish semantic version baseline.";
    semver:module-version "1.0.0";
  }
  revision 2019-03-30 {
    description
      "Initial version";
  }

  typedef Bgp-address-family {
    type enumeration {
      enum "ipv4-unicast" {
        value 0;
        description
          "IPv4 unicast";
      }
      enum "ipv4-multicast" {
        value 1;
        description
          "IPv4 multicast";
      }
      enum "ipv4-labeled-unicast" {
        value 2;
        description
          "IPv4 labeled-unicast";
      }
      enum "ipv4-tunnel" {
        value 3;
        description
          "IPv4 tunnel";
      }
      enum "vpnv4-unicast" {
        value 4;
        description
          "VPNv4 unicast";
      }
      enum "ipv6-unicast" {
        value 5;
        description
          "IPv6 unicast";
      }
      enum "ipv6-multicast" {
        value 6;
        description
          "IPv6 multicast";
      }
      enum "ipv6-labeled-unicast" {
        value 7;
        description
          "IPv6 labeled-unicast";
      }
      enum "vpnv6-unicast" {
        value 8;
        description
          "VPNv6 unicast";
      }
      enum "ipv4-mdt" {
        value 9;
        description
          "IPv4 MDT";
      }
      enum "l2vpn-vpls-vpws" {
        value 10;
        description
          "L2VPN VPLS-VPWS";
      }
      enum "ipv4-rt-filter" {
        value 11;
        description
          "IPv4 rt-filter";
      }
      enum "ipv4-mvpn" {
        value 12;
        description
          "IPv4 MVPN";
      }
      enum "ipv6-mvpn" {
        value 13;
        description
          "IPv6 MVPN";
      }
      enum "l2vpn-evpn" {
        value 14;
        description
          "L2VPN EVPN";
      }
      enum "link-state-link-state" {
        value 15;
        description
          "Link-state link-state";
      }
      enum "vpnv4-multicast" {
        value 16;
        description
          "VPNv4 Multicast";
      }
      enum "vpnv6-multicast" {
        value 17;
        description
          "VPNv6 Multicast";
      }
      enum "ipv4-flowspec" {
        value 18;
        description
          "IPv4 flowspec";
      }
      enum "ipv6-flowspec" {
        value 19;
        description
          "IPv6 flowspec";
      }
      enum "vpnv4-flowspec" {
        value 20;
        description
          "VPNv4 flowspec";
      }
      enum "vpnv6-flowspec" {
        value 21;
        description
          "VPNv6 flowspec";
      }
      enum "l2vpn-mspw" {
        value 22;
        description
          "L2VPN MSPW";
      }
      enum "ipv4-sr-policy" {
        value 23;
        description
          "IPv4 SRPolicy";
      }
      enum "ipv6-sr-policy" {
        value 24;
        description
          "IPv6 SRPolicy";
      }
      enum "all-address-family" {
        value 25;
        description
          "All Address Families";
      }
    }
    description
      "Bgp address family";
  }

  grouping GROUP-SNMP-SERVER-CFG-SNMP-SERVER-TRAPS-BODY {
    description
      "Enable BGP4-MIB and CISCO-BGP4-MIB traps";
    container bgp {
      description
        "Enable BGP4-MIB and CISCO-BGP4-MIB traps";
      container cbgp-two {
        description
          "Enable CISCO-BGP4-MIB v2 traps";
        choice CBGP-TWO {
          description
            "Enable CISCO-BGP4-MIB v2 traps";
          case ENABLE {
            leaf enable {
              type empty;
              description
                "Enable CISCO-BGP4-MIB v2 traps";
            }
          }
          case UPDOWN {
            leaf updown {
              type empty;
              description
                "Enable CISCO-BGP4-MIB v2 up/down traps";
            }
          }
        }
      }
      container enable {
        description
          "Enable BGP4-MIB and CISCO-BGP4-MIB traps";
        choice ENABLE {
          description
            "Enable BGP4-MIB and CISCO-BGP4-MIB traps";
          case CISCO-BGP4-MIB {
            leaf cisco-bgp4-mib {
              type empty;
              description
                "Enable BGP4-MIB and CISCO-BGP4-MIB traps";
            }
          }
          case UPDOWN {
            leaf updown {
              type empty;
              description
                "Enable CISCO-BGP4-MIB v2 up/down traps";
            }
          }
        }
      }
    }
  }

  grouping GROUP-VRF-CFG-RD-BODY {
    description
      "route distinguisher(Used within BGP context to distinguish VRF routes)";
    container rd {
      description
        "route distinguisher(Used within BGP context to distinguish VRF routes)";
      choice RD {
        description
          "route distinguisher(Used within BGP context to distinguish VRF routes)";
        case TWO-BYTE-AS {
          container two-byte-as {
            presence "2-byte AS number";
            description
              "2-byte AS number";
            leaf two-byte-as-number {
              type xr:Bgp-as-number;
              mandatory true;
              description
                "2-byte AS number";
            }
            leaf asn2-index {
              type uint32 {
                range "0..4294967295" {
                  description
                    "ASN2:index (hex or decimal format)";
                }
              }
              mandatory true;
              description
                "ASN2:index (hex or decimal format)";
            }
          }
        }
        case FOUR-BYTE-AS {
          container four-byte-as {
            presence "4-byte AS number in asplain format";
            description
              "4-byte AS number in asplain format";
            leaf four-byte-as-number {
              type xr:Bgp-as-number;
              mandatory true;
              description
                "4-byte AS number in asplain format";
            }
            leaf asn4-index {
              type uint32 {
                range "0..65535" {
                  description
                    "ASN4:index (hex or decimal format)";
                }
              }
              mandatory true;
              description
                "ASN4:index (hex or decimal format)";
            }
          }
        }
        case IPV4-ADDRESS {
          container ipv4-address {
            presence "IPv4 address";
            description
              "IPv4 address";
            leaf address {
              type inet:ipv4-address-no-zone;
              mandatory true;
              description
                "IPv4 address";
            }
            leaf ipv4address-index {
              type uint32 {
                range "0..65535" {
                  description
                    "IPv4Address:index (hex or decimal format)";
                }
              }
              mandatory true;
              description
                "IPv4Address:index (hex or decimal format)";
            }
          }
        }
      }
    }
  }

  grouping GROUP-VRF-CFG-IMPORT-BODY {
    description
      "Grouping for import vrf augment";
    container import {
      description
        "VRF import";
      container from {
        description
          "Import routes from a VRF";
        container vrf {
          must "advertise-as-vpn or allow";
          presence "VRF import";
          description
            "VRF import";
          leaf advertise-as-vpn {
            type empty;
            description
              "Advertise imported routes to PEs";
          }
          container allow {
            description
              "Allow import of paths based on path-types";
            leaf backup {
              type empty;
              description
                "Allow import of backup path";
            }
            leaf best-external {
              type empty;
              description
                "Allow import of best-external path";
            }
          }
        }
        container bridge-domain {
          description
            "VRF import";
          leaf advertise-as-vpn {
            type empty;
            description
              "Advertise local EVPN imported routes to PEs";
          }
        }
        container default-vrf {
          description
            "Import routes from the default VRF";
          leaf route-policy {
            type xr:Route-policy-name;
            description
              "Use route-policy for import filtering";
          }
          leaf advertise-as-vpn {
            type empty;
            must "../route-policy";
            description
              "Advertise imported routes to PEs";
          }
        }
      }
      leaf route-policy {
        type xr:Route-policy-name;
        description
          "Use route-policy for import filtering";
      }
      container route-target {
        description
          "Specify import route target extended communities";
        container two-byte-as-route-targets {
          description
            "two byte as route target";
          list two-byte-as-route-target {
            key "two-byte-as-number asn2-index stitching";
            description
              "2-byte AS number";
            leaf two-byte-as-number {
              type uint32 {
                range "1..65535" {
                  description
                    "2-byte AS number";
                }
              }
              description
                "2-byte AS number";
            }
            leaf asn2-index {
              type uint32 {
                range "0..4294967295" {
                  description
                    "ASN2:index (hex or decimal format)";
                }
              }
              description
                "ASN2:index (hex or decimal format)";
            }
            leaf stitching {
              type enumeration {
                enum "enable" {
                  value 1;
                  description
                    "Enable";
                }
                enum "disable" {
                  value 0;
                  description
                    "Disable";
                }
              }
              description
                "These are stitching RTs";
            }
          }
        }
        container four-byte-as-route-targets {
          description
            "four byte as route target";
          list four-byte-as-route-target {
            key "four-byte-as-number asn4-index stitching";
            description
              "4-byte AS number";
            leaf four-byte-as-number {
              type uint32 {
                range "65536..4294967295" {
                  description
                    "4-byte AS number";
                }
              }
              description
                "4-byte AS number";
            }
            leaf asn4-index {
              type uint32 {
                range "0..65535" {
                  description
                    "ASN4:index (hex or decimal format)";
                }
              }
              description
                "ASN4:index (hex or decimal format)";
            }
            leaf stitching {
              type enumeration {
                enum "enable" {
                  value 1;
                  description
                    "Enable";
                }
                enum "disable" {
                  value 0;
                  description
                    "Disable";
                }
              }
              description
                "These are stitching RTs";
            }
          }
        }
        container ipv4-address-route-targets {
          description
            "ipv4 address route target";
          list ipv4-address-route-target {
            key "ipv4-address ipv4-address-index stitching";
            description
              "ipv4 address route target";
            leaf ipv4-address {
              type inet:ipv4-address-no-zone;
              description
                "IPv4 address";
            }
            leaf ipv4-address-index {
              type uint32 {
                range "0..65535" {
                  description
                    "IPv4Address:index (hex or decimal format)";
                }
              }
              description
                "IPv4Address:index (hex or decimal format)";
            }
            leaf stitching {
              type enumeration {
                enum "enable" {
                  value 1;
                  description
                    "Enable";
                }
                enum "disable" {
                  value 0;
                  description
                    "Disable";
                }
              }
              description
                "These are stitching RTs";
            }
          }
        }
      }
    }
    container export {
      description
        "VRF export";
      container to {
        description
          "Export routes to a VRF";
        container vrf {
          must "allow-imported-vpn or allow";
          presence "VRF export";
          description
            "VRF export";
          container allow-imported-vpn {
            presence "Allow export of imported VPN routes to non-default VRF";
            description
              "Allow export of imported VPN routes to non-default VRF";
            leaf disable-adv-source-vrf-vni {
              type empty;
              description
                "Disable advertisement of source vrf vni for leaked route";
            }
          }
          container allow {
            description
              "Allow export of paths based on path-types";
            leaf backup {
              type empty;
              description
                "Allow Export of backup path";
            }
            leaf best-external {
              type empty;
              description
                "Allow Export of best-external path";
            }
          }
        }
        container default-vrf {
          description
            "Export routes to the default VRF";
          leaf route-policy {
            type xr:Route-policy-name;
            description
              "Use route-policy for export";
          }
          leaf allow-imported-vpn {
            type empty;
            must "../route-policy";
            description
              "Export imported VPN routes to default VRF";
          }
        }
      }
      leaf route-policy {
        type xr:Route-policy-name;
        description
          "Use route-policy for export";
      }
      container route-target {
        description
          "Specify export route target extended communities";
        container two-byte-as-route-targets {
          description
            "two byte as route target";
          list two-byte-as-route-target {
            key "two-byte-as-number asn2-index stitching";
            description
              "2-byte AS number";
            leaf two-byte-as-number {
              type uint32 {
                range "1..65535" {
                  description
                    "2-byte AS number";
                }
              }
              description
                "2-byte AS number";
            }
            leaf asn2-index {
              type uint32 {
                range "0..4294967295" {
                  description
                    "ASN2:index (hex or decimal format)";
                }
              }
              description
                "ASN2:index (hex or decimal format)";
            }
            leaf stitching {
              type enumeration {
                enum "enable" {
                  value 1;
                  description
                    "Enable";
                }
                enum "disable" {
                  value 0;
                  description
                    "Disable";
                }
              }
              description
                "These are stitching RTs";
            }
          }
        }
        container four-byte-as-route-targets {
          description
            "four byte as route target";
          list four-byte-as-route-target {
            key "four-byte-as-number asn4-index stitching";
            description
              "4-byte AS number";
            leaf four-byte-as-number {
              type uint32 {
                range "65536..4294967295" {
                  description
                    "4-byte AS number";
                }
              }
              description
                "4-byte AS number";
            }
            leaf asn4-index {
              type uint32 {
                range "0..65535" {
                  description
                    "ASN4:index (hex or decimal format)";
                }
              }
              description
                "ASN4:index (hex or decimal format)";
            }
            leaf stitching {
              type enumeration {
                enum "enable" {
                  value 1;
                  description
                    "Enable";
                }
                enum "disable" {
                  value 0;
                  description
                    "Disable";
                }
              }
              description
                "These are stitching RTs";
            }
          }
        }
        container ipv4-address-route-targets {
          description
            "ipv4 address route target";
          list ipv4-address-route-target {
            key "ipv4-address ipv4-address-index stitching";
            description
              "ipv4 address route target";
            leaf ipv4-address {
              type inet:ipv4-address-no-zone;
              description
                "IPv4 address";
            }
            leaf ipv4-address-index {
              type uint32 {
                range "0..65535" {
                  description
                    "IPv4Address:index (hex or decimal format)";
                }
              }
              description
                "IPv4Address:index (hex or decimal format)";
            }
            leaf stitching {
              type enumeration {
                enum "enable" {
                  value 1;
                  description
                    "Enable";
                }
                enum "disable" {
                  value 0;
                  description
                    "Disable";
                }
              }
              description
                "These are stitching RTs";
            }
          }
        }
      }
    }
    container advertise {
      description
        "VRF advertise";
      container vpn-imported {
        description
          "imported routes learnt from L3VPN";
        container label-mode {
          description
            "label allocation mode";
          leaf per-vrf {
            type empty;
            description
              "label allocation mode per vrf";
          }
        }
      }
    }
  }

  grouping INSTANCE-AS {
    description
      "Insteance-as";

    grouping NEIGHBOR {
      description
        "Neighbor";
      leaf remote-as {
        type xr:Bgp-as-number;
        description
          "Set remote AS";
      }
      leaf maximum-peers {
        type uint32 {
          range "1..4095" {
            description
              "Maximum number of peers";
          }
        }
        description
          "Maximum dynamic neighbors";
      }
      leaf maximum-prefix-restart-time {
        type uint32 {
          range "1..65535" {
            description
              "(Deprecated in 7.11.1) Maximum prefix restart time (seconds)";
          }
        }
        description
          "(Deprecated in 7.11.1) Restart timer interval";
      }
      leaf remote-as-list {
        type string {
          length "1..1024" {
            description
              "as-list name";
          }
        }
        description
          "Remote as-list configuration";
      }
      container as-path-loopcheck {
        description
          "(Deprecated in 7.11.1) Configure AS Path loop checking";
        leaf out {
          type enumeration {
            enum "enable" {
              value 1;
              description
                "(Deprecated in 7.11.1) Disable as-path loop checking";
            }
            enum "disable" {
              value 2;
              description
                "(Deprecated in 7.11.1) Disable as-path loop checking";
            }
          }
          description
            "For outbound updates";
        }
      }
      container use {
        description
          "Inherit configuration from a group";
        leaf neighbor-group {
          type string {
            length "1..1024" {
              description
                "Neighbor-group name";
            }
          }
          description
            "Inherit configuration from a neighbor-group";
        }
        leaf session-group {
          type string {
            length "1..1024" {
              description
                "Session group name";
            }
          }
          description
            "Inherit address-family independent config from a session-group";
        }
      }
      container advertisement-interval {
        description
          "Minimum interval between sending BGP routing updates";
        leaf advertisement-interval-time-in-seconds {
          type uint32 {
            range "0..600" {
              description
                "time in seconds";
            }
          }
          description
            "time in seconds";
        }
        leaf advertisement-interval-time-in-milliseconds {
          type uint32 {
            range "0..999" {
              description
                "time in milliseconds";
            }
          }
          must "../advertisement-interval-time-in-seconds";
          description
            "time in milliseconds";
        }
      }
      leaf description {
        type string {
          length "1..1024" {
            description
              "Up to 80 characters describing this neighbor";
          }
        }
        description
          "Neighbor specific description";
      }
      container ignore-connected-check {
        presence "Bypass the directly connected nexthop check for single-hop eBGP peering";
        description
          "Bypass the directly connected nexthop check for single-hop eBGP peering";
        leaf inheritance-disable {
          type empty;
          description
            "Prevent ignore-connected-check from being inherited from the parent";
        }
      }
      container ebgp-multihop {
        presence "Allow EBGP neighbors not on directly connected networks";
        description
          "Allow EBGP neighbors not on directly connected networks";
        leaf maximum-hop-count {
          type uint32 {
            range "1..255" {
              description
                "maximum hop count";
            }
          }
          description
            "maximum hop count";
        }
        leaf mpls {
          type empty;
          description
            "Disable BGP MPLS forwarding";
        }
      }
      container tcp {
        description
          "TCP session configuration commands";
        container mss {
          description
            "Maximum Segment Size";
          choice MSS {
            description
              "Maximum Segment Size";
            case TCP-INITIAL-MAXIMUM-SEGMENT-SIZE {
              leaf tcp-initial-maximum-segment-size {
                type uint32 {
                  range "68..10000" {
                    description
                      "TCP initial maximum segment size";
                  }
                }
                description
                  "TCP initial maximum segment size";
              }
            }
            case INHERITANCE-DISABLE {
              leaf inheritance-disable {
                type empty;
                description
                  "Prevent tcp mss from being inherited from the parent";
              }
            }
          }
        }
        container mtu-discovery {
          presence "Enable Path MTU discovery on TCP session";
          description
            "Enable Path MTU discovery on TCP session";
          leaf inheritance-disable {
            type empty;
            description
              "Prevent TCP MTU cfg from being inherited from the parent";
          }
        }
        container ip-only-preferred {
          presence "Prefer to send BGP control plane traffic on IP";
          description
            "Prefer to send BGP control plane traffic on IP";
          leaf inheritance-disable {
            type empty;
            description
              "Do not inherit this configuration from parent group";
          }
        }
      }
      container bmp-activate {
        description
          "Enable BMP logging for this neighbor";
        container servers {
          description
            "Enable BMP connection to particular server";
          list server {
            key "server-number";
            description
              "Enable BMP connection to particular server";
            leaf server-number {
              type uint32 {
                range "1..8" {
                  description
                    "Enable BMP connection to particular server";
                }
              }
              description
                "Enable BMP connection to particular server";
            }
          }
        }
      }
      container bfd {
        description
          "Configure BFD parameters";
        container fast-detect {
          presence "Enable Fast detection";
          description
            "Enable Fast detection";
          leaf strict-mode {
            type empty;
            description
              "(Deprecated) Hold down neighbor session until BFD is up (based on IOS-XR proprietary mechanism)";
          }
          container strict-mode-negotiate {
            presence "Hold down neighbor session until BFD is up (based on strict-mode capability negotiation)";
            description
              "Hold down neighbor session until BFD is up (based on strict-mode capability negotiation)";
            leaf override {
              type empty;
              description
                "Do not bring up neighbor session until BFD up even if strict-mode capability is not received";
            }
          }
          leaf disable {
            type empty;
            description
              "Prevent bfd settings from being inherited from the parent";
          }
        }
        leaf minimum-interval {
          type uint32 {
            range "3..30000" {
              description
                "hello interval in milli-seconds";
            }
          }
          description
            "Hello interval";
        }
        leaf multiplier {
          type uint32 {
            range "2..16" {
              description
                "Detect multiplier";
            }
          }
          description
            "Detect multiplier";
        }
      }
      container keychain {
        description
          "Set keychain based authentication";
        choice KEYCHAIN {
          description
            "Set keychain based authentication";
          case KEYCHAIN-NAME {
            leaf keychain-name {
              type string {
                length "1..32" {
                  description
                    "Name of the key chain - maximum 32 characters";
                }
              }
              description
                "Name of the key chain - maximum 32 characters";
            }
          }
          case INHERITANCE-DISABLE {
            leaf inheritance-disable {
              type empty;
              description
                "Prevent keychain from being inherited from parent";
            }
          }
        }
      }
      container local-as {
        description
          "Specify local AS number";
        choice LOCAL-AS {
          description
            "Specify local AS number";
          case INHERITANCE-DISABLE {
            leaf inheritance-disable {
              type empty;
              description
                "Prevent local AS from being inherited from parent";
            }
          }
          case AS {
            container as {
              description
                "AS number";
              leaf as-number {
                type xr:Bgp-as-number;
                description
                  "AS number";
              }
              container no-prepend {
                must "../as-number";
                presence "Do not prepend local AS to announcements from this neighbor";
                description
                  "Do not prepend local AS to announcements from this neighbor";
                container replace-as {
                  presence "Prepend only local AS to announcements to this neighbor";
                  description
                    "Prepend only local AS to announcements to this neighbor";
                  leaf dual-as {
                    type empty;
                    description
                      "Dual-AS mode";
                  }
                }
              }
            }
          }
        }
      }
      container password {
        description
          "Set a password";
        choice PASSWORD {
          description
            "Set a password";
          case ENCRYPTED {
            leaf encrypted {
              type xr:Proprietary-password;
              description
                "Specifies a password will follow";
            }
          }
          case INHERITANCE-DISABLE {
            leaf inheritance-disable {
              type empty;
              description
                "Prevent password from being inherited from parent";
            }
          }
        }
      }
      container receive-buffer-size {
        description
          "Set socket and BGP receive buffer size";
        leaf receive-buffer-size-number {
          type uint32 {
            range "512..131072" {
              description
                "Receive socket buffer size in bytes";
            }
          }
          description
            "Receive socket buffer size in bytes";
        }
        leaf bgp-read-buffer-size-byte {
          type uint32 {
            range "512..131072" {
              description
                "BGP Read buffer size in bytes";
            }
          }
          must "../receive-buffer-size-number";
          description
            "BGP Read buffer size in bytes";
        }
      }
      container send-buffer-size {
        description
          "Set socket and BGP send buffer size";
        leaf send-buffer-size-number {
          type uint32 {
            range "4096..131072" {
              description
                "Send socket buffer size in bytes";
            }
          }
          description
            "Send socket buffer size in bytes";
        }
        leaf bgp-write-buffer-size-byte {
          type uint32 {
            range "4096..131072" {
              description
                "BGP Write buffer size in bytes";
            }
          }
          must "../send-buffer-size-number";
          description
            "BGP Write buffer size in bytes";
        }
      }
      container fast-fallover {
        presence "Force neighbor to be directly connected. Bring neighbor down if its interface goes down";
        description
          "Force neighbor to be directly connected. Bring neighbor down if its interface goes down";
        leaf inheritance-disable {
          type empty;
          description
            "Prevent this neighbor from inheriting this config from a group it is in";
        }
      }
      container shutdown {
        presence "Administratively shut down this neighbor";
        description
          "Administratively shut down this neighbor";
        leaf inheritance-disable {
          type empty;
          description
            "Prevent this neighbor being shutdown, even if its parent is";
        }
      }
      container timers {
        description
          "BGP per neighbor timers";

        grouping KEEPALIVE-OPTIONS {
          description
            "Keepalive-options";
          choice KEEPALIVE-OPTIONS {
            description
              "Keepalive-options";
            case ZERO {
              leaf zero {
                type empty;
                description
                  "Disable keepalives/hold time";
              }
            }
            case MINIMUM-ACCEPTABLE-HOLDTIME {
              leaf minimum-acceptable-holdtime {
                type uint32 {
                  range "3..65535" {
                    description
                      "Minimum acceptable holdtime from neighbor";
                  }
                }
                description
                  "Minimum acceptable holdtime from neighbor";
              }
            }
          }
        }
        leaf keepalive-interval {
          type uint32 {
            range "0..65535" {
              description
                "Keepalive interval";
            }
          }
          description
            "Keepalive interval";
        }
        choice KEEPALIVE-INTERVAL {
          description
            "Keepalive interval";
          case ZERO {
            container zero {
              must "../keepalive-interval";
              presence "Disable keepalives/hold time";
              description
                "Disable keepalives/hold time";
              uses KEEPALIVE-OPTIONS;
            }
          }
          case HOLDTIME {
            container holdtime {
              must "../keepalive-interval and holdtime-number";
              presence "Holdtime";
              description
                "Holdtime";
              leaf holdtime-number {
                type uint32 {
                  range "3..65535" {
                    description
                      "Holdtime";
                  }
                }
                description
                  "Holdtime";
              }
              uses KEEPALIVE-OPTIONS;
            }
          }
        }
      }
      container local {
        description
          "Configure local parameter";
        container address {
          description
            "use configured local address for bgp peering";
          choice ADDRESS {
            description
              "use configured local address for bgp peering";
            case IP-ADDRESS {
              leaf ip-address {
                type inet:ip-address-no-zone;
                description
                  "IP address";
              }
            }
            case INHERITANCE-DISABLE {
              leaf inheritance-disable {
                type empty;
                description
                  "Prevent local address from being inherited from parent";
              }
            }
          }
        }
      }
      container log {
        description
          "Logging update messages per neighbor";
        container neighbor {
          description
            "Log neighbor state info";
          container changes {
            description
              "Log neighbor state changes";
            choice CHANGES {
              description
                "Log neighbor state changes";
              case DETAIL {
                leaf detail {
                  type empty;
                  description
                    "detail";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
        container message {
          description
            "Logging update/notification messages per neighbor";
          container in {
            description
              "Inbound log messages";
            choice IN {
              description
                "Inbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
          container out {
            description
              "Outbound log messages";
            choice OUT {
              description
                "Outbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
      }
      leaf update-source {
        type xr:Interface-name;
        description
          "Source of routing updates";
      }
      container local-address-subnet {
        presence "Local address subnet of routing updates";
        description
          "Local address subnet of routing updates";
        leaf address {
          type inet:ip-address-no-zone;
          mandatory true;
          description
            "IPaddress";
        }
        leaf address-prefix {
          type uint32 {
            range "0..128";
          }
          mandatory true;
          description
            "IP address prefix";
        }
      }
      container dmz-link-bandwidth {
        presence "Propagate the DMZ link bandwidth";
        description
          "Propagate the DMZ link bandwidth";
        leaf inheritance-disable {
          type empty;
          description
            "Prevent dmz-link-bandwidth from being inherited from the parent";
        }
      }
      container ebgp-recv-extcommunity-dmz {
        presence "Receive extcommunity dmz link bandwidth from ebgp neighbor";
        description
          "Receive extcommunity dmz link bandwidth from ebgp neighbor";
        leaf inheritance-disable {
          type empty;
          description
            "Prevent ebgp-send-community-dmz from being inherited from parent";
        }
      }
      container ebgp-send-extcommunity-dmz {
        presence "Send extended community dmz link bandwidth to ebgp neighbor";
        description
          "Send extended community dmz link bandwidth to ebgp neighbor";
        choice EBGP-SEND-EXTCOMMUNITY-DMZ {
          description
            "Send extended community dmz link bandwidth to ebgp neighbor";
          case CUMULATIVE {
            leaf cumulative {
              type empty;
              description
                "Send cumulative community dmz link bandwidth of all multipaths to ebgp neighbor";
            }
          }
          case INHERITANCE-DISABLE {
            leaf inheritance-disable {
              type empty;
              description
                "Prevent ebgp-send-extcommunity-dmz from being inherited from parent";
            }
          }
        }
      }
      container ttl-security {
        presence "Enable EBGP TTL security";
        description
          "Enable EBGP TTL security";
        leaf inheritance-disable {
          type empty;
          description
            "Prevent ttl-security from being inherited from the parent";
        }
      }
      leaf session-open-mode {
        type enumeration {
          enum "active-only" {
            value 1;
            description
              "Active only";
          }
          enum "passive-only" {
            value 2;
            description
              "Passive only";
          }
          enum "both" {
            value 0;
            description
              "Prevent session-open-mode being inherited from the parent";
          }
        }
        description
          "Establish BGP session using this TCP open mode";
      }
      leaf dscp {
        type union {
          type uint32 {
            range "0..63" {
              description
                "Differentiated services codepoint value";
            }
          }
          type enumeration {
            enum "af11" {
              value 10;
              description
                "Set packets with AF11 dscp (001010)";
            }
            enum "af12" {
              value 12;
              description
                "Set packets with AF12 dscp (001100)";
            }
            enum "af13" {
              value 14;
              description
                "Set packets with AF13 dscp (001110)";
            }
            enum "af21" {
              value 18;
              description
                "Set packets with AF21 dscp (010010)";
            }
            enum "af22" {
              value 20;
              description
                "Set packets with AF22 dscp (010100)";
            }
            enum "af23" {
              value 22;
              description
                "Set packets with AF23 dscp (010110)";
            }
            enum "af31" {
              value 26;
              description
                "Set packets with AF31 dscp (011010)";
            }
            enum "af32" {
              value 28;
              description
                "Set packets with AF32 dscp (011100)";
            }
            enum "af33" {
              value 30;
              description
                "Set packets with AF33 dscp (011110)";
            }
            enum "af41" {
              value 34;
              description
                "Set packets with AF41 dscp (100010)";
            }
            enum "af42" {
              value 36;
              description
                "Set packets with AF42 dscp (100100)";
            }
            enum "af43" {
              value 38;
              description
                "Set packets with AF43 dscp (100110)";
            }
            enum "cs1" {
              value 8;
              description
                "Set packets with CS1(precedence 1) dscp (001000)";
            }
            enum "cs2" {
              value 16;
              description
                "Set packets with CS2(precedence 2) dscp (010000)";
            }
            enum "cs3" {
              value 24;
              description
                "Set packets with CS3(precedence 3) dscp (011000)";
            }
            enum "cs4" {
              value 32;
              description
                "Set packets with CS4(precedence 4) dscp (100000)";
            }
            enum "cs5" {
              value 40;
              description
                "Set packets with CS5(precedence 5) dscp (101000)";
            }
            enum "cs6" {
              value 48;
              description
                "Set packets with CS6(precedence 6) dscp (110000)";
            }
            enum "cs7" {
              value 56;
              description
                "Set packets with CS7(precedence 7) dscp (111000)";
            }
            enum "default" {
              value 0;
              description
                "Set packets with default dscp (000000)";
            }
            enum "ef" {
              value 46;
              description
                "Set packets with EF dscp (101110)";
            }
          }
        }
        description
          "Set IP DSCP (DiffServ CodePoint)";
      }
      leaf precedence {
        type union {
          type uint32 {
            range "0..7" {
              description
                "Precedence value";
            }
          }
          type enumeration {
            enum "critical" {
              value 5;
              description
                "Set packets with critical precedence (5)";
            }
            enum "flash" {
              value 3;
              description
                "Set packets with flash precedence (3)";
            }
            enum "flash-override" {
              value 4;
              description
                "Set packets with flash override precedence (4)";
            }
            enum "immediate" {
              value 2;
              description
                "Set packets with immediate precedence (2)";
            }
            enum "internet" {
              value 6;
              description
                "Set packets with internetwork control precedence (6)";
            }
            enum "network" {
              value 7;
              description
                "Set packets with network control precedence (7)";
            }
            enum "priority" {
              value 1;
              description
                "Set packets with priority precedence (1)";
            }
            enum "routine" {
              value 0;
              description
                "Set packets with routine precedence (0)";
            }
          }
        }
        description
          "Set precedence";
      }
      container capability {
        description
          "Advertise capability to the peer";
        container additional-paths {
          description
            "Additional paths capability";
          container send {
            presence "Additional paths Send capability";
            description
              "Additional paths Send capability";
            leaf disable {
              type empty;
              description
                "Do not advertise additional paths Send capability";
            }
          }
          container receive {
            presence "Additional paths Receive capability";
            description
              "Additional paths Receive capability";
            leaf disable {
              type empty;
              description
                "Do not advertise additional paths Receive capability";
            }
          }
        }
        container suppress {
          description
            "Suppress advertising capability to the peer";
          container all {
            presence "All capabilities";
            description
              "All capabilities";
            leaf inheritance-disable {
              type empty;
              description
                "Do not inherit this configuration from parent group";
            }
          }
          container extended-nexthop-encoding {
            presence "Extended-nexthop-encoding capabilities (IETF RFC 5549)";
            description
              "Extended-nexthop-encoding capabilities (IETF RFC 5549)";
            leaf inheritance-disable {
              type empty;
              description
                "Do not inherit this configuration from parent group";
            }
          }
          container four-byte-as {
            presence "4-byte-as capability";
            description
              "4-byte-as capability";
            leaf inheritance-disable {
              type empty;
              description
                "Prevent capability suppress 4-type-as being inherited from the parent";
            }
          }
        }
      }
      container graceful-restart {
        description
          "Enable graceful restart support for this neighbor";
        container graceful-restart-enable {
          presence "Enable graceful restart support for this neighbor";
          description
            "Enable graceful restart support for this neighbor";
          leaf disable {
            type empty;
            description
              "Disable graceful restart support for this neighbor";
          }
        }
        container helper-only {
          presence "Enable graceful restart in helper-mode only.Forwarding state will not retained in local restart. Peer's routes will ne retained when peer restarts";
          description
            "Enable graceful restart in helper-mode only.Forwarding state will not retained in local restart. Peer's routes will ne retained when peer restarts";
          leaf inheritance-disable {
            type empty;
            description
              "Prevent GR helper-mode cfg from being inherited from the parent";
          }
        }
        leaf restart-time {
          type uint32 {
            range "1..4095" {
              description
                "Max time (seconds)";
            }
          }
          description
            "Restart time advertised to the neighbor";
        }
        leaf stalepath-time {
          type uint32 {
            range "0..4095" {
              description
                "Max time (seconds)";
            }
          }
          description
            "Maximum time to wait for restart of GR capable peer";
        }
      }
      leaf enforce-first-as {
        type enumeration {
          enum "enable" {
            value 1;
            description
              "enable";
          }
          enum "disable" {
            value 0;
            description
              "Do not enforce the first AS for EBGP routes";
          }
        }
        description
          "enforce-first-as";
      }
      container cluster-id {
        description
          "Enter cluster id for this neighbor";
        choice CLUSTER-ID {
          description
            "Enter cluster id for this neighbor";
          case ROUTE-REFLECTOR-NUMBER {
            leaf route-reflector-number {
              type uint32 {
                range "1..4294967295" {
                  description
                    "Route-Reflector Cluster-id as 32 bit quantity";
                }
              }
              description
                "Route-Reflector Cluster-id as 32 bit quantity";
            }
          }
          case ROUTE-REFLECTOR-IP-ADDRESS {
            leaf route-reflector-ip-address {
              type inet:ipv4-address-no-zone;
              description
                "Route-Reflector Cluster-id in IP address format";
            }
          }
        }
      }
      leaf idle-watch-time {
        type uint32 {
          range "30..1800" {
            description
              "Max time (seconds)";
          }
        }
        description
          "Maximum time to wait for deletion of IDLE state dynamic peer";
      }
      container allowas-in {
        description
          "Allow as-path with my AS present in it";
        leaf number-of-occurrences-of-as-number {
          type uint32 {
            range "1..10" {
              description
                "Number of occurrences of AS number";
            }
          }
          description
            "Number of occurrences of AS number";
        }
      }
      container egress-engineering {
        presence "Enable egress peer engineering for this neighbor";
        description
          "Enable egress peer engineering for this neighbor";
        leaf inheritance-disable {
          type empty;
          description
            "Do not inherit egress-engineering from the parent";
        }
      }
      container peer-set {
        description
          "Assign this neighbor to a peer-set used for egress peer engineering";
        list peer-sets {
          key "peer";
          description
            "Assign this neighbor to a peer-set used for egress peer engineering";
          leaf peer {
            type uint32 {
              range "1..255" {
                description
                  "Identity value of peer-set";
              }
            }
            description
              "Identity value of peer-set";
          }
        }
      }
      container peer-node-sid {
        description
          "Assign this neighbor a manual SID for egress peer engineering";
        leaf index {
          type uint32 {
            range "0..1033575" {
              description
                "Segment Index to be assigned to this peer. The index will be off SRLB
                 Note: This is the maximum index configurable in dynaminc SRLB range.
                 Since SRLB can be a dynamic range, actual maximum index can vary.
                 So please look at the currently configured SRLB range";
            }
          }
          description
            "Segment Index value which is offset of SRLB";
        }
      }
      container ao {
        description
          "Enable Authentiation Option";
        choice AO {
          description
            "Enable Authentiation Option";
          case KEY-CHAIN-NAME {
            container key-chain-name {
              presence "Name of the key chain - maximum 32 characters";
              description
                "Name of the key chain - maximum 32 characters";
              leaf key-chain-name {
                type string {
                  length "1..32" {
                    description
                      "Name of the key chain - maximum 32 characters";
                  }
                }
                mandatory true;
                description
                  "Name of the key chain - maximum 32 characters";
              }
              leaf include-tcp-options {
                type enumeration {
                  enum "enable" {
                    value 1;
                    description
                      "Include other TCP options in the header";
                  }
                  enum "disable" {
                    value 0;
                    description
                      "Exclude other TCP options in the header";
                  }
                }
                mandatory true;
                description
                  "Include/Exclude other TCP options in the header";
              }
              leaf accept-ao-mismatch-connection {
                type empty;
                description
                  "Accept new connection even if AO mismatched";
              }
            }
          }
          case INHERITANCE-DISABLE {
            leaf inheritance-disable {
              type empty;
              description
                "Prevent keychain from being inherited from parent";
            }
          }
        }
      }
      leaf dampening {
        type enumeration {
          enum "enable" {
            value 1;
            description
              "(Deprecated in 7.11.1) Enable route-flap-damping";
          }
          enum "disable" {
            value 2;
            description
              "(Deprecated in 7.11.1) Enable route-flap-damping";
          }
        }
        description
          "(Deprecated in 7.11.1) Enable route-flap-damping";
      }
      leaf as-override {
        type enumeration {
          enum "enable" {
            value 1;
            description
              "(Deprecated in 7.11.1) Override matching AS-number while sending update";
          }
          enum "disable" {
            value 2;
            description
              "(Deprecated in 7.11.1) Override matching AS-number while sending update";
          }
        }
        description
          "(Deprecated in 7.11.1) Override matching AS-number while sending update";
      }
      container default-policy-action {
        description
          "Set a default action if a route does not satify the policy definition";
        leaf in {
          type enumeration {
            enum "accept" {
              value 1;
              description
                "accept the route if does not satisfy the inbound policy";
            }
            enum "reject" {
              value 2;
              description
                "reject the route if does not satisfy the inbound policy";
            }
          }
          description
            "Default action if route does not satisfy inbound route-policy";
        }
        leaf out {
          type enumeration {
            enum "accept" {
              value 1;
              description
                "accept the route if does not satisfy the outbound policy";
            }
            enum "reject" {
              value 2;
              description
                "reject the route if does not satisfy the outbound policy";
            }
          }
          description
            "Default action if route does not satisfy outbound route-policy";
        }
      }
      container origin-as {
        description
          "BGP origin-AS knobs";
        container validation {
          description
            "BGP origin-AS validation knobs";
          leaf disable {
            type empty;
            description
              "Disable RPKI origin-AS validation";
          }
        }
      }
      container send-community-ebgp {
        presence "Send community attribute to this external neighbor";
        description
          "Send community attribute to this external neighbor";
        leaf inheritance-disable {
          type empty;
          description
            "Prevent send-community-ebgp from being inherited from the parent";
        }
      }
      container send-extended-community-ebgp {
        presence "Send extended community attribute to this external neighbor";
        description
          "Send extended community attribute to this external neighbor";
        leaf inheritance-disable {
          type empty;
          description
            "Prevent send-extended-community-ebgp from being inherited from parent";
        }
      }
      container bestpath {
        description
          "Change default route selection criteria";
        container origin-as {
          description
            "BGP origin-AS knobs";
          container allow {
            description
              "BGP origin-AS knobs";
            leaf invalid {
              type empty;
              description
                "BGP bestpath selection will allow 'invalid' origin-AS";
            }
          }
        }
      }
      container update {
        description
          "BGP Update configuration";
        container in {
          description
            "Inbound update message handling";
          container filtering {
            presence "Inbound update message filtering";
            description
              "Inbound update message filtering";
            container message {
              description
                "Filtered update messages";
              container buffers {
                presence "Filtered update message buffers";
                description
                  "Filtered update message buffers";
                leaf buffers-number {
                  type uint32 {
                    range "0..25" {
                      description
                        "Number of buffers to store filtered update messages (resizing does not take effect after filtering action has started)";
                    }
                  }
                  mandatory true;
                  description
                    "Number of buffers to store filtered update messages (resizing does not take effect after filtering action has started)";
                }
                leaf buffer-list {
                  type enumeration {
                    enum "buffers-number-enable" {
                      value 0;
                      description
                        "buffers-number-enable";
                    }
                    enum "non-circular" {
                      value 1;
                      description
                        "Message buffer list is not circular";
                    }
                  }
                  mandatory true;
                  description
                    "buffer-list";
                }
              }
            }
            container logging {
              description
                "Update filtering syslog message";
              leaf disable {
                type empty;
                description
                  "Disable update filtering syslog message";
              }
            }
            container attribute-filter {
              description
                "Attribute-filter configuration";
              leaf group {
                type string {
                  length "1..1024" {
                    description
                      "Attribute-filter group name";
                  }
                }
                description
                  "Attribute-filter group configuration";
              }
            }
          }
          container labeled-unicast {
            description
              "IPv4/IPv6 labeled-unicast inbound updates (paths)";
            container equivalent {
              presence "IPv4/IPv6 labeled-unicast inbound updates (paths) treated equivalent to unicast updates (paths)";
              description
                "IPv4/IPv6 labeled-unicast inbound updates (paths) treated equivalent to unicast updates (paths)";
              leaf inheritance-disable {
                type empty;
                description
                  "Do not inherit this configuration from parent group";
              }
            }
          }
          container error-handling {
            description
              "Inbound update message error handling";
            choice ERROR-HANDLING {
              description
                "Inbound update message error handling";
              case AVOID-RESET {
                leaf avoid-reset {
                  type enumeration {
                    enum "enable" {
                      value 1;
                      description
                        "avoid-reset-enable";
                    }
                    enum "disable" {
                      value 0;
                      description
                        "Neighbor may be reset during inbound update message error handling";
                    }
                  }
                  description
                    "Avoid neighbor reset during inbound update message error handling";
                }
              }
              case TREAT-AS-WITHDRAW {
                leaf treat-as-withdraw {
                  type enumeration {
                    enum "enable" {
                      value 1;
                      description
                        "(Deprecated in 7.11.1) Treat NLRIs as withdraws during inbound update message error handling";
                    }
                    enum "disable" {
                      value 0;
                      description
                        "(Deprecated in 7.11.1) Treat NLRIs as withdraws during inbound update message error handling";
                    }
                  }
                  description
                    "(Deprecated in 7.11.1) Treat NLRIs as withdraws during inbound update message error handling";
                }
              }
            }
          }
        }
      }
      container graceful-maintenance {
        presence
          "Attributes for Graceful Maintenance. This will cause
           neighbors to de-prefer routes from this router andn
           hoose alternates. This allows the router to be
           brought in or out of service gracefully.";
        description
          "Attributes for Graceful Maintenance. This will cause
           neighbors to de-prefer routes from this router andn
           hoose alternates. This allows the router to be
           brought in or out of service gracefully.";
        container local-preference {
          description
            "local preference with which to advertise routes tonibgp neigbors. Default=No Touch";
          choice LOCAL-PREFERENCE {
            description
              "local preference with which to advertise routes tonibgp neigbors. Default=No Touch";
            case LOCAL-PREFERENCE-NUMBER {
              leaf local-preference-number {
                type uint32 {
                  range "0..4294967295" {
                    description
                      "Range of values for Local Preference";
                  }
                }
                description
                  "Range of values for Local Preference";
              }
            }
            case INHERITANCE-DISABLE {
              leaf inheritance-disable {
                type empty;
                description
                  "Prevent local preference from being inherited from the parent";
              }
            }
          }
        }
        container as-prepends {
          description
            "Number of times to prepend the local AS number to thenAS path of routes. Default=0";
          choice AS-PREPENDS {
            description
              "Number of times to prepend the local AS number to thenAS path of routes. Default=0";
            case PREPENDS-NUMBER {
              leaf prepends-number {
                type uint32 {
                  range "0..6" {
                    description
                      "Range of number of AS prepends";
                  }
                }
                description
                  "Range of number of AS prepends";
              }
            }
            case INHERITANCE-DISABLE {
              leaf inheritance-disable {
                type empty;
                description
                  "Prevent AS prepends from being inherited from the parent";
              }
            }
          }
        }
        container activate {
          presence
            "Routes will be announced with the graceful maintenance
             attributes while activated either here or under router
             bgp configuration. While activated, all routes to this
             neighbor will be announced with the attributes
             configured here and all routes from this neighbor will
             be announced to other neighbors with the graceful
             maintenance attributes configured under those
             neighbors. The g-shut community will be announced
             regardless of the other attributes configured here. To
             allow the g-shut community to be announced to ebgp
             neighbors, the send-community-gshut-ebgp configuration
             is also required. Note: changes to the attributes will
             not take effect while activated.";
          description
            "Routes will be announced with the graceful maintenance
             attributes while activated either here or under router
             bgp configuration. While activated, all routes to this
             neighbor will be announced with the attributes
             configured here and all routes from this neighbor will
             be announced to other neighbors with the graceful
             maintenance attributes configured under those
             neighbors. The g-shut community will be announced
             regardless of the other attributes configured here. To
             allow the g-shut community to be announced to ebgp
             neighbors, the send-community-gshut-ebgp configuration
             is also required. Note: changes to the attributes will
             not take effect while activated.";
          leaf inheritance-disable {
            type empty;
            description
              "Prevent activate from being inherited from the parent";
          }
        }
        container bandwidth-aware {
          description
            "Session interface Bandwidth based Graceful-Maintenance
             Only restricted to eBGP directly connected, this will
             enable Graceful maintenance whenever the link effective
             bandwidth goes below a configurable low-threshold and deactivates
             based on effective bandwidth reaches the high-threshold
             or low-threshold if high-threshold is not configured";
          choice BANDWIDTH-AWARE {
            description
              "Session interface Bandwidth based Graceful-Maintenance
               Only restricted to eBGP directly connected, this will
               enable Graceful maintenance whenever the link effective
               bandwidth goes below a configurable low-threshold and deactivates
               based on effective bandwidth reaches the high-threshold
               or low-threshold if high-threshold is not configured";
            case PERCENTAGE-THRESHOLD {
              container percentage-threshold {
                presence "Threshold in Percentage of Effective Bandwidth nover Maximum Bandwidth";
                description
                  "Threshold in Percentage of Effective Bandwidth nover Maximum Bandwidth";
                leaf percentage-threshold-number {
                  type uint32 {
                    range "1..100" {
                      description
                        "Low threshold of effective bandwidth
                         (in percentage of max bandwidth) to enter/exit
                         graceful-maintenance";
                    }
                  }
                  mandatory true;
                  description
                    "Low threshold of effective bandwidth (in kbps)
                     to enter/exit graceful-maintenance";
                }
                leaf optional-high-threshold {
                  type uint32 {
                    range "1..100" {
                      description
                        "Optional High threshold of effective bandwidth
                         (in kbps) to exit graceful-maintenance";
                    }
                  }
                  description
                    "Optional High threshold of effective bandwidth
                     (in kbps) to exit graceful-maintenance";
                }
              }
            }
            case INHERITANCE-DISABLE {
              leaf inheritance-disable {
                type empty;
                description
                  "Prevent bandwidth-aware from being inherited from the parent";
              }
            }
            case BANDWIDTH-THRESHOLD {
              container bandwidth-threshold {
                presence "Bandwidth based threshold detection in kbps";
                description
                  "Bandwidth based threshold detection in kbps";
                leaf bandwidth-threshold-number {
                  type uint32 {
                    range "1..4294967295" {
                      description
                        "Low threshold of effective bandwidth (in kbps)
                         to enter/exit graceful-maintenance";
                    }
                  }
                  mandatory true;
                  description
                    "Low threshold of effective bandwidth (in kbps)
                     to enter/exit graceful-maintenance";
                }
                leaf optional-high-threshold-number {
                  type uint32 {
                    range "1..4294967295" {
                      description
                        "Optional High threshold of effective bandwidth
                         (in kbps) to exit graceful-maintenance";
                    }
                  }
                  description
                    "Optional High threshold of effective bandwidth
                     (in kbps) to exit graceful-maintenance";
                }
              }
            }
          }
        }
      }
      container address-families {
        description
          "Enter Address Family command mode";
        list address-family {
          key "af-name";
          description
            "Enter Address Family command mode";
          leaf af-name {
            type Bgp-address-family;
            description
              "Enter Address Family command mode";
          }
          uses ADDRESS-FAMILY;
        }
      }
    }

    grouping ADDRESS-FAMILY {
      description
        "Address-family";
      container use {
        description
          "Inherit configuration for this address-family from a group";
        leaf af-group {
          type string {
            length "1..1024" {
              description
                "AF group name";
            }
          }
          description
            "Inherit configuration for this address-family from an af-group";
        }
      }
      container capability {
        description
          "Advertise capability to the peer";
        container orf {
          description
            "Advertise ORF capability to the peer";
          container prefix {
            description
              "Advertise address prefix ORF capability to this neighbor";
            leaf capability-receive-orf-neighbor {
              type enumeration {
                enum "receive" {
                  value 1;
                  description
                    "Capability to RECEIVE the ORF from this neighbor";
                }
                enum "send" {
                  value 2;
                  description
                    "Capability to SEND the ORF to this neighbor";
                }
                enum "both" {
                  value 3;
                  description
                    "Capability to RECEIVE and SEND the ORF from/to this neighbor";
                }
                enum "none" {
                  value 0;
                  description
                    "No capability to RECEIVE or SEND the ORF from/to this neighbor";
                }
              }
              description
                "Capability to RECEIVE the ORF from this neighbor";
            }
          }
        }
      }
      container additional-paths {
        description
          "Additional paths capability";
        container send {
          presence "Additional paths Send capability";
          description
            "Additional paths Send capability";
          leaf disable {
            type empty;
            description
              "Prevent additional-paths receive from being inherited from the parent";
          }
        }
        container receive {
          presence "Additional paths Send capability";
          description
            "Additional paths Send capability";
          leaf disable {
            type empty;
            description
              "Prevent additional-paths receive from being inherited from the parent";
          }
        }
      }
      container default-originate {
        presence "Originate default route to this neighbor";
        description
          "Originate default route to this neighbor";
        choice DEFAULT-ORIGINATE {
          description
            "Originate default route to this neighbor";
          case ROUTE-POLICY {
            leaf route-policy {
              type xr:Route-policy-name;
              description
                "Route policy to specify criteria to originate default";
            }
          }
          case INHERITANCE-DISABLE {
            leaf inheritance-disable {
              type empty;
              description
                "Prevent default-originate being inherited from a parent group";
            }
          }
        }
      }
      container maximum-prefix {
        presence "Maximum number of prefixes to accept from this peer";
        description
          "Maximum number of prefixes to accept from this peer";
        leaf maximum-prefix-number {
          type uint32 {
            range "1..4294967295" {
              description
                "maximum no. of prefix limit";
            }
          }
          mandatory true;
          description
            "maximum no. of prefix limit";
        }
        leaf threshold-value {
          type uint32 {
            range "1..100" {
              description
                "Threshold value (%) at which to generate a warning msg";
            }
          }
          mandatory true;
          description
            "Threshold value (%) at which to generate a warning msg";
        }
        leaf warning-only {
          type empty;
          description
            "Only give warning message when limit is exceeded";
        }
        leaf restart {
          type uint32 {
            range "1..65535" {
              description
                "Time interval (min) after which peering session will be reestablished";
            }
          }
          description
            "Restart time interval";
        }
        leaf discard-extra-paths {
          type empty;
          description
            "Discard extra paths when limit is exceeded";
        }
      }
      leaf optimal-route-reflection {
        type string {
          length "1..32" {
            description
              "ORR group name - maximum 32 characters";
          }
        }
        description
          "Configure optiomal-route-reflection for this neighbor. Currently supported on Global V4/V4/Label-V4/Label-V6 address family only";
      }
      container next-hop-self {
        presence "Disable the next hop calculation for this neighbor";
        description
          "Disable the next hop calculation for this neighbor";
        leaf inheritance-disable {
          type empty;
          description
            "Prevent next-hop-self from being inherited from the parent";
        }
      }
      container next-hop-unchanged {
        description
          "Do not overwrite next hop before advertising to eBGP peers";
        leaf multipath {
          type empty;
          description
            "Do not overwrite nexthop before advertising multipaths";
        }
        container next-hop-unchanged-enable {
          presence "Do not overwrite next hop before advertising to eBGP peers";
          description
            "Do not overwrite next hop before advertising to eBGP peers";
          leaf inheritance-disable {
            type empty;
            description
              "Prevent next-hop-unchanged from being inherited from the parent";
          }
        }
      }
      container route-policy {
        description
          "route-policy";
        leaf out {
          type xr:Route-policy-name;
          description
            "Apply route policy to outbound routes";
        }
        leaf in {
          type xr:Route-policy-name;
          description
            "Apply route policy to inbound routes";
        }
        container retention {
          presence "Apply retention policy to inbound routes";
          description
            "Apply retention policy to inbound routes";
          leaf route-policy-name {
            type xr:Route-policy-name;
            mandatory true;
            description
              "route-policy name";
          }
          leaf retention-time {
            type uint32 {
              range "0..2147483647" {
                description
                  "Max time (seconds)";
              }
            }
            mandatory true;
            description
              "Retention-time for this neighbor";
          }
        }
      }
      container orf {
        description
          "Specify ORF and inbound filtering criteria";
        leaf route-policy {
          type xr:Route-policy-name;
          description
            "Route policy to specify ORF and inbound filter";
        }
      }
      container cluster-id {
        description
          "Allow routes with first cluster-id in list is same as the router's cluster id";
        container allow-equal {
          presence "Accept routes with first cluster-id in list is same as the router's cluster id";
          description
            "Accept routes with first cluster-id in list is same as the router's cluster id";
          leaf disable {
            type empty;
            description
              "Prevent the configuration from being inherited.";
          }
        }
      }
      container replace-private-as {
        presence "Replace private AS number from outbound updates";
        description
          "Replace private AS number from outbound updates";
        leaf internal {
          type empty;
          description
            "remove only if all ASes in the path are private";
        }
      }
      container remove-private-as {
        description
          "Remove private AS number from outbound updates";
        container inbound {
          presence "Remove private AS number from inbound updates";
          description
            "Remove private AS number from inbound updates";
          leaf entire-aspath {
            type empty;
            description
              "remove only if all ASes in the path are private";
          }
          leaf inheritance-disable {
            type empty;
            description
              "Prevent remove-private-AS from being inherited from the parent";
          }
        }
        container remove-private-as-outbound {
          presence "Remove private AS number from outbound updates";
          description
            "Remove private AS number from outbound updates";
          leaf entire-aspath {
            type empty;
            description
              "remove only if all ASes in the path are private";
          }
          leaf internal {
            type empty;
            description
              "remove only if all ASes in the path are private";
          }
          leaf inheritance-disable {
            type empty;
            description
              "Prevent remove-private-AS from being inherited from the parent";
          }
        }
      }
      container enforce-multiple-labels {
        presence "Enforce support for multiple labels (requires manual session flap)";
        description
          "Enforce support for multiple labels (requires manual session flap)";
        leaf inheritance-disable {
          type empty;
          description
            "Prevent enforce-multiple-labels from being inherited from the parent";
        }
      }
      container route-reflector-client {
        presence "Configure a neighbor as Route Reflector client";
        description
          "Configure a neighbor as Route Reflector client";
        leaf inheritance-disable {
          type empty;
          description
            "Prevent route-reflector-client from being inherited from the parent";
        }
      }
      container accept-route-legacy-rt {
        presence "Configure a neighbor to support legacy PE for RT-Constraint AF";
        description
          "Configure a neighbor to support legacy PE for RT-Constraint AF";
        leaf inheritance-disable {
          type empty;
          description
            "Prevent accept-route-legacy-RT from being inherited from the parent";
        }
      }
      container send-community-ebgp {
        presence "Send community attribute to this external neighbor";
        description
          "Send community attribute to this external neighbor";
        leaf inheritance-disable {
          type empty;
          description
            "Prevent send-community-ebgp from being inherited from the parent";
        }
      }
      container send-community-gshut-ebgp {
        presence "Allow the g-shut community to be sent to this external neighbor";
        description
          "Allow the g-shut community to be sent to this external neighbor";
        leaf inheritance-disable {
          type empty;
          description
            "Prevent send-community-gshut-ebgp from being inherited from the parent";
        }
      }
      container send-extended-community-ebgp {
        presence "Send extended community attribute to this external neighbor";
        description
          "Send extended community attribute to this external neighbor";
        leaf inheritance-disable {
          type empty;
          description
            "Prevent send-extended-community-ebgp from being inherited from parent";
        }
      }
      container soft-reconfiguration {
        description
          "Per neighbor soft reconfiguration";
        container inbound {
          presence "Allow inbound soft reconfiguration for this neighbor";
          description
            "Allow inbound soft reconfiguration for this neighbor";
          leaf rpki-dropped-only {
            type empty;
            description
              "Use soft-reconfig, for paths dropped by route-policy which have RPKI validity state check";
          }
          leaf rpki-tested-only {
            type empty;
            description
              "Use soft-reconfig for paths tested or dropped by route-policy which have RPKI validity state check";
          }
          leaf always {
            type empty;
            description
              "Always use soft reconfig, even if route refresh is supported";
          }
          leaf inheritance-disable {
            type empty;
            description
              "Prevent soft-reconfiguration from being inherited from the parent";
          }
        }
      }
      container default-policy-action {
        description
          "Set a default action if a route does not satify the policy definition";
        leaf in {
          type enumeration {
            enum "accept" {
              value 1;
              description
                "accept the route if does not satisfy the inbound policy";
            }
            enum "reject" {
              value 2;
              description
                "reject the route if does not satisfy the inbound policy";
            }
          }
          description
            "Default action if route does not satisfy inbound route-policy";
        }
        leaf out {
          type enumeration {
            enum "accept" {
              value 1;
              description
                "accept the route if does not satisfy the outbound policy";
            }
            enum "reject" {
              value 2;
              description
                "reject the route if does not satisfy the outbound policy";
            }
          }
          description
            "Default action if route does not satisfy outbound route-policy";
        }
      }
      container update {
        description
          "BGP out bound message";
        container out {
          description
            "BGP out bound message handling";
          container originator-loopcheck {
            presence "Loop check for same originator which sent the route";
            description
              "Loop check for same originator which sent the route";
            leaf disable {
              type empty;
              description
                "Disable originator loop check";
            }
          }
        }
      }
      container advertise {
        description
          "Per neighbor advertisement options";
        leaf permanent-network {
          when
            "../../af-name != 'vpnv4-unicast' and
             ../../af-name != 'vpnv4-multicast' and
             ../../af-name != 'vpnv4-flowspec' and
             ../../af-name != 'vpnv6-flowspec' and
             ../../af-name != 'vpnv6-multicast' and
             ../../af-name != 'vpnv6-unicast' and
             ../../af-name != 'l2vpn-evpn' and
             ../../af-name != 'l2vpn-mspw' and
             ../../af-name != 'l2vpn-vpls-vpws'";
          type empty;
          description
            "Allow permanent networks for this neighbor";
        }
        container local-labeled-route {
          when
            "../../af-name != 'vpnv4-unicast' and
             ../../af-name != 'vpnv4-multicast' and
             ../../af-name != 'vpnv4-flowspec' and
             ../../af-name != 'vpnv6-flowspec' and
             ../../af-name != 'vpnv6-multicast' and
             ../../af-name != 'vpnv6-unicast' and
             ../../af-name != 'l2vpn-evpn' and
             ../../af-name != 'l2vpn-mspw' and
             ../../af-name != 'l2vpn-vpls-vpws'";
          presence "Indicates a local-labeled-route node is configured.";
          description
            "Advertisement of routes with local-label";
          leaf disable {
            type empty;
            description
              "Do not advertise routes with local-label via Unicast SAFI";
          }
        }
        container vpnv4 {
          when
            "../../af-name = 'vpnv4-unicast' or
             ../../af-name = 'vpnv6-unicast' or
             ../../af-name = 'l2vpn-evpn'";
          description
            "VPNv4 Address Family";
          container unicast {
            description
              "Address Family modifier";
            container enable {
              presence "Enable advertise vpnv4 unicast";
              description
                "Enable advertise vpnv4 unicast";
              container re-originated {
                presence "Advertise re-orignated and local routes only";
                description
                  "Advertise re-orignated and local routes only";
                leaf stitching-rt {
                  type empty;
                  description
                    "Advertise re-originated and local routes with stitching Route-Targets";
                }
              }
            }
            container imported-from-default-vrf {
              description
                "Default VRF imported routes";
              leaf disable {
                type empty;
                description
                  "Disable advertisement of default VRF imported routes";
              }
            }
            container imported-from-vrf {
              description
                "VRF extranet imported routes";
              leaf disable {
                type empty;
                description
                  "Disable advertisement of VRF extranet imported routes";
              }
            }
            container imported-from-bridgedomain {
              description
                "VRF EVPN extranet imported routes ";
              leaf disable {
                type empty;
                description
                  "Disable advertisement of VRF EVPN extranet imported routes";
              }
            }
          }
        }
        container vpnv6 {
          when
            "../../af-name = 'vpnv4-unicast' or
             ../../af-name = 'vpnv6-unicast' or
             ../../af-name = 'l2vpn-evpn'";
          description
            "VPNv6 Address Family";
          container unicast {
            description
              "Address Family modifier";
            container enable {
              presence "Enable advertise vpnv6 unicast";
              description
                "Enable advertise vpnv6 unicast";
              container re-originated {
                presence "Advertise Re-orignated routes only";
                description
                  "Advertise Re-orignated routes only";
                leaf stitching-rt {
                  type empty;
                  description
                    "Advertise re-originated routes with stitching Route-Targets";
                }
              }
            }
            container imported-from-default-vrf {
              description
                "Default VRF imported routes";
              leaf disable {
                type empty;
                description
                  "Disable advertisement of default VRF imported routes";
              }
            }
            container imported-from-vrf {
              description
                "VRF imported routes";
              leaf disable {
                type empty;
                description
                  "Disable advertisement of VRF extranet imported routes";
              }
            }
            container imported-from-bridgedomain {
              description
                "VRF EVPN extranet imported routes";
              leaf disable {
                type empty;
                description
                  "Disable advertisement of VRF EVPN extranet imported routes";
              }
            }
          }
        }
        container l2vpn {
          when
            "../../af-name = 'vpnv4-unicast' or
             ../../af-name = 'vpnv6-unicast' or
             ../../af-name = 'l2vpn-evpn'";
          description
            "L2VPN Address Family";
          container evpn {
            when "../../../af-name = 'l2vpn-evpn'";
            presence "Address Family modifier";
            description
              "Address Family modifier";
            container re-originated {
              presence "Advertise Re-orignated routes only";
              description
                "Advertise Re-orignated routes only";
              leaf stitching-rt {
                type empty;
                description
                  "Advertise re-originated routes with stitching Route-Targets";
              }
            }
          }
          leaf evpn-disable {
            type empty;
            description
              "Disable Advertisement of selected SAFI";
          }
          container vpls-vpws {
            description
              "Address Family modifier";
            leaf disable {
              type empty;
              description
                "Disable Advertisement of selected SAFI";
            }
          }
          container mspw {
            description
              "Address Family modifier";
            leaf disable {
              type empty;
              description
                "Disable Advertisement of selected SAFI";
            }
          }
          container gateway-ip-disable {
            when "../../../af-name = 'l2vpn-evpn'";
            presence "Disable advertisement of non-zero EVPN Gateway-IP";
            description
              "Disable advertisement of non-zero EVPN Gateway-IP";
            leaf inheritance-disable {
              type empty;
              description
                "Prevent EVPN Gateway-IP disable being inherited from a parent group";
            }
          }
        }
      }
      leaf encapsulation-type {
        type enumeration {
          enum "srv6" {
            value 2;
            description
              "SRv6 encapsulation";
          }
          enum "vxlan" {
            value 1;
            description
              "VxLAN encapsulation";
          }
        }
        description
          "Specify encapsulation type";
      }
      container segment-routing {
        description
          "enable segment-routing srv6 version 4";
        container srv6 {
          description
            "srv6 version 4";
          leaf prefix-sid-type4 {
            type empty;
            description
              "Enable prefix sid version 4 encoding";
          }
        }
      }
      container import {
        presence "Import options for neighbor address-family routes";
        description
          "Import options for neighbor address-family routes";
        choice IMPORT {
          description
            "Import options for neighbor address-family routes";
          case STITCHING-RT {
            container stitching-rt {
              presence "Import routes using stitching RTs";
              description
                "Import routes using stitching RTs";
              container re-originate {
                presence "Re-originate imported routes";
                description
                  "Re-originate imported routes";
                leaf stitching-rt {
                  type empty;
                  description
                    "Reoriginate imported routes by attaching stitching RTs";
                }
              }
            }
          }
          case RE-ORIGINATE {
            leaf re-originate {
              type empty;
              description
                "Reoriginate imported routes by attaching stitching RTs";
            }
          }
        }
      }
      leaf weight {
        type uint32 {
          range "0..65535" {
            description
              "default weight";
          }
        }
        description
          "Set default weight for routes from this neighbor";
      }
      container allowas-in {
        description
          "Allow as-path with my AS present in it";
        leaf number-of-occurrences-of-as-number {
          type uint32 {
            range "1..10" {
              description
                "Number of occurrences of AS number";
            }
          }
          description
            "Number of occurrences of AS number";
        }
      }
      container allowconfedas-in {
        presence "Allow as-path with my confederation AS present in it";
        description
          "Allow as-path with my confederation AS present in it";
        leaf number-of-occurrences-of-confederation-number {
          type uint32 {
            range "1..10" {
              description
                "Number of occurrences of Confederation AS number";
            }
          }
          description
            "Number of occurrences of Confederation AS number";
        }
      }
      container long-lived-graceful-restart {
        description
          "Enable long lived graceful restart support";
        container stale-time {
          presence "Maximum time to wait before purging long-lived stale routes";
          description
            "Maximum time to wait before purging long-lived stale routes";
          leaf send {
            type uint32 {
              range "0..16777215" {
                description
                  "Max time (seconds)";
              }
            }
            description
              "Stale-time sent in LLGR Capability";
          }
          leaf accept {
            type uint32 {
              range "0..16777215" {
                description
                  "Max time (seconds)";
              }
            }
            description
              "Maximum stale-time acceptable from neighbor";
          }
        }
        leaf capable {
          type empty;
          description
            "Treat neighbor as LLGR capable";
        }
      }
      container site-of-origin {
        description
          "Site-of-Origin extended community associated with the neighbor";
        choice SITE-OF-ORIGIN {
          description
            "Site-of-Origin extended community associated with the neighbor";
          case TWO-BYTE-AS {
            container two-byte-as {
              presence "2-byte AS number";
              description
                "2-byte AS number";
              leaf two-byte-as-number {
                type xr:Bgp-as-number;
                mandatory true;
                description
                  "2-byte AS number";
              }
              leaf asn2-index {
                type uint32 {
                  range "0..4294967295" {
                    description
                      "ASN2:index (hex or decimal format)";
                  }
                }
                mandatory true;
                description
                  "ASN2:index (hex or decimal format)";
              }
            }
          }
          case FOUR-BYTE-AS {
            container four-byte-as {
              presence "4-byte AS number in asplain format";
              description
                "4-byte AS number in asplain format";
              leaf four-byte-as-number {
                type xr:Bgp-as-number;
                mandatory true;
                description
                  "4-byte AS number in asplain format";
              }
              leaf asn4-index {
                type uint32 {
                  range "0..65535" {
                    description
                      "ASN4:index (hex or decimal format)";
                  }
                }
                mandatory true;
                description
                  "ASN4:index (hex or decimal format)";
              }
            }
          }
          case IPV4-ADDRESS {
            container ipv4-address {
              presence "IPv4 address";
              description
                "IPv4 address";
              leaf address {
                type inet:ipv4-address-no-zone;
                mandatory true;
                description
                  "IPv4 address";
              }
              leaf ipv4address-index {
                type uint32 {
                  range "0..65535" {
                    description
                      "IPv4Address:index (hex or decimal format)";
                  }
                }
                mandatory true;
                description
                  "IPv4Address:index (hex or decimal format)";
              }
            }
          }
        }
      }
      container as-override {
        presence "Override matching AS-number while sending update";
        description
          "Override matching AS-number while sending update";
        leaf inheritance-disable {
          type empty;
          description
            "Prevent as-override from being inherited from the parent";
        }
      }
      container aigp {
        description
          "Enable AIGP for this neighbor";
        container send {
          description
            "Copy AIGP";
          container med {
            presence "Send AIGP value in MED";
            description
              "Send AIGP value in MED";
            leaf disable {
              type empty;
              description
                "Disable aigp send med";
            }
          }
          container cost-community {
            presence "Send AIGP value in Cost Community";
            description
              "Send AIGP value in Cost Community";
            choice COST-COMMUNITY {
              description
                "Send AIGP value in Cost Community";
              case DISABLE {
                leaf disable {
                  type empty;
                  description
                    "Disable aigp send cost-community";
                }
              }
              case COST-COMMUNITY-ID {
                container cost-community-id {
                  description
                    "Cost community ID";
                  leaf cost-community-id-number {
                    type uint32 {
                      range "0..255" {
                        description
                          "Cost community ID";
                      }
                    }
                    description
                      "Cost community ID";
                  }
                  container poi {
                    description
                      "Point of insertion for bestpath calculation";
                    container igp-cost {
                      must "../../cost-community-id-number";
                      presence "Cost community is used after IGP distance to next hop";
                      description
                        "Cost community is used after IGP distance to next hop";
                      leaf transitive {
                        type empty;
                        description
                          "Enable transitive cost community";
                      }
                    }
                    container pre-bestpath {
                      must "../../cost-community-id-number";
                      presence "Cost community is first step in best path calculation";
                      description
                        "Cost community is first step in best path calculation";
                      leaf transitive {
                        type empty;
                        description
                          "Enable transitive cost community";
                      }
                    }
                  }
                }
              }
            }
          }
        }
        container enable {
          presence "Enable AIGP";
          description
            "Enable AIGP";
          leaf disable {
            type empty;
            description
              "Disable AIGP";
          }
        }
      }
      container validation {
        presence "Flowspec Validation for this neighbor";
        description
          "Flowspec Validation for this neighbor";
        choice VALIDATION {
          description
            "Flowspec Validation for this neighbor";
          case DISABLE {
            leaf disable {
              type empty;
              description
                "Disable Flowspec Validation";
            }
          }
          case REDIRECT {
            container redirect {
              description
                "Flowspec Redirect nexthop Validation";
              leaf disable {
                type empty;
                description
                  "Disable Flowspec Redirect nexthop Validation";
              }
            }
          }
        }
      }
      container send-multicast-attributes {
        presence "Send multicast attributes to this neighbor";
        description
          "Send multicast attributes to this neighbor";
        leaf disable {
          type empty;
          description
            "Disable send multicast attribute";
        }
      }
      container signalling {
        description
          "Signalling protocols to disable, BGP or LDP";
        container bgp {
          description
            "Select BGP to disable";
          leaf disable {
            type empty;
            description
              "Disable Signalling type";
          }
        }
        container ldp {
          description
            "Select LDP to disable";
          leaf disable {
            type empty;
            description
              "Disable Signalling type";
          }
        }
      }
      container accept-own {
        presence "Handle self-originated routes with Accept-Own community";
        description
          "Handle self-originated routes with Accept-Own community";
        leaf inheritance-disable {
          type empty;
          description
            "Prevent item being inherited from a parent group";
        }
      }
      leaf multipath {
        type empty;
        description
          "Paths from this neighbor is eligible for multipath";
      }
      container slow-peer {
        description
          "Configure this neighbor as slow-peer";
        choice SLOW-PEER {
          description
            "Configure this neighbor as slow-peer";
          case STATIC {
            leaf static {
              type empty;
              description
                "Configure this neighbor as static slow-peer";
            }
          }
          case DYNAMIC {
            container dynamic {
              presence "Configure this neighbor as dynamic slow-peer";
              description
                "Configure this neighbor as dynamic slow-peer";
              leaf threshold {
                type uint32 {
                  range "120..3600" {
                    description
                      "Threshold (in seconds) to detect this neighbor as slow-peer";
                  }
                }
                description
                  "Threshold (in seconds) to detect this neighbor as slow-peer";
              }
              leaf disable {
                type empty;
                description
                  "Disable dynamic slow-peer";
              }
            }
          }
        }
      }
      leaf advertise-entropy-label-disable {
        type empty;
        description
          "Disable propagation of entropy label to this peer";
      }
      container origin-as {
        description
          "BGP origin-AS knobs";
        container validation {
          description
            "BGP origin-AS validation knobs";
          leaf disable {
            type empty;
            description
              "Disable RPKI origin-AS validation";
          }
        }
      }
      container bestpath {
        description
          "Change default route selection criteria";
        container origin-as {
          description
            "BGP origin-AS knobs";
          container allow {
            description
              "BGP origin-AS knobs";
            leaf invalid {
              type empty;
              description
                "BGP bestpath selection will allow 'invalid' origin-AS";
            }
          }
        }
      }
    }

    grouping SNGRP {
      description
        "sngrp";
      container send-community-ebgp {
        presence "Send community attribute to this external neighbor";
        description
          "Send community attribute to this external neighbor";
        leaf inheritance-disable {
          type empty;
          description
            "Prevent send-community-ebgp from being inherited from the parent";
        }
      }
      container send-extended-community-ebgp {
        presence "Send extended community attribute to this external neighbor";
        description
          "Send extended community attribute to this external neighbor";
        leaf inheritance-disable {
          type empty;
          description
            "Prevent send-extended-community-ebgp from being inherited from parent";
        }
      }
      leaf remote-as {
        type xr:Bgp-as-number;
        description
          "Set remote AS";
      }
      leaf remote-as-list {
        type string {
          length "1..1024" {
            description
              "as-list name";
          }
        }
        description
          "Remote as-list configuration";
      }
      leaf maximum-peers {
        type uint32 {
          range "1..4095" {
            description
              "Maximum number of peers";
          }
        }
        description
          "Maximum dynamic neighbors";
      }
      leaf maximum-prefix-restart-time {
        type uint32 {
          range "1..65535" {
            description
              "(Deprecated in 7.11.1) Maximum prefix restart time (seconds)";
          }
        }
        description
          "(Deprecated in 7.11.1) Restart timer interval";
      }
      container as-path-loopcheck {
        description
          "(Deprecated in 7.11.1) Configure AS Path loop checking";
        leaf out {
          type enumeration {
            enum "enable" {
              value 1;
              description
                "(Deprecated in 7.11.1) Disable as-path loop checking";
            }
            enum "disable" {
              value 2;
              description
                "(Deprecated in 7.11.1) Disable as-path loop checking";
            }
          }
          description
            "For outbound updates";
        }
      }
      leaf dampening {
        type enumeration {
          enum "enable" {
            value 1;
            description
              "(Deprecated in 7.11.1) Enable route-flap-damping";
          }
          enum "disable" {
            value 2;
            description
              "(Deprecated in 7.11.1) Enable route-flap-damping";
          }
        }
        description
          "(Deprecated in 7.11.1) Enable route-flap-damping";
      }
      leaf as-override {
        type enumeration {
          enum "enable" {
            value 1;
            description
              "(Deprecated in 7.11.1) Override matching AS-number while sending update";
          }
          enum "disable" {
            value 2;
            description
              "(Deprecated in 7.11.1) Override matching AS-number while sending update";
          }
        }
        description
          "(Deprecated in 7.11.1) Override matching AS-number while sending update";
      }
      container use {
        description
          "Inherit configuration from a group";
        leaf session-group {
          type string {
            length "1..1024" {
              description
                "Session group name";
            }
          }
          description
            "Inherit address-family independent config from a session-group";
        }
      }
      container advertisement-interval {
        description
          "Minimum interval between sending BGP routing updates";
        leaf advertisement-interval-time-in-seconds {
          type uint32 {
            range "0..600" {
              description
                "time in seconds";
            }
          }
          description
            "time in seconds";
        }
        leaf advertisement-interval-time-in-milliseconds {
          type uint32 {
            range "0..999" {
              description
                "time in milliseconds";
            }
          }
          must "../advertisement-interval-time-in-seconds";
          description
            "time in milliseconds";
        }
      }
      leaf description {
        type string {
          length "1..1024" {
            description
              "Up to 80 characters describing this neighbor";
          }
        }
        description
          "Neighbor specific description";
      }
      container ignore-connected-check {
        presence "Bypass the directly connected nexthop check for single-hop eBGP peering";
        description
          "Bypass the directly connected nexthop check for single-hop eBGP peering";
        leaf inheritance-disable {
          type empty;
          description
            "Prevent ignore-connected-check from being inherited from the parent";
        }
      }
      leaf internal-vpn-client {
        type empty;
        description
          "Preserve iBGP CE neighbor path in ATTR_SET across VPN core";
      }
      container ebgp-multihop {
        presence "Allow EBGP neighbors not on directly connected networks";
        description
          "Allow EBGP neighbors not on directly connected networks";
        leaf maximum-hop-count {
          type uint32 {
            range "1..255" {
              description
                "maximum hop count";
            }
          }
          description
            "maximum hop count";
        }
        leaf mpls {
          type empty;
          description
            "Disable BGP MPLS forwarding";
        }
      }
      container tcp {
        description
          "TCP session configuration commands";
        container mss {
          description
            "Maximum Segment Size";
          choice MSS {
            description
              "Maximum Segment Size";
            case TCP-INITIAL-MAXIMUM-SEGMENT-SIZE {
              leaf tcp-initial-maximum-segment-size {
                type uint32 {
                  range "68..10000" {
                    description
                      "TCP initial maximum segment size";
                  }
                }
                description
                  "TCP initial maximum segment size";
              }
            }
            case INHERITANCE-DISABLE {
              leaf inheritance-disable {
                type empty;
                description
                  "Prevent tcp mss from being inherited from the parent";
              }
            }
          }
        }
        container mtu-discovery {
          presence "Enable Path MTU discovery on TCP session";
          description
            "Enable Path MTU discovery on TCP session";
          leaf inheritance-disable {
            type empty;
            description
              "Prevent TCP MTU cfg from being inherited from the parent";
          }
        }
        container ip-only-preferred {
          presence "Prefer to send BGP control plane traffic on IP";
          description
            "Prefer to send BGP control plane traffic on IP";
          leaf inheritance-disable {
            type empty;
            description
              "Do not inherit this configuration from parent group";
          }
        }
      }
      container bmp-activate {
        description
          "Enable BMP logging for this neighbor";
        container servers {
          description
            "Enable BMP connection to particular server";
          list server {
            key "server-number";
            description
              "Enable BMP connection to particular server";
            leaf server-number {
              type uint32 {
                range "1..8" {
                  description
                    "Enable BMP connection to particular server";
                }
              }
              description
                "Enable BMP connection to particular server";
            }
          }
        }
      }
      container bfd {
        description
          "Configure BFD parameters";
        container fast-detect {
          presence "Enable Fast detection";
          description
            "Enable Fast detection";
          leaf strict-mode {
            type empty;
            description
              "(Deprecated) Hold down neighbor session until BFD is up (based on IOS-XR proprietary mechanism)";
          }
          container strict-mode-negotiate {
            presence "Hold down neighbor session until BFD is up (based on strict-mode capability negotiation)";
            description
              "Hold down neighbor session until BFD is up (based on strict-mode capability negotiation)";
            leaf override {
              type empty;
              description
                "Do not bring up neighbor session until BFD up even if strict-mode capability is not received";
            }
          }
          leaf disable {
            type empty;
            description
              "Prevent bfd settings from being inherited from the parent";
          }
        }
        leaf minimum-interval {
          type uint32 {
            range "3..30000" {
              description
                "hello interval in milli-seconds";
            }
          }
          description
            "Hello interval";
        }
        leaf multiplier {
          type uint32 {
            range "2..16" {
              description
                "Detect multiplier";
            }
          }
          description
            "Detect multiplier";
        }
      }
      container keychain {
        description
          "Set keychain based authentication";
        choice KEYCHAIN {
          description
            "Set keychain based authentication";
          case KEYCHAIN-NAME {
            leaf keychain-name {
              type string {
                length "1..32" {
                  description
                    "Name of the key chain - maximum 32 characters";
                }
              }
              description
                "Name of the key chain - maximum 32 characters";
            }
          }
          case INHERITANCE-DISABLE {
            leaf inheritance-disable {
              type empty;
              description
                "Prevent keychain from being inherited from parent";
            }
          }
        }
      }
      container local-as {
        description
          "Specify local AS number";
        choice LOCAL-AS {
          description
            "Specify local AS number";
          case INHERITANCE-DISABLE {
            leaf inheritance-disable {
              type empty;
              description
                "Prevent local AS from being inherited from parent";
            }
          }
          case AS {
            container as {
              description
                "AS";

              grouping OPTIONS {
                description
                  "Options";
                container no-prepend {
                  must "../as-number";
                  presence "Do not prepend local AS to announcements from this neighbor";
                  description
                    "Do not prepend local AS to announcements from this neighbor";
                  container replace-as {
                    presence "Prepend only local AS to announcements to this neighbor";
                    description
                      "Prepend only local AS to announcements to this neighbor";
                    leaf dual-as {
                      type empty;
                      description
                        "Dual-AS mode";
                    }
                  }
                }
              }
              leaf as-number {
                type xr:Bgp-as-number;
                description
                  "AS number";
              }
              uses OPTIONS;
            }
          }
        }
      }
      container password {
        description
          "Set a password";
        choice PASSWORD {
          description
            "Set a password";
          case PASSWORD {
            leaf password {
              type xr:Proprietary-password;
              description
                "Specifies a password will follow";
            }
          }
          case INHERITANCE-DISABLE {
            leaf inheritance-disable {
              type empty;
              description
                "Prevent password from being inherited from parent";
            }
          }
        }
      }
      container receive-buffer-size {
        description
          "Set socket and BGP receive buffer size";
        leaf receive-buffer-size-number {
          type uint32 {
            range "512..131072" {
              description
                "Receive socket buffer size in bytes";
            }
          }
          description
            "Receive socket buffer size in bytes";
        }
        leaf bgp-read-buffer-size-byte {
          type uint32 {
            range "512..131072" {
              description
                "BGP Read buffer size in bytes";
            }
          }
          must "../receive-buffer-size-number";
          description
            "BGP Read buffer size in bytes";
        }
      }
      container send-buffer-size {
        description
          "Set socket and BGP send buffer size";
        leaf send-buffer-size-number {
          type uint32 {
            range "4096..131072" {
              description
                "Send socket buffer size in bytes";
            }
          }
          description
            "Send socket buffer size in bytes";
        }
        leaf bgp-write-buffer-size-byte {
          type uint32 {
            range "4096..131072" {
              description
                "BGP Write buffer size in bytes";
            }
          }
          must "../send-buffer-size-number";
          description
            "BGP Write buffer size in bytes";
        }
      }
      container shutdown {
        presence "Administratively shut down this neighbor";
        description
          "Administratively shut down this neighbor";
        leaf inheritance-disable {
          type empty;
          description
            "Prevent this neighbor being shutdown, even if its parent is";
        }
      }
      container timers {
        description
          "BGP per neighbor timers";

        grouping KEEPALIVE-OPTIONS {
          description
            "Keepalive interval";
          choice KEEPALIVE-OPTIONS {
            description
              "Keepalive interval";
            case ZERO {
              leaf zero {
                type empty;
                description
                  "Disable keepalives/hold time";
              }
            }
            case MINIMUM-ACCEPTABLE-HOLDTIME {
              leaf minimum-acceptable-holdtime {
                type uint32 {
                  range "3..65535" {
                    description
                      "Minimum acceptable holdtime from neighbor";
                  }
                }
                description
                  "Minimum acceptable holdtime from neighbor";
              }
            }
          }
        }
        leaf keepalive-interval {
          type uint32 {
            range "0..65535" {
              description
                "Keepalive interval";
            }
          }
          description
            "Keepalive interval";
        }
        choice KEEPALIVE-INTERVAL {
          description
            "Keepalive interval";
          case ZERO {
            container zero {
              must "../keepalive-interval";
              presence "Disable keepalives/hold time";
              description
                "Disable keepalives/hold time";
              uses KEEPALIVE-OPTIONS;
            }
          }
          case HOLDTIME {
            container holdtime {
              must "../keepalive-interval and holdtime-number";
              presence "Holdtime";
              description
                "Holdtime";
              leaf holdtime-number {
                type uint32 {
                  range "3..65535" {
                    description
                      "Holdtime";
                  }
                }
                description
                  "Holdtime";
              }
              uses KEEPALIVE-OPTIONS;
            }
          }
        }
      }
      container local {
        description
          "Configure local parameter";
        container address {
          description
            "use configured local address for bgp peering";
          choice ADDRESS {
            description
              "use configured local address for bgp peering";
            case IP-ADDRESS {
              leaf ip-address {
                type inet:ip-address-no-zone;
                description
                  "IP address";
              }
            }
            case INHERITANCE-DISABLE {
              leaf inheritance-disable {
                type empty;
                description
                  "Prevent local address from being inherited from parent";
              }
            }
          }
        }
      }
      container log {
        description
          "Logging update messages per neighbor";
        container neighbor {
          description
            "Log neighbor state info";
          container changes {
            description
              "Log neighbor state changes";
            choice CHANGES {
              description
                "Log neighbor state changes";
              case DETAIL {
                leaf detail {
                  type empty;
                  description
                    "detail";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
        container message {
          description
            "Logging update/notification messages per neighbor";
          container in {
            description
              "Inbound log messages";
            choice IN {
              description
                "Inbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
          container out {
            description
              "Outbound log messages";
            choice OUT {
              description
                "Outbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
      }
      leaf update-source {
        type xr:Interface-name;
        description
          "Source of routing updates";
      }
      container local-address-subnet {
        presence "Local address subnet of routing updates";
        description
          "Local address subnet of routing updates";
        leaf address {
          type inet:ip-address-no-zone;
          mandatory true;
          description
            "IPaddress";
        }
        leaf address-prefix {
          type uint32 {
            range "0..128";
          }
          mandatory true;
          description
            "IP address prefix";
        }
      }
      container dmz-link-bandwidth {
        presence "Propagate the DMZ link bandwidth";
        description
          "Propagate the DMZ link bandwidth";
        leaf inheritance-disable {
          type empty;
          description
            "Prevent dmz-link-bandwidth from being inherited from the parent";
        }
      }
      container ebgp-recv-extcommunity-dmz {
        presence "Receive extcommunity dmz link bandwidth from ebgp neighbor";
        description
          "Receive extcommunity dmz link bandwidth from ebgp neighbor";
        leaf inheritance-disable {
          type empty;
          description
            "Prevent ebgp-send-community-dmz from being inherited from parent";
        }
      }
      container ebgp-send-extcommunity-dmz {
        presence "Send extended community dmz link bandwidth to ebgp neighbor";
        description
          "Send extended community dmz link bandwidth to ebgp neighbor";
        choice EBGP-SEND-EXTCOMMUNITY-DMZ {
          description
            "Send extended community dmz link bandwidth to ebgp neighbor";
          case CUMULATIVE {
            leaf cumulative {
              type empty;
              description
                "Send cumulative community dmz link bandwidth of all multipaths to ebgp neighbor";
            }
          }
          case INHERITANCE-DISABLE {
            leaf inheritance-disable {
              type empty;
              description
                "Prevent ebgp-send-extcommunity-dmz from being inherited from parent";
            }
          }
        }
      }
      container ttl-security {
        presence "Enable EBGP TTL security";
        description
          "Enable EBGP TTL security";
        leaf inheritance-disable {
          type empty;
          description
            "Prevent ttl-security from being inherited from the parent";
        }
      }
      leaf session-open-mode {
        type enumeration {
          enum "active-only" {
            value 1;
            description
              "Active only";
          }
          enum "passive-only" {
            value 2;
            description
              "Passive only";
          }
          enum "both" {
            value 0;
            description
              "Prevent session-open-mode being inherited from the parent";
          }
        }
        description
          "Establish BGP session using this TCP open mode";
      }
      leaf dscp {
        type union {
          type uint32 {
            range "0..63" {
              description
                "Differentiated services codepoint value";
            }
          }
          type enumeration {
            enum "af11" {
              value 10;
              description
                "Set packets with AF11 dscp (001010)";
            }
            enum "af12" {
              value 12;
              description
                "Set packets with AF12 dscp (001100)";
            }
            enum "af13" {
              value 14;
              description
                "Set packets with AF13 dscp (001110)";
            }
            enum "af21" {
              value 18;
              description
                "Set packets with AF21 dscp (010010)";
            }
            enum "af22" {
              value 20;
              description
                "Set packets with AF22 dscp (010100)";
            }
            enum "af23" {
              value 22;
              description
                "Set packets with AF23 dscp (010110)";
            }
            enum "af31" {
              value 26;
              description
                "Set packets with AF31 dscp (011010)";
            }
            enum "af32" {
              value 28;
              description
                "Set packets with AF32 dscp (011100)";
            }
            enum "af33" {
              value 30;
              description
                "Set packets with AF33 dscp (011110)";
            }
            enum "af41" {
              value 34;
              description
                "Set packets with AF41 dscp (100010)";
            }
            enum "af42" {
              value 36;
              description
                "Set packets with AF42 dscp (100100)";
            }
            enum "af43" {
              value 38;
              description
                "Set packets with AF43 dscp (100110)";
            }
            enum "cs1" {
              value 8;
              description
                "Set packets with CS1(precedence 1) dscp (001000)";
            }
            enum "cs2" {
              value 16;
              description
                "Set packets with CS2(precedence 2) dscp (010000)";
            }
            enum "cs3" {
              value 24;
              description
                "Set packets with CS3(precedence 3) dscp (011000)";
            }
            enum "cs4" {
              value 32;
              description
                "Set packets with CS4(precedence 4) dscp (100000)";
            }
            enum "cs5" {
              value 40;
              description
                "Set packets with CS5(precedence 5) dscp (101000)";
            }
            enum "cs6" {
              value 48;
              description
                "Set packets with CS6(precedence 6) dscp (110000)";
            }
            enum "cs7" {
              value 56;
              description
                "Set packets with CS7(precedence 7) dscp (111000)";
            }
            enum "default" {
              value 0;
              description
                "Set packets with default dscp (000000)";
            }
            enum "ef" {
              value 46;
              description
                "Set packets with EF dscp (101110)";
            }
          }
        }
        description
          "Set IP DSCP (DiffServ CodePoint)";
      }
      leaf precedence {
        type union {
          type uint32 {
            range "0..7" {
              description
                "Precedence value";
            }
          }
          type enumeration {
            enum "critical" {
              value 5;
              description
                "Set packets with critical precedence (5)";
            }
            enum "flash" {
              value 3;
              description
                "Set packets with flash precedence (3)";
            }
            enum "flash-override" {
              value 4;
              description
                "Set packets with flash override precedence (4)";
            }
            enum "immediate" {
              value 2;
              description
                "Set packets with immediate precedence (2)";
            }
            enum "internet" {
              value 6;
              description
                "Set packets with internetwork control precedence (6)";
            }
            enum "network" {
              value 7;
              description
                "Set packets with network control precedence (7)";
            }
            enum "priority" {
              value 1;
              description
                "Set packets with priority precedence (1)";
            }
            enum "routine" {
              value 0;
              description
                "Set packets with routine precedence (0)";
            }
          }
        }
        description
          "Set precedence";
      }
      container capability {
        description
          "Advertise capability to the peer";
        container additional-paths {
          description
            "Additional paths capability";
          container send {
            presence "Additional paths Send capability";
            description
              "Additional paths Send capability";
            leaf disable {
              type empty;
              description
                "Do not advertise additional paths Send capability";
            }
          }
          container receive {
            presence "Additional paths Receive capability";
            description
              "Additional paths Receive capability";
            leaf disable {
              type empty;
              description
                "Do not advertise additional paths Receive capability";
            }
          }
        }
        container suppress {
          description
            "Suppress advertising capability to the peer";
          container all {
            presence "All capabilities";
            description
              "All capabilities";
            leaf inheritance-disable {
              type empty;
              description
                "Do not inherit this configuration from parent group";
            }
          }
          container extended-nexthop-encoding {
            presence "Extended-nexthop-encoding capabilities (IETF RFC 5549)";
            description
              "Extended-nexthop-encoding capabilities (IETF RFC 5549)";
            leaf inheritance-disable {
              type empty;
              description
                "Do not inherit this configuration from parent group";
            }
          }
          container four-byte-as {
            presence "4-byte-as capability";
            description
              "4-byte-as capability";
            leaf inheritance-disable {
              type empty;
              description
                "Prevent capability suppress 4-type-as being inherited from the parent";
            }
          }
        }
      }
      container graceful-restart {
        description
          "Enable graceful restart support for this neighbor";
        container graceful-restart-enable {
          presence "Enable graceful restart support for this neighbor";
          description
            "Enable graceful restart support for this neighbor";
          leaf disable {
            type empty;
            description
              "Disable graceful restart support for this neighbor";
          }
        }
        container helper-only {
          presence "Enable graceful restart in helper-mode only.Forwarding state will not retained in local restart. Peer's routes will ne retained when peer restarts";
          description
            "Enable graceful restart in helper-mode only.Forwarding state will not retained in local restart. Peer's routes will ne retained when peer restarts";
          leaf inheritance-disable {
            type empty;
            description
              "Prevent GR helper-mode cfg from being inherited from the parent";
          }
        }
        leaf restart-time {
          type uint32 {
            range "1..4095" {
              description
                "Max time (seconds)";
            }
          }
          description
            "Restart time advertised to the neighbor";
        }
        leaf stalepath-time {
          type uint32 {
            range "0..4095" {
              description
                "Max time (seconds)";
            }
          }
          description
            "Maximum time to wait for restart of GR capable peer";
        }
      }
      leaf enforce-first-as {
        type enumeration {
          enum "enable" {
            value 1;
            description
              "enable";
          }
          enum "disable" {
            value 0;
            description
              "Do not enforce the first AS for EBGP routes";
          }
        }
        description
          "enforce-first-as";
      }
      container cluster-id {
        description
          "Enter cluster id for this neighbor";
        choice CLUSTER-ID {
          description
            "Enter cluster id for this neighbor";
          case ROUTE-REFLECTOR-NUMBER {
            leaf route-reflector-number {
              type uint32 {
                range "1..4294967295" {
                  description
                    "Route-Reflector Cluster-id as 32 bit quantity";
                }
              }
              description
                "Route-Reflector Cluster-id as 32 bit quantity";
            }
          }
          case ROUTE-REFLECTOR-IP-ADDRESS {
            leaf route-reflector-ip-address {
              type inet:ipv4-address-no-zone;
              description
                "Route-Reflector Cluster-id in IP address format";
            }
          }
        }
      }
      leaf idle-watch-time {
        type uint32 {
          range "30..1800" {
            description
              "Max time (seconds)";
          }
        }
        description
          "Maximum time to wait for deletion of IDLE state dynamic peer";
      }
      container allowas-in {
        description
          "Allow as-path with my AS present in it";
        leaf number-of-occurrences-of-as-number {
          type uint32 {
            range "1..10" {
              description
                "Number of occurrences of AS number";
            }
          }
          description
            "Number of occurrences of AS number";
        }
      }
      container peer-set {
        description
          "Assign this neighbor to a peer-set used for egress peer engineering";
        list peer-sets {
          key "peer";
          description
            "Assign this neighbor to a peer-set used for egress peer engineering";
          leaf peer {
            type uint32 {
              range "1..255" {
                description
                  "Identity value of peer-set";
              }
            }
            description
              "Assign this neighbor to a peer-set used for egress peer engineering";
          }
        }
      }
      container egress-engineering {
        presence "Enable egress peer engineering for this neighbor";
        description
          "Enable egress peer engineering for this neighbor";
        leaf inheritance-disable {
          type empty;
          description
            "Do not inherit egress-engineering from the parent";
        }
      }
      container ao {
        description
          "Enable Authentiation Option";
        choice AO {
          description
            "Enable Authentiation Option";
          case KEY-CHAIN-NAME {
            container key-chain-name {
              presence "Name of the key chain - maximum 32 characters";
              description
                "Name of the key chain - maximum 32 characters";
              leaf key-chain-name {
                type string {
                  length "1..32" {
                    description
                      "Name of the key chain - maximum 32 characters";
                  }
                }
                mandatory true;
                description
                  "Name of the key chain - maximum 32 characters";
              }
              leaf include-tcp-options {
                type enumeration {
                  enum "enable" {
                    value 1;
                    description
                      "Include other TCP options in the header";
                  }
                  enum "disable" {
                    value 0;
                    description
                      "Exclude other TCP options in the header";
                  }
                }
                mandatory true;
                description
                  "Include/Exclude other TCP options in the header";
              }
              leaf accept-ao-mismatch-connection {
                type empty;
                description
                  "Accept new connection even if AO mismatched";
              }
            }
          }
          case INHERITANCE-DISABLE {
            leaf inheritance-disable {
              type empty;
              description
                "Prevent keychain from being inherited from parent";
            }
          }
        }
      }
      container default-policy-action {
        description
          "Set a default action if a route does not satify the policy definition";
        leaf in {
          type enumeration {
            enum "accept" {
              value 1;
              description
                "accept the route if does not satisfy the inbound policy";
            }
            enum "reject" {
              value 2;
              description
                "reject the route if does not satisfy the inbound policy";
            }
          }
          description
            "Default action if route does not satisfy inbound route-policy";
        }
        leaf out {
          type enumeration {
            enum "accept" {
              value 1;
              description
                "accept the route if does not satisfy the outbound policy";
            }
            enum "reject" {
              value 2;
              description
                "reject the route if does not satisfy the outbound policy";
            }
          }
          description
            "Default action if route does not satisfy outbound route-policy";
        }
      }
      container fast-fallover {
        presence "Force neighbor to be directly connected. Bring neighbor down if its interface goes down";
        description
          "Force neighbor to be directly connected. Bring neighbor down if its interface goes down";
        leaf inheritance-disable {
          type empty;
          description
            "Prevent this neighbor from inheriting this config from a group it is in";
        }
      }
      container update {
        description
          "BGP Update configuration";
        container in {
          description
            "Inbound update message handling";
          container labeled-unicast {
            description
              "IPv4/IPv6 labeled-unicast inbound updates (paths)";
            container equivalent {
              presence "IPv4/IPv6 labeled-unicast inbound updates (paths) treated equivalent to unicast updates (paths)";
              description
                "IPv4/IPv6 labeled-unicast inbound updates (paths) treated equivalent to unicast updates (paths)";
              leaf inheritance-disable {
                type empty;
                description
                  "Do not inherit this configuration from parent group";
              }
            }
          }
          container error-handling {
            description
              "Inbound update message error handling";
            choice ERROR-HANDLING {
              description
                "Inbound update message error handling";
              case AVOID-RESET {
                leaf avoid-reset {
                  type enumeration {
                    enum "enable" {
                      value 1;
                      description
                        "avoid-reset-enable";
                    }
                    enum "disable" {
                      value 0;
                      description
                        "Neighbor may be reset during inbound update message error handling";
                    }
                  }
                  description
                    "Avoid neighbor reset during inbound update message error handling";
                }
              }
              case TREAT-AS-WITHDRAW {
                leaf treat-as-withdraw {
                  type enumeration {
                    enum "enable" {
                      value 1;
                      description
                        "(Deprecated in 7.11.1) Treat NLRIs as withdraws during inbound update message error handling";
                    }
                    enum "disable" {
                      value 0;
                      description
                        "(Deprecated in 7.11.1) Treat NLRIs as withdraws during inbound update message error handling";
                    }
                  }
                  description
                    "(Deprecated in 7.11.1) Treat NLRIs as withdraws during inbound update message error handling";
                }
              }
            }
          }
        }
      }
    }

    grouping NBRGRP {
      description
        "nbrgrp";
      leaf remote-as {
        type xr:Bgp-as-number;
        description
          "Set remote AS";
      }
      leaf remote-as-list {
        type string {
          length "1..1024" {
            description
              "as-list name";
          }
        }
        description
          "Remote as-list configuration";
      }
      leaf maximum-peers {
        type uint32 {
          range "1..4095" {
            description
              "Maximum number of peers";
          }
        }
        description
          "Maximum dynamic neighbors";
      }
      leaf maximum-prefix-restart-time {
        type uint32 {
          range "1..65535" {
            description
              "(Deprecated in 7.11.1) Maximum prefix restart time (seconds)";
          }
        }
        description
          "(Deprecated in 7.11.1) Restart timer interval";
      }
      container as-path-loopcheck {
        description
          "(Deprecated in 7.11.1) Configure AS Path loop checking";
        leaf out {
          type enumeration {
            enum "enable" {
              value 1;
              description
                "(Deprecated in 7.11.1) Disable as-path loop checking";
            }
            enum "disable" {
              value 2;
              description
                "(Deprecated in 7.11.1) Disable as-path loop checking";
            }
          }
          description
            "For outbound updates";
        }
      }
      container use {
        description
          "Inherit configuration from a group";
        leaf neighbor-group {
          type string {
            length "1..1024" {
              description
                "Neighbor-group name";
            }
          }
          description
            "Inherit configuration from a neighbor-group";
        }
        leaf session-group {
          type string {
            length "1..1024" {
              description
                "Session group name";
            }
          }
          description
            "Inherit address-family independent config from a session-group";
        }
      }
      container advertisement-interval {
        description
          "Minimum interval between sending BGP routing updates";
        leaf advertisement-interval-time-in-seconds {
          type uint32 {
            range "0..600" {
              description
                "time in seconds";
            }
          }
          description
            "time in seconds";
        }
        leaf advertisement-interval-time-in-milliseconds {
          type uint32 {
            range "0..999" {
              description
                "time in milliseconds";
            }
          }
          must "../advertisement-interval-time-in-seconds";
          description
            "time in milliseconds";
        }
      }
      leaf description {
        type string {
          length "1..1024" {
            description
              "Up to 80 characters describing this neighbor";
          }
        }
        description
          "Neighbor specific description";
      }
      container ignore-connected-check {
        presence "Bypass the directly connected nexthop check for single-hop eBGP peering";
        description
          "Bypass the directly connected nexthop check for single-hop eBGP peering";
        leaf inheritance-disable {
          type empty;
          description
            "Prevent ignore-connected-check from being inherited from the parent";
        }
      }
      container ebgp-multihop {
        presence "Allow EBGP neighbors not on directly connected networks";
        description
          "Allow EBGP neighbors not on directly connected networks";
        leaf maximum-hop-count {
          type uint32 {
            range "1..255" {
              description
                "maximum hop count";
            }
          }
          description
            "maximum hop count";
        }
        leaf mpls {
          type empty;
          description
            "Disable BGP MPLS forwarding";
        }
      }
      container tcp {
        description
          "TCP session configuration commands";
        container mss {
          description
            "Maximum Segment Size";
          choice MSS {
            description
              "Maximum Segment Size";
            case TCP-INITIAL-MAXIMUM-SEGMENT-SIZE {
              leaf tcp-initial-maximum-segment-size {
                type uint32 {
                  range "68..10000" {
                    description
                      "TCP initial maximum segment size";
                  }
                }
                description
                  "TCP initial maximum segment size";
              }
            }
            case INHERITANCE-DISABLE {
              leaf inheritance-disable {
                type empty;
                description
                  "Prevent tcp mss from being inherited from the parent";
              }
            }
          }
        }
        container mtu-discovery {
          presence "Enable Path MTU discovery on TCP session";
          description
            "Enable Path MTU discovery on TCP session";
          leaf inheritance-disable {
            type empty;
            description
              "Prevent TCP MTU cfg from being inherited from the parent";
          }
        }
        container ip-only-preferred {
          presence "Prefer to send BGP control plane traffic on IP";
          description
            "Prefer to send BGP control plane traffic on IP";
          leaf inheritance-disable {
            type empty;
            description
              "Do not inherit this configuration from parent group";
          }
        }
      }
      container fast-fallover {
        presence "Force neighbor to be directly connected. Bring neighbor down if its interface goes down";
        description
          "Force neighbor to be directly connected. Bring neighbor down if its interface goes down";
        leaf inheritance-disable {
          type empty;
          description
            "Prevent this neighbor from inheriting this config from a group it is in";
        }
      }
      leaf internal-vpn-client {
        type empty;
        description
          "Preserve iBGP CE neighbor path in ATTR_SET across VPN core";
      }
      container bmp-activate {
        description
          "Enable BMP logging for this neighbor";
        container servers {
          description
            "Enable BMP connection to particular server";
          list server {
            key "server-number";
            description
              "Enable BMP connection to particular server";
            leaf server-number {
              type uint32 {
                range "1..8" {
                  description
                    "Enable BMP connection to particular server";
                }
              }
              description
                "Enable BMP connection to particular server";
            }
          }
        }
      }
      container bfd {
        description
          "Configure BFD parameters";
        container fast-detect {
          presence "Enable Fast detection";
          description
            "Enable Fast detection";
          leaf strict-mode {
            type empty;
            description
              "(Deprecated) Hold down neighbor session until BFD is up (based on IOS-XR proprietary mechanism)";
          }
          container strict-mode-negotiate {
            presence "Hold down neighbor session until BFD is up (based on strict-mode capability negotiation)";
            description
              "Hold down neighbor session until BFD is up (based on strict-mode capability negotiation)";
            leaf override {
              type empty;
              description
                "Do not bring up neighbor session until BFD up even if strict-mode capability is not received";
            }
          }
          leaf disable {
            type empty;
            description
              "Prevent bfd settings from being inherited from the parent";
          }
        }
        leaf minimum-interval {
          type uint32 {
            range "3..30000" {
              description
                "hello interval in milli-seconds";
            }
          }
          description
            "Hello interval";
        }
        leaf multiplier {
          type uint32 {
            range "2..16" {
              description
                "Detect multiplier";
            }
          }
          description
            "Detect multiplier";
        }
      }
      container keychain {
        description
          "Set keychain based authentication";
        choice KEYCHAIN {
          description
            "Set keychain based authentication";
          case KEYCHAIN-NAME {
            leaf keychain-name {
              type string {
                length "1..32" {
                  description
                    "Name of the key chain - maximum 32 characters";
                }
              }
              description
                "Name of the key chain - maximum 32 characters";
            }
          }
          case INHERITANCE-DISABLE {
            leaf inheritance-disable {
              type empty;
              description
                "Prevent keychain from being inherited from parent";
            }
          }
        }
      }
      container local-as {
        description
          "Specify local AS number";
        choice LOCAL-AS {
          description
            "Specify local AS number";
          case INHERITANCE-DISABLE {
            leaf inheritance-disable {
              type empty;
              description
                "Prevent local AS from being inherited from parent";
            }
          }
          case AS {
            container as {
              presence "AS";
              description
                "AS";

              grouping OPTIONS {
                description
                  "Options";
                container no-prepend {
                  presence "Do not prepend local AS to announcements from this neighbor";
                  description
                    "Do not prepend local AS to announcements from this neighbor";
                  container replace-as {
                    presence "Prepend only local AS to announcements to this neighbor";
                    description
                      "Prepend only local AS to announcements to this neighbor";
                    leaf dual-as {
                      type empty;
                      description
                        "Dual-AS mode";
                    }
                  }
                }
              }
              leaf as-number {
                type xr:Bgp-as-number;
                mandatory true;
                description
                  "AS number";
              }
              uses OPTIONS;
            }
          }
        }
      }
      container password {
        description
          "Set a password";
        choice PASSWORD {
          description
            "Set a password";
          case ENCRYPTED {
            leaf encrypted {
              type xr:Proprietary-password;
              description
                "Specifies a password will follow";
            }
          }
          case INHERITANCE-DISABLE {
            leaf inheritance-disable {
              type empty;
              description
                "Prevent password from being inherited from parent";
            }
          }
        }
      }
      container receive-buffer-size {
        description
          "Set socket and BGP receive buffer size";
        leaf receive-buffer-size-number {
          type uint32 {
            range "512..131072" {
              description
                "Receive socket buffer size in bytes";
            }
          }
          description
            "Receive socket buffer size in bytes";
        }
        leaf bgp-read-buffer-size-byte {
          type uint32 {
            range "512..131072" {
              description
                "BGP Read buffer size in bytes";
            }
          }
          must "../receive-buffer-size-number";
          description
            "BGP Read buffer size in bytes";
        }
      }
      container send-buffer-size {
        description
          "Set socket and BGP send buffer size";
        leaf send-buffer-size-number {
          type uint32 {
            range "4096..131072" {
              description
                "Send socket buffer size in bytes";
            }
          }
          description
            "Send socket buffer size in bytes";
        }
        leaf bgp-write-buffer-size-byte {
          type uint32 {
            range "4096..131072" {
              description
                "BGP Write buffer size in bytes";
            }
          }
          must "../send-buffer-size-number";
          description
            "BGP Write buffer size in bytes";
        }
      }
      leaf dampening {
        type enumeration {
          enum "enable" {
            value 1;
            description
              "(Deprecated in 7.11.1) Enable route-flap-damping";
          }
          enum "disable" {
            value 2;
            description
              "(Deprecated in 7.11.1) Enable route-flap-damping";
          }
        }
        description
          "(Deprecated in 7.11.1) Enable route-flap-damping";
      }
      leaf as-override {
        type enumeration {
          enum "enable" {
            value 1;
            description
              "(Deprecated in 7.11.1) Override matching AS-number while sending update";
          }
          enum "disable" {
            value 2;
            description
              "(Deprecated in 7.11.1) Override matching AS-number while sending update";
          }
        }
        description
          "(Deprecated in 7.11.1) Override matching AS-number while sending update";
      }
      container shutdown {
        presence "Administratively shut down this neighbor";
        description
          "Administratively shut down this neighbor";
        leaf inheritance-disable {
          type empty;
          description
            "Prevent this neighbor being shutdown, even if its parent is";
        }
      }
      container timers {
        description
          "BGP per neighbor timers";

        grouping KEEPALIVE-OPTIONS {
          description
            "Keepalive interval";
          choice KEEPALIVE-OPTIONS {
            description
              "Keepalive interval";
            case ZERO {
              leaf zero {
                type empty;
                description
                  "Disable keepalives/hold time";
              }
            }
            case MINIMUM-ACCEPTABLE-HOLDTIME {
              leaf minimum-acceptable-holdtime {
                type uint32 {
                  range "3..65535" {
                    description
                      "Minimum acceptable holdtime from neighbor";
                  }
                }
                description
                  "Minimum acceptable holdtime from neighbor";
              }
            }
          }
        }
        leaf keepalive-interval {
          type uint32 {
            range "0..65535" {
              description
                "Keepalive interval";
            }
          }
          description
            "Keepalive interval";
        }
        choice KEEPALIVE-INTERVAL {
          description
            "Keepalive interval";
          case ZERO {
            container zero {
              must "../keepalive-interval";
              presence "Disable keepalives/hold time";
              description
                "Disable keepalives/hold time";
              uses KEEPALIVE-OPTIONS;
            }
          }
          case HOLDTIME {
            container holdtime {
              must "../keepalive-interval and holdtime-number";
              presence "Holdtime";
              description
                "Holdtime";
              leaf holdtime-number {
                type uint32 {
                  range "3..65535" {
                    description
                      "Holdtime";
                  }
                }
                description
                  "Holdtime";
              }
              uses KEEPALIVE-OPTIONS;
            }
          }
        }
      }
      container local {
        description
          "Configure local parameter";
        container address {
          description
            "use configured local address for bgp peering";
          choice ADDRESS {
            description
              "use configured local address for bgp peering";
            case IP-ADDRESS {
              leaf ip-address {
                type inet:ip-address-no-zone;
                description
                  "IP address";
              }
            }
            case INHERITANCE-DISABLE {
              leaf inheritance-disable {
                type empty;
                description
                  "Prevent local address from being inherited from parent";
              }
            }
          }
        }
      }
      container log {
        description
          "Logging update messages per neighbor";
        container neighbor {
          description
            "Log neighbor state info";
          container changes {
            description
              "Log neighbor state changes";
            choice CHANGES {
              description
                "Log neighbor state changes";
              case DETAIL {
                leaf detail {
                  type empty;
                  description
                    "detail";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
        container message {
          description
            "Logging update/notification messages per neighbor";
          container in {
            description
              "Inbound log messages";
            choice IN {
              description
                "Inbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
          container out {
            description
              "Outbound log messages";
            choice OUT {
              description
                "Outbound log messages";
              case LOG-BUFFER-SIZE {
                leaf log-buffer-size {
                  type uint32 {
                    range "1..500" {
                      description
                        "Range for message log buffer size";
                    }
                  }
                  description
                    "Range for message log buffer size";
                }
              }
              case DISABLE {
                leaf disable {
                  type empty;
                  description
                    "disable";
                }
              }
              case INHERITANCE-DISABLE {
                leaf inheritance-disable {
                  type empty;
                  description
                    "Prevents the log state changes from being inherited from the parent";
                }
              }
            }
          }
        }
      }
      leaf update-source {
        type xr:Interface-name;
        description
          "Source of routing updates";
      }
      container local-address-subnet {
        presence "Local address subnet of routing updates";
        description
          "Local address subnet of routing updates";
        leaf address {
          type inet:ip-address-no-zone;
          mandatory true;
          description
            "IPaddress";
        }
        leaf address-prefix {
          type uint32 {
            range "0..128";
          }
          mandatory true;
          description
            "IP address prefix";
        }
      }
      container dmz-link-bandwidth {
        presence "Propagate the DMZ link bandwidth";
        description
          "Propagate the DMZ link bandwidth";
        leaf inheritance-disable {
          type empty;
          description
            "Prevent dmz-link-bandwidth from being inherited from the parent";
        }
      }
      container ebgp-recv-extcommunity-dmz {
        presence "Receive extcommunity dmz link bandwidth from ebgp neighbor";
        description
          "Receive extcommunity dmz link bandwidth from ebgp neighbor";
        leaf inheritance-disable {
          type empty;
          description
            "Prevent ebgp-send-community-dmz from being inherited from parent";
        }
      }
      container ebgp-send-extcommunity-dmz {
        presence "Send extended community dmz link bandwidth to ebgp neighbor";
        description
          "Send extended community dmz link bandwidth to ebgp neighbor";
        choice EBGP-SEND-EXTCOMMUNITY-DMZ {
          description
            "Send extended community dmz link bandwidth to ebgp neighbor";
          case CUMULATIVE {
            leaf cumulative {
              type empty;
              description
                "Send cumulative community dmz link bandwidth of all multipaths to ebgp neighbor";
            }
          }
          case INHERITANCE-DISABLE {
            leaf inheritance-disable {
              type empty;
              description
                "Prevent ebgp-send-extcommunity-dmz from being inherited from parent";
            }
          }
        }
      }
      container ttl-security {
        presence "Enable EBGP TTL security";
        description
          "Enable EBGP TTL security";
        leaf inheritance-disable {
          type empty;
          description
            "Prevent ttl-security from being inherited from the parent";
        }
      }
      leaf session-open-mode {
        type enumeration {
          enum "active-only" {
            value 1;
            description
              "Active only";
          }
          enum "passive-only" {
            value 2;
            description
              "Passive only";
          }
          enum "both" {
            value 0;
            description
              "Prevent session-open-mode being inherited from the parent";
          }
        }
        description
          "Establish BGP session using this TCP open mode";
      }
      leaf dscp {
        type union {
          type uint32 {
            range "0..63" {
              description
                "Differentiated services codepoint value";
            }
          }
          type enumeration {
            enum "af11" {
              value 10;
              description
                "Set packets with AF11 dscp (001010)";
            }
            enum "af12" {
              value 12;
              description
                "Set packets with AF12 dscp (001100)";
            }
            enum "af13" {
              value 14;
              description
                "Set packets with AF13 dscp (001110)";
            }
            enum "af21" {
              value 18;
              description
                "Set packets with AF21 dscp (010010)";
            }
            enum "af22" {
              value 20;
              description
                "Set packets with AF22 dscp (010100)";
            }
            enum "af23" {
              value 22;
              description
                "Set packets with AF23 dscp (010110)";
            }
            enum "af31" {
              value 26;
              description
                "Set packets with AF31 dscp (011010)";
            }
            enum "af32" {
              value 28;
              description
                "Set packets with AF32 dscp (011100)";
            }
            enum "af33" {
              value 30;
              description
                "Set packets with AF33 dscp (011110)";
            }
            enum "af41" {
              value 34;
              description
                "Set packets with AF41 dscp (100010)";
            }
            enum "af42" {
              value 36;
              description
                "Set packets with AF42 dscp (100100)";
            }
            enum "af43" {
              value 38;
              description
                "Set packets with AF43 dscp (100110)";
            }
            enum "cs1" {
              value 8;
              description
                "Set packets with CS1(precedence 1) dscp (001000)";
            }
            enum "cs2" {
              value 16;
              description
                "Set packets with CS2(precedence 2) dscp (010000)";
            }
            enum "cs3" {
              value 24;
              description
                "Set packets with CS3(precedence 3) dscp (011000)";
            }
            enum "cs4" {
              value 32;
              description
                "Set packets with CS4(precedence 4) dscp (100000)";
            }
            enum "cs5" {
              value 40;
              description
                "Set packets with CS5(precedence 5) dscp (101000)";
            }
            enum "cs6" {
              value 48;
              description
                "Set packets with CS6(precedence 6) dscp (110000)";
            }
            enum "cs7" {
              value 56;
              description
                "Set packets with CS7(precedence 7) dscp (111000)";
            }
            enum "default" {
              value 0;
              description
                "Set packets with default dscp (000000)";
            }
            enum "ef" {
              value 46;
              description
                "Set packets with EF dscp (101110)";
            }
          }
        }
        description
          "Set IP DSCP (DiffServ CodePoint)";
      }
      leaf precedence {
        type union {
          type uint32 {
            range "0..7" {
              description
                "Precedence value";
            }
          }
          type enumeration {
            enum "critical" {
              value 5;
              description
                "Set packets with critical precedence (5)";
            }
            enum "flash" {
              value 3;
              description
                "Set packets with flash precedence (3)";
            }
            enum "flash-override" {
              value 4;
              description
                "Set packets with flash override precedence (4)";
            }
            enum "immediate" {
              value 2;
              description
                "Set packets with immediate precedence (2)";
            }
            enum "internet" {
              value 6;
              description
                "Set packets with internetwork control precedence (6)";
            }
            enum "network" {
              value 7;
              description
                "Set packets with network control precedence (7)";
            }
            enum "priority" {
              value 1;
              description
                "Set packets with priority precedence (1)";
            }
            enum "routine" {
              value 0;
              description
                "Set packets with routine precedence (0)";
            }
          }
        }
        description
          "Set precedence";
      }
      container capability {
        description
          "Advertise capability to the peer";
        container additional-paths {
          description
            "Additional paths capability";
          container send {
            presence "Additional paths Send capability";
            description
              "Additional paths Send capability";
            leaf disable {
              type empty;
              description
                "Do not advertise additional paths Send capability";
            }
          }
          container receive {
            presence "Additional paths Receive capability";
            description
              "Additional paths Receive capability";
            leaf disable {
              type empty;
              description
                "Do not advertise additional paths Receive capability";
            }
          }
        }
        container suppress {
          description
            "Suppress advertising capability to the peer";
          container all {
            presence "All capabilities";
            description
              "All capabilities";
            leaf inheritance-disable {
              type empty;
              description
                "Do not inherit this configuration from parent group";
            }
          }
          container extended-nexthop-encoding {
            presence "Extended-nexthop-encoding capabilities (IETF RFC 5549)";
            description
              "Extended-nexthop-encoding capabilities (IETF RFC 5549)";
            leaf inheritance-disable {
              type empty;
              description
                "Do not inherit this configuration from parent group";
            }
          }
          container four-byte-as {
            presence "4-byte-as capability";
            description
              "4-byte-as capability";
            leaf inheritance-disable {
              type empty;
              description
                "Prevent capability suppress 4-type-as being inherited from the parent";
            }
          }
        }
      }
      container graceful-restart {
        description
          "Enable graceful restart support for this neighbor";
        container graceful-restart-enable {
          presence "Enable graceful restart support for this neighbor";
          description
            "Enable graceful restart support for this neighbor";
          leaf disable {
            type empty;
            description
              "Disable graceful restart support for this neighbor";
          }
        }
        container helper-only {
          presence "Enable graceful restart in helper-mode only.Forwarding state will not retained in local restart. Peer's routes will ne retained when peer restarts";
          description
            "Enable graceful restart in helper-mode only.Forwarding state will not retained in local restart. Peer's routes will ne retained when peer restarts";
          leaf inheritance-disable {
            type empty;
            description
              "Prevent GR helper-mode cfg from being inherited from the parent";
          }
        }
        leaf restart-time {
          type uint32 {
            range "1..4095" {
              description
                "Max time (seconds)";
            }
          }
          description
            "Restart time advertised to the neighbor";
        }
        leaf stalepath-time {
          type uint32 {
            range "0..4095" {
              description
                "Max time (seconds)";
            }
          }
          description
            "Maximum time to wait for restart of GR capable peer";
        }
      }
      leaf enforce-first-as {
        type enumeration {
          enum "enable" {
            value 1;
            description
              "enable";
          }
          enum "disable" {
            value 0;
            description
              "Do not enforce the first AS for EBGP routes";
          }
        }
        description
          "enforce-first-as";
      }
      container cluster-id {
        description
          "Enter cluster id for this neighbor";
        choice CLUSTER-ID {
          description
            "Enter cluster id for this neighbor";
          case ROUTE-REFLECTOR-NUMBER {
            leaf route-reflector-number {
              type uint32 {
                range "1..4294967295" {
                  description
                    "Route-Reflector Cluster-id as 32 bit quantity";
                }
              }
              description
                "Route-Reflector Cluster-id as 32 bit quantity";
            }
          }
          case ROUTE-REFLECTOR-IP-ADDRESS {
            leaf route-reflector-ip-address {
              type inet:ipv4-address-no-zone;
              description
                "Route-Reflector Cluster-id in IP address format";
            }
          }
        }
      }
      leaf idle-watch-time {
        type uint32 {
          range "30..1800" {
            description
              "Max time (seconds)";
          }
        }
        description
          "Maximum time to wait for deletion of IDLE state dynamic peer";
      }
      container allowas-in {
        description
          "Allow as-path with my AS present in it";
        leaf number-of-occurrences-of-as-number {
          type uint32 {
            range "1..10" {
              description
                "Number of occurrences of AS number";
            }
          }
          description
            "Number of occurrences of AS number";
        }
      }
      container egress-engineering {
        presence "Enable egress peer engineering for this neighbor";
        description
          "Enable egress peer engineering for this neighbor";
        leaf inheritance-disable {
          type empty;
          description
            "Do not inherit egress-engineering from the parent";
        }
      }
      container peer-set {
        description
          "Assign this neighbor to a peer-set used for egress peer engineering";
        list peer-sets {
          key "peer";
          description
            "Assign this neighbor to a peer-set used for egress peer engineering";
          leaf peer {
            type uint32 {
              range "1..255" {
                description
                  "Identity value of peer-set";
              }
            }
            description
              "Assign this neighbor to a peer-set used for egress peer engineering";
          }
        }
      }
      container ao {
        description
          "Enable Authentiation Option";
        choice AO {
          description
            "Enable Authentiation Option";
          case KEY-CHAIN-NAME {
            container key-chain-name {
              presence "Name of the key chain - maximum 32 characters";
              description
                "Name of the key chain - maximum 32 characters";
              leaf key-chain-name {
                type string {
                  length "1..32" {
                    description
                      "Name of the key chain - maximum 32 characters";
                  }
                }
                mandatory true;
                description
                  "Name of the key chain - maximum 32 characters";
              }
              leaf include-tcp-options {
                type enumeration {
                  enum "enable" {
                    value 1;
                    description
                      "Include other TCP options in the header";
                  }
                  enum "disable" {
                    value 0;
                    description
                      "Exclude other TCP options in the header";
                  }
                }
                mandatory true;
                description
                  "Include/Exclude other TCP options in the header";
              }
              leaf accept-ao-mismatch-connection {
                type empty;
                description
                  "Accept new connection even if AO mismatched";
              }
            }
          }
          case INHERITANCE-DISABLE {
            leaf inheritance-disable {
              type empty;
              description
                "Prevent keychain from being inherited from parent";
            }
          }
        }
      }
      container default-policy-action {
        description
          "Set a default action if a route does not satify the policy definition";
        leaf in {
          type enumeration {
            enum "accept" {
              value 1;
              description
                "accept the route if does not satisfy the inbound policy";
            }
            enum "reject" {
              value 2;
              description
                "reject the route if does not satisfy the inbound policy";
            }
          }
          description
            "Default action if route does not satisfy inbound route-policy";
        }
        leaf out {
          type enumeration {
            enum "accept" {
              value 1;
              description
                "accept the route if does not satisfy the outbound policy";
            }
            enum "reject" {
              value 2;
              description
                "reject the route if does not satisfy the outbound policy";
            }
          }
          description
            "Default action if route does not satisfy outbound route-policy";
        }
      }
      container update {
        description
          "BGP Update configuration";
        container in {
          description
            "Inbound update message handling";
          container filtering {
            presence "Inbound update message filtering";
            description
              "Inbound update message filtering";
            container message {
              description
                "Filtered update messages";
              container buffers {
                presence "Filtered update message buffers";
                description
                  "Filtered update message buffers";
                leaf buffers-number {
                  type uint32 {
                    range "0..25" {
                      description
                        "Number of buffers to store filtered update messages (resizing does not take effect after filtering action has started)";
                    }
                  }
                  mandatory true;
                  description
                    "Number of buffers to store filtered update messages (resizing does not take effect after filtering action has started)";
                }
                leaf buffer-list {
                  type enumeration {
                    enum "buffers-number-enable" {
                      value 0;
                      description
                        "buffers-number-enable";
                    }
                    enum "non-circular" {
                      value 1;
                      description
                        "Message buffer list is not circular";
                    }
                  }
                  mandatory true;
                  description
                    "buffer-list";
                }
              }
            }
            container logging {
              description
                "Update filtering syslog message";
              leaf disable {
                type empty;
                description
                  "Disable update filtering syslog message";
              }
            }
            container attribute-filter {
              description
                "Attribute-filter configuration";
              leaf group {
                type string {
                  length "1..1024" {
                    description
                      "Attribute-filter group name";
                  }
                }
                description
                  "Attribute-filter group configuration";
              }
            }
          }
          container labeled-unicast {
            description
              "IPv4/IPv6 labeled-unicast inbound updates (paths)";
            container equivalent {
              presence "IPv4/IPv6 labeled-unicast inbound updates (paths) treated equivalent to unicast updates (paths)";
              description
                "IPv4/IPv6 labeled-unicast inbound updates (paths) treated equivalent to unicast updates (paths)";
              leaf inheritance-disable {
                type empty;
                description
                  "Do not inherit this configuration from parent group";
              }
            }
          }
          container error-handling {
            description
              "Inbound update message error handling";
            choice ERROR-HANDLING {
              description
                "Inbound update message error handling";
              case AVOID-RESET {
                leaf avoid-reset {
                  type enumeration {
                    enum "enable" {
                      value 1;
                      description
                        "avoid-reset-enable";
                    }
                    enum "disable" {
                      value 0;
                      description
                        "Neighbor may be reset during inbound update message error handling";
                    }
                  }
                  description
                    "Avoid neighbor reset during inbound update message error handling";
                }
              }
              case TREAT-AS-WITHDRAW {
                leaf treat-as-withdraw {
                  type enumeration {
                    enum "enable" {
                      value 1;
                      description
                        "(Deprecated in 7.11.1) Treat NLRIs as withdraws during inbound update message error handling";
                    }
                    enum "disable" {
                      value 0;
                      description
                        "(Deprecated in 7.11.1) Treat NLRIs as withdraws during inbound update message error handling";
                    }
                  }
                  description
                    "(Deprecated in 7.11.1) Treat NLRIs as withdraws during inbound update message error handling";
                }
              }
            }
          }
        }
      }
      container graceful-maintenance {
        presence
          "Attributes for Graceful Maintenance. This will cause
           neighbors to de-prefer routes from this router and
           choose alternates. This allows the router to be
           brought in or out of service gracefully.";
        description
          "Attributes for Graceful Maintenance. This will cause
           neighbors to de-prefer routes from this router and
           choose alternates. This allows the router to be
           brought in or out of service gracefully.";
        container local-preference {
          description
            "local preference with which to advertise routes tonibgp neigbors. Default=No Touch";
          choice LOCAL-PREFERENCE {
            description
              "local preference with which to advertise routes tonibgp neigbors. Default=No Touch";
            case LOCAL-PREFERENCE-NUMBER {
              leaf local-preference-number {
                type uint32 {
                  range "0..4294967295" {
                    description
                      "Range of values for Local Preference";
                  }
                }
                description
                  "Range of values for Local Preference";
              }
            }
            case INHERITANCE-DISABLE {
              leaf inheritance-disable {
                type empty;
                description
                  "Prevent local preference from being inherited from the parent";
              }
            }
          }
        }
        container as-prepends {
          description
            "Number of times to prepend the local AS number to thenAS path of routes. Default=0";
          choice AS-PREPENDS {
            description
              "Number of times to prepend the local AS number to thenAS path of routes. Default=0";
            case PREPENDS-NUMBER {
              leaf prepends-number {
                type uint32 {
                  range "0..6" {
                    description
                      "Range of number of AS prepends";
                  }
                }
                description
                  "Range of number of AS prepends";
              }
            }
            case INHERITANCE-DISABLE {
              leaf inheritance-disable {
                type empty;
                description
                  "Prevent AS prepends from being inherited from the parent";
              }
            }
          }
        }
        container activate {
          presence
            "Routes will be announced with the graceful maintenance
             attributes while activated either here or under router
             bgp configuration. While activated, all routes to this
             neighbor will be announced with the attributes
             configured here and all routes from this neighbor will
             be announced to other neighbors with the graceful
             maintenance attributes configured under those
             neighbors. The g-shut community will be announced
             regardless of the other attributes configured here. To
             allow the g-shut community to be announced to ebgp
             neighbors, the send-community-gshut-ebgp configuration
             is also required. Note: changes to the attributes will
             not take effect while activated.";
          description
            "Routes will be announced with the graceful maintenance
             attributes while activated either here or under router
             bgp configuration. While activated, all routes to this
             neighbor will be announced with the attributes
             configured here and all routes from this neighbor will
             be announced to other neighbors with the graceful
             maintenance attributes configured under those
             neighbors. The g-shut community will be announced
             regardless of the other attributes configured here. To
             allow the g-shut community to be announced to ebgp
             neighbors, the send-community-gshut-ebgp configuration
             is also required. Note: changes to the attributes will
             not take effect while activated.";
          leaf inheritance-disable {
            type empty;
            description
              "Prevent activate from being inherited from the parent";
          }
        }
        container bandwidth-aware {
          description
            "Session interface Bandwidth based Graceful-Maintenance
             Only restricted to eBGP directly connected, this will
             enable Graceful maintenance whenever the link effective
             bandwidth goes below a configurable low-threshold and deactivates
             based on effective bandwidth reaches the high-threshold
             or low-threshold if high-threshold is not configured";
          choice BANDWIDTH-AWARE {
            description
              "Session interface Bandwidth based Graceful-Maintenance
               Only restricted to eBGP directly connected, this will
               enable Graceful maintenance whenever the link effective
               bandwidth goes below a configurable low-threshold and deactivates
               based on effective bandwidth reaches the high-threshold
               or low-threshold if high-threshold is not configured";
            case BANDWIDTH {
              container bandwidth {
                description
                  "Session interface Bandwidth based Graceful-Maintenance
                   Only restricted to eBGP directly connected, this will
                   enable Graceful maintenance whenever the link effective
                   bandwidth goes below a configurable low-threshold and deactivates
                   based on effective bandwidth reaches the high-threshold
                   or low-threshold if high-threshold is not configured";
                choice BANDWIDTH {
                  description
                    "Session interface Bandwidth based Graceful-Maintenance
                     Only restricted to eBGP directly connected, this will
                     enable Graceful maintenance whenever the link effective
                     bandwidth goes below a configurable low-threshold and deactivates
                     based on effective bandwidth reaches the high-threshold
                     or low-threshold if high-threshold is not configured";
                  case PERCENTAGE-THRESHOLD {
                    container percentage-threshold {
                      presence "Threshold in Percentage of Effective Bandwidth nover Maximum Bandwidth";
                      description
                        "Threshold in Percentage of Effective Bandwidth nover Maximum Bandwidth";
                      leaf percentage-threshold-number {
                        type uint32 {
                          range "1..100" {
                            description
                              "Low threshold of effective bandwidth
                               (in percentage of max bandwidth) to enter/exit
                               graceful-maintenance";
                          }
                        }
                        mandatory true;
                        description
                          "Low threshold of effective bandwidth
                           (in percentage of max bandwidth) to enter/exit
                           graceful-maintenance";
                      }
                      leaf optional-high-threshold {
                        type uint32 {
                          range "1..100" {
                            description
                              "Optional High threshold of effective bandwidth
                               (in kbps) to exit graceful-maintenance";
                          }
                        }
                        description
                          "Optional High threshold of effective bandwidth
                           (in kbps) to exit graceful-maintenance";
                      }
                    }
                  }
                  case BANDWIDTH-THRESHOLD {
                    container bandwidth-threshold {
                      presence "Bandwidth based threshold detection in kbps";
                      description
                        "Bandwidth based threshold detection in kbps";
                      leaf bandwidth-threshold-number {
                        type uint32 {
                          range "1..4294967295" {
                            description
                              "Low threshold of effective bandwidth (in kbps)
                               to enter/exit graceful-maintenance";
                          }
                        }
                        mandatory true;
                        description
                          "Low threshold of effective bandwidth (in kbps)
                           to enter/exit graceful-maintenance";
                      }
                      leaf optional-high-threshold-number {
                        type uint32 {
                          range "1..4294967295" {
                            description
                              "Optional High threshold of effective bandwidth
                               (in kbps) to exit graceful-maintenance";
                          }
                        }
                        description
                          "Optional High threshold of effective bandwidth
                           (in kbps) to exit graceful-maintenance";
                      }
                    }
                  }
                }
              }
            }
            case INHERITANCE-DISABLE {
              leaf inheritance-disable {
                type empty;
                description
                  "Prevent bandwidth-aware from being inherited from the parent";
              }
            }
          }
        }
      }
      container address-families {
        description
          "Enter Address Family command mode";
        list address-family {
          key "af-name";
          description
            "Enter Address Family command mode";
          leaf af-name {
            type Bgp-address-family;
            description
              "Enter Address Family command mode";
          }
          uses ADDRESS-FAMILY;
        }
      }
    }
    container segment-routing {
      description
        "Specify Segment-routing configurations";
      container srv6 {
        presence "Specify SRv6 configurations";
        description
          "Specify SRv6 configurations";
        leaf locator {
          type xr:Cisco-ios-xr-string {
            length "1..1024" {
              description
                "locator name";
            }
          }
          description
            "Specify locator";
        }
        container usid {
          description
            "Micro-SID configuration";
          container allocation {
            description
              "Allocation mode";
            leaf wide-local-id-block {
              type empty;
              description
                "Wide LIB allocation";
            }
          }
        }
      }
    }
    container neighbors {
      description
        "Specify a neighbor router";
      list neighbor {
        key "address";
        description
          "Specify a neighbor router";
        leaf address {
          type inet:ip-address-no-zone;
          description
            "IPaddress";
        }
        uses NEIGHBOR;
      }
      list neighbor-range {
        key "address address-prefix";
        description
          "Specify a neighbor router";
        leaf address {
          type inet:ip-address-no-zone;
          description
            "IPaddress";
        }
        leaf address-prefix {
          type uint32 {
            range "0..128";
          }
          description
            "IP address prefix";
        }
        uses NEIGHBOR;
      }
    }
    container af-groups {
      description
        "Specify a AF group";
      list af-group {
        must "address-families";
        key "af-group-name";
        description
          "Specify a AF group";
        leaf af-group-name {
          type xr:Cisco-ios-xr-string {
            length "1..900" {
              description
                "AF group name";
            }
          }
          description
            "AF group name";
        }
        container address-families {
          description
            "Enter Address Family command mode";
          list address-family {
            key "af-name";
            description
              "Enter Address Family command mode";
            leaf af-name {
              type Bgp-address-family;
              description
                "Specify a AF name";
            }
            uses ADDRESS-FAMILY;
          }
        }
      }
    }
    container session-groups {
      description
        "Specify a Session group";
      list session-group {
        key "session-group-name";
        description
          "Specify a Session group";
        leaf session-group-name {
          type xr:Cisco-ios-xr-string {
            length "1..900" {
              description
                "Session group name";
            }
          }
          description
            "Session group name";
        }
        uses SNGRP;
      }
    }
    container neighbor-groups {
      description
        "Specify a Neighbor-group";
      list neighbor-group {
        key "neighbor-group-name";
        description
          "Specify a Neighbor-group";
        leaf neighbor-group-name {
          type xr:Cisco-ios-xr-string {
            length "1..900" {
              description
                "Neighbor-group name";
            }
          }
          description
            "Neighbor-group name";
        }
        uses NBRGRP;
      }
    }
    container graceful-maintenance {
      description
        "Announce routes with the g-shut community and other
         attributes as configured under the neighbors. This
         will cause neighbors to de-prefer routes from this
         router and choose alternates. This allows the router
         to be brought in or out of service gracefully.";
      container activate {
        presence "All neighbors with graceful-maintenance config";
        description
          "All neighbors with graceful-maintenance config";
        leaf all-neighbors {
          type empty;
          description
            "Also neighbors without graceful-maintenance config";
        }
        leaf retain-routes {
          type empty;
          description
            "Keep BGP routes in RIB once BGP process stops";
        }
        container interfaces {
          description
            "Enable graceful-maintenance on all directly connected ebgp neighbors whose session is going over this interface";
          list interface {
            key "interface-name";
            description
              "Enable graceful-maintenance on all directly connected ebgp neighbors whose session is going over this interface";
            leaf interface-name {
              type xr:Interface-name;
              description
                "Select an interface to configure";
            }
          }
        }
        container locations {
          description
            "Enable graceful-maintenance on all directly connected ebgp neighbors whose session is going over this line card location";
          list location {
            key "location-value";
            description
              "Enable graceful-maintenance on all directly connected ebgp neighbors whose session is going over this line card location";
            leaf location-value {
              type xr:Node-id;
              description
                "location";
            }
          }
        }
      }
    }
    container address-families {
      description
        "Enter Address Family command mode";
      list address-family {
        key "af-name";
        description
          "Enter Address Family command mode";
        leaf af-name {
          type Bgp-address-family;
          description
            "Enter Address Family command mode";
        }
        container ecmp-delay {
          description
            "Specify a delay in best path calculation for prefix with ECMP paths";
          container fixed {
            description
              "Enable ECMP delay with a fixed delay";
            leaf delay {
              type uint32 {
                range "10..300000" {
                  description
                    "Delay interval (in msecs)";
                }
              }
              description
                "Provide a delay interval in msecs";
            }
          }
          container platform-oor-based {
            description
              "Enable ECMP delay with an OOR threshold";
            leaf delay {
              type uint32 {
                range "10..300000" {
                  description
                    "Delay interval (in msecs)";
                }
              }
              must "../threshold";
              description
                "Provide a delay interval in msecs";
            }
            leaf threshold {
              type uint32 {
                range "10..90" {
                  description
                    "Out-Of-Resource threshold (in percentage)";
                }
              }
              must "../delay";
              description
                "Delay only when platform resource usage is above specified threshold";
            }
          }
          container as-based {
            description
              "Enable ECMP delay based on the neighbor AS";
            leaf delay {
              type uint32 {
                range "10..300000" {
                  description
                    "Delay interval (in msecs)";
                }
              }
              description
                "Provide a delay interval in msecs";
            }
            leaf as-list {
              type string {
                length "1..1024" {
                  description
                    "as-list name";
                }
              }
              must "../delay";
              description
                "Enable ECMP delay for neighbor AS'es included in the AS list";
            }
          }
        }
        container vrf {
          description
            "Specify configurations to be inherited to all vrfs";
          container all {
            presence "Specify configurations to be inherited to all vrfs";
            description
              "Specify configurations to be inherited to all vrfs";
            container segment-routing {
              description
                "Specify Segment-routing configurations";
              container srv6 {
                presence "Specify SRv6 configurations";
                description
                  "Specify SRv6 configurations";
                container alloc {
                  description
                    "Segment-Routing Allocation";
                  container mode {
                    description
                      "Select Segment-Routing Allocation mode";
                    choice MODE {
                      description
                        "Select Segment-Routing Allocation mode";
                      case PER-CE {
                        leaf per-ce {
                          type empty;
                          description
                            "Set SRv6 per CE SID  mode";
                        }
                      }
                      case PER-VRF {
                        leaf per-vrf {
                          type empty;
                          description
                            "Set SRv6 per VRF SID  mode";
                        }
                      }
                      case PER-VRF-46 {
                        leaf per-vrf-46 {
                          type empty;
                          description
                            "Set SRv6 per VRF 46 SID  mode";
                        }
                      }
                    }
                  }
                }
                leaf locator {
                  type xr:Cisco-ios-xr-string {
                    length "1..1024" {
                      description
                        "locator name";
                    }
                  }
                  description
                    "Specify locator";
                }
                container usid {
                  description
                    "Micro-SID configuration";
                  container allocation {
                    description
                      "Allocation mode";
                    leaf wide-local-id-block {
                      type empty;
                      description
                        "Wide LIB allocation";
                    }
                  }
                }
              }
            }
            container source {
              description
                "Source import route-targets from import-policy";
              container rt {
                description
                  "Source import route-targets from import-policy";
                leaf import-policy {
                  type empty;
                  description
                    "Source import route-targets from import-policy";
                }
              }
            }
            container label {
              description
                "Label-related configuration";
              container mode {
                description
                  "Select label mode";
                choice MODE {
                  description
                    "Select label mode";
                  case PER-CE {
                    leaf per-ce {
                      type empty;
                      description
                        "Set per CE label mode";
                    }
                  }
                  case PER-VRF {
                    leaf per-vrf {
                      type empty;
                      description
                        "Set per VRF label mode";
                    }
                  }
                  case PER-VRF-46 {
                    leaf per-vrf-46 {
                      type empty;
                      description
                        "Set per VRF 46 label mode";
                    }
                  }
                  case ROUTE-POLICY {
                    container route-policy {
                      presence "Use a route policy to select prefixes for label allocation mode";
                      description
                        "Use a route policy to select prefixes for label allocation mode";
                      leaf route-policy-name {
                        type xr:Route-policy-name;
                        mandatory true;
                        description
                          "route policy name";
                      }
                    }
                  }
                }
              }
            }
            container rnh {
              description
                "Remote nexthop";
              container install {
                description
                  "Install remote nexthop";
                container extcomm {
                  presence "Install remote nexthop in extended community and opaque format";
                  description
                    "Install remote nexthop in extended community and opaque format";
                  leaf only {
                    type empty;
                    description
                      "Install remote nexthop in extended community format only";
                  }
                }
              }
            }
            leaf table-policy {
              type xr:Route-policy-name;
              description
                "Configure policy for installation of routes to RIB";
            }
          }
        }
        container domain-distinguisher {
          description
            "Globally unique identifier for IGP domain";
          leaf domain-distinguisher-number {
            type uint32 {
              range "1..4294967295" {
                description
                  "4 octet ASN";
              }
            }
            description
              "4 octet ASN";
          }
          leaf octet-routerid {
            type inet:ipv4-address-no-zone;
            description
              "4 octet router-id";
          }
        }
        container distance {
          description
            "Define an administrative distance";
          container bgp {
            must "external-route-distance and internal-route-distance and local-route-distance";
            presence "BGP distance";
            description
              "BGP distance";
            leaf external-route-distance {
              type uint32 {
                range "1..20000" {
                  description
                    "Distance for routes external to the AS";
                }
              }
              description
                "Distance for routes external to the AS";
            }
            leaf internal-route-distance {
              type uint32 {
                range "1..20000" {
                  description
                    "Distance for routes internal to the AS";
                }
              }
              description
                "Distance for routes internal to the AS";
            }
            leaf local-route-distance {
              type uint32 {
                range "1..20000" {
                  description
                    "Distance for local routes";
                }
              }
              description
                "Distance for local routes";
            }
          }
        }
        container optimal-route-reflections {
          description
            "Configure optimal-route-reflection group.[Maximum ORR groups is 255]. Currently only supported in Global V4/V6 address family";
          list optimal-route-reflection {
            must "primary-root";
            key "optimal-route-reflection-name";
            description
              "Configure optimal-route-reflection group.[Maximum ORR groups is 255]. Currently only supported in Global V4/V6 address family";
            leaf optimal-route-reflection-name {
              type xr:Cisco-ios-xr-string {
                length "1..32" {
                  description
                    "ORR group name - maximum 32 characters";
                }
              }
              description
                "ORR group name - maximum 32 characters";
            }
            leaf primary-root {
              type inet:ip-address-no-zone;
              description
                "IP primary root address";
            }
            leaf secondary-root {
              type inet:ip-address-no-zone;
              must "../primary-root";
              description
                "IP secondary root address";
            }
            leaf tertiary-root {
              type inet:ip-address-no-zone;
              must "../primary-root and ../secondary-root";
              description
                "IP tertiary root address";
            }
          }
          container applies {
            description
              "Apply optimal-route-reflection group";
            list apply {
              key "apply-string";
              description
                "Apply optimal-route-reflection group";
              leaf apply-string {
                type xr:Cisco-ios-xr-string {
                  length "1..32" {
                    description
                      "ORR group name - maximum 32 characters";
                  }
                }
                description
                  "ORR group name - maximum 32 characters";
              }
            }
          }
          leaf fallback-default-bestpath {
            type empty;
            description
              "In case none of the paths are accessible in an ORR table, fallback to default table bestpath as ORR bestpath";
          }
        }
        container maximum-paths {
          description
            "Forward packets over multiple paths";
          container ebgp {
            presence "eBGP-multipath";
            description
              "eBGP-multipath";
            leaf ebgp-number {
              type uint32 {
                range "2..1024" {
                  description
                    "Number of paths (limit includes backup path)";
                }
              }
              mandatory true;
              description
                "Number of paths (limit includes backup path)";
            }
            leaf selective {
              type empty;
              description
                "Allow multipaths only from marked neighbors";
            }
            leaf route-policy {
              type xr:Route-policy-name;
              description
                "Route policy to specify ORF and inbound filter";
            }
          }
          container ibgp {
            presence "iBGP-multipath";
            description
              "iBGP-multipath";
            leaf ibgp-number {
              type uint32 {
                range "2..1024" {
                  description
                    "Number of paths (limit includes backup path)";
                }
              }
              mandatory true;
              description
                "Number of paths (limit includes backup path)";
            }
            container unequal-cost {
              presence "Allow multipaths to have different BGP nexthop IGP metrics";
              description
                "Allow multipaths to have different BGP nexthop IGP metrics";
              leaf deterministic {
                type empty;
                description
                  "Deterministic Multipath selection primarily on IGP metric order";
              }
            }
            leaf selective {
              type empty;
              description
                "Allow multipaths only from marked neighbors";
            }
            leaf route-policy {
              type xr:Route-policy-name;
              description
                "Route policy to specify ORF and inbound filter";
            }
          }
          container eibgp {
            presence "eiBGP-multipath";
            description
              "eiBGP-multipath";
            leaf eibgp-number {
              type uint32 {
                range "2..1024" {
                  description
                    "Number of paths (limit includes backup path)";
                }
              }
              mandatory true;
              description
                "Number of paths (limit includes backup path)";
            }
            leaf equal-cost {
              type empty;
              description
                "Preserve equal nexthop IGP metric criteria for multipath eligiblity between same path-types (iBGP or eBGP)";
            }
            leaf selective {
              type empty;
              description
                "Allow multipaths only from marked neighbors";
            }
            leaf route-policy {
              type xr:Route-policy-name;
              description
                "Route policy to specify ORF and inbound filter";
            }
          }
          leaf unique-nexthop-check-disable {
            type empty;
            description
              "Disable multipath unique nexthop check";
          }
        }
        container import {
          description
            "Configure import rules";
          container from {
            description
              "Import routes from source";
            leaf bridge-domain {
              type empty;
              description
                "Import IP hosts from EVPN bridge-domain";
            }
          }
        }
        container additional-paths {
          description
            "Additional paths configuration";
          container send {
            presence "Additional paths Send capability";
            description
              "Additional paths Send capability";
            leaf disable {
              type empty;
              description
                "Do not advertise additional paths Send capability";
            }
          }
          container receive {
            presence "Additional paths Receive capability";
            description
              "Additional paths Receive capability";
            leaf disable {
              type empty;
              description
                "Do not advertise additional paths Receive capability";
            }
          }
          container advertise-limit {
            description
              "advertise-limit";
            choice ADVERTISE-LIMIT {
              description
                "advertise-limit";
              case DISABLE {
                leaf disable {
                  type empty;
                  description
                    "Disable additional paths selection";
                }
              }
              case ADVERTISE-PATH-LIMIT {
                leaf advertise-path-limit {
                  type uint32 {
                    range "1..20000" {
                      description
                        "Advertise path limit value";
                    }
                  }
                  description
                    "Limit the number of paths to be advertised (default 32)";
                }
              }
            }
          }
          container selection {
            description
              "Additional paths selection";
            choice SELECTION {
              description
                "Additional paths selection";
              case DISABLE {
                leaf disable {
                  type empty;
                  description
                    "Disable additional paths selection";
                }
              }
              case ROUTE-POLICY {
                leaf route-policy {
                  type xr:Route-policy-name;
                  description
                    "Route-policy for additional paths selection";
                }
              }
            }
          }
        }
        container permanent-network {
          description
            "Permanent network configuration";
          leaf route-policy {
            type xr:Route-policy-name;
            description
              "Route policy to read the prefixes from";
          }
        }
        container advertise {
          description
            "Advertise BGP path";
          container local-labeled-route {
            description
              "Advertisement of routes with local-label";
            leaf safi-unicast {
              type enumeration {
                enum "enable" {
                  value 1;
                  description
                    "Advertise routes with local-label via Unicast SAFI";
                }
                enum "disable" {
                  value 2;
                  description
                    "Do not advertise routes with local-label via Unicast SAFI";
                }
              }
              description
                "Advertisement of routes with local-label via Unicast SAFI";
            }
          }
          container best-external {
            presence "Advertise best-external path";
            description
              "Advertise best-external path";
            leaf labeled-unicast {
              type empty;
              description
                "Limit best-external to Labeled-Unicast address family";
            }
            leaf disable {
              type empty;
              description
                "Do not advertise best-external path";
            }
          }
          container epe-bgp {
            description
              "Advertise bgp epe as label unicast prefix";
            leaf labeled-unicast {
              type empty;
              description
                "Limit epe-bgplu to Labeled-Unicast address family";
            }
          }
        }
        container networks {
          description
            "Specify a network to announce via BGP";
          list network {
            key "address address-prefix";
            description
              "Specify a network to announce via BGP";
            leaf address {
              type inet:ip-address-no-zone;
              description
                "IPaddress";
            }
            leaf address-prefix {
              type uint32 {
                range "0..128";
              }
              description
                "IP address prefix";
            }
            choice NETWORK {
              description
                "Specify a network to announce via BGP";
              case ROUTE-POLICY {
                leaf route-policy {
                  type xr:Route-policy-name;
                  description
                    "Route-policy to modify the attributes";
                }
              }
              case BACKDOOR {
                leaf backdoor {
                  type empty;
                  description
                    "Specify a BGP backdoor route";
                }
              }
              case MULTIPATH {
                leaf multipath {
                  type empty;
                  description
                    "Enable installation of multiple paths from RIB";
                }
              }
            }
          }
        }
        container aggregate-addresses {
          description
            "Configure BGP aggregate entries";
          list aggregate-address {
            key "address address-prefix";
            description
              "Configure BGP aggregate entries";
            leaf address {
              type inet:ip-address-no-zone;
              description
                "IPaddress";
            }
            leaf address-prefix {
              type uint32 {
                range "0..128";
              }
              description
                "IP address prefix";
            }
            leaf as-set {
              type empty;
              description
                "Generate AS set path information";
            }
            leaf as-confed-set {
              type empty;
              description
                "Generate AS confed set path information";
            }
            leaf summary-only {
              type empty;
              description
                "Filter more specific routes from updates";
            }
            leaf route-policy {
              type xr:Route-policy-name;
              description
                "Route-policy to modify the attributes";
            }
            leaf description {
              type xr:Cisco-ios-xr-string {
                length "1..1024" {
                  description
                    "Description";
                }
              }
              description
                "Aggreate address specific description";
            }
            leaf set-tag {
              type uint32 {
                range "0..4294967295";
              }
              description
                "Set a IGP tag value on the route";
            }
          }
        }
        container redistribute {
          description
            "Redistribute information from another routing protocol";

          grouping REDISTRIBUTE {
            description
              "redistribute";
            leaf metric {
              type uint32 {
                range "0..4294967295" {
                  description
                    "Default metric";
                }
              }
              description
                "Metric for redistributed routes";
            }
            leaf multipath {
              type empty;
              description
                "Enable installation of multiple paths from RIB";
            }
            leaf route-policy {
              type xr:Route-policy-name;
              description
                "Route policy reference";
            }
            leaf default-policy-action-in {
              type enumeration {
                enum "accept" {
                  value 1;
                  description
                    "accept the route if does not satisfy the import policy";
                }
                enum "reject" {
                  value 2;
                  description
                    "reject the route if does not satisfy the import policy";
                }
              }
              description
                "Set a default action if a route does not satify the policy definition";
            }
          }
          container ospfs {
            description
              "Open Shortest Path First (OSPF)";
            list ospf {
              key "ospf-router-tag";
              description
                "Open Shortest Path First (OSPF)";
              leaf ospf-router-tag {
                type string {
                  length "1..1024" {
                    description
                      "OSPF router tag";
                  }
                }
                description
                  "OSPF router tag";
              }
              container match {
                description
                  "Redistribution of OSPF routes";
                choice MATCH {
                  description
                    "Redistribution of OSPF routes";
                  case INTERNAL {
                    container internal {
                      presence "Redistribute OSPF internal routes";
                      description
                        "Redistribute OSPF internal routes";
                      choice INTERNAL {
                        description
                          "Redistribute OSPF internal routes";
                        case EXTERNAL {
                          container external {
                            presence "Redistribute OSPF external routes";
                            description
                              "Redistribute OSPF external routes";
                            choice EXTERNAL {
                              description
                                "Redistribute OSPF external routes";
                              case ONE {
                                container one {
                                  presence "Redistribute external type 1 routes";
                                  description
                                    "Redistribute external type 1 routes";
                                  container nssa-external {
                                    presence "Redistribute OSPF NSSA external routes";
                                    description
                                      "Redistribute OSPF NSSA external routes";
                                    choice NSSA-EXTERNAL {
                                      description
                                        "Redistribute OSPF NSSA external routes";
                                      case ONE {
                                        leaf one {
                                          type empty;
                                          description
                                            "Redistribute NSSA external type 1 routes";
                                        }
                                      }
                                      case TWO {
                                        leaf two {
                                          type empty;
                                          description
                                            "Redistribute NSSA external type 2 routes";
                                        }
                                      }
                                    }
                                  }
                                }
                              }
                              case TWO {
                                container two {
                                  presence "Redistribute external type 2 routes";
                                  description
                                    "Redistribute external type 2 routes";
                                  container nssa-external {
                                    presence "Redistribute OSPF NSSA external routes";
                                    description
                                      "Redistribute OSPF NSSA external routes";
                                    choice NSSA-EXTERNAL {
                                      description
                                        "Redistribute OSPF NSSA external routes";
                                      case ONE {
                                        leaf one {
                                          type empty;
                                          description
                                            "Redistribute NSSA external type 1 routes";
                                        }
                                      }
                                      case TWO {
                                        leaf two {
                                          type empty;
                                          description
                                            "Redistribute NSSA external type 2 routes";
                                        }
                                      }
                                    }
                                  }
                                }
                              }
                              case NSSA-EXTERNAL {
                                container nssa-external {
                                  presence "Redistribute OSPF NSSA external routes";
                                  description
                                    "Redistribute OSPF NSSA external routes";
                                  choice NSSA-EXTERNAL {
                                    description
                                      "Redistribute OSPF NSSA external routes";
                                    case ONE {
                                      leaf one {
                                        type empty;
                                        description
                                          "Redistribute NSSA external type 1 routes";
                                      }
                                    }
                                    case TWO {
                                      leaf two {
                                        type empty;
                                        description
                                          "Redistribute NSSA external type 2 routes";
                                      }
                                    }
                                  }
                                }
                              }
                            }
                          }
                        }
                        case NSSA-EXTERNAL {
                          container nssa-external {
                            presence "Redistribute OSPF NSSA external routes";
                            description
                              "Redistribute OSPF NSSA external routes";
                            choice NSSA-EXTERNAL {
                              description
                                "Redistribute OSPF NSSA external routes";
                              case ONE {
                                leaf one {
                                  type empty;
                                  description
                                    "Redistribute NSSA external type 1 routes";
                                }
                              }
                              case TWO {
                                leaf two {
                                  type empty;
                                  description
                                    "Redistribute NSSA external type 2 routes";
                                }
                              }
                            }
                          }
                        }
                      }
                    }
                  }
                  case EXTERNAL {
                    container external {
                      presence "Redistribute OSPF external routes";
                      description
                        "Redistribute OSPF external routes";
                      choice EXTERNAL {
                        description
                          "Redistribute OSPF external routes";
                        case ONE {
                          container one {
                            presence "Redistribute external type 1 routes";
                            description
                              "Redistribute external type 1 routes";
                            container nssa-external {
                              presence "Redistribute OSPF NSSA external routes";
                              description
                                "Redistribute OSPF NSSA external routes";
                              choice NSSA-EXTERNAL {
                                description
                                  "Redistribute OSPF NSSA external routes";
                                case ONE {
                                  leaf one {
                                    type empty;
                                    description
                                      "Redistribute NSSA external type 1 routes";
                                  }
                                }
                                case TWO {
                                  leaf two {
                                    type empty;
                                    description
                                      "Redistribute NSSA external type 2 routes";
                                  }
                                }
                              }
                            }
                          }
                        }
                        case TWO {
                          container two {
                            presence "Redistribute external type 2 routes";
                            description
                              "Redistribute external type 2 routes";
                            container nssa-external {
                              presence "Redistribute OSPF NSSA external routes";
                              description
                                "Redistribute OSPF NSSA external routes";
                              leaf one {
                                type empty;
                                description
                                  "Redistribute NSSA external type 1 routes";
                              }
                              leaf two {
                                type empty;
                                description
                                  "Redistribute NSSA external type 2 routes";
                              }
                            }
                          }
                        }
                        case NSSA-EXTERNAL {
                          container nssa-external {
                            presence "Redistribute OSPF NSSA external routes";
                            description
                              "Redistribute OSPF NSSA external routes";
                            choice NSSA-EXTERNAL {
                              description
                                "Redistribute OSPF NSSA external routes";
                              case ONE {
                                leaf one {
                                  type empty;
                                  description
                                    "Redistribute NSSA external type 1 routes";
                                }
                              }
                              case TWO {
                                leaf two {
                                  type empty;
                                  description
                                    "Redistribute NSSA external type 2 routes";
                                }
                              }
                            }
                          }
                        }
                      }
                    }
                  }
                  case NSSA-EXTERNAL {
                    container nssa-external {
                      presence "Redistribute OSPF NSSA external routes";
                      description
                        "Redistribute OSPF NSSA external routes";
                      choice NSSA-EXTERNAL {
                        description
                          "Redistribute OSPF NSSA external routes";
                        case ONE {
                          leaf one {
                            type empty;
                            description
                              "Redistribute NSSA external type 1 routes";
                          }
                        }
                        case TWO {
                          leaf two {
                            type empty;
                            description
                              "Redistribute NSSA external type 2 routes";
                          }
                        }
                      }
                    }
                  }
                }
              }
              uses REDISTRIBUTE;
            }
          }
          container ospfv3s {
            description
              "IPv6 Open Shortest Path First (OSPFv3)";
            list ospfv3 {
              key "ospfv3-router-tag";
              description
                "IPv6 Open Shortest Path First (OSPFv3)";
              leaf ospfv3-router-tag {
                type string {
                  length "1..1024" {
                    description
                      "OSPFv3 router tag";
                  }
                }
                description
                  "OSPFv3 router tag";
              }
              container match {
                description
                  "Redistribution of OSPF routes";
                choice MATCH {
                  description
                    "Redistribution of OSPF routes";
                  case INTERNAL {
                    container internal {
                      presence "Redistribute OSPF internal routes";
                      description
                        "Redistribute OSPF internal routes";
                      choice INTERNAL {
                        description
                          "Redistribute OSPF internal routes";
                        case EXTERNAL {
                          container external {
                            presence "Redistribute OSPF external routes";
                            description
                              "Redistribute OSPF external routes";
                            choice EXTERNAL {
                              description
                                "Redistribute OSPF external routes";
                              case ONE {
                                container one {
                                  presence "Redistribute external type 1 routes";
                                  description
                                    "Redistribute external type 1 routes";
                                  container nssa-external {
                                    presence "Redistribute OSPF NSSA external routes";
                                    description
                                      "Redistribute OSPF NSSA external routes";
                                    choice NSSA-EXTERNAL {
                                      description
                                        "Redistribute OSPF NSSA external routes";
                                      case ONE {
                                        leaf one {
                                          type empty;
                                          description
                                            "Redistribute NSSA external type 1 routes";
                                        }
                                      }
                                      case TWO {
                                        leaf two {
                                          type empty;
                                          description
                                            "Redistribute NSSA external type 2 routes";
                                        }
                                      }
                                    }
                                  }
                                }
                              }
                              case TWO {
                                container two {
                                  presence "Redistribute external type 2 routes";
                                  description
                                    "Redistribute external type 2 routes";
                                  container nssa-external {
                                    presence "Redistribute OSPF NSSA external routes";
                                    description
                                      "Redistribute OSPF NSSA external routes";
                                    choice NSSA-EXTERNAL {
                                      description
                                        "Redistribute OSPF NSSA external routes";
                                      case ONE {
                                        leaf one {
                                          type empty;
                                          description
                                            "Redistribute NSSA external type 1 routes";
                                        }
                                      }
                                      case TWO {
                                        leaf two {
                                          type empty;
                                          description
                                            "Redistribute NSSA external type 2 routes";
                                        }
                                      }
                                    }
                                  }
                                }
                              }
                              case NSSA-EXTERNAL {
                                container nssa-external {
                                  presence "Redistribute OSPF NSSA external routes";
                                  description
                                    "Redistribute OSPF NSSA external routes";
                                  choice NSSA-EXTERNAL {
                                    description
                                      "Redistribute OSPF NSSA external routes";
                                    case ONE {
                                      leaf one {
                                        type empty;
                                        description
                                          "Redistribute NSSA external type 1 routes";
                                      }
                                    }
                                    case TWO {
                                      leaf two {
                                        type empty;
                                        description
                                          "Redistribute NSSA external type 2 routes";
                                      }
                                    }
                                  }
                                }
                              }
                            }
                          }
                        }
                        case NSSA-EXTERNAL {
                          container nssa-external {
                            presence "Redistribute OSPF NSSA external routes";
                            description
                              "Redistribute OSPF NSSA external routes";
                            choice NSSA-EXTERNAL {
                              description
                                "Redistribute OSPF NSSA external routes";
                              case ONE {
                                leaf one {
                                  type empty;
                                  description
                                    "Redistribute NSSA external type 1 routes";
                                }
                              }
                              case TWO {
                                leaf two {
                                  type empty;
                                  description
                                    "Redistribute NSSA external type 2 routes";
                                }
                              }
                            }
                          }
                        }
                      }
                    }
                  }
                  case EXTERNAL {
                    container external {
                      presence "Redistribute OSPF external routes";
                      description
                        "Redistribute OSPF external routes";
                      choice EXTERNAL {
                        description
                          "Redistribute OSPF external routes";
                        case ONE {
                          container one {
                            presence "Redistribute external type 1 routes";
                            description
                              "Redistribute external type 1 routes";
                            container nssa-external {
                              presence "Redistribute OSPF NSSA external routes";
                              description
                                "Redistribute OSPF NSSA external routes";
                              choice NSSA-EXTERNAL {
                                description
                                  "Redistribute OSPF NSSA external routes";
                                case ONE {
                                  leaf one {
                                    type empty;
                                    description
                                      "Redistribute NSSA external type 1 routes";
                                  }
                                }
                                case TWO {
                                  leaf two {
                                    type empty;
                                    description
                                      "Redistribute NSSA external type 2 routes";
                                  }
                                }
                              }
                            }
                          }
                        }
                        case TWO {
                          container two {
                            presence "Redistribute external type 2 routes";
                            description
                              "Redistribute external type 2 routes";
                            container nssa-external {
                              presence "Redistribute OSPF NSSA external routes";
                              description
                                "Redistribute OSPF NSSA external routes";
                              leaf one {
                                type empty;
                                description
                                  "Redistribute NSSA external type 1 routes";
                              }
                              leaf two {
                                type empty;
                                description
                                  "Redistribute NSSA external type 2 routes";
                              }
                            }
                          }
                        }
                        case NSSA-EXTERNAL {
                          container nssa-external {
                            presence "Redistribute OSPF NSSA external routes";
                            description
                              "Redistribute OSPF NSSA external routes";
                            choice NSSA-EXTERNAL {
                              description
                                "Redistribute OSPF NSSA external routes";
                              case ONE {
                                leaf one {
                                  type empty;
                                  description
                                    "Redistribute NSSA external type 1 routes";
                                }
                              }
                              case TWO {
                                leaf two {
                                  type empty;
                                  description
                                    "Redistribute NSSA external type 2 routes";
                                }
                              }
                            }
                          }
                        }
                      }
                    }
                  }
                  case NSSA-EXTERNAL {
                    container nssa-external {
                      presence "Redistribute OSPF NSSA external routes";
                      description
                        "Redistribute OSPF NSSA external routes";
                      choice NSSA-EXTERNAL {
                        description
                          "Redistribute OSPF NSSA external routes";
                        case ONE {
                          leaf one {
                            type empty;
                            description
                              "Redistribute NSSA external type 1 routes";
                          }
                        }
                        case TWO {
                          leaf two {
                            type empty;
                            description
                              "Redistribute NSSA external type 2 routes";
                          }
                        }
                      }
                    }
                  }
                }
              }
              uses REDISTRIBUTE;
            }
          }
          container eigrps {
            description
              "Enhanced Interior Gateway Routing Protocol (EIGRP)";
            list eigrp {
              key "eigrp-name";
              description
                "Enhanced Interior Gateway Routing Protocol (EIGRP)";
              leaf eigrp-name {
                type string {
                  length "1..1024" {
                    description
                      "EIGRP instance name";
                  }
                }
                description
                  "EIGRP instance name";
              }
              container match {
                description
                  "EIGRP route type for redistribution";
                choice MATCH {
                  description
                    "EIGRP route type for redistribution";
                  case INTERNAL {
                    container internal {
                      presence "Redistribute EIGRP internal routes";
                      description
                        "Redistribute EIGRP internal routes";
                      leaf external {
                        type empty;
                        description
                          "Redistribute EIGRP external routes";
                      }
                    }
                  }
                  case EXTERNAL {
                    leaf external {
                      type empty;
                      description
                        "Redistribute EIGRP external routes";
                    }
                  }
                }
              }
              uses REDISTRIBUTE;
            }
          }
          container isis-processes {
            description
              "ISO IS-IS";
            list isis-process {
              key "isis-name";
              description
                "ISO IS-IS";
              leaf isis-name {
                type string {
                  length "1..1024" {
                    description
                      "IS-IS instance name";
                  }
                }
                description
                  "IS-IS instance name";
              }
              container level {
                description
                  "Redistribute routes from the specified ISIS levels";
                choice LEVEL {
                  description
                    "Redistribute routes from the specified ISIS levels";
                  case ONE {
                    container one {
                      presence "Redistribute ISIS level 1 routes";
                      description
                        "Redistribute ISIS level 1 routes";
                      container level {
                        description
                          "Redistribute routes from the specified ISIS levels";
                        choice LEVEL {
                          description
                            "Redistribute routes from the specified ISIS levels";
                          case TWO {
                            container two {
                              presence "Redistribute ISIS level 2 ISIS routes";
                              description
                                "Redistribute ISIS level 2 ISIS routes";
                              container level {
                                description
                                  "Redistribute routes from the specified ISIS levels";
                                leaf one-inter-area {
                                  type empty;
                                  description
                                    "Redistribute ISIS level 1 inter-area routes";
                                }
                              }
                            }
                          }
                          case ONE-INTER-AREA {
                            leaf one-inter-area {
                              type empty;
                              description
                                "Redistribute ISIS level 1 inter-area routes";
                            }
                          }
                        }
                      }
                    }
                  }
                  case TWO {
                    container two {
                      presence "Redistribute ISIS level 2 ISIS routes";
                      description
                        "Redistribute ISIS level 2 ISIS routes";
                      container level {
                        description
                          "Redistribute routes from the specified ISIS levels";
                        leaf one-inter-area {
                          type empty;
                          description
                            "Redistribute ISIS level 1 inter-area routes";
                        }
                      }
                    }
                  }
                  case ONE-INTER-AREA {
                    leaf one-inter-area {
                      type empty;
                      description
                        "Redistribute ISIS level 1 inter-area routes";
                    }
                  }
                }
              }
              uses REDISTRIBUTE;
            }
          }
          container connected {
            presence "Connected routes";
            description
              "Connected routes";
            uses REDISTRIBUTE;
          }
          container static {
            presence "Static routes";
            description
              "Static routes";
            uses REDISTRIBUTE;
          }
          container rip {
            presence "Routing Information Protocol (RIP)";
            description
              "Routing Information Protocol (RIP)";
            uses REDISTRIBUTE;
          }
          container subscriber {
            presence "subscriber routes";
            description
              "subscriber routes";
            uses REDISTRIBUTE;
          }
          container mobile {
            presence "Mobile routes";
            description
              "Mobile routes";
            uses REDISTRIBUTE;
          }
          container lisp {
            presence "Locator/ID Separation Protocol (LISP)";
            description
              "Locator/ID Separation Protocol (LISP)";
            uses REDISTRIBUTE;
          }
          container applications {
            description
              "OnePK application routes";
            list application {
              key "application-name";
              description
                "OnePK application routes";
              leaf application-name {
                type string {
                  length "1..1024" {
                    description
                      "OnePK application name";
                  }
                }
                description
                  "OnePK application name";
              }
              uses REDISTRIBUTE;
            }
          }
        }
        leaf table-policy {
          type xr:Route-policy-name;
          description
            "Configure policy for installation of routes to RIB";
        }
        container retain {
          description
            "Accept/Retain specified bgp parameters";
          container route-target {
            description
              "Accept received updates with the specified route targets";
            choice ROUTE-TARGET {
              description
                "Accept received updates with the specified route targets";
              case ALL {
                leaf all {
                  type empty;
                  description
                    "Accept received updates containing at least one route target";
                }
              }
              case ROUTE-POLICY {
                leaf route-policy {
                  type xr:Route-policy-name;
                  description
                    "Accept received updates accepted by the specified policy";
                }
              }
            }
          }
          leaf local-label {
            type uint32 {
              range "3..60" {
                description
                  "Label retention time in minutes";
              }
            }
            description
              "Delay the release of the local label as configured";
          }
        }
        container allocate-label {
          description
            "Allocate label for selected prefixes";
          choice ALLOCATE-LABEL {
            description
              "Allocate label for selected prefixes";
            case ALL {
              container all {
                presence "Allocate labels for all prefixes";
                description
                  "Allocate labels for all prefixes";
                leaf unlabeled-path {
                  type empty;
                  description
                    "Allocate label for unlabeled paths too";
                }
              }
            }
            case ROUTE-POLICY {
              container route-policy {
                presence "Use a route policy to select prefixes for label allocation";
                description
                  "Use a route policy to select prefixes for label allocation";
                leaf route-policy-name {
                  type xr:Route-policy-name;
                  mandatory true;
                  description
                    "route-policy-name";
                }
                leaf unlabeled-path {
                  type empty;
                  description
                    "Allocate label for unlabeled paths too";
                }
              }
            }
          }
        }
        container label {
          description
            "Label-related configuration";
          container mode {
            description
              "Select label mode";
            choice MODE {
              description
                "Select label mode";
              case PER-PREFIX {
                leaf per-prefix {
                  type empty;
                  description
                    "Set per perfix label mode";
                }
              }
              case PER-CE {
                leaf per-ce {
                  type empty;
                  description
                    "Set per CE label mode";
                }
              }
              case PER-VRF {
                leaf per-vrf {
                  type empty;
                  description
                    "Set per VRF label mode";
                }
              }
              case PER-VRF-46 {
                leaf per-vrf-46 {
                  type empty;
                  description
                    "Set per VRF 46 label mode";
                }
              }
              case ROUTE-POLICY {
                leaf route-policy {
                  type xr:Route-policy-name;
                  description
                    "Use a route policy to select prefixes for label allocation mode";
                }
              }
              case PER-NEXTHOP-RECEIVED-LABEL {
                container per-nexthop-received-label {
                  presence "Set label mode per nexthop and received label";
                  description
                    "Set label mode per nexthop and received label";
                  leaf allocate-secondary-label {
                    type empty;
                    description
                      "Allocate secondary label to avoid label oscillation insymmetric PIC deployments";
                  }
                }
              }
            }
          }
        }
        container rnh {
          description
            "Remote nexthop";
          container install {
            description
              "Install remote nexthop";
            container extcomm {
              presence "Install remote nexthop in extended community and opaque format";
              description
                "Install remote nexthop in extended community and opaque format";
              leaf only {
                type empty;
                description
                  "Install remote nexthop in extended community format only";
              }
            }
          }
        }
        container prefix-ecmp-delay {
          description
            "Enable delay in best path calculation (will be deprecated from 26.01.01)";
          leaf prefix-ecmp-delay-number {
            type uint32 {
              range "10..60000" {
                description
                  "Interval(ms)";
              }
            }
            description
              "Interval(ms)";
          }
          leaf oor-threshold {
            type uint32 {
              range "10..90" {
                description
                  "Out-Of-Resource threshold (in percentage)";
              }
            }
            must "../prefix-ecmp-delay-number";
            description
              "Delay only when platform resource usage is above threshold";
          }
        }
        container bgp {
          description
            "BGP Commands";
          container origin-as {
            description
              "BGP origin-AS knobs";
            container validation {
              description
                "BGP origin-AS validation knobs";
              leaf enable {
                type empty;
                description
                  "Enable RPKI origin-AS validation";
              }
              container signal {
                description
                  "Signal origin-AS validity towards peers";
                leaf ibgp {
                  type empty;
                  description
                    "Signal origin-AS validity towards iBGP peers";
                }
              }
            }
          }
          container bestpath {
            description
              "Change default route selection criteria";
            container origin-as {
              description
                "BGP origin-AS knobs";
              container use {
                description
                  "BGP origin-AS knobs";
                leaf validity {
                  type empty;
                  description
                    "BGP bestpath selection will use origin-AS validity";
                }
              }
              container allow {
                description
                  "BGP origin-AS knobs";
                leaf invalid {
                  type empty;
                  description
                    "BGP bestpath selection will allow 'invalid' origin-AS";
                }
              }
            }
          }
          leaf scan-time {
            type uint32 {
              range "5..3600" {
                description
                  "Scanner interval (seconds)";
              }
            }
            description
              "Configure background scanner interval for this address-family";
          }
          leaf attribute-download {
            type empty;
            description
              "Configure attribute download for this address-family";
          }
          leaf implicit-import {
            type empty;
            description
              "Configure implicit import for this address-family";
          }
          container import-delay {
            description
              "Specify delay for batching import processing";
            leaf import-delay-seconds {
              type uint32 {
                range "0..10" {
                  description
                    "Delay, seconds part";
                }
              }
              must "../import-delay-milliseconds";
              description
                "Delay, seconds part";
            }
            leaf import-delay-milliseconds {
              type uint32 {
                range "0..999" {
                  description
                    "Delay, milliseconds part";
                }
              }
              must "../import-delay-seconds";
              description
                "Delay, milliseconds part";
            }
          }
          container label-delay {
            description
              "Specify delay for batching label processing";
            leaf label-delay-seconds {
              type uint32 {
                range "0..10" {
                  description
                    "Delay, seconds part";
                }
              }
              description
                "Delay, seconds part";
            }
            leaf label-delay-milliseconds {
              type uint32 {
                range "0..999" {
                  description
                    "Delay, milliseconds part";
                }
              }
              description
                "Delay, milliseconds part";
            }
          }
          container client-to-client {
            description
              "Configure client to client route reflection";
            container reflection {
              description
                "Reflection";
              leaf disable {
                type empty;
                description
                  "Disable";
              }
              container cluster-ids {
                description
                  "ID of Cluster for which reflection is to be disabled";
                list cluster-id-number {
                  must "disable";
                  key "cluster-number";
                  description
                    "ID of Cluster for which reflection is to be disabled";
                  leaf cluster-number {
                    type uint32 {
                      range "1..4294967295" {
                        description
                          "Route-Reflector Cluster-id as 32 bit quantity";
                      }
                    }
                    description
                      "Route-Reflector Cluster-id as 32 bit quantity";
                  }
                  leaf disable {
                    type empty;
                    description
                      "Disable";
                  }
                }
                list cluster-id-ip-address {
                  must "disable";
                  key "cluster-ip-address";
                  description
                    "ID of Cluster for which reflection is to be disabled";
                  leaf cluster-ip-address {
                    type inet:ip-address-no-zone;
                    description
                      "Route-Reflector Cluster-id in IP address format";
                  }
                  leaf disable {
                    type empty;
                    description
                      "Disable";
                  }
                }
              }
            }
          }
          container dampening {
            description
              "Enable route-flap dampening";
            choice DAMPENING {
              description
                "Enable route-flap dampening";
              case HALFLIFE-TIME {
                container halflife-time {
                  description
                    "Half-life time for the penalty";
                  leaf half-life-time-number {
                    type uint32 {
                      range "1..255" {
                        description
                          "Half-life time for the penalty";
                      }
                    }
                    description
                      "Half-life time for the penalty";
                  }
                  leaf route-reuse-number {
                    type uint32 {
                      range "1..255" {
                        description
                          "Value to start reusing a route";
                      }
                    }
                    must "../half-life-time-number and ../suppress-route-number and ../stable-route-max-suppress-number";
                    description
                      "Value to start reusing a route";
                  }
                  leaf suppress-route-number {
                    type uint32 {
                      range "1..255" {
                        description
                          "Value to start suppressing a route";
                      }
                    }
                    must "../half-life-time-number and ../route-reuse-number and ../stable-route-max-suppress-number";
                    description
                      "Value to start suppressing a route";
                  }
                  leaf stable-route-max-suppress-number {
                    type uint32 {
                      range "0..4294967295" {
                        description
                          "Maximum duration to suppress a stable route";
                      }
                    }
                    must "../half-life-time-number and ../route-reuse-number and ../suppress-route-number";
                    description
                      "Maximum duration to suppress a stable route";
                  }
                }
              }
              case ROUTE-POLICY {
                leaf route-policy {
                  type xr:Route-policy-name;
                  description
                    "Route policy to specify criteria for dampening";
                }
              }
            }
          }
        }
        container event {
          description
            "Policy for per-prefix tracing";
          container prefix {
            description
              "Policy for per-prefix tracing";
            leaf route-policy {
              type xr:Route-policy-name;
              description
                "Policy for per-prefix tracing";
            }
          }
        }
        container dynamic-med {
          description
            "Dynamic MED Interval";
          leaf interval {
            type uint32 {
              range "0..10" {
                description
                  "Update generation delay in minutes";
              }
            }
            description
              "Update generation delay (in minutes) after a MED change";
          }
        }
        container weight {
          description
            "Define or modify weight";
          container reset-on-import {
            presence "Reset weight of paths on import";
            description
              "Reset weight of paths on import";
            leaf disable {
              type empty;
              description
                "Do not reset weight of paths on import";
            }
          }
        }
        container nexthop {
          description
            "Nexthop";
          leaf route-policy {
            type xr:Route-policy-name;
            description
              "Policy to filter out nexthop notification";
          }
          container trigger-delay {
            description
              "Processing trigger delay";
            leaf critical {
              type uint32 {
                range "0..4294967295" {
                  description
                    "Delay in milliseconds";
                }
              }
              description
                "For critical notification";
            }
            leaf non-critical {
              type uint32 {
                range "0..4294967295" {
                  description
                    "Delay in milliseconds";
                }
              }
              description
                "For non-critical notification";
            }
          }
          container resolution {
            description
              "Nexthop resolution";
            container prefix-length {
              description
                "Nexthop resolution prefix-length";
              container minimum {
                description
                  "Set minimum prefix-length for nexthop resolution";
                leaf ipv6-minimum {
                  type uint32 {
                    range "0..128" {
                      description
                        "Prefix-length value";
                    }
                  }
                  description
                    "IPv6 prefix-length value";
                }
                leaf ipv4-minimum {
                  type uint32 {
                    range "0..32" {
                      description
                        "Prefix-length value";
                    }
                  }
                  description
                    "IPv4 Prefix-length value";
                }
              }
            }
          }
        }
        leaf table-version {
          type uint64 {
            range "0..18446744073709551615" {
              description
                "Version number to be set (0 - 18446744073709551615)";
            }
          }
          description
            "Set BGP table version. Cannot go backwards.";
        }
        container update {
          description
            "BGP Update generation configuration";
          container limit {
            description
              "Upper bound on transient memory usage for update generation";
            container sub-group {
              description
                "Update limit for sub-groups";
              leaf ebgp {
                type uint32 {
                  range "1..512" {
                    description
                      "Update limit in MegaBytes(MB); default is 32 MB";
                  }
                }
                description
                  "Update limit for eBGP sub-groups";
              }
              leaf ibgp {
                type uint32 {
                  range "1..512" {
                    description
                      "Update limit in MegaBytes(MB); default is 32 MB";
                  }
                }
                description
                  "Update limit for iBGP sub-groups";
              }
            }
            leaf address-family {
              type uint32 {
                range "4..2048" {
                  description
                    "Update limit in MegaBytes(MB); default is 256 MB";
                }
              }
              description
                "Update limit for address-family";
            }
          }
          container wait-install {
            presence "Wait for route install";
            description
              "Wait for route install";
            container delay {
              description
                "Configure a delay";
              leaf startup {
                type uint32 {
                  range "1..600" {
                    description
                      "Delay in seconds";
                  }
                }
                description
                  "Configure a delay for the startup phase";
              }
            }
          }
        }
        container as-path-loopcheck {
          description
            "Configure AS Path loop checking";
          container out {
            description
              "For outbound updates";
            leaf disable {
              type empty;
              description
                "Disable";
            }
          }
        }
        container inter-as {
          description
            "Inter AS";
          leaf install {
            type empty;
            description
              "Install remote mvpn routes in default vrf";
          }
        }
        leaf global-table-multicast {
          type empty;
          description
            "Enable global table multicast";
        }
        leaf segmented-multicast {
          type empty;
          description
            "Enable segmented multicast";
        }
        container label-security {
          description
            "BGP Label Security";
          container asbr {
            description
              "Label Security for ASBR peers";
            leaf rpf {
              type empty;
              description
                "RPF Label Security for Option-B";
            }
          }
        }
        container mvpn {
          description
            "MVPN commands";
          leaf single-forwarder-selection {
            type enumeration {
              enum "highest-ip-address" {
                value 2;
                description
                  "Select PE with highest ip address";
              }
              enum "all" {
                value 1;
                description
                  "Select all paths";
              }
            }
            description
              "Enable single forwarder selection";
          }
        }
        container epe {
          description
            "EPE related Global AFI knobs";
          container backup {
            description
              "Install a Backup path for the EPE labels";
            leaf enable {
              type empty;
              description
                "Enable the EPE backup under current AFI";
            }
          }
        }
        leaf originator-pe-id {
          type inet:ipv4-address-no-zone;
          description
            "Set and send originator PE ID.";
        }
        leaf option-b-asbr-only {
          type empty;
          description
            "Enable the ASBR router for option-B label exchange.This option makes the router an Option B ASBR for EVPN.Its assumed no DCI configs are present";
        }
        container default-martian-check {
          description
            "Martian check default";
          leaf disable {
            type empty;
            description
              "Disable";
          }
        }
        container export {
          description
            "Enable allowing leak/export of non-bestpaths";
          container to {
            description
              "Leak to Destination Vrf";
            container vrf {
              description
                "Enable leak to a destination vrf";
              container allow {
                presence "Allow leak of path-type";
                description
                  "Allow leak of path-type";
                leaf backup {
                  type empty;
                  description
                    "Allow Export of backup path";
                }
                leaf best-external {
                  type empty;
                  description
                    "Allow Export of best-external";
                }
              }
            }
          }
        }
        container segment-routing {
          description
            "Segment Routing";
          leaf prefix-sid-map {
            type empty;
            description
              "Retrieve prefix id mapping from SRMS";
          }
          container srv6 {
            presence "Specify SRv6 configurations";
            description
              "Specify SRv6 configurations";
            container alloc {
              description
                "SID Allocation";
              container mode {
                description
                  "SID Allocation mode";
                choice MODE {
                  description
                    "SID Allocation mode";
                  case PER-CE {
                    leaf per-ce {
                      type empty;
                      description
                        "Set SRv6 per CE SID mode";
                    }
                  }
                  case PER-VRF {
                    leaf per-vrf {
                      type empty;
                      description
                        "Set SRv6 per VRF SID mode";
                    }
                  }
                  case PER-VRF-46 {
                    leaf per-vrf-46 {
                      type empty;
                      description
                        "Set SRv6 per VRF 46 SID mode";
                    }
                  }
                  case ROUTE-POLICY {
                    leaf route-policy {
                      type xr:Route-policy-name;
                      description
                        "Use a route policy to determine the SID allocation mode and locator (if provided) for given prefix";
                    }
                  }
                }
              }
            }
            leaf locator {
              type xr:Cisco-ios-xr-string {
                length "1..1024" {
                  description
                    "locator name";
                }
              }
              description
                "Specify locator";
            }
            container usid {
              description
                "Micro-SID configuration";
              container allocation {
                description
                  "Allocation mode";
                leaf wide-local-id-block {
                  type empty;
                  description
                    "Wide LIB allocation";
                }
              }
            }
          }
        }
        container peer-set-ids {
          description
            "configuration for a single EPE Peer Set";
          list peer-set-id {
            key "peer-set-id-number";
            description
              "configuration for a single EPE Peer Set";
            leaf peer-set-id-number {
              type uint32 {
                range "1..255" {
                  description
                    "Identifier for Each Peer-set SID we are going to create";
                }
              }
              description
                "Identifier for Each Peer-set SID we are going to create";
            }
            container peer-set-sid {
              description
                "configure a SID for peer-set EPE object";
              leaf index {
                type uint32 {
                  range "0..1033575" {
                    description
                      "Segment Index to be assigned to this peer-set. The index will be off SRLB
                       Note: This is the maximum index configurable in dynaminc SRLB range.
                       Since SRLB can be a dynamic range, actual maximum index can vary.
                       So please look at the currently configured SRLB range";
                  }
                }
                description
                  "Segment Index value to assign. This will be off SRLB range";
              }
            }
          }
        }
      }
    }
    container mpls {
      description
        "Enable mpls parameters";
      container activate {
        description
          "Enter mpls interfaces in BGP mpls activate mode";
        container interfaces {
          description
            "Interface to enable mpls";
          list interface {
            key "interface-name";
            description
              "Interface to enable mpls";
            leaf interface-name {
              type xr:Interface-name;
              description
                "Select an interface to configure";
            }
          }
        }
      }
    }
    container as-league {
      presence "AS League command mode";
      description
        "AS League command mode";
      container peers {
        description
          "AS League peers mode";
        list peer {
          key "peer-as-number";
          description
            "AS League peers mode";
          leaf peer-as-number {
            type xr:Bgp-as-number;
            description
              "AS number";
          }
        }
      }
    }
    container attribute-filter {
      description
        "Attribute-filter configuration";
      container groups {
        description
          "Attribute-filter group command mode";
        list group {
          key "group-name";
          description
            "Attribute-filter group command mode";
          leaf group-name {
            type string {
              length "1..1024" {
                description
                  "Attribute-filter group name";
              }
            }
            description
              "Attribute-filter group name";
          }
          container attributes {
            description
              "Attribute code";
            container attribute-code-ranges {
              description
                "Attribute code in range";
              list attribute-code-range {
                must "discard or treat-as-withdraw";
                key "start end";
                description
                  "Attribute code in range";
                leaf start {
                  type uint32 {
                    range "4..255";
                  }
                  description
                    "Attribute code range start";
                }
                leaf end {
                  type uint32 {
                    range "5..255";
                  }
                  description
                    "Attribute code range end";
                }
                leaf discard {
                  type empty;
                  description
                    "Discard this attribute";
                }
                leaf treat-as-withdraw {
                  type empty;
                  description
                    "Treat the update message as a Withdraw";
                }
              }
            }
            list attribute {
              must "discard or treat-as-withdraw";
              key "attribute-code";
              description
                "Attribute code";
              leaf attribute-code {
                type enumeration {
                  enum "MULTI-EXIT-DISC" {
                    value 4;
                    description
                      "MED attribute (4)";
                  }
                  enum "LOCAL-PREF" {
                    value 5;
                    description
                      "Local Preference attribute (5)";
                  }
                  enum "ATOMIC-AGGREGATE" {
                    value 6;
                    description
                      "Atomic aggrgate attribute (6)";
                  }
                  enum "AGGREGATOR" {
                    value 7;
                    description
                      "Aggregator attribute (7)";
                  }
                  enum "COMMUNITY" {
                    value 8;
                    description
                      "Community attribute (8)";
                  }
                  enum "ORIGINATOR-ID" {
                    value 9;
                    description
                      "Originator attribute (9)";
                  }
                  enum "CLUSTER-LIST" {
                    value 10;
                    description
                      "Cluster List attribute (10)";
                  }
                  enum "EXTENDED-COMMUNITIES" {
                    value 16;
                    description
                      "Extended community attribute (16)";
                  }
                  enum "AS4-PATH" {
                    value 17;
                    description
                      "AS4_PATH attribute (17)";
                  }
                  enum "AS4-AGGREGATOR" {
                    value 18;
                    description
                      "AS4_AGGREGATOR attribute (18)";
                  }
                  enum "SSA" {
                    value 19;
                    description
                      "SAFI specific attribute (19)";
                  }
                  enum "CONNECTOR" {
                    value 20;
                    description
                      "Connector attribute (20)";
                  }
                  enum "PMSI-TUNNEL" {
                    value 22;
                    description
                      "PMSI Tunnel attribute (22)";
                  }
                  enum "AIGP" {
                    value 26;
                    description
                      "AIGP attribute (26)";
                  }
                  enum "LARGE-COMMUNITY" {
                    value 32;
                    description
                      "Large Community attribute (32)";
                  }
                  enum "PPMP" {
                    value 70;
                    description
                      "PPMP attribute (70)";
                  }
                  enum "LSATTR" {
                    value 99;
                    description
                      "Link-state attribute (29)";
                  }
                  enum "ATTRSET" {
                    value 128;
                    description
                      "ATTR_SET attribute (128)";
                  }
                  enum "TUNNEL-ENCAP" {
                    value 23;
                    description
                      "Tunnel-Encapsulation attribute (23)";
                  }
                  enum "PREFIX-SID" {
                    value 40;
                    description
                      "Prefix-SID attribute (40)";
                  }
                  enum "unrecognized" {
                    value 256;
                    description
                      "All unrecognized attributes";
                  }
                  enum "zero" {
                    value 0;
                    description
                      "Attribute code";
                  }
                }
                description
                  "Attribute code. Also to be set as range start";
              }
              leaf discard {
                type empty;
                description
                  "Discard this attribute";
              }
              leaf treat-as-withdraw {
                type empty;
                description
                  "Treat the update message as a Withdraw";
              }
            }
          }
        }
      }
    }
    container as-lists {
      description
        "List of AS numbers";
      list as-list {
        key "as-list-name";
        description
          "List of AS numbers";
        leaf as-list-name {
          type xr:Cisco-ios-xr-string {
            length "1..1024" {
              description
                "as-list name";
            }
          }
          description
            "as-list name";
        }
        container as-list-numbers {
          description
            "AS number";
          list as-list-number {
            key "as-list-value";
            description
              "AS number";
            leaf as-list-value {
              type xr:Bgp-as-number;
              description
                "AS number";
            }
          }
        }
      }
    }
    container adjacencies {
      description
        "Submode to configure adjacencies in an EPE set";
      container ip-addresses {
        description
          "Firsthop address of the adjacency";
        list ip-address {
          key "address";
          description
            "Firsthop address of the adjacency";
          leaf address {
            type inet:ip-address-no-zone;
            description
              "Firsthop address of the adjacency";
          }
          container peer-sets {
            description
              "Assign this adjacency to a peer-set used for egress peer engineering";
            list peer-set {
              key "peer-set-number";
              description
                "Assign this adjacency to a peer-set used for egress peer engineering";
              leaf peer-set-number {
                type uint32 {
                  range "1..255" {
                    description
                      "Identity value of peer-set";
                  }
                }
                description
                  "Identity value of peer-set";
              }
            }
          }
          container adjacency-sid {
            description
              "Configure SID value for this Adjacency EPE object";
            leaf index {
              type uint32 {
                range "0..1033575" {
                  description
                    "Segment Index to be assigned to this adjacency. The index will be off SRLB
                     Note: This is the maximum index configurable in dynaminc SRLB range.
                     Since SRLB can be a dynamic range, actual maximum index can vary.
                     So please look at the currently configured SRLB range";
                }
              }
              description
                "Segment Index value to assign. This will be off SRLB range";
            }
          }
        }
      }
    }
    container default-information {
      description
        "Control distribution of default information";
      leaf originate {
        type empty;
        description
          "Distribute a default route";
      }
    }
    leaf default-metric {
      type uint32 {
        range "1..4294967295" {
          description
            "Default metric";
        }
      }
      description
        "default redistributed metric";
    }
    container socket {
      description
        "set socket parameters";
      container receive-buffer-size {
        description
          "socket receive buffer size";
        leaf receive-buffer-size-number {
          type uint32 {
            range "512..131072" {
              description
                "Receive socket buffer size in bytes";
            }
          }
          description
            "Receive socket buffer size in bytes";
        }
        leaf bgp-read-buffer-size-byte {
          type uint32 {
            range "512..131072" {
              description
                "BGP Read buffer size in bytes";
            }
          }
          must "../receive-buffer-size-number";
          description
            "BGP Read buffer size in bytes";
        }
      }
      container send-buffer-size {
        description
          "socket send buffer size";
        leaf send-buffer-size-number {
          type uint32 {
            range "4096..131072" {
              description
                "Send socket buffer size in bytes";
            }
          }
          description
            "Send socket buffer size in bytes";
        }
        leaf bgp-write-buffer-size-byte {
          type uint32 {
            range "4096..131072" {
              description
                "BGP Write buffer size in bytes";
            }
          }
          must "../send-buffer-size-number";
          description
            "BGP Write buffer size in bytes";
        }
      }
    }
    container nexthop {
      description
        "Configure next-hop related items";
      container mpls {
        description
          "Configure next-hop related items for mpls";
        container forwarding {
          description
            "Enable next hop mpls forwarding path";
          leaf ibgp {
            type empty;
            description
              "Enable mpls forwarding path for ibgp learnt nexthops";
          }
        }
      }
      container validation {
        description
          "Configure next-hop reachability validation";
        container color-extcomm {
          description
            "Configure next-hop reachability validation for color-extcomm paths";
          leaf disable {
            type empty;
            description
              "Disable next-hop reachability validation for color-extcomm paths";
          }
          leaf sr-policy {
            type empty;
            description
              "Enable BGP next-hop reachability validation by SR Policy for color-extcomm paths";
          }
        }
      }
      container resolution {
        description
          "Configure next-hop related items for resolution";
        leaf allow-default {
          type empty;
          description
            "Enable nexthops resolution using default route";
        }
      }
      container srte-metric {
        description
          "Configure BGP next-hop metric inheritance from SR policy";
        leaf disable {
          type empty;
          description
            "Disable BGP next-hop metric inheritance from SR policy";
        }
      }
    }
    container slow-peer {
      description
        "Configure slow-peer";
      choice SLOW-PEER {
        description
          "Configure slow-peer";
        case DYNAMIC {
          container dynamic {
            presence "Configure all neighbors as dynamic slow-peer";
            description
              "Configure all neighbors as dynamic slow-peer";
            leaf threshold {
              type uint32 {
                range "120..3600" {
                  description
                    "Threshold (in seconds) to detect neighbors as slow-peer";
                }
              }
              description
                "Threshold (in seconds) to detect neighbors as slow-peer";
            }
          }
        }
        case DETECTION-DISABLE {
          leaf detection-disable {
            type empty;
            description
              "Disable dynamic slow-peer detection";
          }
        }
      }
    }
    container optimal-route-reflections {
      description
        "optimal-route-reflections";
      list optimal-route-reflection-ipv4 {
        must "primary-root";
        key "orr-group-name";
        description
          "optimal-route-reflections";
        leaf orr-group-name {
          type xr:Cisco-ios-xr-string {
            length "1..32" {
              description
                "ORR group name - maximum 32 characters";
            }
          }
          description
            "ORR group name - maximum 32 characters";
        }
        leaf primary-root {
          type inet:ip-address-no-zone;
          description
            "IP primary root address";
        }
        leaf secondary-root {
          type inet:ip-address-no-zone;
          description
            "IP secondary root address";
        }
        leaf tertiary-root {
          type inet:ip-address-no-zone;
          must "../secondary-root";
          description
            "IP tertiary root address";
        }
        leaf flex-algo {
          type uint32 {
            range "128..255" {
              description
                "Flexiable Algorithm value";
            }
          }
          must "../primary-root";
          description
            "Flexible Algorithm";
        }
        leaf route-policy {
          type xr:Route-policy-name;
          must "../primary-root";
          description
            "Route-policy for additional paths selection";
        }
      }
      list optimal-route-reflection-ipv6 {
        must "primary-root";
        key "orr-group-name";
        description
          "optimal-route-reflections";
        leaf orr-group-name {
          type xr:Cisco-ios-xr-string {
            length "1..32" {
              description
                "ORR group name - maximum 32 characters";
            }
          }
          description
            "ORR group name - maximum 32 characters";
        }
        leaf primary-root {
          type inet:ip-address-no-zone;
          description
            "IP primary root address";
        }
        leaf secondary-root {
          type inet:ip-address-no-zone;
          description
            "IP secondary root address";
        }
        leaf tertiary-root {
          type inet:ip-address-no-zone;
          must "../secondary-root";
          description
            "IP tertiary root address";
        }
        leaf route-policy {
          type xr:Route-policy-name;
          must "../primary-root";
          description
            "Route-policy for additional paths selection";
        }
      }
    }
    container bgp {
      description
        "BGP commands";
      leaf as-path-loopcheck {
        type empty;
        description
          "Enable AS-path loop checking for iBGP peers";
      }
      container auto-policy-soft-reset {
        description
          "Enable automatic soft peer reset on policy reconfiguration";
        leaf disable {
          type empty;
          description
            "Disable automatic soft peer reset on policy reconfiguration";
        }
      }
      container bestpath {
        description
          "Change default route selection criteria";
        container cost-community {
          description
            "Cost community";
          leaf ignore {
            type empty;
            description
              "Ignore cost-community comparison";
          }
        }
        leaf compare-routerid {
          type empty;
          description
            "Compare router-id for identical EBGP paths";
        }
        container aigp {
          description
            "AIGP attribute";
          leaf ignore {
            type empty;
            description
              "Ignore AIGP attribute";
          }
        }
        container igp-metric {
          description
            "IGP metric values considered at Next Hop metric comparison stage";
          leaf sr-policy {
            type empty;
            description
              "Use next-hop admin/metric from SR policy at Next Hop metric comparison stage";
          }
          leaf ignore {
            type empty;
            description
              "Ignore IGP metric during path comparison";
          }
        }
        container med {
          description
            "MED related";
          leaf missing-as-worst {
            type empty;
            description
              "Treat missing MED as the least preferred one";
          }
          leaf always {
            type empty;
            description
              "Treat missing MED as the least preferred one";
          }
        }
        container as-path {
          description
            "AS path length";
          leaf ignore {
            type empty;
            description
              "Indicates a ignore node is configured.";
          }
          leaf multipath-relax {
            type empty;
            description
              "Indicates a multipath-relax node is configured.";
          }
        }
        container origin-as {
          description
            "BGP origin-AS knobs";
          container use {
            description
              "BGP origin-AS knobs";
            leaf validity {
              type empty;
              description
                "BGP bestpath selection will use origin-AS validity";
            }
          }
          container allow {
            description
              "BGP origin-AS knobs";
            leaf invalid {
              type empty;
              description
                "BGP bestpath selection will allow 'invalid' origin-AS";
            }
          }
        }
        container sr-policy {
          description
            "Paths over SR-policy";
          choice SR-POLICY {
            description
              "Paths over SR-policy";
            case PREFER {
              leaf prefer {
                type empty;
                description
                  "Consider only paths over SR Policy for bestpath selection, eBGP no-color eligible";
              }
            }
            case FORCE {
              leaf force {
                type empty;
                description
                  "Consider only paths over SR Policy for bestpath selection, eBGP no-color ineligible";
              }
            }
          }
        }
      }
      container cluster-id {
        description
          "Configure Route-Reflector Cluster-id";
        choice CLUSTER-ID {
          description
            "Configure Route-Reflector Cluster-id";
          case ROUTE-REFLECTOR-NUMBER {
            leaf route-reflector-number {
              type uint32 {
                range "1..4294967295" {
                  description
                    "Route-Reflector Cluster-id as 32 bit quantity";
                }
              }
              description
                "Route-Reflector Cluster-id as 32 bit quantity";
            }
          }
          case ROUTE-REFLECTOR-IP-ADDRESS {
            leaf route-reflector-ip-address {
              type inet:ipv4-address-no-zone;
              description
                "Route-Reflector Cluster-id in IP address format";
            }
          }
        }
      }
      container default {
        description
          "Configure default value";
        leaf local-preference {
          type uint32 {
            range "0..4294967295" {
              description
                "Higher = more preferred";
            }
          }
          description
            "Local preference";
        }
      }
      container enforce-first-as {
        description
          "Enforce the first AS for EBGP routes";
        leaf disable {
          type empty;
          description
            "Disable";
        }
      }
      container fast-external-fallover {
        description
          "Immediately reset session if a link to a directly connected external peer goes down";
        leaf disable {
          type empty;
          description
            "Disable";
        }
      }
      container log {
        description
          "Log bgp info";
        container neighbor {
          description
            "Log neighbor state info";
          container changes {
            description
              "Log neighbor up/down and reset reason";
            leaf disable {
              type empty;
              description
                "Disable logging";
            }
            leaf detail {
              type empty;
              description
                "Include extra detail in change messages";
            }
          }
        }
        container message {
          description
            "Log neighbor inbound/outbound message";
          leaf disable {
            type empty;
            description
              "Disable inbound and outbound message logging for all neighbors under the vrf";
          }
        }
        container memory-threshold {
          must "memory-warning-number";
          presence "IOS message to log message when BGP process memory exceeds configured limit";
          description
            "IOS message to log message when BGP process memory exceeds configured limit";
          leaf memory-warning-number {
            type uint32 {
              range "1..100" {
                description
                  "warning threshold value (percentage)";
              }
            }
            mandatory true;
            description
              "warning threshold value (percentage)";
          }
          leaf memory-critical-number {
            type uint32 {
              range "1..100" {
                description
                  "critical threshold value (percentage)";
              }
            }
            must "../memory-warning-number";
            description
              "critical threshold value (percentage)";
          }
        }
        container total-paths {
          must "total-paths-number";
          presence "Maximum expected path scale across VRF's and AFI/SAFI's";
          description
            "Maximum expected path scale across VRF's and AFI/SAFI's";
          leaf total-paths-number {
            type uint32 {
              range "1..2147483647" {
                description
                  "Maximum expected path scale";
              }
            }
            description
              "Maximum expected path scale";
          }
          leaf warn-threshold-value {
            type uint32 {
              range "1..100" {
                description
                  "Warning threshold value (percentage)";
              }
            }
            must "../total-paths-number";
            description
              "Warning threshold value (percentage)";
          }
        }
      }
      container multipath {
        description
          "Change multipath selection criteria";
        container use {
          description
            "Considered in Multipath Selection";
          leaf cluster-list-length {
            type empty;
            description
              "Use Cluster-List Length in BGP Multipath consideration";
          }
        }
        container as-path {
          description
            "AS path";
          container ignore {
            description
              "Ignore as-path related check for multipath selection";
            leaf onwards {
              type empty;
              description
                "Ignore everything onwards as-path for multipath selection";
            }
            leaf exact-match {
              type empty;
              description
                "(Deprecated from 7.4.1) Ignore as-path for multipath selection";
            }
          }
        }
      }
      leaf redistribute-internal {
        type empty;
        description
          "Allow redistribution of iBGP into IGPs (dangerous)";
      }
      leaf router-id {
        type inet:ipv4-address-no-zone;
        description
          "Configure Router-id";
      }
      leaf unsafe-ebgp-policy {
        type empty;
        description
          "Make eBGP neighbors with no policy pass all routes";
      }
      leaf scan-time {
        type uint32 {
          range "5..3600" {
            description
              "Scanner interval (seconds)";
          }
        }
        description
          "Configure background scanner interval for this address-family";
      }
      container confederation {
        description
          "AS confederation parameters";
        leaf identifier {
          type xr:Bgp-as-number;
          description
            "Set routing domain confederation AS";
        }
        list peers {
          key "peer-as-number";
          description
            "Enter peer ASs in BGP confederation mode";
          leaf peer-as-number {
            type xr:Bgp-as-number;
            description
              "bgp as-number";
          }
        }
      }
      container graceful-restart {
        description
          "Enable Graceful Restart support";
        leaf enable {
          type empty;
          description
            "Enable Graceful Restart support";
        }
        leaf purge-time {
          type uint32 {
            range "0..6000" {
              description
                "Max time (seconds)";
            }
          }
          description
            "Time before stale routes are purged.";
        }
        leaf restart-time {
          type uint32 {
            range "1..4095" {
              description
                "Max time (seconds)";
            }
          }
          description
            "Restart time advertised to neighbors";
        }
        leaf stalepath-time {
          type uint32 {
            range "1..4095" {
              description
                "Max time (seconds)";
            }
          }
          description
            "Maximum time to wait for restart of GR capable peers";
        }
        leaf graceful-reset {
          type empty;
          description
            "Reset gracefully if configuration change forces a peer reset";
        }
        container retain-nbr-routes {
          description
            "Retain neighbor routes when neighbor session resets if neighbor also has graceful restart disabled";
          leaf disable {
            type empty;
            description
              "do not retain neighbor routes";
          }
        }
      }
      leaf read-only {
        type empty;
        description
          "Allow duplicate table config and disable update generation";
      }
      container install {
        description
          "Install diversion path to RIB/CEF";
        leaf diversion {
          type empty;
          description
            "Install diversion path to RIB/CEF";
        }
      }
      leaf lpts-secure-binding {
        type empty;
        description
          "Enable installation of LPTS secure binding for directly connected eBGP neighbor";
      }
      container update-delay {
        presence "Set the max initial delay for sending updates";
        description
          "Set the max initial delay for sending updates";
        leaf delay {
          type uint32 {
            range "0..3600" {
              description
                "Delay value (seconds)";
            }
          }
          mandatory true;
          description
            "Set the max initial delay for sending updates";
        }
        leaf always {
          type empty;
          description
            "Keepalive trigger bestpath is disabled and delay is enforced";
        }
      }
      container maximum {
        description
          "Maximum number that can be configured";
        leaf neighbor {
          type uint32 {
            range "1..15000" {
              description
                "Maximum number of neighbors";
            }
          }
          description
            "Maximum number of neighbors that can be configured";
        }
      }
      container origin-as {
        description
          "BGP origin-AS knobs";
        container validation {
          description
            "BGP origin-AS validation knobs";
          container signal {
            description
              "Signal origin-AS validity towards peers";
            leaf ibgp {
              type empty;
              description
                "Signal origin-AS validity towards iBGP peers";
            }
          }
          container time {
            description
              "Time to wait between an RPKI update and a BGP table walk";
            choice TIME {
              description
                "Time to wait between an RPKI update and a BGP table walk";
              case OFF {
                leaf off {
                  type empty;
                  description
                    "No automatic prefix validation after an RPKI update";
                }
              }
              case PREFIX-VALIDATION-TIME {
                leaf prefix-validation-time {
                  type uint32 {
                    range "5..60" {
                      description
                        "Prefix validation time (in seconds)";
                    }
                  }
                  description
                    "Prefix validation time (in seconds)";
                }
              }
            }
          }
        }
      }
    }
    container timers {
      description
        "Adjust routing timers";
      container bgp {
        description
          "BGP per neighbor timers";

        grouping KEEPALIVE-OPTIONS {
          description
            "Keepalive-options";
          choice KEEPALIVE-OPTIONS {
            description
              "Keepalive-options";
            case ZERO {
              leaf zero {
                type empty;
                description
                  "Disable keepalives/hold time";
              }
            }
            case MINIMUM-ACCEPTABLE-HOLDTIME {
              leaf minimum-acceptable-holdtime {
                type uint32 {
                  range "3..65535" {
                    description
                      "Minimum acceptable holdtime from neighbor";
                  }
                }
                description
                  "Minimum acceptable holdtime from neighbor";
              }
            }
          }
        }
        leaf keepalive-interval {
          type uint32 {
            range "0..65535" {
              description
                "Keepalive interval";
            }
          }
          description
            "Keepalive interval";
        }
        choice KEEPALIVE-INTERVAL {
          description
            "Keepalive interval";
          case ZERO {
            container zero {
              must "../keepalive-interval";
              presence "Disable keepalives/hold time";
              description
                "Disable keepalives/hold time";
              uses KEEPALIVE-OPTIONS;
            }
          }
          case HOLDTIME {
            container holdtime {
              must "../keepalive-interval and holdtime-number";
              presence "Holdtime";
              description
                "Holdtime";
              leaf holdtime-number {
                type uint32 {
                  range "3..65535" {
                    description
                      "Holdtime";
                  }
                }
                description
                  "Holdtime";
              }
              uses KEEPALIVE-OPTIONS;
            }
          }
        }
      }
    }
    container nsr {
      presence "Enable non-stop-routing support for all neighbors";
      description
        "Enable non-stop-routing support for all neighbors";
      leaf disable {
        type empty;
        description
          "Disable non-stop-routing support for all neighbors";
      }
    }
    container ibgp {
      description
        "Set options for iBGP peers";
      container policy {
        description
          "Set options for route-policy";
        container out {
          description
            "Set options for outbound policy";
          leaf enforce-modifications {
            type empty;
            description
              "Allow policy to modify all attributes";
          }
        }
      }
    }
    leaf mvpn {
      type empty;
      description
        "Connect to PIM/PIM6";
    }
    container openconfig {
      description
        "OpenConfig network-instance model related knob";
      leaf rib-telemetry {
        type empty;
        description
          "Telemetry streaming enabled for OC RIB model. Also, triggers the setting up of new data structures per latest OCNI model";
      }
    }
    container update {
      description
        "BGP Update configuration";
      leaf limit {
        type uint32 {
          range "16..2048" {
            description
              "Update limit in MegaBytes(MB); default is 512 MB";
          }
        }
        description
          "Upper bound on transient memory usage for update generation";
      }
      container in {
        description
          "Inbound update message handling";
        container error-handling {
          description
            "Inbound update message error handling";
          container basic {
            description
              "Inbound update message basic error handling";
            container ebgp {
              description
                "Inbound update message basic error handling for EBGP neighbors";
              leaf disable {
                type empty;
                description
                  "Disable inbound update message basic error handling for EBGP neighbors";
              }
            }
            container ibgp {
              description
                "Inbound update message basic error handling for IBGP neighbors";
              leaf disable {
                type empty;
                description
                  "Disable inbound update message basic error handling for IBGP neighbors";
              }
            }
          }
          container extended {
            description
              "Inbound update message extended error handling";
            leaf ebgp {
              type empty;
              description
                "Inbound update message extended error handling for EBGP neighbors";
            }
            leaf ibgp {
              type empty;
              description
                "Inbound update message extended error handling for IBGP neighbors";
            }
          }
        }
      }
      container out {
        description
          "BGP Update generation configuration";
        leaf logging {
          type empty;
          description
            "Enable logging of update generation events";
        }
      }
    }
    container bfd {
      description
        "Configure BFD parameters";
      leaf multiplier {
        type uint32 {
          range "2..16" {
            description
              "Detect multiplier";
          }
        }
        description
          "Detect multiplier";
      }
      leaf minimum-interval {
        type uint32 {
          range "3..30000" {
            description
              "hello interval in milli-seconds";
          }
        }
        description
          "Hello interval";
      }
    }
    container rpki {
      description
        "Configure RPKI";
      container routes {
        description
          "Configure an RPKI route";
        list route {
          key "route-address route-prefix max origin";
          description
            "Configure an RPKI route";
          leaf route-address {
            type inet:ip-address-no-zone;
            description
              "Network/Minimum prefix length";
          }
          leaf route-prefix {
            type uint32 {
              range "1..128" {
                description
                  "route prefix";
              }
            }
            description
              "route prefix";
          }
          leaf origin {
            type uint32 {
              range "1..4294967295" {
                description
                  "Origin Autonomous System number (in asplain format)";
              }
            }
            description
              "Origin Autonomous System number (in asplain format)";
          }
          leaf max {
            type uint32 {
              range "1..128" {
                description
                  "Maximum prefix length";
              }
            }
            description
              "Maximum prefix length";
          }
        }
      }
      container servers {
        description
          "Configure RPKI cache-servers";
        list server {
          key "server-name";
          description
            "Configure RPKI cache-servers";
          leaf server-name {
            type xr:Cisco-ios-xr-string {
              length "1..255" {
                description
                  "Hostname or IP address";
              }
            }
            description
              "Hostname or IP address";
          }
          container refresh-time {
            description
              "Time between sending serial-queries for the RPKI cache-server";
            choice REFRESH-TIME {
              description
                "Time between sending serial-queries for the RPKI cache-server";
              case REFRESH-TIME-SECONDS {
                leaf refresh-time-seconds {
                  type uint32 {
                    range "15..3600" {
                      description
                        "Refresh time (in seconds)";
                    }
                  }
                  description
                    "Refresh time (in seconds)";
                }
              }
              case OFF {
                leaf off {
                  type empty;
                  description
                    "Do not send serial-queries periodically";
                }
              }
            }
          }
          container response-time {
            description
              "Time to wait for a response from the RPKI cache-server";
            choice RESPONSE-TIME {
              description
                "Time to wait for a response from the RPKI cache-server";
              case RESPONSE-TIME-SECONDS {
                leaf response-time-seconds {
                  type uint32 {
                    range "15..3600" {
                      description
                        "Response time (in seconds)";
                    }
                  }
                  description
                    "Response time (in seconds)";
                }
              }
              case OFF {
                leaf off {
                  type empty;
                  description
                    "Wait indefinitely for a response";
                }
              }
            }
          }
          leaf purge-time {
            type uint32 {
              range "30..65535" {
                description
                  "Purge time (in seconds)";
              }
            }
            description
              "Time to wait after a cache goes down to clean up stale routes";
          }
          leaf username {
            type string {
              length "1..1024" {
                description
                  "RPKI cache (SSH) username";
              }
            }
            description
              "Specify a (SSH) username for the RPKI cache-server";
          }
          leaf password {
            type string {
              length "1..1024" {
                description
                  "RPKI cache (SSH) password";
              }
            }
            description
              "Specify a (SSH) password for the RPKI cache-server";
          }
          container transport {
            description
              "Specify a transport method for the RPKI cache-server";
            choice TRANSPORT {
              description
                "Specify a transport method for the RPKI cache-server";
              case TCP {
                container tcp {
                  presence "Connect to the RPKI cache-server using TCP (unencrypted)";
                  description
                    "Connect to the RPKI cache-server using TCP (unencrypted)";
                  leaf port {
                    type uint32 {
                      range "1..65535" {
                        description
                          "Specify a port number for the RPKI cache-server transport";
                      }
                    }
                    mandatory true;
                    description
                      "Specify a port number for the RPKI cache-server transport";
                  }
                }
              }
              case SSH {
                container ssh {
                  presence "Connect to the RPKI cache-server using SSH";
                  description
                    "Connect to the RPKI cache-server using SSH";
                  leaf port {
                    type uint32 {
                      range "1..65535" {
                        description
                          "Specify a port number for the RPKI cache-server transport";
                      }
                    }
                    mandatory true;
                    description
                      "Specify a port number for the RPKI cache-server transport";
                  }
                }
              }
            }
          }
          container bind-source {
            description
              "Specify a bind source for RPKI cache-server";
            leaf interface {
              type xr:Interface-name;
              description
                "Select a source interface to bind the RPKI cache-server transport";
            }
          }
          leaf shutdown {
            type empty;
            description
              "Shutdown the RPKI cache-server";
          }
        }
      }
    }
    container vrfs {
      description
        "Specify a vrf name";
      list vrf {
        key "vrf-name";
        description
          "Specify a vrf name";

        grouping NEIGHBOR-VRF {
          description
            "Neighbor";
          container evpn-link-bandwidth {
            presence "Propagate the EVPN link bandwidth";
            description
              "Propagate the EVPN link bandwidth";
            choice EVPN-LINK-BANDWIDTH {
              description
                "Propagate the EVPN link bandwidth";
              case PER-PATH {
                container per-path {
                  presence "EVPN Link Bandwidth using per-path generalized unit";
                  description
                    "EVPN Link Bandwidth using per-path generalized unit";
                  leaf per-path-evpn-link-bandwidth-number {
                    type uint32 {
                      range "1..65535" {
                        description
                          "Unit per-path";
                      }
                    }
                    mandatory true;
                    description
                      "Unit per-path";
                  }
                }
              }
              case INHERITANCE-DISABLE {
                leaf inheritance-disable {
                  type empty;
                  description
                    "Prevent evpn-link-bandwidth from being inherited from the parent";
                }
              }
            }
          }
          leaf remote-as {
            type xr:Bgp-as-number;
            description
              "Set remote AS";
          }
          leaf maximum-peers {
            type uint32 {
              range "1..4095" {
                description
                  "Maximum number of peers";
              }
            }
            description
              "Maximum dynamic neighbors";
          }
          leaf maximum-prefix-restart-time {
            type uint32 {
              range "1..65535" {
                description
                  "(Deprecated in 7.11.1) Maximum prefix restart time (seconds)";
              }
            }
            description
              "(Deprecated in 7.11.1) Restart timer interval";
          }
          leaf remote-as-list {
            type string {
              length "1..1024" {
                description
                  "as-list name";
              }
            }
            description
              "Remote as-list configuration";
          }
          container as-path-loopcheck {
            description
              "(Deprecated in 7.11.1) Configure AS Path loop checking";
            leaf out {
              type enumeration {
                enum "enable" {
                  value 1;
                  description
                    "(Deprecated in 7.11.1) Disable as-path loop checking";
                }
                enum "disable" {
                  value 2;
                  description
                    "(Deprecated in 7.11.1) Disable as-path loop checking";
                }
              }
              description
                "For outbound updates";
            }
          }
          container use {
            description
              "Inherit configuration from a group";
            leaf neighbor-group {
              type string {
                length "1..1024" {
                  description
                    "Neighbor-group name";
                }
              }
              description
                "Inherit configuration from a neighbor-group";
            }
            leaf session-group {
              type string {
                length "1..1024" {
                  description
                    "Session group name";
                }
              }
              description
                "Inherit address-family independent config from a session-group";
            }
          }
          container advertisement-interval {
            description
              "Minimum interval between sending BGP routing updates";
            leaf advertisement-interval-time-in-seconds {
              type uint32 {
                range "0..600" {
                  description
                    "time in seconds";
                }
              }
              description
                "time in seconds";
            }
            leaf advertisement-interval-time-in-milliseconds {
              type uint32 {
                range "0..999" {
                  description
                    "time in milliseconds";
                }
              }
              must "../advertisement-interval-time-in-seconds";
              description
                "time in milliseconds";
            }
          }
          leaf description {
            type string {
              length "1..1024" {
                description
                  "Up to 80 characters describing this neighbor";
              }
            }
            description
              "Neighbor specific description";
          }
          container ignore-connected-check {
            presence "Bypass the directly connected nexthop check for single-hop eBGP peering";
            description
              "Bypass the directly connected nexthop check for single-hop eBGP peering";
            leaf inheritance-disable {
              type empty;
              description
                "Prevent ignore-connected-check from being inherited from the parent";
            }
          }
          container ebgp-multihop {
            presence "Allow EBGP neighbors not on directly connected networks";
            description
              "Allow EBGP neighbors not on directly connected networks";
            leaf maximum-hop-count {
              type uint32 {
                range "1..255" {
                  description
                    "maximum hop count";
                }
              }
              description
                "maximum hop count";
            }
            leaf mpls {
              type empty;
              description
                "Disable BGP MPLS forwarding";
            }
          }
          container tcp {
            description
              "TCP session configuration commands";
            container mss {
              description
                "Maximum Segment Size";
              choice MSS {
                description
                  "Maximum Segment Size";
                case TCP-INITIAL-MAXIMUM-SEGMENT-SIZE {
                  leaf tcp-initial-maximum-segment-size {
                    type uint32 {
                      range "68..10000" {
                        description
                          "TCP initial maximum segment size";
                      }
                    }
                    description
                      "TCP initial maximum segment size";
                  }
                }
                case INHERITANCE-DISABLE {
                  leaf inheritance-disable {
                    type empty;
                    description
                      "Prevent tcp mss from being inherited from the parent";
                  }
                }
              }
            }
            container mtu-discovery {
              presence "Enable Path MTU discovery on TCP session";
              description
                "Enable Path MTU discovery on TCP session";
              leaf inheritance-disable {
                type empty;
                description
                  "Prevent TCP MTU cfg from being inherited from the parent";
              }
            }
            container ip-only-preferred {
              presence "Prefer to send BGP control plane traffic on IP";
              description
                "Prefer to send BGP control plane traffic on IP";
              leaf inheritance-disable {
                type empty;
                description
                  "Do not inherit this configuration from parent group";
              }
            }
          }
          container bmp-activate {
            description
              "Enable BMP logging for this neighbor";
            container servers {
              description
                "Enable BMP connection to particular server";
              list server {
                key "server-number";
                description
                  "Enable BMP connection to particular server";
                leaf server-number {
                  type uint32 {
                    range "1..8" {
                      description
                        "Enable BMP connection to particular server";
                    }
                  }
                  description
                    "Enable BMP connection to particular server";
                }
              }
            }
          }
          container bfd {
            description
              "Configure BFD parameters";
            container fast-detect {
              presence "Enable Fast detection";
              description
                "Enable Fast detection";
              leaf strict-mode {
                type empty;
                description
                  "(Deprecated) Hold down neighbor session until BFD is up (based on IOS-XR proprietary mechanism)";
              }
              container strict-mode-negotiate {
                presence "Hold down neighbor session until BFD is up (based on strict-mode capability negotiation)";
                description
                  "Hold down neighbor session until BFD is up (based on strict-mode capability negotiation)";
                leaf override {
                  type empty;
                  description
                    "Do not bring up neighbor session until BFD up even if strict-mode capability is not received";
                }
              }
              leaf disable {
                type empty;
                description
                  "Prevent bfd settings from being inherited from the parent";
              }
            }
            leaf minimum-interval {
              type uint32 {
                range "3..30000" {
                  description
                    "hello interval in milli-seconds";
                }
              }
              description
                "Hello interval";
            }
            leaf multiplier {
              type uint32 {
                range "2..16" {
                  description
                    "Detect multiplier";
                }
              }
              description
                "Detect multiplier";
            }
          }
          container keychain {
            description
              "Set keychain based authentication";
            choice KEYCHAIN {
              description
                "Set keychain based authentication";
              case KEYCHAIN-NAME {
                leaf keychain-name {
                  type string {
                    length "1..32" {
                      description
                        "Name of the key chain - maximum 32 characters";
                    }
                  }
                  description
                    "Name of the key chain - maximum 32 characters";
                }
              }
              case INHERITANCE-DISABLE {
                leaf inheritance-disable {
                  type empty;
                  description
                    "Prevent keychain from being inherited from parent";
                }
              }
            }
          }
          container local-as {
            description
              "Specify local AS number";
            choice LOCAL-AS {
              description
                "Specify local AS number";
              case INHERITANCE-DISABLE {
                leaf inheritance-disable {
                  type empty;
                  description
                    "Prevent local AS from being inherited from parent";
                }
              }
              case AS {
                container as {
                  description
                    "AS number";
                  leaf as-number {
                    type xr:Bgp-as-number;
                    description
                      "AS number";
                  }
                  container no-prepend {
                    must "../as-number";
                    presence "Do not prepend local AS to announcements from this neighbor";
                    description
                      "Do not prepend local AS to announcements from this neighbor";
                    container replace-as {
                      presence "Prepend only local AS to announcements to this neighbor";
                      description
                        "Prepend only local AS to announcements to this neighbor";
                      leaf dual-as {
                        type empty;
                        description
                          "Dual-AS mode";
                      }
                    }
                  }
                }
              }
            }
          }
          container password {
            description
              "Set a password";
            choice PASSWORD {
              description
                "Set a password";
              case ENCRYPTED {
                leaf encrypted {
                  type xr:Proprietary-password;
                  description
                    "Specifies a password will follow";
                }
              }
              case INHERITANCE-DISABLE {
                leaf inheritance-disable {
                  type empty;
                  description
                    "Prevent password from being inherited from parent";
                }
              }
            }
          }
          container receive-buffer-size {
            description
              "Set socket and BGP receive buffer size";
            leaf receive-buffer-size-number {
              type uint32 {
                range "512..131072" {
                  description
                    "Receive socket buffer size in bytes";
                }
              }
              description
                "Receive socket buffer size in bytes";
            }
            leaf bgp-read-buffer-size-byte {
              type uint32 {
                range "512..131072" {
                  description
                    "BGP Read buffer size in bytes";
                }
              }
              must "../receive-buffer-size-number";
              description
                "BGP Read buffer size in bytes";
            }
          }
          container send-buffer-size {
            description
              "Set socket and BGP send buffer size";
            leaf send-buffer-size-number {
              type uint32 {
                range "4096..131072" {
                  description
                    "Send socket buffer size in bytes";
                }
              }
              description
                "Send socket buffer size in bytes";
            }
            leaf bgp-write-buffer-size-byte {
              type uint32 {
                range "4096..131072" {
                  description
                    "BGP Write buffer size in bytes";
                }
              }
              must "../send-buffer-size-number";
              description
                "BGP Write buffer size in bytes";
            }
          }
          container fast-fallover {
            presence "Force neighbor to be directly connected. Bring neighbor down if its interface goes down";
            description
              "Force neighbor to be directly connected. Bring neighbor down if its interface goes down";
            leaf inheritance-disable {
              type empty;
              description
                "Prevent this neighbor from inheriting this config from a group it is in";
            }
          }
          container shutdown {
            presence "Administratively shut down this neighbor";
            description
              "Administratively shut down this neighbor";
            leaf inheritance-disable {
              type empty;
              description
                "Prevent this neighbor being shutdown, even if its parent is";
            }
          }
          container timers {
            description
              "BGP per neighbor timers";

            grouping KEEPALIVE-OPTIONS {
              description
                "Keepalive-options";
              choice KEEPALIVE-OPTIONS {
                description
                  "Keepalive-options";
                case ZERO {
                  leaf zero {
                    type empty;
                    description
                      "Disable keepalives/hold time";
                  }
                }
                case MINIMUM-ACCEPTABLE-HOLDTIME {
                  leaf minimum-acceptable-holdtime {
                    type uint32 {
                      range "3..65535" {
                        description
                          "Minimum acceptable holdtime from neighbor";
                      }
                    }
                    description
                      "Minimum acceptable holdtime from neighbor";
                  }
                }
              }
            }
            leaf keepalive-interval {
              type uint32 {
                range "0..65535" {
                  description
                    "Keepalive interval";
                }
              }
              description
                "Keepalive interval";
            }
            choice KEEPALIVE-INTERVAL {
              description
                "Keepalive interval";
              case ZERO {
                container zero {
                  must "../keepalive-interval";
                  presence "Disable keepalives/hold time";
                  description
                    "Disable keepalives/hold time";
                  uses KEEPALIVE-OPTIONS;
                }
              }
              case HOLDTIME {
                container holdtime {
                  must "../keepalive-interval and holdtime-number";
                  presence "Holdtime";
                  description
                    "Holdtime";
                  leaf holdtime-number {
                    type uint32 {
                      range "3..65535" {
                        description
                          "Holdtime";
                      }
                    }
                    description
                      "Holdtime";
                  }
                  uses KEEPALIVE-OPTIONS;
                }
              }
            }
          }
          container local {
            description
              "Configure local parameter";
            container address {
              description
                "use configured local address for bgp peering";
              choice ADDRESS {
                description
                  "use configured local address for bgp peering";
                case IP-ADDRESS {
                  leaf ip-address {
                    type inet:ip-address-no-zone;
                    description
                      "IP address";
                  }
                }
                case INHERITANCE-DISABLE {
                  leaf inheritance-disable {
                    type empty;
                    description
                      "Prevent local address from being inherited from parent";
                  }
                }
              }
            }
          }
          container log {
            description
              "Logging update messages per neighbor";
            container neighbor {
              description
                "Log neighbor state info";
              container changes {
                description
                  "Log neighbor state changes";
                choice CHANGES {
                  description
                    "Log neighbor state changes";
                  case DETAIL {
                    leaf detail {
                      type empty;
                      description
                        "detail";
                    }
                  }
                  case DISABLE {
                    leaf disable {
                      type empty;
                      description
                        "disable";
                    }
                  }
                  case INHERITANCE-DISABLE {
                    leaf inheritance-disable {
                      type empty;
                      description
                        "Prevents the log state changes from being inherited from the parent";
                    }
                  }
                }
              }
            }
            container message {
              description
                "Logging update/notification messages per neighbor";
              container in {
                description
                  "Inbound log messages";
                choice IN {
                  description
                    "Inbound log messages";
                  case LOG-BUFFER-SIZE {
                    leaf log-buffer-size {
                      type uint32 {
                        range "1..500" {
                          description
                            "Range for message log buffer size";
                        }
                      }
                      description
                        "Range for message log buffer size";
                    }
                  }
                  case DISABLE {
                    leaf disable {
                      type empty;
                      description
                        "disable";
                    }
                  }
                  case INHERITANCE-DISABLE {
                    leaf inheritance-disable {
                      type empty;
                      description
                        "Prevents the log state changes from being inherited from the parent";
                    }
                  }
                }
              }
              container out {
                description
                  "Outbound log messages";
                choice OUT {
                  description
                    "Outbound log messages";
                  case LOG-BUFFER-SIZE {
                    leaf log-buffer-size {
                      type uint32 {
                        range "1..500" {
                          description
                            "Range for message log buffer size";
                        }
                      }
                      description
                        "Range for message log buffer size";
                    }
                  }
                  case DISABLE {
                    leaf disable {
                      type empty;
                      description
                        "disable";
                    }
                  }
                  case INHERITANCE-DISABLE {
                    leaf inheritance-disable {
                      type empty;
                      description
                        "Prevents the log state changes from being inherited from the parent";
                    }
                  }
                }
              }
            }
          }
          leaf update-source {
            type xr:Interface-name;
            description
              "Source of routing updates";
          }
          container local-address-subnet {
            presence "Local address subnet of routing updates";
            description
              "Local address subnet of routing updates";
            leaf address {
              type inet:ip-address-no-zone;
              mandatory true;
              description
                "IPaddress";
            }
            leaf address-prefix {
              type uint32 {
                range "0..128";
              }
              mandatory true;
              description
                "IP address prefix";
            }
          }
          container dmz-link-bandwidth {
            presence "Propagate the DMZ link bandwidth";
            description
              "Propagate the DMZ link bandwidth";
            leaf inheritance-disable {
              type empty;
              description
                "Prevent dmz-link-bandwidth from being inherited from the parent";
            }
          }
          container ebgp-recv-extcommunity-dmz {
            presence "Receive extcommunity dmz link bandwidth from ebgp neighbor";
            description
              "Receive extcommunity dmz link bandwidth from ebgp neighbor";
            leaf inheritance-disable {
              type empty;
              description
                "Prevent ebgp-send-community-dmz from being inherited from parent";
            }
          }
          container ebgp-send-extcommunity-dmz {
            presence "Send extended community dmz link bandwidth to ebgp neighbor";
            description
              "Send extended community dmz link bandwidth to ebgp neighbor";
            choice EBGP-SEND-EXTCOMMUNITY-DMZ {
              description
                "Send extended community dmz link bandwidth to ebgp neighbor";
              case CUMULATIVE {
                leaf cumulative {
                  type empty;
                  description
                    "Send cumulative community dmz link bandwidth of all multipaths to ebgp neighbor";
                }
              }
              case INHERITANCE-DISABLE {
                leaf inheritance-disable {
                  type empty;
                  description
                    "Prevent ebgp-send-extcommunity-dmz from being inherited from parent";
                }
              }
            }
          }
          container ttl-security {
            presence "Enable EBGP TTL security";
            description
              "Enable EBGP TTL security";
            leaf inheritance-disable {
              type empty;
              description
                "Prevent ttl-security from being inherited from the parent";
            }
          }
          leaf session-open-mode {
            type enumeration {
              enum "active-only" {
                value 1;
                description
                  "Active only";
              }
              enum "passive-only" {
                value 2;
                description
                  "Passive only";
              }
              enum "both" {
                value 0;
                description
                  "Prevent session-open-mode being inherited from the parent";
              }
            }
            description
              "Establish BGP session using this TCP open mode";
          }
          leaf dscp {
            type union {
              type uint32 {
                range "0..63" {
                  description
                    "Differentiated services codepoint value";
                }
              }
              type enumeration {
                enum "af11" {
                  value 10;
                  description
                    "Set packets with AF11 dscp (001010)";
                }
                enum "af12" {
                  value 12;
                  description
                    "Set packets with AF12 dscp (001100)";
                }
                enum "af13" {
                  value 14;
                  description
                    "Set packets with AF13 dscp (001110)";
                }
                enum "af21" {
                  value 18;
                  description
                    "Set packets with AF21 dscp (010010)";
                }
                enum "af22" {
                  value 20;
                  description
                    "Set packets with AF22 dscp (010100)";
                }
                enum "af23" {
                  value 22;
                  description
                    "Set packets with AF23 dscp (010110)";
                }
                enum "af31" {
                  value 26;
                  description
                    "Set packets with AF31 dscp (011010)";
                }
                enum "af32" {
                  value 28;
                  description
                    "Set packets with AF32 dscp (011100)";
                }
                enum "af33" {
                  value 30;
                  description
                    "Set packets with AF33 dscp (011110)";
                }
                enum "af41" {
                  value 34;
                  description
                    "Set packets with AF41 dscp (100010)";
                }
                enum "af42" {
                  value 36;
                  description
                    "Set packets with AF42 dscp (100100)";
                }
                enum "af43" {
                  value 38;
                  description
                    "Set packets with AF43 dscp (100110)";
                }
                enum "cs1" {
                  value 8;
                  description
                    "Set packets with CS1(precedence 1) dscp (001000)";
                }
                enum "cs2" {
                  value 16;
                  description
                    "Set packets with CS2(precedence 2) dscp (010000)";
                }
                enum "cs3" {
                  value 24;
                  description
                    "Set packets with CS3(precedence 3) dscp (011000)";
                }
                enum "cs4" {
                  value 32;
                  description
                    "Set packets with CS4(precedence 4) dscp (100000)";
                }
                enum "cs5" {
                  value 40;
                  description
                    "Set packets with CS5(precedence 5) dscp (101000)";
                }
                enum "cs6" {
                  value 48;
                  description
                    "Set packets with CS6(precedence 6) dscp (110000)";
                }
                enum "cs7" {
                  value 56;
                  description
                    "Set packets with CS7(precedence 7) dscp (111000)";
                }
                enum "default" {
                  value 0;
                  description
                    "Set packets with default dscp (000000)";
                }
                enum "ef" {
                  value 46;
                  description
                    "Set packets with EF dscp (101110)";
                }
              }
            }
            description
              "Set IP DSCP (DiffServ CodePoint)";
          }
          leaf precedence {
            type union {
              type uint32 {
                range "0..7" {
                  description
                    "Precedence value";
                }
              }
              type enumeration {
                enum "critical" {
                  value 5;
                  description
                    "Set packets with critical precedence (5)";
                }
                enum "flash" {
                  value 3;
                  description
                    "Set packets with flash precedence (3)";
                }
                enum "flash-override" {
                  value 4;
                  description
                    "Set packets with flash override precedence (4)";
                }
                enum "immediate" {
                  value 2;
                  description
                    "Set packets with immediate precedence (2)";
                }
                enum "internet" {
                  value 6;
                  description
                    "Set packets with internetwork control precedence (6)";
                }
                enum "network" {
                  value 7;
                  description
                    "Set packets with network control precedence (7)";
                }
                enum "priority" {
                  value 1;
                  description
                    "Set packets with priority precedence (1)";
                }
                enum "routine" {
                  value 0;
                  description
                    "Set packets with routine precedence (0)";
                }
              }
            }
            description
              "Set precedence";
          }
          container capability {
            description
              "Advertise capability to the peer";
            container additional-paths {
              description
                "Additional paths capability";
              container send {
                presence "Additional paths Send capability";
                description
                  "Additional paths Send capability";
                leaf disable {
                  type empty;
                  description
                    "Do not advertise additional paths Send capability";
                }
              }
              container receive {
                presence "Additional paths Receive capability";
                description
                  "Additional paths Receive capability";
                leaf disable {
                  type empty;
                  description
                    "Do not advertise additional paths Receive capability";
                }
              }
            }
            container suppress {
              description
                "Suppress advertising capability to the peer";
              container all {
                presence "All capabilities";
                description
                  "All capabilities";
                leaf inheritance-disable {
                  type empty;
                  description
                    "Do not inherit this configuration from parent group";
                }
              }
              container extended-nexthop-encoding {
                presence "Extended-nexthop-encoding capabilities (IETF RFC 5549)";
                description
                  "Extended-nexthop-encoding capabilities (IETF RFC 5549)";
                leaf inheritance-disable {
                  type empty;
                  description
                    "Do not inherit this configuration from parent group";
                }
              }
              container four-byte-as {
                presence "4-byte-as capability";
                description
                  "4-byte-as capability";
                leaf inheritance-disable {
                  type empty;
                  description
                    "Prevent capability suppress 4-type-as being inherited from the parent";
                }
              }
            }
          }
          container graceful-restart {
            description
              "Enable graceful restart support for this neighbor";
            container graceful-restart-enable {
              presence "Enable graceful restart support for this neighbor";
              description
                "Enable graceful restart support for this neighbor";
              leaf disable {
                type empty;
                description
                  "Disable graceful restart support for this neighbor";
              }
            }
            container helper-only {
              presence "Enable graceful restart in helper-mode only.Forwarding state will not retained in local restart. Peer's routes will ne retained when peer restarts";
              description
                "Enable graceful restart in helper-mode only.Forwarding state will not retained in local restart. Peer's routes will ne retained when peer restarts";
              leaf inheritance-disable {
                type empty;
                description
                  "Prevent GR helper-mode cfg from being inherited from the parent";
              }
            }
            leaf restart-time {
              type uint32 {
                range "1..4095" {
                  description
                    "Max time (seconds)";
                }
              }
              description
                "Restart time advertised to the neighbor";
            }
            leaf stalepath-time {
              type uint32 {
                range "0..4095" {
                  description
                    "Max time (seconds)";
                }
              }
              description
                "Maximum time to wait for restart of GR capable peer";
            }
          }
          leaf enforce-first-as {
            type enumeration {
              enum "enable" {
                value 1;
                description
                  "enable";
              }
              enum "disable" {
                value 0;
                description
                  "Do not enforce the first AS for EBGP routes";
              }
            }
            description
              "enforce-first-as";
          }
          container cluster-id {
            description
              "Enter cluster id for this neighbor";
            choice CLUSTER-ID {
              description
                "Enter cluster id for this neighbor";
              case ROUTE-REFLECTOR-NUMBER {
                leaf route-reflector-number {
                  type uint32 {
                    range "1..4294967295" {
                      description
                        "Route-Reflector Cluster-id as 32 bit quantity";
                    }
                  }
                  description
                    "Route-Reflector Cluster-id as 32 bit quantity";
                }
              }
              case ROUTE-REFLECTOR-IP-ADDRESS {
                leaf route-reflector-ip-address {
                  type inet:ipv4-address-no-zone;
                  description
                    "Route-Reflector Cluster-id in IP address format";
                }
              }
            }
          }
          leaf idle-watch-time {
            type uint32 {
              range "30..1800" {
                description
                  "Max time (seconds)";
              }
            }
            description
              "Maximum time to wait for deletion of IDLE state dynamic peer";
          }
          container allowas-in {
            description
              "Allow as-path with my AS present in it";
            leaf number-of-occurrences-of-as-number {
              type uint32 {
                range "1..10" {
                  description
                    "Number of occurrences of AS number";
                }
              }
              description
                "Number of occurrences of AS number";
            }
          }
          container egress-engineering {
            presence "Enable egress peer engineering for this neighbor";
            description
              "Enable egress peer engineering for this neighbor";
            leaf inheritance-disable {
              type empty;
              description
                "Do not inherit egress-engineering from the parent";
            }
          }
          container peer-set {
            description
              "Assign this neighbor to a peer-set used for egress peer engineering";
            list peer-sets {
              key "peer";
              description
                "Assign this neighbor to a peer-set used for egress peer engineering";
              leaf peer {
                type uint32 {
                  range "1..255" {
                    description
                      "Identity value of peer-set";
                  }
                }
                description
                  "Identity value of peer-set";
              }
            }
          }
          container peer-node-sid {
            description
              "Assign this neighbor a manual SID for egress peer engineering";
            leaf index {
              type uint32 {
                range "0..1033575" {
                  description
                    "Segment Index to be assigned to this peer. The index will be off SRLB
                     Note: This is the maximum index configurable in dynaminc SRLB range.
                     Since SRLB can be a dynamic range, actual maximum index can vary.
                     So please look at the currently configured SRLB range";
                }
              }
              description
                "Segment Index value which is offset of SRLB";
            }
          }
          container ao {
            description
              "Enable Authentiation Option";
            choice AO {
              description
                "Enable Authentiation Option";
              case KEY-CHAIN-NAME {
                container key-chain-name {
                  presence "Name of the key chain - maximum 32 characters";
                  description
                    "Name of the key chain - maximum 32 characters";
                  leaf key-chain-name {
                    type string {
                      length "1..32" {
                        description
                          "Name of the key chain - maximum 32 characters";
                      }
                    }
                    mandatory true;
                    description
                      "Name of the key chain - maximum 32 characters";
                  }
                  leaf include-tcp-options {
                    type enumeration {
                      enum "enable" {
                        value 1;
                        description
                          "Include other TCP options in the header";
                      }
                      enum "disable" {
                        value 0;
                        description
                          "Exclude other TCP options in the header";
                      }
                    }
                    mandatory true;
                    description
                      "Include/Exclude other TCP options in the header";
                  }
                  leaf accept-ao-mismatch-connection {
                    type empty;
                    description
                      "Accept new connection even if AO mismatched";
                  }
                }
              }
              case INHERITANCE-DISABLE {
                leaf inheritance-disable {
                  type empty;
                  description
                    "Prevent keychain from being inherited from parent";
                }
              }
            }
          }
          leaf dampening {
            type enumeration {
              enum "enable" {
                value 1;
                description
                  "(Deprecated in 7.11.1) Enable route-flap-damping";
              }
              enum "disable" {
                value 2;
                description
                  "(Deprecated in 7.11.1) Enable route-flap-damping";
              }
            }
            description
              "(Deprecated in 7.11.1) Enable route-flap-damping";
          }
          leaf as-override {
            type enumeration {
              enum "enable" {
                value 1;
                description
                  "(Deprecated in 7.11.1) Override matching AS-number while sending update";
              }
              enum "disable" {
                value 2;
                description
                  "(Deprecated in 7.11.1) Override matching AS-number while sending update";
              }
            }
            description
              "(Deprecated in 7.11.1) Override matching AS-number while sending update";
          }
          container default-policy-action {
            description
              "Set a default action if a route does not satify the policy definition";
            leaf in {
              type enumeration {
                enum "accept" {
                  value 1;
                  description
                    "accept the route if does not satisfy the inbound policy";
                }
                enum "reject" {
                  value 2;
                  description
                    "reject the route if does not satisfy the inbound policy";
                }
              }
              description
                "Default action if route does not satisfy inbound route-policy";
            }
            leaf out {
              type enumeration {
                enum "accept" {
                  value 1;
                  description
                    "accept the route if does not satisfy the outbound policy";
                }
                enum "reject" {
                  value 2;
                  description
                    "reject the route if does not satisfy the outbound policy";
                }
              }
              description
                "Default action if route does not satisfy outbound route-policy";
            }
          }
          container origin-as {
            description
              "BGP origin-AS knobs";
            container validation {
              description
                "BGP origin-AS validation knobs";
              leaf disable {
                type empty;
                description
                  "Disable RPKI origin-AS validation";
              }
            }
          }
          container send-community-ebgp {
            presence "Send community attribute to this external neighbor";
            description
              "Send community attribute to this external neighbor";
            leaf inheritance-disable {
              type empty;
              description
                "Prevent send-community-ebgp from being inherited from the parent";
            }
          }
          container send-extended-community-ebgp {
            presence "Send extended community attribute to this external neighbor";
            description
              "Send extended community attribute to this external neighbor";
            leaf inheritance-disable {
              type empty;
              description
                "Prevent send-extended-community-ebgp from being inherited from parent";
            }
          }
          container bestpath {
            description
              "Change default route selection criteria";
            container origin-as {
              description
                "BGP origin-AS knobs";
              container allow {
                description
                  "BGP origin-AS knobs";
                leaf invalid {
                  type empty;
                  description
                    "BGP bestpath selection will allow 'invalid' origin-AS";
                }
              }
            }
          }
          container update {
            description
              "BGP Update configuration";
            container in {
              description
                "Inbound update message handling";
              container filtering {
                presence "Inbound update message filtering";
                description
                  "Inbound update message filtering";
                container message {
                  description
                    "Filtered update messages";
                  container buffers {
                    presence "Filtered update message buffers";
                    description
                      "Filtered update message buffers";
                    leaf buffers-number {
                      type uint32 {
                        range "0..25" {
                          description
                            "Number of buffers to store filtered update messages (resizing does not take effect after filtering action has started)";
                        }
                      }
                      mandatory true;
                      description
                        "Number of buffers to store filtered update messages (resizing does not take effect after filtering action has started)";
                    }
                    leaf buffer-list {
                      type enumeration {
                        enum "buffers-number-enable" {
                          value 0;
                          description
                            "buffers-number-enable";
                        }
                        enum "non-circular" {
                          value 1;
                          description
                            "Message buffer list is not circular";
                        }
                      }
                      mandatory true;
                      description
                        "buffer-list";
                    }
                  }
                }
                container logging {
                  description
                    "Update filtering syslog message";
                  leaf disable {
                    type empty;
                    description
                      "Disable update filtering syslog message";
                  }
                }
                container attribute-filter {
                  description
                    "Attribute-filter configuration";
                  leaf group {
                    type string {
                      length "1..1024" {
                        description
                          "Attribute-filter group name";
                      }
                    }
                    description
                      "Attribute-filter group configuration";
                  }
                }
              }
              container labeled-unicast {
                description
                  "IPv4/IPv6 labeled-unicast inbound updates (paths)";
                container equivalent {
                  presence "IPv4/IPv6 labeled-unicast inbound updates (paths) treated equivalent to unicast updates (paths)";
                  description
                    "IPv4/IPv6 labeled-unicast inbound updates (paths) treated equivalent to unicast updates (paths)";
                  leaf inheritance-disable {
                    type empty;
                    description
                      "Do not inherit this configuration from parent group";
                  }
                }
              }
              container error-handling {
                description
                  "Inbound update message error handling";
                choice ERROR-HANDLING {
                  description
                    "Inbound update message error handling";
                  case AVOID-RESET {
                    leaf avoid-reset {
                      type enumeration {
                        enum "enable" {
                          value 1;
                          description
                            "avoid-reset-enable";
                        }
                        enum "disable" {
                          value 0;
                          description
                            "Neighbor may be reset during inbound update message error handling";
                        }
                      }
                      description
                        "Avoid neighbor reset during inbound update message error handling";
                    }
                  }
                  case TREAT-AS-WITHDRAW {
                    leaf treat-as-withdraw {
                      type enumeration {
                        enum "enable" {
                          value 1;
                          description
                            "(Deprecated in 7.11.1) Treat NLRIs as withdraws during inbound update message error handling";
                        }
                        enum "disable" {
                          value 0;
                          description
                            "(Deprecated in 7.11.1) Treat NLRIs as withdraws during inbound update message error handling";
                        }
                      }
                      description
                        "(Deprecated in 7.11.1) Treat NLRIs as withdraws during inbound update message error handling";
                    }
                  }
                }
              }
            }
          }
          container graceful-maintenance {
            presence
              "Attributes for Graceful Maintenance. This will cause
               neighbors to de-prefer routes from this router andn
               hoose alternates. This allows the router to be
               brought in or out of service gracefully.";
            description
              "Attributes for Graceful Maintenance. This will cause
               neighbors to de-prefer routes from this router andn
               hoose alternates. This allows the router to be
               brought in or out of service gracefully.";
            container local-preference {
              description
                "local preference with which to advertise routes tonibgp neigbors. Default=No Touch";
              choice LOCAL-PREFERENCE {
                description
                  "local preference with which to advertise routes tonibgp neigbors. Default=No Touch";
                case LOCAL-PREFERENCE-NUMBER {
                  leaf local-preference-number {
                    type uint32 {
                      range "0..4294967295" {
                        description
                          "Range of values for Local Preference";
                      }
                    }
                    description
                      "Range of values for Local Preference";
                  }
                }
                case INHERITANCE-DISABLE {
                  leaf inheritance-disable {
                    type empty;
                    description
                      "Prevent local preference from being inherited from the parent";
                  }
                }
              }
            }
            container as-prepends {
              description
                "Number of times to prepend the local AS number to thenAS path of routes. Default=0";
              choice AS-PREPENDS {
                description
                  "Number of times to prepend the local AS number to thenAS path of routes. Default=0";
                case PREPENDS-NUMBER {
                  leaf prepends-number {
                    type uint32 {
                      range "0..6" {
                        description
                          "Range of number of AS prepends";
                      }
                    }
                    description
                      "Range of number of AS prepends";
                  }
                }
                case INHERITANCE-DISABLE {
                  leaf inheritance-disable {
                    type empty;
                    description
                      "Prevent AS prepends from being inherited from the parent";
                  }
                }
              }
            }
            container activate {
              presence
                "Routes will be announced with the graceful maintenance
                 attributes while activated either here or under router
                 bgp configuration. While activated, all routes to this
                 neighbor will be announced with the attributes
                 configured here and all routes from this neighbor will
                 be announced to other neighbors with the graceful
                 maintenance attributes configured under those
                 neighbors. The g-shut community will be announced
                 regardless of the other attributes configured here. To
                 allow the g-shut community to be announced to ebgp
                 neighbors, the send-community-gshut-ebgp configuration
                 is also required. Note: changes to the attributes will
                 not take effect while activated.";
              description
                "Routes will be announced with the graceful maintenance
                 attributes while activated either here or under router
                 bgp configuration. While activated, all routes to this
                 neighbor will be announced with the attributes
                 configured here and all routes from this neighbor will
                 be announced to other neighbors with the graceful
                 maintenance attributes configured under those
                 neighbors. The g-shut community will be announced
                 regardless of the other attributes configured here. To
                 allow the g-shut community to be announced to ebgp
                 neighbors, the send-community-gshut-ebgp configuration
                 is also required. Note: changes to the attributes will
                 not take effect while activated.";
              leaf inheritance-disable {
                type empty;
                description
                  "Prevent activate from being inherited from the parent";
              }
            }
            container bandwidth-aware {
              description
                "Session interface Bandwidth based Graceful-Maintenance
                 Only restricted to eBGP directly connected, this will
                 enable Graceful maintenance whenever the link effective
                 bandwidth goes below a configurable low-threshold and deactivates
                 based on effective bandwidth reaches the high-threshold
                 or low-threshold if high-threshold is not configured";
              choice BANDWIDTH-AWARE {
                description
                  "Session interface Bandwidth based Graceful-Maintenance
                   Only restricted to eBGP directly connected, this will
                   enable Graceful maintenance whenever the link effective
                   bandwidth goes below a configurable low-threshold and deactivates
                   based on effective bandwidth reaches the high-threshold
                   or low-threshold if high-threshold is not configured";
                case PERCENTAGE-THRESHOLD {
                  container percentage-threshold {
                    presence "Threshold in Percentage of Effective Bandwidth nover Maximum Bandwidth";
                    description
                      "Threshold in Percentage of Effective Bandwidth nover Maximum Bandwidth";
                    leaf percentage-threshold-number {
                      type uint32 {
                        range "1..100" {
                          description
                            "Low threshold of effective bandwidth
                             (in percentage of max bandwidth) to enter/exit
                             graceful-maintenance";
                        }
                      }
                      mandatory true;
                      description
                        "Low threshold of effective bandwidth (in kbps)
                         to enter/exit graceful-maintenance";
                    }
                    leaf optional-high-threshold {
                      type uint32 {
                        range "1..100" {
                          description
                            "Optional High threshold of effective bandwidth
                             (in kbps) to exit graceful-maintenance";
                        }
                      }
                      description
                        "Optional High threshold of effective bandwidth
                         (in kbps) to exit graceful-maintenance";
                    }
                  }
                }
                case INHERITANCE-DISABLE {
                  leaf inheritance-disable {
                    type empty;
                    description
                      "Prevent bandwidth-aware from being inherited from the parent";
                  }
                }
                case BANDWIDTH-THRESHOLD {
                  container bandwidth-threshold {
                    presence "Bandwidth based threshold detection in kbps";
                    description
                      "Bandwidth based threshold detection in kbps";
                    leaf bandwidth-threshold-number {
                      type uint32 {
                        range "1..4294967295" {
                          description
                            "Low threshold of effective bandwidth (in kbps)
                             to enter/exit graceful-maintenance";
                        }
                      }
                      mandatory true;
                      description
                        "Low threshold of effective bandwidth (in kbps)
                         to enter/exit graceful-maintenance";
                    }
                    leaf optional-high-threshold-number {
                      type uint32 {
                        range "1..4294967295" {
                          description
                            "Optional High threshold of effective bandwidth
                             (in kbps) to exit graceful-maintenance";
                        }
                      }
                      description
                        "Optional High threshold of effective bandwidth
                         (in kbps) to exit graceful-maintenance";
                    }
                  }
                }
              }
            }
          }
          container address-families {
            description
              "Enter Address Family command mode";
            list address-family {
              key "af-name";
              description
                "Enter Address Family command mode";
              leaf af-name {
                type Bgp-address-family;
                description
                  "Enter Address Family command mode";
              }
              uses ADDRESS-FAMILY;
            }
          }
        }
        leaf vrf-name {
          type xr:Cisco-ios-xr-string {
            length "1..32" {
              description
                "VRF name - maximum length 32 characters";
            }
          }
          description
            "VRF name - maximum length 32 characters";
        }
        container mpls {
          description
            "Enable mpls parameters";
          container activate {
            description
              "Enter mpls interfaces in BGP vrf mpls activation mode";
            container interfaces {
              description
                "Interface to enable mpls";
              list interface {
                key "interface-name";
                description
                  "Interface to enable mpls";
                leaf interface-name {
                  type xr:Interface-name;
                  description
                    "Select an interface to configure";
                }
              }
            }
          }
        }
        container default-information {
          description
            "Control distribution of default information";
          leaf originate {
            type empty;
            description
              "Distribute a default route";
          }
        }
        leaf default-metric {
          type uint32 {
            range "1..4294967295" {
              description
                "Default metric";
            }
          }
          description
            "default redistributed metric";
        }
        container socket {
          description
            "set socket parameters";
          container receive-buffer-size {
            description
              "socket receive buffer size";
            leaf receive-buffer-size-number {
              type uint32 {
                range "512..131072" {
                  description
                    "Receive socket buffer size in bytes";
                }
              }
              description
                "Receive socket buffer size in bytes";
            }
            leaf bgp-read-buffer-size-number {
              type uint32 {
                range "512..131072" {
                  description
                    "BGP Read buffer size in bytes";
                }
              }
              must "../receive-buffer-size-number";
              description
                "BGP Read buffer size in bytes";
            }
          }
          container send-buffer-size {
            description
              "socket send buffer size";
            leaf send-buffer-size-number {
              type uint32 {
                range "4096..131072" {
                  description
                    "Send socket buffer size in bytes";
                }
              }
              description
                "Send socket buffer size in bytes";
            }
            leaf bgp-write-buffer-size {
              type uint32 {
                range "4096..131072" {
                  description
                    "BGP Write buffer size in bytes";
                }
              }
              must "../send-buffer-size-number";
              description
                "BGP Write buffer size in bytes";
            }
          }
        }
        container nexthop {
          description
            "Configure next-hop related items";
          container mpls {
            description
              "Configure next-hop related items for mpls";
            container forwarding {
              description
                "Enable next hop mpls forwarding path";
              leaf ibgp {
                type empty;
                description
                  "Enable mpls forwarding path for ibgp learnt nexthops";
              }
            }
          }
          container resolution {
            description
              "Configure next-hop related items for resolution";
            leaf allow-default {
              type empty;
              description
                "Enable nexthops resolution using default route";
            }
          }
        }
        container timers {
          description
            "Adjust routing timers";
          container bgp {
            description
              "BGP per neighbor timers";

            grouping KEEPALIVE-OPTIONS {
              description
                "Keepalive-options";
              choice KEEPALIVE-OPTIONS {
                description
                  "Keepalive-options";
                case ZERO {
                  leaf zero {
                    type empty;
                    description
                      "Disable keepalives/hold time";
                  }
                }
                case MINIMUM-ACCEPTABLE-HOLDTIME {
                  leaf minimum-acceptable-holdtime {
                    type uint32 {
                      range "3..65535" {
                        description
                          "Minimum acceptable holdtime from neighbor";
                      }
                    }
                    description
                      "Minimum acceptable holdtime from neighbor";
                  }
                }
              }
            }
            leaf keepalive-interval {
              type uint32 {
                range "0..65535" {
                  description
                    "Keepalive interval";
                }
              }
              description
                "Keepalive interval";
            }
            choice KEEPALIVE-INTERVAL {
              description
                "Keepalive interval";
              case ZERO {
                container zero {
                  must "../keepalive-interval";
                  presence "Disable keepalives/hold time";
                  description
                    "Disable keepalives/hold time";
                  uses KEEPALIVE-OPTIONS;
                }
              }
              case HOLDTIME {
                container holdtime {
                  must "../keepalive-interval and holdtime-number";
                  presence "Holdtime";
                  description
                    "Holdtime";
                  leaf holdtime-number {
                    type uint32 {
                      range "3..65535" {
                        description
                          "Holdtime";
                      }
                    }
                    description
                      "Holdtime";
                  }
                  uses KEEPALIVE-OPTIONS;
                }
              }
            }
          }
        }
        container bgp {
          description
            "BGP commands";
          container auto-policy-soft-reset {
            description
              "Enable automatic soft peer reset on policy reconfiguration";
            leaf disable {
              type empty;
              description
                "Disable automatic soft peer reset on policy reconfiguration";
            }
          }
          container bestpath {
            description
              "Change default route selection criteria";
            container cost-community {
              description
                "Cost community";
              leaf ignore {
                type empty;
                description
                  "Ignore cost-community comparison";
              }
            }
            leaf compare-routerid {
              type empty;
              description
                "Compare router-id for identical EBGP paths";
            }
            container aigp {
              description
                "AIGP attribute";
              leaf ignore {
                type empty;
                description
                  "Ignore AIGP attribute";
              }
            }
            container igp-metric {
              description
                "IGP metric values considered at Next Hop metric comparison stage";
              leaf ignore {
                type empty;
                description
                  "Ignore IGP metric during path comparison";
              }
            }
            container med {
              description
                "MED related";
              leaf missing-as-worst {
                type empty;
                description
                  "Treat missing MED as the least preferred one";
              }
              leaf always {
                type empty;
                description
                  "Allow comparing MED from different neighbors";
              }
            }
            container sr-policy {
              description
                "Paths over SR-policy";
              choice SR-POLICY {
                description
                  "Paths over SR-policy";
                case PREFER {
                  leaf prefer {
                    type empty;
                    description
                      "Consider only paths over SR Policy for bestpath selection, eBGP no-color eligible";
                  }
                }
                case FORCE {
                  leaf force {
                    type empty;
                    description
                      "Consider only paths over SR Policy for bestpath selection, eBGP no-color ineligible";
                  }
                }
              }
            }
            container as-path {
              description
                "AS path length";
              leaf multipath-relax {
                type empty;
                description
                  "Relax as-path check for multipath selection";
              }
              leaf ignore {
                type empty;
                description
                  "Ignore as-path length";
              }
            }
            container origin-as {
              description
                "BGP origin-AS knobs";
              container use {
                description
                  "BGP origin-AS knobs";
                leaf validity {
                  type empty;
                  description
                    "BGP bestpath selection will use origin-AS validity";
                }
              }
              container allow {
                description
                  "BGP origin-AS knobs";
                leaf invalid {
                  type empty;
                  description
                    "BGP bestpath selection will allow 'invalid' origin-AS";
                }
              }
            }
          }
          container default {
            description
              "Configure default value";
            leaf local-preference {
              type uint32 {
                range "0..4294967295" {
                  description
                    "Higher = more preferred";
                }
              }
              description
                "Local preference";
            }
          }
          container enforce-first-as {
            description
              "Enforce the first AS for EBGP routes";
            leaf disable {
              type empty;
              description
                "Disable";
            }
          }
          container fast-external-fallover {
            description
              "Immediately reset session if a link to a directly connected external peer goes down";
            leaf disable {
              type empty;
              description
                "Disable";
            }
          }
          container log {
            description
              "Log bgp info";
            container neighbor {
              description
                "Log neighbor state info";
              container changes {
                description
                  "Log neighbor up/down and reset reason";
                leaf disable {
                  type empty;
                  description
                    "Disable logging";
                }
              }
            }
            container message {
              description
                "Log neighbor inbound/outbound message";
              leaf disable {
                type empty;
                description
                  "Disable inbound and outbound message logging for all neighbors under the vrf";
              }
            }
          }
          container multipath {
            description
              "Change multipath selection criteria";
            container use {
              description
                "Considered in Multipath Selection";
              leaf cluster-list-length {
                type empty;
                description
                  "Use Cluster-List Length in BGP Multipath consideration";
              }
            }
          }
          leaf redistribute-internal {
            type empty;
            description
              "Allow redistribution of iBGP into IGPs (dangerous)";
          }
          leaf router-id {
            type inet:ipv4-address-no-zone;
            description
              "Configure Router-id";
          }
          leaf unsafe-ebgp-policy {
            type empty;
            description
              "Make eBGP neighbors with no policy pass all routes";
          }
          container origin-as {
            description
              "BGP origin-AS knobs";
            container validation {
              description
                "BGP origin-AS validation knobs";
              container signal {
                description
                  "Signal origin-AS validity towards peers";
                leaf ibgp {
                  type empty;
                  description
                    "Signal origin-AS validity towards iBGP peers";
                }
              }
              container time {
                description
                  "Time to wait between an RPKI update and a BGP table walk";
                choice TIME {
                  description
                    "Time to wait between an RPKI update and a BGP table walk";
                  case OFF {
                    leaf off {
                      type empty;
                      description
                        "No automatic prefix validation after an RPKI update";
                    }
                  }
                  case PREFIX-VALIDATION-TIME {
                    leaf prefix-validation-time {
                      type uint32 {
                        range "5..60" {
                          description
                            "Prefix validation time (in seconds)";
                        }
                      }
                      description
                        "Prefix validation time (in seconds)";
                    }
                  }
                }
              }
            }
          }
        }
        container bfd {
          description
            "Configure BFD parameters";
          leaf minimum-interval {
            type uint32 {
              range "3..30000" {
                description
                  "hello interval in milli-seconds";
              }
            }
            description
              "Hello interval";
          }
          leaf multiplier {
            type uint32 {
              range "2..16" {
                description
                  "Detect multiplier";
              }
            }
            description
              "Detect multiplier";
          }
        }
        container rd {
          description
            "route distinguisher";
          choice RD {
            description
              "route distinguisher";
            case AUTO {
              leaf auto {
                type empty;
                description
                  "Automatic route distinguisher";
              }
            }
            case TWO-BYTE-AS {
              container two-byte-as {
                presence "2-byte AS number";
                description
                  "2-byte AS number";
                leaf two-byte-as-number {
                  type xr:Bgp-as-number;
                  mandatory true;
                  description
                    "2-byte AS number";
                }
                leaf asn2-index {
                  type uint32 {
                    range "0..4294967295" {
                      description
                        "ASN2:index (hex or decimal format)";
                    }
                  }
                  mandatory true;
                  description
                    "ASN2:index (hex or decimal format)";
                }
              }
            }
            case FOUR-BYTE-AS {
              container four-byte-as {
                presence "4-byte AS number in asplain format";
                description
                  "4-byte AS number in asplain format";
                leaf four-byte-as-number {
                  type xr:Bgp-as-number;
                  mandatory true;
                  description
                    "4-byte AS number in asplain format";
                }
                leaf asn4-index {
                  type uint32 {
                    range "0..65535" {
                      description
                        "ASN4:index (hex or decimal format)";
                    }
                  }
                  mandatory true;
                  description
                    "ASN4:index (hex or decimal format)";
                }
              }
            }
            case IPV4-ADDRESS {
              container ipv4-address {
                presence "IPv4 address";
                description
                  "IPv4 address";
                leaf address {
                  type inet:ipv4-address-no-zone;
                  mandatory true;
                  description
                    "IPv4 address";
                }
                leaf ipv4address-index {
                  type uint32 {
                    range "0..65535" {
                      description
                        "IPv4Address:index (hex or decimal format)";
                    }
                  }
                  mandatory true;
                  description
                    "IPv4Address:index (hex or decimal format)";
                }
              }
            }
          }
        }
        container address-families {
          description
            "Enter Address Family command mode";
          list address-family {
            key "af-name";
            description
              "Enter Address Family command mode";
            leaf af-name {
              type Bgp-address-family;
              description
                "Enter Address Family command mode";
            }
            container segment-routing {
              description
                "Specify Segment-routing configurations";
              container srv6 {
                presence "Specify SRv6 configurations";
                description
                  "Specify SRv6 configurations";
                container alloc {
                  description
                    "SID Allocation";
                  container mode {
                    description
                      "SID Allocation mode";
                    choice MODE {
                      description
                        "SID Allocation mode";
                      case PER-CE {
                        leaf per-ce {
                          type empty;
                          description
                            "Set SRv6 per CE SID mode";
                        }
                      }
                      case PER-VRF {
                        leaf per-vrf {
                          type empty;
                          description
                            "Set SRv6 per VRF SID mode";
                        }
                      }
                      case PER-VRF-46 {
                        leaf per-vrf-46 {
                          type empty;
                          description
                            "Set SRv6 per VRF 46 SID mode";
                        }
                      }
                      case ROUTE-POLICY {
                        leaf route-policy {
                          type xr:Route-policy-name;
                          description
                            "Use a route policy to determine the SID allocation mode and locator (if provided) for given prefix";
                        }
                      }
                    }
                  }
                }
                leaf locator {
                  type xr:Cisco-ios-xr-string {
                    length "1..1024" {
                      description
                        "locator name";
                    }
                  }
                  description
                    "Specify locator";
                }
                container usid {
                  description
                    "Micro-SID configuration";
                  container allocation {
                    description
                      "Allocation mode";
                    leaf wide-local-id-block {
                      type empty;
                      description
                        "Wide LIB allocation";
                    }
                  }
                }
              }
            }
            container domain-distinguisher {
              description
                "Globally unique identifier for IGP domain";
              leaf domain-distinguisher-number {
                type uint32 {
                  range "1..4294967295" {
                    description
                      "4 octet ASN";
                  }
                }
                description
                  "4 octet ASN";
              }
              leaf octet-routerid {
                type inet:ipv4-address-no-zone;
                description
                  "4 octet router-id";
              }
            }
            container distance {
              description
                "Define an administrative distance";
              container bgp {
                must "external-route-distance and internal-route-distance and local-route-distance";
                presence "BGP distance";
                description
                  "BGP distance";
                leaf external-route-distance {
                  type uint32 {
                    range "1..20000" {
                      description
                        "Distance for routes external to the AS";
                    }
                  }
                  description
                    "Distance for routes external to the AS";
                }
                leaf internal-route-distance {
                  type uint32 {
                    range "1..20000" {
                      description
                        "Distance for routes internal to the AS";
                    }
                  }
                  description
                    "Distance for routes internal to the AS";
                }
                leaf local-route-distance {
                  type uint32 {
                    range "1..20000" {
                      description
                        "Distance for local routes";
                    }
                  }
                  description
                    "Distance for local routes";
                }
              }
            }
            leaf attribute-download {
              type empty;
              description
                "Configure attribute download for this address-family";
            }
            leaf implicit-import {
              type empty;
              description
                "Configure implicit import for this address-family";
            }
            container allow {
              description
                "Allow sending default originate route to VPN neighbor";
              container vpn {
                description
                  "Originate default route to VPN neighbor";
                leaf default-originate {
                  type empty;
                  description
                    "Originate default route to VPN neighbor";
                }
              }
            }
            container optimal-route-reflections {
              description
                "Configure optimal-route-reflection group.[Maximum ORR groups is 255]. Currently only supported in Global V4/V6 address family";
              list optimal-route-reflection {
                must "primary-root";
                key "optimal-route-reflection-name";
                description
                  "Configure optimal-route-reflection group.[Maximum ORR groups is 255]. Currently only supported in Global V4/V6 address family";
                leaf optimal-route-reflection-name {
                  type xr:Cisco-ios-xr-string {
                    length "1..32" {
                      description
                        "ORR group name - maximum 32 characters";
                    }
                  }
                  description
                    "ORR group name - maximum 32 characters";
                }
                leaf primary-root {
                  type inet:ip-address-no-zone;
                  description
                    "IP primary root address";
                }
                leaf secondary-root {
                  type inet:ip-address-no-zone;
                  must "../primary-root";
                  description
                    "IP secondary root address";
                }
                leaf tertiary-root {
                  type inet:ip-address-no-zone;
                  must "../primary-root and ../secondary-root";
                  description
                    "IP tertiary root address";
                }
              }
              container applies {
                description
                  "Apply optimal-route-reflection group";
                list apply {
                  key "apply-string";
                  description
                    "Apply optimal-route-reflection group";
                  leaf apply-string {
                    type xr:Cisco-ios-xr-string {
                      length "1..32" {
                        description
                          "ORR group name - maximum 32 characters";
                      }
                    }
                    description
                      "ORR group name - maximum 32 characters";
                  }
                }
              }
              leaf fallback-default-bestpath {
                type empty;
                description
                  "In case none of the paths are accessible in an ORR table, fallback to default table bestpath as ORR bestpath";
              }
            }
            container maximum-paths {
              description
                "Forward packets over multiple paths";
              container ebgp {
                presence "eBGP-multipath";
                description
                  "eBGP-multipath";
                leaf ebgp-number {
                  type uint32 {
                    range "2..128" {
                      description
                        "Number of paths (limit includes backup path)";
                    }
                  }
                  mandatory true;
                  description
                    "Number of paths (limit includes backup path)";
                }
                leaf selective {
                  type empty;
                  description
                    "Allow multipaths only from marked neighbors";
                }
                leaf route-policy {
                  type xr:Route-policy-name;
                  description
                    "Route policy to specify ORF and inbound filter";
                }
              }
              container ibgp {
                presence "iBGP-multipath";
                description
                  "iBGP-multipath";
                leaf ibgp-number {
                  type uint32 {
                    range "2..128" {
                      description
                        "Number of paths (limit includes backup path)";
                    }
                  }
                  mandatory true;
                  description
                    "Number of paths (limit includes backup path)";
                }
                container unequal-cost {
                  presence "Allow multipaths to have different BGP nexthop IGP metrics";
                  description
                    "Allow multipaths to have different BGP nexthop IGP metrics";
                  leaf deterministic {
                    type empty;
                    description
                      "Deterministic Multipath selection primarily on IGP metric order";
                  }
                }
                leaf selective {
                  type empty;
                  description
                    "Allow multipaths only from marked neighbors";
                }
                leaf route-policy {
                  type xr:Route-policy-name;
                  description
                    "Route policy to specify ORF and inbound filter";
                }
              }
              container eibgp {
                presence "eiBGP-multipath";
                description
                  "eiBGP-multipath";
                leaf eibgp-number {
                  type uint32 {
                    range "2..128" {
                      description
                        "Number of paths (limit includes backup path)";
                    }
                  }
                  mandatory true;
                  description
                    "Number of paths (limit includes backup path)";
                }
                leaf equal-cost {
                  type empty;
                  description
                    "Preserve equal nexthop IGP metric criteria for multipath eligiblity between same path-types (iBGP or eBGP)";
                }
                leaf selective {
                  type empty;
                  description
                    "Allow multipaths only from marked neighbors";
                }
                leaf route-policy {
                  type xr:Route-policy-name;
                  description
                    "Route policy to specify ORF and inbound filter";
                }
              }
              leaf unique-nexthop-check-disable {
                type empty;
                description
                  "Disable multipath unique nexthop check";
              }
            }
            container import {
              description
                "Configure import rules";
              container from {
                description
                  "Import routes from source";
                leaf bridge-domain {
                  type empty;
                  description
                    "Import IP hosts from EVPN bridge-domain";
                }
              }
            }
            container additional-paths {
              description
                "Additional paths configuration";
              container send {
                presence "Additional paths Send capability";
                description
                  "Additional paths Send capability";
                leaf disable {
                  type empty;
                  description
                    "Do not advertise additional paths Send capability";
                }
              }
              container receive {
                presence "Additional paths Receive capability";
                description
                  "Additional paths Receive capability";
                leaf disable {
                  type empty;
                  description
                    "Do not advertise additional paths Receive capability";
                }
              }
              container advertise-limit {
                description
                  "advertise-limit";
                choice ADVERTISE-LIMIT {
                  description
                    "advertise-limit";
                  case DISABLE {
                    leaf disable {
                      type empty;
                      description
                        "Disable additional paths selection";
                    }
                  }
                  case ADVERTISE-PATH-LIMIT {
                    leaf advertise-path-limit {
                      type uint32 {
                        range "1..20000" {
                          description
                            "Advertise path limit value";
                        }
                      }
                      description
                        "Limit the number of paths to be advertised (default 32)";
                    }
                  }
                }
              }
              container selection {
                description
                  "Additional paths selection";
                choice SELECTION {
                  description
                    "Additional paths selection";
                  case DISABLE {
                    leaf disable {
                      type empty;
                      description
                        "Disable additional paths selection";
                    }
                  }
                  case ROUTE-POLICY {
                    leaf route-policy {
                      type xr:Route-policy-name;
                      description
                        "Route-policy for additional paths selection";
                    }
                  }
                }
              }
            }
            container permanent-network {
              description
                "Permanent network configuration";
              leaf route-policy {
                type xr:Route-policy-name;
                description
                  "Route policy to read the prefixes from";
              }
            }
            container advertise {
              description
                "Advertise BGP path";
              container local-labeled-route {
                description
                  "Advertisement of routes with local-label";
                leaf safi-unicast {
                  type enumeration {
                    enum "enable" {
                      value 1;
                      description
                        "Advertise routes with local-label via Unicast SAFI";
                    }
                    enum "disable" {
                      value 2;
                      description
                        "Do not advertise routes with local-label via Unicast SAFI";
                    }
                  }
                  description
                    "Advertisement of routes with local-label via Unicast SAFI";
                }
              }
              container best-external {
                presence "Advertise best-external path";
                description
                  "Advertise best-external path";
                leaf labeled-unicast {
                  type empty;
                  description
                    "Limit best-external to Labeled-Unicast address family";
                }
                leaf disable {
                  type empty;
                  description
                    "Do not advertise best-external path";
                }
              }
              container epe-bgp {
                description
                  "Advertise bgp epe as label unicast prefix";
                leaf labeled-unicast {
                  type empty;
                  description
                    "Limit epe-bgplu to Labeled-Unicast address family";
                }
              }
            }
            container networks {
              description
                "Specify a network to announce via BGP";
              list network {
                key "address address-prefix";
                description
                  "Specify a network to announce via BGP";
                leaf address {
                  type inet:ip-address-no-zone;
                  description
                    "IPaddress";
                }
                leaf address-prefix {
                  type uint32 {
                    range "0..128";
                  }
                  description
                    "IP address prefix";
                }
                choice NETWORK {
                  description
                    "Specify a network to announce via BGP";
                  case ROUTE-POLICY {
                    leaf route-policy {
                      type xr:Route-policy-name;
                      description
                        "Route-policy to modify the attributes";
                    }
                  }
                  case BACKDOOR {
                    leaf backdoor {
                      type empty;
                      description
                        "Specify a BGP backdoor route";
                    }
                  }
                  case MULTIPATH {
                    leaf multipath {
                      type empty;
                      description
                        "Enable installation of multiple paths from RIB";
                    }
                  }
                }
              }
            }
            container aggregate-addresses {
              description
                "Configure BGP aggregate entries";
              list aggregate-address {
                key "address address-prefix";
                description
                  "Configure BGP aggregate entries";
                leaf address {
                  type inet:ip-address-no-zone;
                  description
                    "IPaddress";
                }
                leaf address-prefix {
                  type uint32 {
                    range "0..128";
                  }
                  description
                    "IP address prefix";
                }
                leaf as-set {
                  type empty;
                  description
                    "Generate AS set path information";
                }
                leaf as-confed-set {
                  type empty;
                  description
                    "Generate AS confed set path information";
                }
                leaf summary-only {
                  type empty;
                  description
                    "Filter more specific routes from updates";
                }
                leaf route-policy {
                  type xr:Route-policy-name;
                  description
                    "Route-policy to modify the attributes";
                }
                leaf description {
                  type xr:Cisco-ios-xr-string {
                    length "1..1024" {
                      description
                        "Description";
                    }
                  }
                  description
                    "Aggreate address specific description";
                }
                leaf set-tag {
                  type uint32 {
                    range "0..4294967295";
                  }
                  description
                    "Set a IGP tag value on the route";
                }
              }
            }
            container redistribute {
              description
                "Redistribute information from another routing protocol";

              grouping REDISTRIBUTE {
                description
                  "Redistribute";
                leaf metric {
                  type uint32 {
                    range "0..4294967295" {
                      description
                        "Default metric";
                    }
                  }
                  description
                    "Metric for redistributed routes";
                }
                leaf multipath {
                  type empty;
                  description
                    "Enable installation of multiple paths from RIB";
                }
                leaf route-policy {
                  type xr:Route-policy-name;
                  description
                    "Route policy reference";
                }
                leaf default-policy-action-in {
                  type enumeration {
                    enum "accept" {
                      value 1;
                      description
                        "accept the route if does not satisfy the import policy";
                    }
                    enum "reject" {
                      value 2;
                      description
                        "reject the route if does not satisfy the import policy";
                    }
                  }
                  description
                    "Set a default action if a route does not satify the policy definition";
                }
              }
              container ospfs {
                description
                  "Open Shortest Path First (OSPF)";
                list ospf {
                  key "ospf-router-tag";
                  description
                    "Open Shortest Path First (OSPF)";
                  leaf ospf-router-tag {
                    type xr:Cisco-ios-xr-string {
                      length "1..1024" {
                        description
                          "OSPF router tag";
                      }
                    }
                    description
                      "OSPF router tag";
                  }
                  container match {
                    description
                      "Redistribution of OSPF routes";
                    choice MATCH {
                      description
                        "Redistribution of OSPF routes";
                      case INTERNAL {
                        container internal {
                          presence "Redistribute OSPF internal routes";
                          description
                            "Redistribute OSPF internal routes";
                          choice INTERNAL {
                            description
                              "Redistribute OSPF internal routes";
                            case EXTERNAL {
                              container external {
                                presence "Redistribute OSPF external routes";
                                description
                                  "Redistribute OSPF external routes";
                                choice EXTERNAL {
                                  description
                                    "Redistribute OSPF external routes";
                                  case ONE {
                                    container one {
                                      presence "Redistribute external type 1 routes";
                                      description
                                        "Redistribute external type 1 routes";
                                      container nssa-external {
                                        presence "Redistribute OSPF NSSA external routes";
                                        description
                                          "Redistribute OSPF NSSA external routes";
                                        choice NSSA-EXTERNAL {
                                          description
                                            "Redistribute OSPF NSSA external routes";
                                          case ONE {
                                            leaf one {
                                              type empty;
                                              description
                                                "Redistribute NSSA external type 1 routes";
                                            }
                                          }
                                          case TWO {
                                            leaf two {
                                              type empty;
                                              description
                                                "Redistribute NSSA external type 2 routes";
                                            }
                                          }
                                        }
                                      }
                                    }
                                  }
                                  case TWO {
                                    container two {
                                      presence "Redistribute external type 2 routes";
                                      description
                                        "Redistribute external type 2 routes";
                                      container nssa-external {
                                        presence "Redistribute OSPF NSSA external routes";
                                        description
                                          "Redistribute OSPF NSSA external routes";
                                        choice NSSA-EXTERNAL {
                                          description
                                            "Redistribute OSPF NSSA external routes";
                                          case ONE {
                                            leaf one {
                                              type empty;
                                              description
                                                "Redistribute NSSA external type 1 routes";
                                            }
                                          }
                                          case TWO {
                                            leaf two {
                                              type empty;
                                              description
                                                "Redistribute NSSA external type 2 routes";
                                            }
                                          }
                                        }
                                      }
                                    }
                                  }
                                  case NSSA-EXTERNAL {
                                    container nssa-external {
                                      presence "Redistribute OSPF NSSA external routes";
                                      description
                                        "Redistribute OSPF NSSA external routes";
                                      choice NSSA-EXTERNAL {
                                        description
                                          "Redistribute OSPF NSSA external routes";
                                        case ONE {
                                          leaf one {
                                            type empty;
                                            description
                                              "Redistribute NSSA external type 1 routes";
                                          }
                                        }
                                        case TWO {
                                          leaf two {
                                            type empty;
                                            description
                                              "Redistribute NSSA external type 2 routes";
                                          }
                                        }
                                      }
                                    }
                                  }
                                }
                              }
                            }
                            case NSSA-EXTERNAL {
                              container nssa-external {
                                presence "Redistribute OSPF NSSA external routes";
                                description
                                  "Redistribute OSPF NSSA external routes";
                                choice NSSA-EXTERNAL {
                                  description
                                    "Redistribute OSPF NSSA external routes";
                                  case ONE {
                                    leaf one {
                                      type empty;
                                      description
                                        "Redistribute NSSA external type 1 routes";
                                    }
                                  }
                                  case TWO {
                                    leaf two {
                                      type empty;
                                      description
                                        "Redistribute NSSA external type 2 routes";
                                    }
                                  }
                                }
                              }
                            }
                          }
                        }
                      }
                      case EXTERNAL {
                        container external {
                          presence "Redistribute OSPF external routes";
                          description
                            "Redistribute OSPF external routes";
                          choice EXTERNAL {
                            description
                              "Redistribute OSPF external routes";
                            case ONE {
                              container one {
                                presence "Redistribute external type 1 routes";
                                description
                                  "Redistribute external type 1 routes";
                                container nssa-external {
                                  presence "Redistribute OSPF NSSA external routes";
                                  description
                                    "Redistribute OSPF NSSA external routes";
                                  choice NSSA-EXTERNAL {
                                    description
                                      "Redistribute OSPF NSSA external routes";
                                    case ONE {
                                      leaf one {
                                        type empty;
                                        description
                                          "Redistribute NSSA external type 1 routes";
                                      }
                                    }
                                    case TWO {
                                      leaf two {
                                        type empty;
                                        description
                                          "Redistribute NSSA external type 2 routes";
                                      }
                                    }
                                  }
                                }
                              }
                            }
                            case TWO {
                              container two {
                                presence "Redistribute external type 2 routes";
                                description
                                  "Redistribute external type 2 routes";
                                container nssa-external {
                                  presence "Redistribute OSPF NSSA external routes";
                                  description
                                    "Redistribute OSPF NSSA external routes";
                                  leaf one {
                                    type empty;
                                    description
                                      "Redistribute NSSA external type 1 routes";
                                  }
                                  leaf two {
                                    type empty;
                                    description
                                      "Redistribute NSSA external type 2 routes";
                                  }
                                }
                              }
                            }
                            case NSSA-EXTERNAL {
                              container nssa-external {
                                presence "Redistribute OSPF NSSA external routes";
                                description
                                  "Redistribute OSPF NSSA external routes";
                                choice NSSA-EXTERNAL {
                                  description
                                    "Redistribute OSPF NSSA external routes";
                                  case ONE {
                                    leaf one {
                                      type empty;
                                      description
                                        "Redistribute NSSA external type 1 routes";
                                    }
                                  }
                                  case TWO {
                                    leaf two {
                                      type empty;
                                      description
                                        "Redistribute NSSA external type 2 routes";
                                    }
                                  }
                                }
                              }
                            }
                          }
                        }
                      }
                      case NSSA-EXTERNAL {
                        container nssa-external {
                          presence "Redistribute OSPF NSSA external routes";
                          description
                            "Redistribute OSPF NSSA external routes";
                          choice NSSA-EXTERNAL {
                            description
                              "Redistribute OSPF NSSA external routes";
                            case ONE {
                              leaf one {
                                type empty;
                                description
                                  "Redistribute NSSA external type 1 routes";
                              }
                            }
                            case TWO {
                              leaf two {
                                type empty;
                                description
                                  "Redistribute NSSA external type 2 routes";
                              }
                            }
                          }
                        }
                      }
                    }
                  }
                  uses REDISTRIBUTE;
                }
              }
              container ospfv3s {
                description
                  "IPv6 Open Shortest Path First (OSPFv3)";
                list ospfv3 {
                  key "ospfv3-router-tag";
                  description
                    "IPv6 Open Shortest Path First (OSPFv3)";
                  leaf ospfv3-router-tag {
                    type xr:Cisco-ios-xr-string {
                      length "1..1024" {
                        description
                          "OSPFv3 router tag";
                      }
                    }
                    description
                      "OSPFv3 router tag";
                  }
                  container match {
                    description
                      "Redistribution of OSPF routes";
                    choice MATCH {
                      description
                        "Redistribution of OSPF routes";
                      case INTERNAL {
                        container internal {
                          presence "Redistribute OSPF internal routes";
                          description
                            "Redistribute OSPF internal routes";
                          choice INTERNAL {
                            description
                              "Redistribute OSPF internal routes";
                            case EXTERNAL {
                              container external {
                                presence "Redistribute OSPF external routes";
                                description
                                  "Redistribute OSPF external routes";
                                choice EXTERNAL {
                                  description
                                    "Redistribute OSPF external routes";
                                  case ONE {
                                    container one {
                                      presence "Redistribute external type 1 routes";
                                      description
                                        "Redistribute external type 1 routes";
                                      container nssa-external {
                                        presence "Redistribute OSPF NSSA external routes";
                                        description
                                          "Redistribute OSPF NSSA external routes";
                                        choice NSSA-EXTERNAL {
                                          description
                                            "Redistribute OSPF NSSA external routes";
                                          case ONE {
                                            leaf one {
                                              type empty;
                                              description
                                                "Redistribute NSSA external type 1 routes";
                                            }
                                          }
                                          case TWO {
                                            leaf two {
                                              type empty;
                                              description
                                                "Redistribute NSSA external type 2 routes";
                                            }
                                          }
                                        }
                                      }
                                    }
                                  }
                                  case TWO {
                                    container two {
                                      presence "Redistribute external type 2 routes";
                                      description
                                        "Redistribute external type 2 routes";
                                      container nssa-external {
                                        presence "Redistribute OSPF NSSA external routes";
                                        description
                                          "Redistribute OSPF NSSA external routes";
                                        choice NSSA-EXTERNAL {
                                          description
                                            "Redistribute OSPF NSSA external routes";
                                          case ONE {
                                            leaf one {
                                              type empty;
                                              description
                                                "Redistribute NSSA external type 1 routes";
                                            }
                                          }
                                          case TWO {
                                            leaf two {
                                              type empty;
                                              description
                                                "Redistribute NSSA external type 2 routes";
                                            }
                                          }
                                        }
                                      }
                                    }
                                  }
                                  case NSSA-EXTERNAL {
                                    container nssa-external {
                                      presence "Redistribute OSPF NSSA external routes";
                                      description
                                        "Redistribute OSPF NSSA external routes";
                                      choice NSSA-EXTERNAL {
                                        description
                                          "Redistribute OSPF NSSA external routes";
                                        case ONE {
                                          leaf one {
                                            type empty;
                                            description
                                              "Redistribute NSSA external type 1 routes";
                                          }
                                        }
                                        case TWO {
                                          leaf two {
                                            type empty;
                                            description
                                              "Redistribute NSSA external type 2 routes";
                                          }
                                        }
                                      }
                                    }
                                  }
                                }
                              }
                            }
                            case NSSA-EXTERNAL {
                              container nssa-external {
                                presence "Redistribute OSPF NSSA external routes";
                                description
                                  "Redistribute OSPF NSSA external routes";
                                choice NSSA-EXTERNAL {
                                  description
                                    "Redistribute OSPF NSSA external routes";
                                  case ONE {
                                    leaf one {
                                      type empty;
                                      description
                                        "Redistribute NSSA external type 1 routes";
                                    }
                                  }
                                  case TWO {
                                    leaf two {
                                      type empty;
                                      description
                                        "Redistribute NSSA external type 2 routes";
                                    }
                                  }
                                }
                              }
                            }
                          }
                        }
                      }
                      case EXTERNAL {
                        container external {
                          presence "Redistribute OSPF external routes";
                          description
                            "Redistribute OSPF external routes";
                          choice EXTERNAL {
                            description
                              "Redistribute OSPF external routes";
                            case ONE {
                              container one {
                                presence "Redistribute external type 1 routes";
                                description
                                  "Redistribute external type 1 routes";
                                container nssa-external {
                                  presence "Redistribute OSPF NSSA external routes";
                                  description
                                    "Redistribute OSPF NSSA external routes";
                                  choice NSSA-EXTERNAL {
                                    description
                                      "Redistribute OSPF NSSA external routes";
                                    case ONE {
                                      leaf one {
                                        type empty;
                                        description
                                          "Redistribute NSSA external type 1 routes";
                                      }
                                    }
                                    case TWO {
                                      leaf two {
                                        type empty;
                                        description
                                          "Redistribute NSSA external type 2 routes";
                                      }
                                    }
                                  }
                                }
                              }
                            }
                            case TWO {
                              container two {
                                presence "Redistribute external type 2 routes";
                                description
                                  "Redistribute external type 2 routes";
                                container nssa-external {
                                  presence "Redistribute OSPF NSSA external routes";
                                  description
                                    "Redistribute OSPF NSSA external routes";
                                  leaf one {
                                    type empty;
                                    description
                                      "Redistribute NSSA external type 1 routes";
                                  }
                                  leaf two {
                                    type empty;
                                    description
                                      "Redistribute NSSA external type 2 routes";
                                  }
                                }
                              }
                            }
                            case NSSA-EXTERNAL {
                              container nssa-external {
                                presence "Redistribute OSPF NSSA external routes";
                                description
                                  "Redistribute OSPF NSSA external routes";
                                choice NSSA-EXTERNAL {
                                  description
                                    "Redistribute OSPF NSSA external routes";
                                  case ONE {
                                    leaf one {
                                      type empty;
                                      description
                                        "Redistribute NSSA external type 1 routes";
                                    }
                                  }
                                  case TWO {
                                    leaf two {
                                      type empty;
                                      description
                                        "Redistribute NSSA external type 2 routes";
                                    }
                                  }
                                }
                              }
                            }
                          }
                        }
                      }
                      case NSSA-EXTERNAL {
                        container nssa-external {
                          presence "Redistribute OSPF NSSA external routes";
                          description
                            "Redistribute OSPF NSSA external routes";
                          choice NSSA-EXTERNAL {
                            description
                              "Redistribute OSPF NSSA external routes";
                            case ONE {
                              leaf one {
                                type empty;
                                description
                                  "Redistribute NSSA external type 1 routes";
                              }
                            }
                            case TWO {
                              leaf two {
                                type empty;
                                description
                                  "Redistribute NSSA external type 2 routes";
                              }
                            }
                          }
                        }
                      }
                    }
                  }
                  uses REDISTRIBUTE;
                }
              }
              container eigrps {
                description
                  "Enhanced Interior Gateway Routing Protocol (EIGRP)";
                list eigrp {
                  key "eigrp-name";
                  description
                    "Enhanced Interior Gateway Routing Protocol (EIGRP)";
                  leaf eigrp-name {
                    type xr:Cisco-ios-xr-string {
                      length "1..1024" {
                        description
                          "EIGRP instance name";
                      }
                    }
                    description
                      "EIGRP instance name";
                  }
                  container match {
                    description
                      "EIGRP route type for redistribution";
                    choice MATCH {
                      description
                        "EIGRP route type for redistribution";
                      case INTERNAL {
                        container internal {
                          presence "Redistribute EIGRP internal routes";
                          description
                            "Redistribute EIGRP internal routes";
                          leaf external {
                            type empty;
                            description
                              "Redistribute EIGRP external routes";
                          }
                        }
                      }
                      case EXTERNAL {
                        leaf external {
                          type empty;
                          description
                            "Redistribute EIGRP external routes";
                        }
                      }
                    }
                  }
                  uses REDISTRIBUTE;
                }
              }
              container isis-processes {
                description
                  "ISO IS-IS";
                list isis-process {
                  key "isis-name";
                  description
                    "ISO IS-IS";
                  leaf isis-name {
                    type xr:Cisco-ios-xr-string {
                      length "1..1024" {
                        description
                          "IS-IS instance name";
                      }
                    }
                    description
                      "IS-IS instance name";
                  }
                  container level {
                    description
                      "Redistribute routes from the specified ISIS levels";
                    choice LEVEL {
                      description
                        "Redistribute routes from the specified ISIS levels";
                      case ONE {
                        container one {
                          presence "Redistribute ISIS level 1 routes";
                          description
                            "Redistribute ISIS level 1 routes";
                          container level {
                            description
                              "Redistribute routes from the specified ISIS levels";
                            choice LEVEL {
                              description
                                "Redistribute routes from the specified ISIS levels";
                              case TWO {
                                container two {
                                  presence "Redistribute ISIS level 2 ISIS routes";
                                  description
                                    "Redistribute ISIS level 2 ISIS routes";
                                  container level {
                                    description
                                      "Redistribute routes from the specified ISIS levels";
                                    leaf one-inter-area {
                                      type empty;
                                      description
                                        "Redistribute ISIS level 1 inter-area routes";
                                    }
                                  }
                                }
                              }
                              case ONE-INTER-AREA {
                                leaf one-inter-area {
                                  type empty;
                                  description
                                    "Redistribute ISIS level 1 inter-area routes";
                                }
                              }
                            }
                          }
                        }
                      }
                      case TWO {
                        container two {
                          presence "Redistribute ISIS level 2 ISIS routes";
                          description
                            "Redistribute ISIS level 2 ISIS routes";
                          container level {
                            description
                              "Redistribute routes from the specified ISIS levels";
                            leaf one-inter-area {
                              type empty;
                              description
                                "Redistribute ISIS level 1 inter-area routes";
                            }
                          }
                        }
                      }
                      case ONE-INTER-AREA {
                        leaf one-inter-area {
                          type empty;
                          description
                            "Redistribute ISIS level 1 inter-area routes";
                        }
                      }
                    }
                  }
                  uses REDISTRIBUTE;
                }
              }
              container connected {
                presence "Connected routes";
                description
                  "Connected routes";
                uses REDISTRIBUTE;
              }
              container static {
                presence "Static routes";
                description
                  "Static routes";
                uses REDISTRIBUTE;
              }
              container rip {
                presence "Routing Information Protocol (RIP)";
                description
                  "Routing Information Protocol (RIP)";
                uses REDISTRIBUTE;
              }
              container subscriber {
                presence "subscriber routes";
                description
                  "subscriber routes";
                uses REDISTRIBUTE;
              }
              container mobile {
                presence "Mobile routes";
                description
                  "Mobile routes";
                uses REDISTRIBUTE;
              }
              container lisp {
                presence "Locator/ID Separation Protocol (LISP)";
                description
                  "Locator/ID Separation Protocol (LISP)";
                uses REDISTRIBUTE;
              }
              container applications {
                description
                  "OnePK application routes";
                list application {
                  key "application-name";
                  description
                    "OnePK application routes";
                  leaf application-name {
                    type string {
                      length "1..1024" {
                        description
                          "OnePK application name";
                      }
                    }
                    description
                      "OnePK application name";
                  }
                  uses REDISTRIBUTE;
                }
              }
            }
            leaf table-policy {
              type xr:Route-policy-name;
              description
                "Configure policy for installation of routes to RIB";
            }
            container retain {
              description
                "Accept/Retain specified bgp parameters";
              container route-target {
                description
                  "Accept received updates with the specified route targets";
                choice ROUTE-TARGET {
                  description
                    "Accept received updates with the specified route targets";
                  case ALL {
                    leaf all {
                      type empty;
                      description
                        "Accept received updates containing at least one route target";
                    }
                  }
                  case ROUTE-POLICY {
                    leaf route-policy {
                      type xr:Route-policy-name;
                      description
                        "Accept received updates accepted by the specified policy";
                    }
                  }
                }
              }
              leaf local-label {
                type uint32 {
                  range "3..60" {
                    description
                      "Label retention time in minutes";
                  }
                }
                description
                  "Delay the release of the local label as configured";
              }
            }
            container source {
              description
                "Accept/Retain specified bgp parameters";
              container route-target {
                description
                  "Accept received updates with the specified route targets";
                leaf route-policy {
                  type xr:Route-policy-name;
                  description
                    "Accept received updates accepted by the specified policy";
                }
              }
            }
            container allocate-label {
              description
                "Allocate label for selected prefixes";
              choice ALLOCATE-LABEL {
                description
                  "Allocate label for selected prefixes";
                case ALL {
                  container all {
                    presence "Allocate labels for all prefixes";
                    description
                      "Allocate labels for all prefixes";
                    leaf unlabeled-path {
                      type empty;
                      description
                        "Allocate label for unlabeled paths too";
                    }
                  }
                }
                case ROUTE-POLICY {
                  container route-policy {
                    presence "Use a route policy to select prefixes for label allocation";
                    description
                      "Use a route policy to select prefixes for label allocation";
                    leaf route-policy-name {
                      type xr:Route-policy-name;
                      mandatory true;
                      description
                        "route policy name";
                    }
                    leaf unlabeled-path {
                      type empty;
                      description
                        "Allocate label for unlabeled paths too";
                    }
                  }
                }
              }
            }
            container label {
              description
                "Label-related configuration";
              container mode {
                description
                  "Select label mode";
                choice MODE {
                  description
                    "Select label mode";
                  case PER-PREFIX {
                    leaf per-prefix {
                      type empty;
                      description
                        "Set per perfix label mode";
                    }
                  }
                  case PER-CE {
                    leaf per-ce {
                      type empty;
                      description
                        "Set per CE label mode";
                    }
                  }
                  case PER-VRF {
                    leaf per-vrf {
                      type empty;
                      description
                        "Set per VRF label mode";
                    }
                  }
                  case PER-VRF-46 {
                    leaf per-vrf-46 {
                      type empty;
                      description
                        "Set per VRF 46 label mode";
                    }
                  }
                  case ROUTE-POLICY {
                    leaf route-policy {
                      type xr:Route-policy-name;
                      description
                        "Use a route policy to select prefixes for label allocation mode";
                    }
                  }
                  case PER-NEXTHOP-RECEIVED-LABEL {
                    container per-nexthop-received-label {
                      presence "Set label mode per nexthop and received label";
                      description
                        "Set label mode per nexthop and received label";
                      leaf allocate-secondary-label {
                        type empty;
                        description
                          "Allocate secondary label to avoid label oscillation insymmetric PIC deployments";
                      }
                    }
                  }
                }
              }
            }
            container bgp {
              description
                "BGP Commands";
              container event {
                description
                  "Policy for per-prefix tracing";
                container prefix {
                  description
                    "Policy for per-prefix tracing";
                  leaf route-policy {
                    type xr:Route-policy-name;
                    description
                      "Policy for per-prefix tracing";
                  }
                }
              }
              container origin-as {
                description
                  "BGP origin-AS knobs";
                container validation {
                  description
                    "BGP origin-AS validation knobs";
                  leaf enable {
                    type empty;
                    description
                      "Enable RPKI origin-AS validation";
                  }
                  container signal {
                    description
                      "Signal origin-AS validity towards peers";
                    leaf ibgp {
                      type empty;
                      description
                        "Signal origin-AS validity towards iBGP peers";
                    }
                  }
                }
              }
              container bestpath {
                description
                  "Change default route selection criteria";
                container origin-as {
                  description
                    "BGP origin-AS knobs";
                  container use {
                    description
                      "BGP origin-AS knobs";
                    leaf validity {
                      type empty;
                      description
                        "BGP bestpath selection will use origin-AS validity";
                    }
                  }
                  container allow {
                    description
                      "BGP origin-AS knobs";
                    leaf invalid {
                      type empty;
                      description
                        "BGP bestpath selection will allow 'invalid' origin-AS";
                    }
                  }
                }
              }
              container dampening {
                presence "Enable route-flap dampening";
                description
                  "Enable route-flap dampening";
                choice DAMPENING {
                  description
                    "Enable route-flap dampening";
                  case HALFLIFE-TIME {
                    container halflife-time {
                      description
                        "Half-life time for the penalty";
                      leaf half-life-time-number {
                        type uint32 {
                          range "1..255" {
                            description
                              "Half-life time for the penalty";
                          }
                        }
                        mandatory true;
                        description
                          "Half-life time for the penalty";
                      }
                      leaf route-reuse-number {
                        type uint32 {
                          range "1..255" {
                            description
                              "Value to start reusing a route";
                          }
                        }
                        must "../half-life-time-number and ../suppress-route-number and ../stable-route-max-suppress-number";
                        description
                          "Value to start reusing a route";
                      }
                      leaf suppress-route-number {
                        type uint32 {
                          range "1..255" {
                            description
                              "Value to start suppressing a route";
                          }
                        }
                        must "../half-life-time-number and ../route-reuse-number and ../stable-route-max-suppress-number";
                        description
                          "Value to start suppressing a route";
                      }
                      leaf stable-route-max-suppress-number {
                        type uint32 {
                          range "0..4294967295" {
                            description
                              "Maximum duration to suppress a stable route";
                          }
                        }
                        must "../half-life-time-number and ../route-reuse-number and ../suppress-route-number";
                        description
                          "Maximum duration to suppress a stable route";
                      }
                    }
                  }
                  case ROUTE-POLICY {
                    leaf route-policy {
                      type xr:Route-policy-name;
                      description
                        "Route policy to specify criteria for dampening";
                    }
                  }
                }
              }
            }
            container dynamic-med {
              description
                "Dynamic MED Interval";
              leaf interval {
                type uint32 {
                  range "0..10" {
                    description
                      "Update generation delay in minutes";
                  }
                }
                description
                  "Update generation delay (in minutes) after a MED change";
              }
            }
            container weight {
              description
                "Define or modify weight";
              container reset-on-import {
                presence "Reset weight of paths on import";
                description
                  "Reset weight of paths on import";
                leaf disable {
                  type empty;
                  description
                    "Do not reset weight of paths on import";
                }
              }
            }
            container nexthop {
              description
                "Nexthop";
              leaf route-policy {
                type xr:Route-policy-name;
                description
                  "Policy to filter out nexthop notification";
              }
            }
            container as-path-loopcheck {
              description
                "Configure AS Path loop checking";
              container out {
                description
                  "For outbound updates";
                leaf disable {
                  type empty;
                  description
                    "Disable";
                }
              }
            }
            container inter-as {
              description
                "Inter AS";
              leaf install {
                type empty;
                description
                  "Install remote mvpn routes in default vrf";
              }
            }
            leaf global-table-multicast {
              type empty;
              description
                "Enable global table multicast";
            }
            leaf segmented-multicast {
              type empty;
              description
                "Enable segmented multicast";
            }
            container label-security {
              description
                "BGP Label Security";
              container asbr {
                description
                  "Label Security for ASBR peers";
                leaf rpf {
                  type empty;
                  description
                    "RPF Label Security for Option-B";
                }
              }
            }
            container mvpn {
              description
                "MVPN commands";
              leaf single-forwarder-selection {
                type enumeration {
                  enum "highest-ip-address" {
                    value 2;
                    description
                      "Select PE with highest ip address";
                  }
                  enum "all" {
                    value 1;
                    description
                      "Select all paths";
                  }
                }
                description
                  "Enable single forwarder selection";
              }
            }
            leaf originator-pe-id {
              type inet:ipv4-address-no-zone;
              description
                "Set and send originator PE ID.";
            }
            leaf option-b-asbr-only {
              type empty;
              description
                "Enable the ASBR router for option-B label exchange.This option makes the router an Option B ASBR for EVPN.Its assumed no DCI configs are present";
            }
            container default-martian-check {
              description
                "Martian check default";
              leaf disable {
                type empty;
                description
                  "Disable";
              }
            }
          }
        }
        container neighbors {
          description
            "Specify a neighbor router";
          list neighbor {
            key "address";
            description
              "Specify a neighbor router";
            leaf address {
              type inet:ip-address-no-zone;
              description
                "IPaddress";
            }
            uses NEIGHBOR-VRF;
          }
          list neighbor-range {
            key "address address-prefix";
            description
              "Specify a neighbor router";
            leaf address {
              type inet:ip-address-no-zone;
              description
                "IPaddress";
            }
            leaf address-prefix {
              type uint32 {
                range "0..128";
              }
              description
                "IP address prefix";
            }
            uses NEIGHBOR-VRF;
          }
        }
      }
    }
  }

  augment "/snmp-server-cfg:snmp-server/snmp-server-cfg:traps" {
    description
      "This augment extends the configuration data of Cisco-IOS-XR-um-snmp-server-cfg";
    uses GROUP-SNMP-SERVER-CFG-SNMP-SERVER-TRAPS-BODY;
  }
  augment "/vrf-cfg:vrfs/vrf-cfg:vrf" {
    description
      "This augment extends the configuration data of Cisco-IOS-XR-um-vrf-cfg";
    uses GROUP-VRF-CFG-RD-BODY;
  }
  augment "/vrf-cfg:vrfs/vrf-cfg:vrf/vrf-cfg:address-family/vrf-cfg:ipv4/vrf-cfg:unicast" {
    description
      "This augment extends the configuration data of Cisco-IOS-XR-um-vrf-cfg";
    uses GROUP-VRF-CFG-IMPORT-BODY;
  }
  augment "/vrf-cfg:vrfs/vrf-cfg:vrf/vrf-cfg:address-family/vrf-cfg:ipv4/vrf-cfg:multicast" {
    description
      "This augment extends the configuration data of Cisco-IOS-XR-um-vrf-cfg";
    uses GROUP-VRF-CFG-IMPORT-BODY;
  }
  augment "/vrf-cfg:vrfs/vrf-cfg:vrf/vrf-cfg:address-family/vrf-cfg:ipv4/vrf-cfg:flowspec" {
    description
      "This augment extends the configuration data of Cisco-IOS-XR-um-vrf-cfg";
    uses GROUP-VRF-CFG-IMPORT-BODY;
  }
  augment "/vrf-cfg:vrfs/vrf-cfg:vrf/vrf-cfg:address-family/vrf-cfg:ipv6/vrf-cfg:unicast" {
    description
      "This augment extends the configuration data of Cisco-IOS-XR-um-vrf-cfg";
    uses GROUP-VRF-CFG-IMPORT-BODY;
  }
  augment "/vrf-cfg:vrfs/vrf-cfg:vrf/vrf-cfg:address-family/vrf-cfg:ipv6/vrf-cfg:multicast" {
    description
      "This augment extends the configuration data of Cisco-IOS-XR-um-vrf-cfg";
    uses GROUP-VRF-CFG-IMPORT-BODY;
  }
  augment "/vrf-cfg:vrfs/vrf-cfg:vrf/vrf-cfg:address-family/vrf-cfg:ipv6/vrf-cfg:flowspec" {
    description
      "This augment extends the configuration data of Cisco-IOS-XR-um-vrf-cfg";
    uses GROUP-VRF-CFG-IMPORT-BODY;
  }
  container router {
    description
      "Enable a routing process";
    container bgp {
      description
        "BGP configuration subcommands";
      container instances {
        description
          "Specify a instance name";
        list instance {
          must "as";
          key "instance-name";
          description
            "Specify a instance name";
          leaf instance-name {
            type xr:Cisco-ios-xr-string {
              length "1..32" {
                description
                  "instance name (maximum length 32 characters)";
              }
            }
            description
              "Specify a instance name";
          }
          list as {
            key "as-number";
            description
              "bgp as-number";
            leaf as-number {
              type xr:Bgp-as-number;
              description
                "bgp as-number";
            }
            uses INSTANCE-AS;
          }
        }
      }
      list as {
        key "as-number";
        description
          "bgp as-number";
        leaf as-number {
          type xr:Bgp-as-number;
          description
            "bgp as-number";
        }
        uses INSTANCE-AS;
      }
    }
  }
  leaf as-format {
    type enumeration {
      enum "asdot" {
        value 2;
        description
          "AS Dot format";
      }
      enum "asplain" {
        value 1;
        description
          "AS Plain format";
      }
    }
    description
      "Autonomous system number format";
  }
  container bmp {
    description
      "BGP Monitoring Protocol commands";
    container servers {
      description
        "BMP server configuration";
      container all {
        presence "Common commands for all BMP servers";
        description
          "Common commands for all BMP servers";
        container route-monitorings {
          description
            "Enable Route Monitoring capability for the BMP servers.nBGP update messages will be regenerated with a table walkn";
          list route-monitoring {
            key "route-mon";
            description
              "Enable Route Monitoring capability for the BMP servers.nBGP update messages will be regenerated with a table walkn";
            leaf route-mon {
              type enumeration {
                enum "inbound-pre-policy" {
                  value 0;
                  description
                    "Monitor inbound route updates before policy application (Adj-RIB-In Pre-Policy)";
                }
                enum "inbound-post-policy" {
                  value 1;
                  description
                    "Monitor inbound route updates before policy application (Adj-RIB-In Pre-Policy)";
                }
                enum "local-rib" {
                  value 4;
                  description
                    "Monitor routes in the local Routing Information Base (Local-RIB)";
                }
              }
              description
                "Enable Route Monitoring capability for the BMP servers.nBGP update messages will be regenerated with a table walkn";
            }
            leaf advertisement-interval {
              type uint32 {
                range "2..600" {
                  description
                    "Time in seconds";
                }
              }
              description
                "Minimum interval between updates sent to BMP servers";
            }
            leaf scan-time {
              type uint32 {
                range "5..3600" {
                  description
                    "Time in seconds";
                }
              }
              description
                "Configure scanner interval";
            }
          }
        }
        container route-mirroring {
          description
            "Enable Route Mirroring capability for the BMP servers.nBGP update messages will be mirrored.";
          container inbound {
            description
              "Mirror inbound route updates (peer router to self)";
            container pre-policy {
              presence "Mirror inbound route updates before policy application";
              description
                "Mirror inbound route updates before policy application";
            }
          }
        }
        leaf max-buffer-size {
          type uint32 {
            range "1..4096" {
              description
                "Range in MegaBytes for the maximum buffer size of BMP message queue.";
            }
          }
          description
            "Maximum buffer limit upto which BMP messages will be queued to TCP sockets.
             If total size of BMP messages queued up for BMP sockets exceeds this set limit,
             messages will be dropped. The maximum buf-size is 20% and default buf-size is 15%
             of the platform virtual memory max-limit (aka rlimit). Please run
             show bgp process performance-statistics
             to see the individual values. Unit is in MegaBytes.";
        }
      }
      list server {
        key "server-number";
        description
          "BMP server configuration";
        leaf server-number {
          type uint32 {
            range "1..8" {
              description
                "BMP server ID to configure";
            }
          }
          description
            "BMP server ID to configure";
        }
        leaf shutdown {
          type empty;
          description
            "Shutdown connection to BMP server";
        }
        container host {
          description
            "Hostname of BMP Server";
          leaf host-name {
            type string {
              length "1..1024" {
                description
                  "Name of the BMP server(accepts IP Address format too)";
              }
            }
            must "../port";
            description
              "Name of the BMP server(accepts IP Address format too)";
          }
          leaf port {
            type uint32 {
              range "1..65535" {
                description
                  "Port Number of listening BMP server";
              }
            }
            must "../host-name";
            description
              "BMP Server Listen Port";
          }
        }
        leaf initial-delay {
          type uint32 {
            range "1..3600" {
              description
                "Initial connect delay in sending BMP server updates";
            }
          }
          description
            "Initial connect delay in sending BMP server updates. Default=0";
        }
        leaf flapping-delay {
          type uint32 {
            range "60..3600" {
              description
                "Range in seconds for the connection delay after flap";
            }
          }
          description
            "delay in connecting to BMP Server after a flap had been detected. Default=300";
        }
        container initial-refresh {
          description
            "Initial refresh to generate BGP updates. Default=1";
          choice INITIAL-REFRESH {
            description
              "Initial refresh to generate BGP updates. Default=1";
            case DELAY {
              leaf delay {
                type uint32 {
                  range "1..3600" {
                    description
                      "Delay in sending Refresh request to Peers (default : 30 secs)";
                  }
                }
                description
                  "Initial delay before sending route refresh request";
              }
              leaf spread {
                type uint32 {
                  range "1..3600" {
                    description
                      "Maximum additional random delay (in secs)";
                  }
                }
                must "../delay";
                description
                  "Maximum additional random delay for initial Refresh Request";
              }
            }
            case SKIP {
              leaf skip {
                type empty;
                description
                  "Skip sending Refresh request to Peers";
              }
            }
          }
        }
        leaf stats-reporting-period {
          type uint32 {
            range "1..3600" {
              description
                "Stats-report-period in seconds";
            }
          }
          description
            "Stats reporting period for BMP server. Default=0";
        }
        leaf description {
          type string {
            length "1..1024" {
              description
                "Up to 250 characters describing this BMP server";
            }
          }
          description
            "BMP server specific description";
        }
        container dscp {
          presence "Set IP DSCP (DiffServ CodePoint)";
          description
            "Set IP DSCP (DiffServ CodePoint)";
          leaf dscp-value {
            type union {
              type uint32 {
                range "0..63" {
                  description
                    "Differentiated services codepoint value";
                }
              }
              type enumeration {
                enum "af11" {
                  value 10;
                  description
                    "Set packets with AF11 dscp (001010)";
                }
                enum "af12" {
                  value 12;
                  description
                    "Set packets with AF12 dscp (001100)";
                }
                enum "af13" {
                  value 14;
                  description
                    "Set packets with AF13 dscp (001110)";
                }
                enum "af21" {
                  value 18;
                  description
                    "Set packets with AF21 dscp (010010)";
                }
                enum "af22" {
                  value 20;
                  description
                    "Set packets with AF22 dscp (010100)";
                }
                enum "af23" {
                  value 22;
                  description
                    "Set packets with AF23 dscp (010110)";
                }
                enum "af31" {
                  value 26;
                  description
                    "Set packets with AF31 dscp (011010)";
                }
                enum "af32" {
                  value 28;
                  description
                    "Set packets with AF32 dscp (011100)";
                }
                enum "af33" {
                  value 30;
                  description
                    "Set packets with AF33 dscp (011110)";
                }
                enum "af41" {
                  value 34;
                  description
                    "Set packets with AF41 dscp (100010)";
                }
                enum "af42" {
                  value 36;
                  description
                    "Set packets with AF42 dscp (100100)";
                }
                enum "af43" {
                  value 38;
                  description
                    "Set packets with AF43 dscp (100110)";
                }
                enum "cs1" {
                  value 8;
                  description
                    "Set packets with CS1(precedence 1) dscp (001000)";
                }
                enum "cs2" {
                  value 16;
                  description
                    "Set packets with CS2(precedence 2) dscp (010000)";
                }
                enum "cs3" {
                  value 24;
                  description
                    "Set packets with CS3(precedence 3) dscp (011000)";
                }
                enum "cs4" {
                  value 32;
                  description
                    "Set packets with CS4(precedence 4) dscp (100000)";
                }
                enum "cs5" {
                  value 40;
                  description
                    "Set packets with CS5(precedence 5) dscp (101000)";
                }
                enum "cs6" {
                  value 48;
                  description
                    "Set packets with CS6(precedence 6) dscp (110000)";
                }
                enum "cs7" {
                  value 56;
                  description
                    "Set packets with CS7(precedence 7) dscp (111000)";
                }
                enum "default" {
                  value 0;
                  description
                    "Set packets with default dscp (000000)";
                }
                enum "ef" {
                  value 46;
                  description
                    "Set packets with EF dscp (101110)";
                }
              }
            }
            mandatory true;
            description
              "Set IP DSCP (DiffServ CodePoint)";
          }
        }
        container precedence {
          presence "Set precedence";
          description
            "Set precedence";
          leaf precedence-value {
            type union {
              type uint32 {
                range "0..7" {
                  description
                    "Precedence value";
                }
              }
              type enumeration {
                enum "critical" {
                  value 5;
                  description
                    "Set packets with critical precedence (5)";
                }
                enum "flash" {
                  value 3;
                  description
                    "Set packets with flash precedence (3)";
                }
                enum "flash-override" {
                  value 4;
                  description
                    "Set packets with flash override precedence (4)";
                }
                enum "immediate" {
                  value 2;
                  description
                    "Set packets with immediate precedence (2)";
                }
                enum "internet" {
                  value 6;
                  description
                    "Set packets with internetwork control precedence (6)";
                }
                enum "network" {
                  value 7;
                  description
                    "Set packets with network control precedence (7)";
                }
                enum "priority" {
                  value 1;
                  description
                    "Set packets with priority precedence (1)";
                }
                enum "routine" {
                  value 0;
                  description
                    "Set packets with routine precedence (0)";
                }
              }
            }
            mandatory true;
            description
              "Set precedence";
          }
        }
        leaf update-source {
          type xr:Interface-name;
          description
            "Source to reach BMP server";
        }
        leaf vrf {
          type string {
            length "1..1024" {
              description
                "VRF Name";
            }
          }
          description
            "VRF for the BMP server";
        }
        container tcp {
          description
            "Configure TCP related parameters";
          leaf mss {
            type uint32 {
              range "68..10000" {
                description
                  "TCP segment size in bytes";
              }
            }
            description
              "configure TCP maximum segment size";
          }
          leaf keep-alive {
            type uint32 {
              range "0..7200" {
                description
                  "Keep Alive interval in seconds";
              }
            }
            description
              "configure TCP keep alives to be exchanged between client and server";
          }
        }
      }
    }
  }
}
