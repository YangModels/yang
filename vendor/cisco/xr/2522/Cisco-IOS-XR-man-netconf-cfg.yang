module Cisco-IOS-XR-man-netconf-cfg {
  namespace "http://cisco.com/ns/yang/Cisco-IOS-XR-man-netconf-cfg";
  prefix man-netconf-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR man-netconf package configuration.
     
     This model is deprecated and is replaced by
     Cisco-IOS-XR-um-netconf-yang-cfg.yang which will provide the
     compatible functionalities.
     
     This module contains definitions
     for the following management objects:
       netconf-yang: NETCONF YANG configuration commands
     
     Copyright (c) 2013-2023 by Cisco Systems, Inc.
     All rights reserved.";

  revision 2023-10-03 {
    description
      "Added new container/leaf to enable NETCONF 1.0 support
       2021-11-22
         Added submod-enter at netconf-yang agent level";
    semver:module-version "1.2.0";
  }
  revision 2019-12-12 {
    description
      "Added new container defaults to enable with-defaults support.";
    semver:module-version "1.1.0";
  }
  revision 2019-05-12 {
    description
      "Deprecated the native model, replaced by UM model.";
    semver:module-version "1.0.1";
  }
  revision 2019-04-05 {
    description
      "Establish semantic version baseline.";
  }
  revision 2018-05-04 {
    description
      "Provison to disable openconfig.";
  }
  revision 2016-03-15 {
    description
      "Descriptions updated.";
  }
  revision 2015-01-07 {
    description
      "IOS XR 5.3.1 revision.";
  }

  typedef Ncy10-support {
    type enumeration {
      enum "enabled" {
        value 1;
        description
          "Enable Netconf 1.0";
      }
      enum "1.0-only" {
        value 2;
        description
          "Enable Netconf 1.0 and disable 1.1";
      }
    }
    description
      "Ncy10 support";
  }

  container netconf-yang {
    status deprecated;
    description
      "This model is deprecated and is replaced by
       Cisco-IOS-XR-um-netconf-yang-cfg.yang which will
       provide the compatible functionalities.  NETCONF
       YANG configuration commands";
    container agent {
      presence "CLI submode compatibility.";
      description
        "NETCONF YANG agent configuration commands";
      container models {
        description
          "Models to be disabled";
        container openconfig {
          description
            "Type of models: openconfig";
          leaf disabled {
            type empty;
            description
              "Disable the specified model type";
          }
        }
      }
      container defaults {
        description
          "Support netconf with-defaults";
        leaf enable {
          type empty;
          description
            "Enable netconf with-defaults support";
        }
      }
      container ssh {
        description
          "NETCONF YANG agent over SSH connection";
        leaf enable {
          type empty;
          description
            "Enable NETCONF YANG agent over SSH connection";
        }
      }
      container session {
        description
          "Session settings";
        leaf limit {
          type uint32 {
            range "1..128";
          }
          default "50";
          description
            "Count of allowable concurrent netconf-yang
             sessions";
        }
        leaf absolute-timeout {
          type uint32 {
            range "1..1440";
          }
          units "minute";
          description
            "Absolute timeout in minutes";
        }
        leaf idle-timeout {
          type uint32 {
            range "1..1440";
          }
          units "minute";
          description
            "Non-active session lifetime";
        }
      }
      container netconf1.0 {
        presence "Indicates a netconf1.0 node is configured.";
        description
          "NETCONF protocol version 1.0 (RFC4741&4742)";
        leaf support {
          type Ncy10-support;
          mandatory true;
          description
            "Enable NETCONF1.0 support";
        }
        leaf streaming-disabled {
          type empty;
          description
            "Disable rpc-reply data streaming";
        }
      }
      leaf rate-limit {
        type uint32 {
          range "4096..4294967295";
        }
        units "byte";
        description
          "Number of bytes to process per sec";
      }
    }
  }
}
