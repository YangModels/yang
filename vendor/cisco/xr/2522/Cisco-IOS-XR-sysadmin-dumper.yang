module Cisco-IOS-XR-sysadmin-dumper {
  namespace "http://www.cisco.com/ns/yang/Cisco-IOS-XR-sysadmin-dumper";
  prefix dumper;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin dumper to
     configure file path options to copy the core files to.
     
     Copyright (c) 2015-2020 by Cisco Systems, Inc.
     All rights reserved.";

  revision 2024-12-29 {
    description
      "Adding the new disk-usage-limit keyword";
    semver:module-version "1.1.0";
  }
  revision 2019-04-15 {
    description
      "Establish semantic version baseline.";
    semver:module-version "1.0.0";
  }
  revision 2017-05-09 {
    description
      "Modified module name, namespace and filename
         to adhere to standard notation";
  }
  revision 2016-05-12 {
    description
      "Initial Version";
  }

  container exception {
    description
      "Core dump configuration commands";
    list choice {
      key "order";
      description
        "Preference of the dump location";
      leaf order {
        type int32 {
          range "1 .. 3";
        }
        description
          "The preference order number";
      }
      leaf filepath {
        type string;
        mandatory true;
        description
          "File path to copy the core";
      }
    }
    leaf disk-usage-limit {
      type int32 {
        range "20 .. 50";
      }
      description
        "The disk usage limit for core dumps in /misc/disk1/coredumps";
    }
  }
}
