module Cisco-IOS-XR-um-fpd-cfg {
  namespace "http://cisco.com/ns/yang/Cisco-IOS-XR-um-fpd-cfg";
  prefix um-fpd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fpd package configuration.
     
     This YANG module augments the
     modules with configuration data.
     
     Copyright (c) 2020-2022 by Cisco Systems, Inc.
     All rights reserved.";

  revision 2020-12-22 {
    description
      "Initial release";
    semver:module-version "1.0.0";
  }

  container fpd {
    description
      "FPD firmware configuration";
    container auto-upgrade {
      description
        "FPD auto-upgrade configuration";
      container enable {
        must "not(../disable)";
        presence "Indicates a enable node is configured.";
        description
          "Enable fpd auto upgrade";
      }
      container disable {
        must "not(../enable)";
        presence "Indicates a disable node is configured.";
        description
          "Disable fpd auto upgrade";
      }
    }
    container auto-reload {
      description
        "Auto-reload node(Linecard) after FPD auto-upgrade";
      container enable {
        must "not(../disable)";
        presence "Indicates a enable node is configured.";
        description
          "Enable fpd auto reload`";
      }
      container disable {
        must "not(../enable)";
        presence "Indicates a disable node is configured.";
        description
          "Disable fpd auto reload`";
      }
    }
  }
}
