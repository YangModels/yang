//*************  DO-NOT EDIT  **************
//*********** Auto-generated file ********** 

 module cisco-xr-openconfig-lacp-deviations {

  namespace "http://cisco.com/ns/yang/cisco-xr-openconfig-lacp-deviations";
  prefix  "oc-lacpdevs";

  import openconfig-lacp { prefix oc-lacp; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-lacp.yang@2021-07-20 

     on Cisco IOS-XR devices.

     Copyright (c) 2017 by Cisco Systems, Inc.
     All rights reserved.";

  revision "2023-03-27" {
    description
      "Initial revision applicable to IOS-XR 6.4.1";
  }

  // "/oc-lacp:lacp/oc-lacp:interfaces/oc-lacp:interface/oc-lacp:state/oc-lacp:interval"
  // Do not add a deviation! Now supported by the "Operational Config" feature.
  // See https://confluence-eng-sjc1.cisco.com/conf/display/CC/YinY+Operational+Config

  deviation /oc-lacp:lacp/oc-lacp:interfaces/oc-lacp:interface/oc-lacp:members/oc-lacp:member/oc-lacp:state/oc-lacp:counters/oc-lacp:lacp-tx-errors {
    deviate not-supported;
  }


}
//total deviations:1
