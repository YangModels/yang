module Cisco-IOS-XR-crypto-svault-oper {
  namespace "http://cisco.com/ns/yang/Cisco-IOS-XR-crypto-svault-oper";
  prefix crypto-svault-oper;

  import Cisco-IOS-XR-types {
    prefix xr;
  }
  import cisco-semver {
    prefix semver;
  }
  include Cisco-IOS-XR-crypto-svault-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-svault package operational data.
     
     This module contains definitions
     for the following management objects:
       svault: Secure Vault operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container svault {
    config false;
    description
      "Secure Vault operational data";
    container nodes {
      description
        "Node-specific Secure Vault operational data";
      list node {
        key "node";
        description
          "Secure Vault operational data for a particular
           node";
        container status {
          description
            "Status of Secure Vault server";
          uses SVAULT-EDM-STATUS-RESULT;
        }
        leaf node {
          type xr:Node-id;
          description
            "The node identifier";
        }
      }
    }
  }
}
