module Cisco-IOS-XR-openconfig-qos-ext {
  yang-version 1;
  namespace "http://cisco.com/ns/yang/Cisco-IOS-XR-openconfig-qos-ext";
  prefix oc-qos-cisco-xr-ext;

  import openconfig-qos {
    prefix oc-qos;
  }
  import openconfig-extensions {
    prefix oc-ext;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module augments the openconfig-qos model to support setting
     PBTS forward-class as a classifier action.
     
     Copyright (c) 2023 by Cisco Systems, Inc.
     All rights reserved.";

  revision 2023-06-06 {
    description
      "Support for forward-class augmentation";
    reference "1.0.0";
    semver:module-version "1.0.0";
  }

  grouping qos-ext-config {
    description
      "Configuration data for global QoS";
    leaf hash-seed {
      type uint32;
      description
        "Internal hash seed value to be used when mapping to IOS-XR QoS
         configuration names. Setting this value may be used to resolve hash
         collision errors for policy-map and/or class-map names.";
    }
  }

  grouping qos-ext-classifier-term-action-config {
    description
      "Configuration parameters for actions for a classifier term.";
    leaf set-forward-class {
      type uint8;
      description
        "Set the PBTS (Policy-Based Tunnel Selection) forward-class for
         the packet. The platform-dependent range of values accepted is
         typically 1..7, with a default value of 0 used for the
         forward-class when no value is explicitly configured.
         
         For more details see documentation for the IOS-XR policy-map
         set forward-class action.";
    }
  }

  augment "/oc-qos:qos/oc-qos:config" {
    description
      "Configuration data for global QoS";
    uses qos-ext-config;
  }
  augment "/oc-qos:qos/oc-qos:state" {
    description
      "Operational state data for global QoS";
    uses qos-ext-config;
  }
  augment "/oc-qos:qos/oc-qos:classifiers/oc-qos:classifier/oc-qos:terms/oc-qos:term/oc-qos:actions/oc-qos:config" {
    description
      "Actions to be applied to packets that match the classifier term.";
    uses qos-ext-classifier-term-action-config;
  }
  augment "/oc-qos:qos/oc-qos:classifiers/oc-qos:classifier/oc-qos:terms/oc-qos:term/oc-qos:actions/oc-qos:state" {
    description
      "Operational state parameters associated with classifier term actions";
    uses qos-ext-classifier-term-action-config;
  }
  oc-ext:openconfig-version "0.8.0";
}
