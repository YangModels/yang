submodule Cisco-IOS-XR-subscriber-pppoe-ma-oper-sub1 {
  belongs-to Cisco-IOS-XR-subscriber-pppoe-ma-oper {
    prefix Cisco-IOS-XR-subscriber-pppoe-ma-oper;
  }

  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-pppoe-ma package operational data.
     
     Copyright (c) 2013-2018 by Cisco Systems, Inc.
     All rights reserved.";

  revision 2015-11-09 {
    description
      "IOS XR 6.0 revision.";
  }

  typedef Pppoe-ma-throttle-state {
    type enumeration {
      enum "idle" {
        value 0;
        description
          "Idle State";
      }
      enum "monitor" {
        value 1;
        description
          "Monitor State";
      }
      enum "block" {
        value 2;
        description
          "Block State";
      }
    }
    description
      "Pppoe ma throttle state";
  }

  typedef Pppoe-ma-limit-state {
    type enumeration {
      enum "ok" {
        value 0;
        description
          "OK State";
      }
      enum "warning" {
        value 1;
        description
          "Warn State";
      }
      enum "block" {
        value 2;
        description
          "Block State";
      }
    }
    description
      "Pppoe ma limit state";
  }

  typedef Pppoe-ma-bag-optional-string {
    type string;
    description
      "String which may be optionally present.";
  }

  typedef Im-state {
    type uint32;
    description
      "Im state";
  }

  typedef Pppoe-ma-session-trig {
    type enumeration {
      enum "pppoe-ma-session-trig-error" {
        value 0;
        description
          "pppoe ma session trig error";
      }
      enum "pppoe-ma-session-trig-publish-encaps-attr-fail" {
        value 1;
        description
          "pppoe ma session trig publish encaps attr fail";
      }
      enum "pppoe-ma-session-trig-if-create-fail" {
        value 2;
        description
          "pppoe ma session trig if create fail";
      }
      enum "pppoe-ma-session-trig-iedge-session-start-fail" {
        value 3;
        description
          "pppoe ma session trig iedge session start fail";
      }
      enum "pppoe-ma-session-trig-iedge-session-update-fail" {
        value 4;
        description
          "pppoe ma session trig iedge session update fail";
      }
      enum "pppoe-ma-session-trig-sub-db-activate-fail" {
        value 5;
        description
          "pppoe ma session trig sub db activate fail";
      }
      enum "pppoe-ma-session-trig-in-flight-timeout" {
        value 6;
        description
          "pppoe ma session trig in flight timeout";
      }
      enum "pppoe-ma-session-trig-down" {
        value 7;
        description
          "pppoe ma session trig down";
      }
      enum "pppoe-ma-session-trig-parent" {
        value 8;
        description
          "pppoe ma session trig parent";
      }
      enum "pppoe-ma-session-trig-padt" {
        value 9;
        description
          "pppoe ma session trig padt";
      }
      enum "pppoe-ma-session-trig-session-pak" {
        value 10;
        description
          "pppoe ma session trig session pak";
      }
      enum "pppoe-ma-session-trig-final" {
        value 11;
        description
          "pppoe ma session trig final";
      }
      enum "pppoe-ma-session-trig-no-im-or" {
        value 12;
        description
          "pppoe ma session trig no im or";
      }
      enum "pppoe-ma-session-trig-restart" {
        value 13;
        description
          "pppoe ma session trig restart";
      }
      enum "pppoe-ma-session-trig-admissions-config-change" {
        value 14;
        description
          "pppoe ma session trig admissions config change";
      }
      enum "pppoe-ma-session-trig-iedge-disconnect" {
        value 15;
        description
          "pppoe ma session trig iedge disconnect";
      }
      enum "pppoe-ma-session-trig-invalid-vlan-tags" {
        value 16;
        description
          "pppoe ma session trig invalid vlan tags";
      }
      enum "pppoe-ma-session-trig-port-limit-disconnect" {
        value 17;
        description
          "pppoe ma session trig port limit disconnect";
      }
      enum "pppoe-ma-session-trig-srg-disconnect" {
        value 18;
        description
          "pppoe ma session trig srg disconnect";
      }
      enum "pppoe-ma-session-trig-srg-sweep" {
        value 19;
        description
          "pppoe ma session trig srg sweep";
      }
      enum "pppoe-ma-session-trig-count" {
        value 20;
        description
          "pppoe ma session trig count";
      }
    }
    description
      "Pppoe ma session trig";
  }

  typedef Pppoe-ma-session-idb-srg-state {
    type enumeration {
      enum "none" {
        value 0;
        description
          "SRG-None state";
      }
      enum "active" {
        value 1;
        description
          "SRG-Active state";
      }
      enum "standby" {
        value 2;
        description
          "SRG-Standby state";
      }
    }
    description
      "Pppoe ma session idb srg state";
  }

  typedef Pppoe-ma-session-state {
    type enumeration {
      enum "destroying" {
        value 0;
        description
          "Destroying session";
      }
      enum "deleting" {
        value 1;
        description
          "Deleting interface";
      }
      enum "initializing" {
        value 2;
        description
          "Initializing";
      }
      enum "created" {
        value 3;
        description
          "Interface created";
      }
      enum "stopping" {
        value 4;
        description
          "Stopping AAA session";
      }
      enum "started" {
        value 5;
        description
          "AAA session started";
      }
      enum "activated" {
        value 6;
        description
          "SubDB Config activated";
      }
      enum "complete" {
        value 7;
        description
          "Complete";
      }
    }
    description
      "Pppoe ma session state";
  }

  grouping PPPOE-MA-SUMMARY-TOTAL-INFO {
    description
      "PPPoE MA Summary Total information";
    leaf ready-access-interfaces {
      type uint32;
      description
        "Ready Access Interface Count";
    }
    leaf not-ready-access-interfaces {
      type uint32;
      description
        "Not Ready Access Interface Count";
    }
    leaf complete-sessions {
      type uint32;
      description
        "Complete Session Count";
    }
    leaf incomplete-sessions {
      type uint32;
      description
        "Incomplete Session Count";
    }
    leaf flow-control-limit {
      type uint32;
      description
        "Flow Control credit limit";
    }
    leaf flow-control-in-flight-sessions {
      type uint32;
      description
        "Flow Control In-Flight Count";
    }
    leaf flow-control-dropped-sessions {
      type uint64;
      description
        "Flow Control Drop Count";
    }
    leaf flow-control-disconnected-sessions {
      type uint64;
      description
        "Flow Control Disconnected Count";
    }
    leaf flow-control-successful-sessions {
      type uint64;
      description
        "Flow Control Success Count, sessions completing
         call flow";
    }
    leaf pppoema-subscriber-infra-flow-control {
      type uint32;
      description
        "PPPoEMASubscriberInfraFlowControl";
    }
  }

  grouping PPPOE-MA-THROTTLE-CONFIG-SINGLE {
    description
      "PPPoE MA Single Throttle Config Information";
    leaf limit {
      type uint32;
      description
        "Limit";
    }
    leaf request-period {
      type uint32;
      description
        "Request Period";
    }
    leaf blocking-period {
      type uint32;
      description
        "Blocking Period";
    }
  }

  grouping PPPOE-MA-THROTTLE-CONFIG-INFO {
    description
      "PPPoE MA Throttle Config Information";
    container mac {
      description
        "MAC";
      uses PPPOE-MA-THROTTLE-CONFIG-SINGLE;
    }
    container mac-access-interface {
      description
        "MAC Access Interface";
      uses PPPOE-MA-THROTTLE-CONFIG-SINGLE;
    }
    container mac-iwf-access-interface {
      description
        "MAC IWF Access Interface";
      uses PPPOE-MA-THROTTLE-CONFIG-SINGLE;
    }
    container circuit-id {
      description
        "Circuit ID";
      uses PPPOE-MA-THROTTLE-CONFIG-SINGLE;
    }
    container remote-id {
      description
        "Remote ID";
      uses PPPOE-MA-THROTTLE-CONFIG-SINGLE;
    }
    container circuit-id-and-remote-id {
      description
        "Circuit ID and Remote ID";
      uses PPPOE-MA-THROTTLE-CONFIG-SINGLE;
    }
    container outer-vlan-id {
      description
        "Outer VLAN ID";
      uses PPPOE-MA-THROTTLE-CONFIG-SINGLE;
    }
    container inner-vlan-id {
      description
        "Inner VLAN ID";
      uses PPPOE-MA-THROTTLE-CONFIG-SINGLE;
    }
    container vlan-id {
      description
        "VLAN ID";
      uses PPPOE-MA-THROTTLE-CONFIG-SINGLE;
    }
  }

  grouping PPPOE-MA-THROTTLE-INFO {
    description
      "PPPoE MA Throttle information";
    leaf state {
      type Pppoe-ma-throttle-state;
      description
        "State";
    }
    leaf time-left {
      type uint32;
      units "second";
      description
        "Time left in seconds";
    }
    leaf since-reset {
      type uint32;
      units "second";
      description
        "Number of seconds since counters reset";
    }
    leaf padi-count {
      type uint32;
      description
        "PADI Count";
    }
    leaf padr-count {
      type uint32;
      description
        "PADR Count";
    }
  }

  grouping PPPOE-MA-LIMIT-INFO {
    description
      "PPPoE MA Limit information";
    leaf state {
      type Pppoe-ma-limit-state;
      description
        "State";
    }
    leaf session-count {
      type uint32;
      description
        "Session Count";
    }
    leaf radius-override-set {
      type int32;
      description
        "Overridden limit has been set";
    }
    leaf override-limit {
      type uint32;
      description
        "Overridden limit if set";
    }
  }

  grouping PPPOE-MA-LIMIT-CONFIG-SINGLE {
    description
      "PPPoE MA Single Limit Config information";
    leaf max-limit {
      type uint32;
      description
        "Max Limit";
    }
    leaf threshold {
      type uint32;
      description
        "Threshold";
    }
    leaf radius-override-enabled {
      type int32;
      description
        "Radius override is enabled";
    }
  }

  grouping PPPOE-MA-LIMIT-CONFIG-INFO {
    description
      "PPPoE MA Limit Configuration Information";
    container card {
      description
        "Card";
      uses PPPOE-MA-LIMIT-CONFIG-SINGLE;
    }
    container access-intf {
      description
        "Access Interface";
      uses PPPOE-MA-LIMIT-CONFIG-SINGLE;
    }
    container mac {
      description
        "MAC";
      uses PPPOE-MA-LIMIT-CONFIG-SINGLE;
    }
    container mac-iwf {
      description
        "MAC IWF";
      uses PPPOE-MA-LIMIT-CONFIG-SINGLE;
    }
    container mac-access-interface {
      description
        "MAC Access Interface";
      uses PPPOE-MA-LIMIT-CONFIG-SINGLE;
    }
    container mac-iwf-access-interface {
      description
        "MAC IWF Access Interface";
      uses PPPOE-MA-LIMIT-CONFIG-SINGLE;
    }
    container circuit-id {
      description
        "Circuit ID";
      uses PPPOE-MA-LIMIT-CONFIG-SINGLE;
    }
    container remote-id {
      description
        "Remote ID";
      uses PPPOE-MA-LIMIT-CONFIG-SINGLE;
    }
    container circuit-id-and-remote-id {
      description
        "Circuit ID and Remote ID";
      uses PPPOE-MA-LIMIT-CONFIG-SINGLE;
    }
    container outer-vlan-id {
      description
        "Outer VLAN ID";
      uses PPPOE-MA-LIMIT-CONFIG-SINGLE;
    }
    container inner-vlan-id {
      description
        "Inner VLAN ID";
      uses PPPOE-MA-LIMIT-CONFIG-SINGLE;
    }
    container vlan-id {
      description
        "VLAN ID";
      uses PPPOE-MA-LIMIT-CONFIG-SINGLE;
    }
  }

  grouping PPPOE-MA-TAGS-INFO {
    description
      "Tags information";
    container access-loop-encapsulation {
      description
        "Access Loop Encapsulation";
      uses PPPOE-MA-TAGS-ALE-INFO;
    }
    leaf service-name {
      type Pppoe-ma-bag-optional-string;
      description
        "Service Name";
    }
    leaf max-payload {
      type uint16;
      description
        "Max Payload";
    }
    leaf host-uniq {
      type yang:hex-string;
      description
        "Host Uniq";
    }
    leaf relay-session-id {
      type yang:hex-string;
      description
        "Relay Session ID";
    }
    leaf remote-id {
      type Pppoe-ma-bag-optional-string;
      description
        "Remote ID";
    }
    leaf circuit-id {
      type Pppoe-ma-bag-optional-string;
      description
        "Circuit ID";
    }
    leaf is-iwf {
      type int32;
      description
        "Is IWF";
    }
    leaf dsl-actual-up {
      type uint32;
      description
        "DSL Actual Up";
    }
    leaf dsl-actual-down {
      type uint32;
      description
        "DSL Actual Down";
    }
    leaf dsl-min-up {
      type uint32;
      description
        "DSL Min Up";
    }
    leaf dsl-min-down {
      type uint32;
      description
        "DSL Min Down";
    }
    leaf dsl-attain-up {
      type uint32;
      description
        "DSL Attain Up";
    }
    leaf dsl-attain-down {
      type uint32;
      description
        "DSL Attain Down";
    }
    leaf dsl-max-up {
      type uint32;
      description
        "DSL Max Up";
    }
    leaf dsl-max-down {
      type uint32;
      description
        "DSL Max Down";
    }
    leaf dsl-min-up-low {
      type uint32;
      description
        "DSL Min Up Low";
    }
    leaf dsl-min-down-low {
      type uint32;
      description
        "DSL Min Down Low";
    }
    leaf dsl-max-delay-up {
      type uint32;
      description
        "DSL Max Delay Up";
    }
    leaf dsl-actual-delay-up {
      type uint32;
      description
        "DSL Actual Delay Up";
    }
    leaf dsl-max-delay-down {
      type uint32;
      description
        "DSL Max Delay Down";
    }
    leaf dsl-actual-delay-down {
      type uint32;
      description
        "DSL Actual Delay Down";
    }
  }

  grouping PPPOE-MA-INTERFACE-INFO {
    description
      "PPPoE MA interface information";
    container tags {
      description
        "Tags";
      uses PPPOE-MA-TAGS-INFO;
    }
    leaf interface-name-xr {
      type xr:Interface-name;
      description
        "Interface";
    }
    leaf access-interface-name {
      type xr:Interface-name;
      description
        "Access Interface";
    }
    leaf bba-group-name {
      type string;
      description
        "BBA Group";
    }
    leaf session-id {
      type uint16;
      description
        "Session ID";
    }
    leaf local-mac-address {
      type yang:mac-address;
      description
        "Local Mac-Address";
    }
    leaf peer-mac-address {
      type yang:mac-address;
      description
        "Peer Mac-Address";
    }
    leaf is-complete {
      type int32;
      description
        "Is Complete";
    }
    leaf vlan-outer-id {
      type uint16;
      description
        "VLAN Outer ID";
    }
    leaf vlan-inner-id {
      type uint16;
      description
        "VLAN Inner ID";
    }
    leaf srg-state {
      type Pppoe-ma-session-idb-srg-state;
      description
        "SRG state";
    }
  }

  grouping PPPOE-MA-ACCESS-INTERFACE-INFO {
    description
      "PPPoE MA Access interface information";
    leaf interface-name-xr {
      type xr:Interface-name;
      description
        "Interface";
    }
    leaf interface-state {
      type Im-state;
      description
        "Interface State";
    }
    leaf mac-address {
      type yang:mac-address;
      description
        "Mac Address";
    }
    leaf bba-group-name {
      type string;
      description
        "BBA Group";
    }
    leaf is-ready {
      type int32;
      description
        "Is Ready";
    }
    leaf sessions {
      type uint32;
      description
        "Session Count";
    }
    leaf incomplete-sessions {
      type uint32;
      description
        "Incomplete Session Count";
    }
  }

  grouping PPPOE-MA-PACKET-ERROR-COUNTS {
    description
      "PPPoE MA Packet Error Counts";
    leaf no-interface-handle {
      type uint32;
      description
        "No interface handle";
    }
    leaf no-packet-payload {
      type uint32;
      description
        "No packet payload";
    }
    leaf no-packet-mac-address {
      type uint32;
      description
        "No packet mac-address";
    }
    leaf invalid-version-type-value {
      type uint32;
      description
        "Invalid version-type value";
    }
    leaf bad-packet-length {
      type uint32;
      description
        "Bad packet length";
    }
    leaf unknown-interface {
      type uint32;
      description
        "Unknown interface";
    }
    leaf pado-received {
      type uint32;
      description
        "PADO received";
    }
    leaf pads-received {
      type uint32;
      description
        "PADS received";
    }
    leaf unknown-packet-type-received {
      type uint32;
      description
        "Unknown packet type received";
    }
    leaf unexpected-session-id-in-packet {
      type uint32;
      description
        "Unexpected Session-ID in packet";
    }
    leaf no-service-name-tag {
      type uint32;
      description
        "No Service-Name Tag";
    }
    leaf padt-for-unknown-session {
      type uint32;
      description
        "PADT for unknown session";
    }
    leaf padt-with-wrong-peer-mac {
      type uint32;
      description
        "PADT with wrong peer-mac";
    }
    leaf padt-with-wrong-vlan-tags {
      type uint32;
      description
        "PADT with wrong VLAN tags";
    }
    leaf zero-length-host-uniq {
      type uint32;
      description
        "Zero-length Host-Uniq tag";
    }
    leaf padt-before-pads-sent {
      type uint32;
      description
        "PADT before PADS sent";
    }
    leaf session-stage-packet-for-unknown-session {
      type uint32;
      description
        "Session-stage packet for unknown session";
    }
    leaf session-stage-packet-with-wrong-mac {
      type uint32;
      description
        "Session-stage packet with wrong mac";
    }
    leaf session-stage-packet-with-wrong-vlan-tags {
      type uint32;
      description
        "Session-stage packet with wrong VLAN tags";
    }
    leaf session-stage-packet-with-no-error {
      type uint32;
      description
        "Session-stage packet with no error";
    }
    leaf tag-too-short {
      type uint32;
      description
        "Tag too short";
    }
    leaf bad-tag-length-field {
      type uint32;
      description
        "Bad tag-length field";
    }
    leaf multiple-service-name-tags {
      type uint32;
      description
        "Multiple Service-Name tags";
    }
    leaf multiple-max-payload-tags {
      type uint32;
      description
        "Multiple Max-Payload tags";
    }
    leaf invalid-max-payload-tag {
      type uint32;
      description
        "Invalid Max-Payload tag";
    }
    leaf multiple-vendor-specific-tags {
      type uint32;
      description
        "Multiple Vendor-specific tags";
    }
    leaf unexpected-ac-name-tag {
      type uint32;
      description
        "Unexpected AC-Name tag";
    }
    leaf unexpected-error-tags {
      type uint32;
      description
        "Unexpected error tags";
    }
    leaf unknown-tag-received {
      type uint32;
      description
        "Unknown tag received";
    }
    leaf no-iana-code-invendor-tag {
      type uint32;
      description
        "No IANA code in vendor tag";
    }
    leaf invalid-iana-code-invendor-tag {
      type uint32;
      description
        "Invalid IANA code in vendor tag";
    }
    leaf vendor-tag-too-short {
      type uint32;
      description
        "Vendor tag too short";
    }
    leaf bad-vendor-tag-length-field {
      type uint32;
      description
        "Bad vendor tag length field";
    }
    leaf multiple-host-uniq-tags {
      type uint32;
      description
        "Multiple Host-Uniq tags";
    }
    leaf multiple-relay-session-id-tags {
      type uint32;
      description
        "Multiple relay-session-id tags";
    }
    leaf multiple-circuit-id-tags {
      type uint32;
      description
        "Multiple Circuit-ID tags";
    }
    leaf multiple-remote-id-tags {
      type uint32;
      description
        "Multiple Remote-ID tags";
    }
    leaf invalid-dsl-tag {
      type uint32;
      description
        "Invalid DSL tag";
    }
    leaf multiple-of-the-same-dsl-tag {
      type uint32;
      description
        "Multiple of the same DSL tag";
    }
    leaf invalid-iwf-tag {
      type uint32;
      description
        "Invalid IWF tag";
    }
    leaf multiple-iwf-tags {
      type uint32;
      description
        "Multiple IWF tags";
    }
    leaf unknownvendor-tag {
      type uint32;
      description
        "Unknown vendor-tag";
    }
    leaf no-space-left-in-packet {
      type uint32;
      description
        "No space left in packet";
    }
    leaf duplicate-host-uniq-tag-received {
      type uint32;
      description
        "Duplicate Host-Uniq tag received";
    }
    leaf duplicate-relay-session-id-tag-received {
      type uint32;
      description
        "Duplicate Relay Session ID tag received";
    }
    leaf packet-too-long {
      type uint32;
      description
        "Packet too long";
    }
    leaf invalid-ale-tag {
      type uint32;
      description
        "Invalid ALE tag";
    }
    leaf multiple-ale-tags {
      type uint32;
      description
        "Multiple ALE tags";
    }
    leaf invalid-service-name {
      type uint32;
      description
        "Invalid Service Name";
    }
    leaf invalid-peer-mac {
      type uint32;
      description
        "Invalid Peer MAC";
    }
    leaf invalid-vlan-tags {
      type uint32;
      description
        "Invalid VLAN Tags";
    }
    leaf packet-on-srg-slave {
      type uint32;
      description
        "Packet Received on SRG Slave";
    }
  }

  grouping PPPOE-MA-TOTAL-STATS-INFO {
    description
      "PPPoE MA Total Statistics Information";
    container packet-counts {
      description
        "Packet Counts";
      uses PPPOE-MA-PACKET-COUNTS;
    }
    container packet-error-counts {
      description
        "Packet Error Counts";
      uses PPPOE-MA-PACKET-ERROR-COUNTS;
    }
  }

  grouping PPPOE-MA-DISC-HISTORY-UNIQUE {
    description
      "Wrapping history of disconnected subscribers";
    leaf-list disconnect-count {
      type uint32;
      max-elements "20";
      description
        "The total number of disconnects";
    }
    list entry {
      max-elements "20";
      description
        "Array of disconnected subscribers";
      uses PPPOE-MA-DISC-ENTRY;
    }
  }

  grouping PPPOE-MA-VLAN-TAG-TYPE {
    description
      "VLAN Tag Information";
    leaf ether-type {
      type uint16;
      description
        "Ethertype. See IEEE 802.1Q for more information.";
    }
    leaf user-priority {
      type uint8;
      description
        "User Priority";
    }
    leaf cfi {
      type uint8;
      description
        "CFI";
    }
    leaf vlan-id {
      type uint16;
      description
        "VLAN ID";
    }
  }

  grouping PPPOE-MA-TAGS-ALE-INFO {
    description
      "Access-Loop-Encapsulation tag. See RFC-4679 for
       more detail";
    leaf data-link {
      type uint8;
      description
        "Data Link";
    }
    leaf encaps1 {
      type uint8;
      description
        "Encaps 1";
    }
    leaf encaps2 {
      type uint8;
      description
        "Encaps 2";
    }
  }

  grouping PPPOE-MA-INTERNAL-TAGS-INFO {
    description
      "Tags information";
    container access-loop-encapsulation {
      description
        "Access Loop Encapsulation";
      uses PPPOE-MA-TAGS-ALE-INFO;
    }
    leaf is-service-name {
      type int32;
      description
        "Is Service Name";
    }
    leaf is-max-payload {
      type int32;
      description
        "Is Max Payload";
    }
    leaf is-host-uniq {
      type int32;
      description
        "Is Host Uniq";
    }
    leaf is-relay-session-id {
      type int32;
      description
        "Is Relay Session ID";
    }
    leaf is-vendor-specific {
      type int32;
      description
        "Is Vendor Specific";
    }
    leaf is-iwf {
      type int32;
      description
        "Is IWF";
    }
    leaf is-remote-id {
      type int32;
      description
        "Is Remote ID";
    }
    leaf is-circuit-id {
      type int32;
      description
        "Is Circuit ID";
    }
    leaf is-dsl-tag {
      type int32;
      description
        "Is DSL Tag";
    }
    leaf service-name {
      type string;
      description
        "Service Name";
    }
    leaf max-payload {
      type uint32;
      description
        "Max Payload";
    }
    leaf host-uniq {
      type yang:hex-string;
      description
        "Host Uniq";
    }
    leaf relay-session-id {
      type yang:hex-string;
      description
        "Relay Session ID";
    }
    leaf remote-id {
      type string;
      description
        "Remote ID";
    }
    leaf circuit-id {
      type string;
      description
        "Circuit ID";
    }
    leaf is-dsl-actual-up {
      type int32;
      description
        "Is DSL Actual Up";
    }
    leaf is-dsl-actual-down {
      type int32;
      description
        "Is DSL Actual Down";
    }
    leaf is-dsl-min-up {
      type int32;
      description
        "Is DSL Min Up";
    }
    leaf is-dsl-min-down {
      type int32;
      description
        "Is DSL Min Down";
    }
    leaf is-dsl-attain-up {
      type int32;
      description
        "Is DSL Attain Up";
    }
    leaf is-dsl-attain-down {
      type int32;
      description
        "Is DSL Attain Down";
    }
    leaf is-dsl-max-up {
      type int32;
      description
        "Is DSL Max Up";
    }
    leaf is-dsl-max-down {
      type int32;
      description
        "Is DSL Max Down";
    }
    leaf is-dsl-min-up-low {
      type int32;
      description
        "Is DSL Min Up Low";
    }
    leaf is-dsl-min-down-low {
      type int32;
      description
        "Is DSL Min Down Low";
    }
    leaf is-dsl-max-delay-up {
      type int32;
      description
        "Is DSL Max Delay Up";
    }
    leaf is-dsl-actual-delay-up {
      type int32;
      description
        "Is DSL Actual Delay Up";
    }
    leaf is-dsl-max-delay-down {
      type int32;
      description
        "Is DSL Max Delay Down";
    }
    leaf is-dsl-actual-delay-down {
      type int32;
      description
        "Is DSL Actual Delay Down";
    }
    leaf is-access-loop-encapsulation {
      type int32;
      description
        "Is Access Loop Encapsulation";
    }
    leaf dsl-actual-up {
      type uint32;
      description
        "DSL Actual Up";
    }
    leaf dsl-actual-down {
      type uint32;
      description
        "DSL Actual Down";
    }
    leaf dsl-min-up {
      type uint32;
      description
        "DSL Min Up";
    }
    leaf dsl-min-down {
      type uint32;
      description
        "DSL Min Down";
    }
    leaf dsl-attain-up {
      type uint32;
      description
        "DSL Attain Up";
    }
    leaf dsl-attain-down {
      type uint32;
      description
        "DSL Attain Down";
    }
    leaf dsl-max-up {
      type uint32;
      description
        "DSL Max Up";
    }
    leaf dsl-max-down {
      type uint32;
      description
        "DSL Max Down";
    }
    leaf dsl-min-up-low {
      type uint32;
      description
        "DSL Min Up Low";
    }
    leaf dsl-min-down-low {
      type uint32;
      description
        "DSL Min Down Low";
    }
    leaf dsl-max-delay-up {
      type uint32;
      description
        "DSL Max Delay Up";
    }
    leaf dsl-actual-delay-up {
      type uint32;
      description
        "DSL Actual Delay Up";
    }
    leaf dsl-max-delay-down {
      type uint32;
      description
        "DSL Max Delay Down";
    }
    leaf dsl-actual-delay-down {
      type uint32;
      description
        "DSL Actual Delay Down";
    }
  }

  grouping PPPOE-MA-SESSION-IDB-INFO {
    description
      "PPPoE MA Session IDB information";
    container tags {
      description
        "Tags";
      uses PPPOE-MA-INTERNAL-TAGS-INFO;
    }
    container vlan-outer-tag {
      description
        "VLAN Outer Tag";
      uses PPPOE-MA-VLAN-TAG-TYPE;
    }
    container vlan-inner-tag {
      description
        "VLAN Inner Tag";
      uses PPPOE-MA-VLAN-TAG-TYPE;
    }
    leaf interface {
      type xr:Interface-name;
      description
        "Interface";
    }
    leaf access-interface {
      type xr:Interface-name;
      description
        "Access Interface";
    }
    leaf session-id {
      type uint16;
      description
        "Session ID";
    }
    leaf sub-label {
      type uint32;
      description
        "Sub Label";
    }
    leaf peer-mac-address {
      type yang:mac-address;
      description
        "Peer Mac-Address";
    }
    leaf state {
      type Pppoe-ma-session-state;
      description
        "State";
    }
    leaf cdm-object-handle {
      type uint32;
      description
        "CDM Object Handle";
    }
    leaf chkpt-id {
      type uint32;
      description
        "Chkpt ID";
    }
    leaf punted-count {
      type uint32;
      description
        "Punted Count";
    }
    leaf port-limit {
      type uint32;
      description
        "Port Limit";
    }
    leaf is-counted {
      type int32;
      description
        "Is BBA Counted";
    }
    leaf is-vlan-outer-tag {
      type int32;
      description
        "Is VLAN Outer Tag";
    }
    leaf is-vlan-inner-tag {
      type int32;
      description
        "Is VLAN Inner Tag";
    }
    leaf is-cleanup-pending {
      type int32;
      description
        "Is Cleanup Pending";
    }
    leaf is-disconnect-done-pending {
      type int32;
      description
        "Is Disconnect Done Pending";
    }
    leaf is-delete-done-pending {
      type int32;
      description
        "Is Delete Done Pending";
    }
    leaf is-intf-create-callback-pending {
      type int32;
      description
        "Is Interface Create Callback pending";
    }
    leaf is-publish-encaps-attr-pending {
      type int32;
      description
        "Is Publish Encaps Attr pending";
    }
    leaf is-publish-encaps-attr-cb-pending {
      type int32;
      description
        "Is Publish Encaps Attr Callback pending";
    }
    leaf is-intf-delete-callback-pending {
      type int32;
      description
        "Is Interface Delete Callback pending";
    }
    leaf is-intf-delete-pending {
      type int32;
      description
        "Is Interface Delete pending";
    }
    leaf is-im-owned-resource {
      type int32;
      description
        "Is IM Owned Resource";
    }
    leaf is-im-final-received {
      type int32;
      description
        "Is IM Final received";
    }
    leaf is-im-owned-resource-missing {
      type int32;
      description
        "Is IM Owned Resource missing";
    }
    leaf is-aaa-start-request-callback-pending {
      type int32;
      description
        "Is AAA Start request callback pending";
    }
    leaf is-aaa-owned-resource {
      type int32;
      description
        "Is AAA Owned Resource";
    }
    leaf is-aaa-disconnect-requested {
      type int32;
      description
        "Is AAA Disconnect Requested";
    }
    leaf is-aaa-disconnect-received {
      type int32;
      description
        "Is AAA Disconnect Received";
    }
    leaf is-sub-db-activate-callback-pending {
      type int32;
      description
        "Is SubDB Activate callback pending";
    }
    leaf is-pads-sent {
      type int32;
      description
        "Is PADS Sent";
    }
    leaf is-padt-received {
      type int32;
      description
        "Is PADT Received";
    }
    leaf is-in-flight {
      type int32;
      description
        "Is Session In Flight";
    }
    leaf is-radius-override {
      type int32;
      description
        "Is RADIUS override enabled";
    }
    leaf expected-notifications {
      type uint8;
      description
        "Expected Notifications";
    }
    leaf received-notifications {
      type uint8;
      description
        "Received Notifications";
    }
    leaf srg-state {
      type Pppoe-ma-session-idb-srg-state;
      description
        "SRG state";
    }
    leaf is-srg-data-received {
      type int32;
      description
        "Is SRG Data Received";
    }
    leaf is-iedge-data-received {
      type int32;
      description
        "Is IEDGE Data Received";
    }
  }

  grouping PPPOE-MA-DISC-ENTRY {
    description
      "PPPoE disconnected subscriber information";
    container session-idb {
      description
        "Session IDB";
      uses PPPOE-MA-SESSION-IDB-INFO;
    }
    leaf timestamp {
      type uint64;
      description
        "Time when disconnected";
    }
    leaf ifname {
      type string;
      description
        "Interface name";
    }
    leaf trigger {
      type Pppoe-ma-session-trig;
      description
        "Disconnect Trigger";
    }
  }

  grouping PPPOE-MA-DISC-HISTORY {
    description
      "Wrapping history of disconnected subscribers";
    leaf current-idx {
      type uint32;
      description
        "Current index of history";
    }
    list entry {
      description
        "Array of disconnected subscribers";
      uses PPPOE-MA-DISC-ENTRY;
    }
  }

  grouping PPPOE-MA-PACKET-TYPE-COUNTS {
    description
      "PPPoE MA Packet type counts";
    leaf sent {
      type uint32;
      description
        "Sent";
    }
    leaf received {
      type uint32;
      description
        "Received";
    }
    leaf dropped {
      type uint32;
      description
        "Dropped";
    }
  }

  grouping PPPOE-MA-PACKET-COUNTS {
    description
      "PPPoE MA Packet Counts";
    container padi {
      description
        "PADI counts";
      uses PPPOE-MA-PACKET-TYPE-COUNTS;
    }
    container pado {
      description
        "PADO counts";
      uses PPPOE-MA-PACKET-TYPE-COUNTS;
    }
    container padr {
      description
        "PADR counts";
      uses PPPOE-MA-PACKET-TYPE-COUNTS;
    }
    container pads-success {
      description
        "PADS Success counts";
      uses PPPOE-MA-PACKET-TYPE-COUNTS;
    }
    container pads-error {
      description
        "PADS Error counts";
      uses PPPOE-MA-PACKET-TYPE-COUNTS;
    }
    container padt {
      description
        "PADT counts";
      uses PPPOE-MA-PACKET-TYPE-COUNTS;
    }
    container session-state {
      description
        "Session Stage counts";
      uses PPPOE-MA-PACKET-TYPE-COUNTS;
    }
    container other {
      description
        "Other counts";
      uses PPPOE-MA-PACKET-TYPE-COUNTS;
    }
  }

  grouping PPPOE-MA-ACCESS-INTERFACE-STATS-INFO {
    description
      "PPPoE MA Access Interface Statistics Information";
    container packet-counts {
      description
        "Packet Counts";
      uses PPPOE-MA-PACKET-COUNTS;
    }
  }
}
