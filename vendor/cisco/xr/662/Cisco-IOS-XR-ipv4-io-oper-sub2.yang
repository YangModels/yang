submodule Cisco-IOS-XR-ipv4-io-oper-sub2 {
  belongs-to Cisco-IOS-XR-ipv4-io-oper {
    prefix Cisco-IOS-XR-ipv4-io-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-io package operational data.
     
     Copyright (c) 2013-2018 by Cisco Systems, Inc.
     All rights reserved.";

  revision 2018-08-01 {
    description
      "Removed empty groupings.";
  }
  revision 2015-10-20 {
    description
      "this schema file has all the latest changes.";
  }
  revision 2015-01-07 {
    description
      "IOS XR 5.3.1 revision.";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Ipv4-ma-oper-config {
    type enumeration {
      enum "ipv4-ma-oper-client-none" {
        value 0;
        description
          "ipv4 ma oper client none";
      }
      enum "ipv4-ma-oper-non-oc-client" {
        value 1;
        description
          "ipv4 ma oper non oc client";
      }
      enum "ipv4-ma-oper-oc-client" {
        value 2;
        description
          "ipv4 ma oper oc client";
      }
    }
    description
      "ipv4 client type";
  }

  typedef Rpf-mode {
    type enumeration {
      enum "strict" {
        description
          "Strict RPF";
      }
      enum "loose" {
        description
          "Loose RPF";
      }
    }
    description
      "Interface line states";
  }

  typedef Str {
    type string;
    description
      "Str";
  }

  typedef Ipv4-ma-oper-line-state {
    type enumeration {
      enum "unknown" {
        description
          "Interface state is unknown";
      }
      enum "shutdown" {
        description
          "Interface has been shutdown";
      }
      enum "down" {
        description
          "Interface state is down";
      }
      enum "up" {
        description
          "Interface state is up";
      }
    }
    description
      "Interface line states";
  }

  grouping IF-SUMMARY {
    description
      "Count of assigned/unnumbered/unassigned
       interfaces";
    leaf ip-assigned {
      type uint32;
      description
        "Number of interfaces with explicit addresses";
    }
    leaf ip-unnumbered {
      type uint32;
      description
        "Number of unnumbered interfaces with explicit
         addresses";
    }
    leaf ip-unassigned {
      type uint32;
      description
        "Number of unassigned interfaces with explicit
         addresses";
    }
  }

  grouping IPV4-IF-SUMMARY {
    description
      "Summary info of IP interfaces";
    container if-up-up {
      description
        "Number of interfaces (up,up)";
      uses IF-SUMMARY;
    }
    container if-up-down {
      description
        "Number of interfaces (up,down)";
      uses IF-SUMMARY;
    }
    container if-down-down {
      description
        "Number of interfaces (down,down)";
      uses IF-SUMMARY;
    }
    container if-shutdown-down {
      description
        "Number of interfaces (shutdown,down)";
      uses IF-SUMMARY;
    }
    leaf if-up-down-basecaps-up {
      type uint32;
      description
        "Number of interfaces (up,down) with basecaps up";
    }
  }

  grouping BGP-PA-DIR {
    description
      "BGP PA config for ingress/egress direction";
    leaf enable {
      type boolean;
      description
        "Enable BGP PA for ingress/egress";
    }
    leaf source {
      type boolean;
      description
        "Enable source accouting";
    }
    leaf destination {
      type boolean;
      description
        "Enable destination accouting";
    }
  }

  grouping BGP-PA-CONFIG {
    description
      "BGP PA config information";
    container input {
      description
        "BGP PA input config";
      uses BGP-PA-DIR;
    }
    container output {
      description
        "BGP PA output config";
      uses BGP-PA-DIR;
    }
  }

  grouping RPF-CONFIG {
    description
      "RPF config information";
    leaf enable {
      type boolean;
      description
        "Enable RPF config";
    }
    leaf allow-default-route {
      type boolean;
      description
        "Allow Default Route";
    }
    leaf allow-self-ping {
      type boolean;
      description
        "Allow Self Ping";
    }
    leaf mode {
      type Rpf-mode;
      description
        "RPF Mode (loose/strict)";
    }
  }

  grouping HADDR-ARRAY {
    description
      "Helper Address List ";
    list address-array {
      description
        "Helper address";
      leaf entry {
        type inet:ipv4-address;
        description
          "Helper address";
      }
    }
  }

  grouping MULTI-ACL-CONFIG {
    description
      "Multi ACL config information";
    list inbound {
      max-elements "5";
      description
        "Inbound ACLs";
      leaf entry {
        type Str;
        description
          "Inbound ACLs";
      }
    }
    list outbound {
      max-elements "5";
      description
        "Outbound ACLs";
      leaf entry {
        type Str;
        description
          "Outbound ACLs";
      }
    }
    list common {
      max-elements "5";
      description
        "Common ACLs";
      leaf entry {
        type Str;
        description
          "Common ACLs";
      }
    }
  }

  grouping ACL-CONFIG {
    description
      "ACL config information";
    leaf inbound {
      type string;
      description
        "ACL applied to incoming packets";
    }
    leaf outbound {
      type string;
      description
        "ACL applied to outgoing packets";
    }
    leaf common-in-bound {
      type string;
      description
        "Common ACL applied to incoming packets";
    }
    leaf common-out-bound {
      type string;
      description
        "Common ACL applied to outgoing packets";
    }
  }

  grouping IP-ADDR-NODE {
    description
      "List of IP Addresses ";
    leaf address {
      type inet:ipv4-address;
      description
        "Address";
    }
    leaf prefix-length {
      type uint32;
      description
        "Prefix length of address";
    }
    leaf route-tag {
      type uint32;
      description
        "Route Tag associated with this address (0 = no
         tag)";
    }
  }

  grouping MCAST-GROUP {
    description
      "MCast Group List ";
    leaf group-address {
      type inet:ipv4-address;
      description
        "Address of multicast group";
    }
  }

  grouping IPV4-IF-DETAIL {
    description
      "Detailed Info of IP Interface";
    container acl {
      description
        "ACLs configured on the interface";
      uses ACL-CONFIG;
    }
    container multi-acl {
      description
        "Multi ACLs configured on the interface";
      uses MULTI-ACL-CONFIG;
    }
    container helper-address {
      description
        "Helper Addresses configured on the interface";
      uses HADDR-ARRAY;
    }
    container rpf {
      description
        "RPF config on the interface";
      uses RPF-CONFIG;
    }
    container bgp-pa {
      description
        "BGP PA config on the interface";
      uses BGP-PA-CONFIG;
    }
    leaf primary-address {
      type inet:ipv4-address;
      description
        "Primary address";
    }
    leaf vrf-id {
      type uint32;
      description
        "VRF ID of the interface";
    }
    leaf line-state {
      type Ipv4-ma-oper-line-state;
      description
        "Line state of the interface";
    }
    leaf prefix-length {
      type uint32;
      description
        "Prefix length of primary address";
    }
    leaf route-tag {
      type uint32;
      description
        "Route tag associated with the primary address (0
         = no tag)";
    }
    leaf mtu {
      type uint32;
      description
        "IP MTU of the interface";
    }
    leaf unreachable {
      type boolean;
      description
        "Are ICMP unreachables sent on the interface?";
    }
    leaf redirect {
      type boolean;
      description
        "Are ICMP redirects sent on the interface?";
    }
    leaf direct-broadcast {
      type boolean;
      description
        "Are direct broadcasts sent on the interface?";
    }
    leaf mask-reply {
      type boolean;
      description
        "Are mask replies sent on the interface?";
    }
    leaf rg-id-exists {
      type boolean;
      description
        "Does ICCP RG ID exist on the interface?";
    }
    leaf mlacp-active {
      type boolean;
      description
        "Is mLACP state Active (valid if RG ID exists)";
    }
    leaf unnumbered-interface-name {
      type string;
      description
        "Name of referenced interface (valid if
         unnumbered)";
    }
    leaf next-unnumbered-interface-name {
      type string;
      description
        "Name of interface which is also unnum to        
         same interface where this intf is unnumbered";
    }
    leaf proxy-arp-disabled {
      type boolean;
      description
        "Is Proxy ARP disabled on the interface?";
    }
    leaf flow-tag-src {
      type boolean;
      description
        "Is BGP Flow Tag Source is enable";
    }
    leaf flow-tag-dst {
      type boolean;
      description
        "Is BGP Flow Tag Destination is enable";
    }
    leaf config-flags {
      type uint16;
      description
        "IDB configuration flags";
    }
    leaf oper-flags {
      type uint64;
      description
        "IDB operational flags";
    }
    leaf arm-flags {
      type uint16;
      description
        "IP ARM operation flags";
    }
    leaf state-recvd-frm-im {
      type Ipv4-ma-oper-line-state;
      description
        "state as recieved                               
         from IM";
    }
    leaf cflct-address {
      type inet:ipv4-address;
      description
        "Conflicated ipv4 address";
    }
    leaf client-type {
      type Ipv4-ma-oper-config;
      description
        "Client type for IDB";
    }
    leaf is-or-event {
      type boolean;
      description
        "Is OR event for IDB";
    }
    leaf or-im-state {
      type Im-state-enum;
      description
        "OR IM state type";
    }
    leaf idb-pointer {
      type uint64;
      description
        "idb pointer value";
    }
    list multicast-group {
      description
        "Multicast groups joined on the interface";
      uses MCAST-GROUP;
    }
    list secondary-address {
      description
        "Secondary addresses on the interface";
      uses IP-ADDR-NODE;
    }
  }

  grouping IPV4-IF-BRIEF {
    description
      "Brief Summary of IP Interface";
    leaf primary-address {
      type inet:ipv4-address;
      description
        "Primary address";
    }
    leaf vrf-id {
      type uint32;
      description
        "VRF ID of the interface";
    }
    leaf vrf-name {
      type string;
      description
        "VRF name of the interface";
    }
    leaf line-state {
      type Ipv4-ma-oper-line-state;
      description
        "Line state of the interface";
    }
  }
}
