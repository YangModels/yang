module Cisco-IOS-XR-asr9k-sc-invmgr-admin-oper {
  namespace "http://cisco.com/ns/yang/Cisco-IOS-XR-asr9k-sc-invmgr-admin-oper";
  prefix asr9k-sc-invmgr-admin-oper;

  include Cisco-IOS-XR-asr9k-sc-invmgr-admin-oper-sub1 {
    revision-date 2018-06-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-sc-invmgr package
     admin-plane operational data.
     
     This module contains definitions
     for the following management objects:
       inventory: Inventory operational data
     
     Copyright (c) 2013-2018 by Cisco Systems, Inc.
     All rights reserved.";

  revision 2018-06-28 {
    description
      "FRU bag elements data type change to enum from value";
  }
  revision 2017-01-04 {
    description
      "IOS-XR 6.2.1 revision.";
  }
  revision 2015-11-09 {
    description
      "IOS XR 6.0 revision.";
  }

  grouping PORT-SLOT-TABLE {
    description
      "Common node of module, card";
    container port-slots {
      description
        "PortSlotTable contains all optics ports in a
         SPA/PLIM.";
      list port-slot {
        key "number";
        description
          "PortSlot number in the SPA/PLIM";
        container port {
          description
            "Port string";
          uses BASIC-ATTRIBUTES;
        }
        leaf number {
          type uint32;
          description
            "portslot number";
        }
        uses BASIC-ATTRIBUTES;
      }
    }
  }

  grouping SENSOR-TABLE {
    description
      "Common node of card, hw-component, module";
    container sensors {
      description
        "ModuleSensorTable contains all sensors in a
         Module.";
      list sensor {
        key "number";
        description
          "Sensor number in the Module";
        leaf number {
          type uint32;
          description
            "sensor number";
        }
        uses BASIC-ATTRIBUTES;
      }
    }
  }

  grouping BASIC-ATTRIBUTES {
    description
      "Common node of slot, card, sub-slot, module,
       port-slot, port, hw-component, sensor";
    container basic-attributes {
      description
        "Attributes";
      container fru-info {
        description
          "Field Replaceable Unit (FRU) inventory
           information";
        uses INV-XML-FRU-INFO;
      }
      container basic-info {
        description
          "Inventory information";
        uses INV-PHY-ENTITY-BASIC-INFO;
      }
    }
  }

  grouping VKG-INVMGR-ADMINOPER-BASIC-ATTRIBUTES {
    description
      "Common node of slot, card, sub-slot, module,
       port-slot, port, hw-component, sensorCommon node
       of rack, power-supply-shelf, fan-tray";
    container basic-attributes {
      description
        "Attributes";
      container basic-info {
        description
          "Inventory information";
        uses INV-PHY-ENTITY-BASIC-INFO;
      }
    }
  }

  container inventory {
    config false;
    description
      "Inventory operational data";
    container racks {
      description
        "Table of racks";
      list rack {
        key "number";
        description
          "Rack number";
        container power-supply-shelfs {
          description
            "Table for rack power supply shelves ";
          list power-supply-shelf {
            key "number";
            description
              "Power Supply Shelf number";
            leaf number {
              type uint32;
              description
                "Power Shelf number";
            }
            uses VKG-INVMGR-ADMINOPER-BASIC-ATTRIBUTES;
          }
        }
        container slots {
          description
            "Slot table contains all slots in the rack";
          list slot {
            key "number";
            description
              "Slot number";
            container cards {
              description
                "Card table contains all cards in the slot";
              list card {
                key "number";
                description
                  "Card number";
                container sub-slots {
                  description
                    "SubSlotTable contains all subslots in a
                     Slot";
                  list sub-slot {
                    key "number";
                    description
                      "SubSlot number";
                    container module {
                      description
                        "Module string";
                      uses PORT-SLOT-TABLE;
                      uses SENSOR-TABLE;
                      uses BASIC-ATTRIBUTES;
                    }
                    leaf number {
                      type uint32;
                      description
                        "subslot number";
                    }
                    uses BASIC-ATTRIBUTES;
                  }
                }
                container hw-components {
                  description
                    "HWComponent table contains all HW modules
                     within the card ";
                  list hw-component {
                    key "number";
                    description
                      "HWComponent number";
                    leaf number {
                      type uint32;
                      description
                        "node number";
                    }
                    uses SENSOR-TABLE;
                    uses BASIC-ATTRIBUTES;
                  }
                }
                leaf number {
                  type uint32;
                  description
                    "card number";
                }
                uses PORT-SLOT-TABLE;
                uses SENSOR-TABLE;
                uses BASIC-ATTRIBUTES;
              }
            }
            leaf number {
              type uint32;
              description
                "Slot number";
            }
            uses BASIC-ATTRIBUTES;
          }
        }
        container fan-trays {
          description
            "Table for rack fan trays";
          list fan-tray {
            key "number";
            description
              "Fan tray number";
            leaf number {
              type uint32;
              description
                "Fan tray number";
            }
            uses VKG-INVMGR-ADMINOPER-BASIC-ATTRIBUTES;
          }
        }
        container power-supply-zones {
          description
            "Table for defining rack power supply zones ";
          list power-supply-zone {
            key "number";
            description
              "Power Supply Zone number";
            container power-supply-zone-attributes {
              description
                "Power suppy zone attributes ";
              container power-supply-group-info {
                description
                  "Power supply group information";
                uses INV-PWG-INFO;
              }
            }
            leaf number {
              type uint32;
              description
                "Power Zone number";
            }
          }
        }
        leaf number {
          type uint32;
          description
            "Rack number";
        }
        uses VKG-INVMGR-ADMINOPER-BASIC-ATTRIBUTES;
      }
    }
  }
}
