submodule Cisco-IOS-XR-controller-odu-oper-sub1 {
  belongs-to Cisco-IOS-XR-controller-odu-oper {
    prefix Cisco-IOS-XR-controller-odu-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-odu package operational data.
     
     Copyright (c) 2013-2018 by Cisco Systems, Inc.
     All rights reserved.";

  revision 2015-11-09 {
    description
      "IOS XR 6.0 revision.";
  }

  typedef Odu-ains-state-et {
    type enumeration {
      enum "none" {
        value 0;
        description
          "None";
      }
      enum "active-running" {
        value 1;
        description
          "Running";
      }
      enum "active-pending" {
        value 2;
        description
          "Pending";
      }
    }
    description
      "Odu ains state et";
  }

  typedef Odu-ether-map-ping-et {
    type enumeration {
      enum "none" {
        value 0;
        description
          "None";
      }
      enum "gfp" {
        value 1;
        description
          "GfpF";
      }
      enum "amp" {
        value 2;
        description
          "Amp";
      }
      enum "bmp" {
        value 3;
        description
          "Bmp";
      }
      enum "gmp" {
        value 4;
        description
          "Gmp";
      }
      enum "wis" {
        value 5;
        description
          "Wis";
      }
      enum "gfp-ext" {
        value 6;
        description
          "GfpF Ext";
      }
    }
    description
      "Odu ether map ping et";
  }

  typedef Odu-tcm-mode {
    type enumeration {
      enum "odu-tcm-mode-trans-parent" {
        value 0;
        description
          "Transparent";
      }
      enum "nim" {
        value 1;
        description
          "Non-Intrusive Monitor";
      }
      enum "oper" {
        value 2;
        description
          "Operational";
      }
    }
    description
      "Odu tcm mode";
  }

  typedef Odu-tcm-per-mon {
    type enumeration {
      enum "disable" {
        value 0;
        description
          "Disable";
      }
      enum "enable" {
        value 1;
        description
          "Enable";
      }
    }
    description
      "Odu tcm per mon";
  }

  typedef Odu-tcm-state-et {
    type enumeration {
      enum "disable" {
        value 0;
        description
          "Disable";
      }
      enum "enable" {
        value 1;
        description
          "Enable";
      }
    }
    description
      "Odu tcm state et";
  }

  typedef Gmpls-tti-mode {
    type enumeration {
      enum "gmpls-odu-tti-mode-none" {
        description
          "Not Set";
      }
      enum "gmpls-odu-tti-mode-sm" {
        description
          "Section Monitoring";
      }
      enum "gmpls-odu-tti-mode-pm" {
        description
          "Path Monitoring";
      }
      enum "gmpls-odu-tti-mode-tcm" {
        description
          "Tandem Connection Monitoring";
      }
    }
    description
      "Gmpls tti mode";
  }

  typedef Odu-pm-mode {
    type enumeration {
      enum "nim" {
        value 0;
        description
          "Non-Intrusive Monitor";
      }
      enum "oper" {
        value 1;
        description
          "Operational";
      }
    }
    description
      "Odu pm mode";
  }

  typedef Odu-pm-ca-et {
    type enumeration {
      enum "disable" {
        value 0;
        description
          "Disable";
      }
      enum "enable" {
        value 1;
        description
          "Enable";
      }
    }
    description
      "Odu pm ca et";
  }

  typedef Odu-per-mon {
    type enumeration {
      enum "disable" {
        value 0;
        description
          "Disable";
      }
      enum "enable" {
        value 1;
        description
          "Enable";
      }
    }
    description
      "Odu per mon";
  }

  typedef Dp-programmed {
    type enumeration {
      enum "dp-not-programmed" {
        description
          "DP not programmed";
      }
      enum "dp-programmed-success" {
        description
          "DP programmed";
      }
      enum "end-pt-first-channel-ized" {
        description
          "ENDPT FIRST CHANNELIZED";
      }
      enum "end-pt-se-cond-channel-ized" {
        description
          "ENDPT SECOND CHANNELIZED";
      }
      enum "end-pt-first-cross-connected" {
        description
          "ENDPT FIRST CROSS CONNECTED";
      }
      enum "end-pt-se-cond-cross-connected" {
        description
          "ENDPT SECOND CROSS CONNECTED";
      }
      enum "end-pt-first-open-connected" {
        description
          "ENDPT FIRST OPEN CONNECTED";
      }
      enum "end-pt-se-cond-open-connected" {
        description
          "ENDPT SECOND OPEN CONNECTED";
      }
      enum "end-pt-first-loop-back-ed" {
        description
          "ENDPT FIRST LOOPBACKED";
      }
      enum "end-pt-se-cond-loop-back-ed" {
        description
          "ENDPT SECOND LOOPBACKED";
      }
      enum "end-pt-odu-type-mismatch" {
        description
          "ENDPT ODU TYPE MISMATCH";
      }
      enum "xc-not-set" {
        description
          "XCONNECT NOT SET";
      }
    }
    description
      "Dp programmed";
  }

  typedef Otm-mpls-lib-c {
    type enumeration {
      enum "otm-mpls-lib-c-type-null" {
        value 0;
        description
          "NULL";
      }
      enum "otm-mpls-lib-c-type-ipv4" {
        value 1;
        description
          "IPV4";
      }
      enum "otm-mpls-lib-c-type-ipv4-p2p-tunnel" {
        value 7;
        description
          "IPV4 P2P TUNNEL";
      }
      enum "otm-mpls-lib-c-type-ipv6-p2p-tunnel" {
        value 8;
        description
          "IPV6 P2P TUNNEL";
      }
      enum "otm-mpls-lib-c-type-ipv4-uni" {
        value 9;
        description
          "IPV4 UNI";
      }
      enum "otm-mpls-lib-c-type-ipv4-p2mp-tunnel" {
        value 13;
        description
          "IPV4 P2MP TUNNEL";
      }
      enum "otm-mpls-lib-c-type-ipv6-p2mp-tunnel" {
        value 14;
        description
          "IPV6 P2MP TUNNEL";
      }
      enum "otm-mpls-lib-c-type-ipv4-tp-tunnel" {
        value 15;
        description
          "IPV4 TP TUNNEL";
      }
      enum "otm-mpls-lib-c-type-ipv6-tp-tunnel" {
        value 16;
        description
          "IPV6 TP TUNNEL";
      }
    }
    description
      "Otm mpls lib c";
  }

  typedef Otm-te-tunnel-info {
    type enumeration {
      enum "otm-te-info-none" {
        description
          "NONE";
      }
      enum "otm-te-info-s2l" {
        description
          "S2L";
      }
      enum "otm-te-info-tunnel-id" {
        description
          "ID";
      }
      enum "otm-te-info-passive-match" {
        description
          "MAT";
      }
    }
    description
      "Otm te tunnel info";
  }

  typedef Otm-optical-rm-ctxt-rm {
    type enumeration {
      enum "otm-opt-rm-ctxt-rm-none" {
        description
          "NONE";
      }
      enum "otm-opt-rm-ctxt-rm-wdm" {
        description
          "WDM";
      }
      enum "otm-opt-rm-ctxt-rm-fsc" {
        description
          "FSC";
      }
      enum "otm-opt-rm-ctxt-rm-tdm" {
        description
          "TDM";
      }
      enum "otm-opt-rm-ctxt-rm-g709-otn" {
        description
          "G709 OTN";
      }
      enum "otm-optical-rm-ctxt-rm-last" {
        description
          "LAST";
      }
    }
    description
      "Otm optical rm ctxt rm";
  }

  typedef Otm-optical-rm-ctxt {
    type enumeration {
      enum "otm-opt-rm-ctxt-type-none" {
        description
          "NONE";
      }
      enum "otm-opt-rm-ctxt-type-down-stream-rw-add" {
        description
          "DOWNSTREAM RW ADD";
      }
      enum "otm-opt-rm-ctxt-type-up-stream-rw-add" {
        description
          "UPSTREAM RW ADD";
      }
      enum "otm-opt-rm-ctxt-type-down-stream-rw-del" {
        description
          "DOWNSTREAM RW DEL";
      }
      enum "otm-opt-rm-ctxt-type-up-stream-rw-del" {
        description
          "UPSTREAM RW DEL";
      }
      enum "otm-opt-rm-ctxt-type-down-stream-lbl-get" {
        description
          "DOWNSTREAM LBL GET";
      }
      enum "otm-opt-rm-ctxt-type-up-stream-lbl-get" {
        description
          "UPSTREAM LBL GET";
      }
      enum "otm-opt-rm-ctxt-type-down-stream-lbl-rel" {
        description
          "DOWNSTREAM LBL REL";
      }
      enum "otm-opt-rm-ctxt-type-up-stream-lbl-rel" {
        description
          "UPSTREAM LBL REL";
      }
      enum "otm-opt-rm-ctxt-type-end-point-rw-add" {
        description
          "ENDPOINT RW ADD";
      }
      enum "otm-opt-rm-ctxt-type-end-point-rw-del" {
        description
          "ENDPOINT RW DEL";
      }
      enum "otm-opt-rm-ctxt-type-odu-group-add" {
        description
          "ODU GROUP ADD";
      }
      enum "otm-opt-rm-ctxt-type-odu-group-del" {
        description
          "ODU GROUP DEL";
      }
      enum "otm-optical-rm-ctxt-type-last" {
        description
          "LAST";
      }
    }
    description
      "Otm optical rm ctxt";
  }

  typedef Odu-ts-g-et {
    type enumeration {
      enum "one-dot-two-five-g" {
        value 0;
        description
          "1.25G";
      }
      enum "two-dot-five-g" {
        value 1;
        description
          "2.5G";
      }
      enum "tsg-not-applicable" {
        value 2;
        description
          "NA";
      }
    }
    description
      "Odu ts g et";
  }

  typedef Odu-flex-type-et {
    type enumeration {
      enum "na" {
        value 0;
        description
          "NA";
      }
      enum "cbr" {
        value 1;
        description
          "ODU Flex Type CBR";
      }
      enum "gfp-resizable" {
        value 2;
        description
          "ODU Flex Type GFP resizable";
      }
      enum "gfp-fix" {
        value 3;
        description
          "ODU Flex Type GFP fix";
      }
    }
    description
      "Odu flex type et";
  }

  typedef Odu-pt-type-et {
    type enumeration {
      enum "na" {
        value 0;
        description
          "NA";
      }
      enum "two-asynchronous-cbr-mapping" {
        value 2;
        description
          "02 (Asynchronous CBR mapping)";
      }
      enum "three-bit-synchronous-cbr-mapping" {
        value 3;
        description
          "03 (Bit synchronous CBR mapping)";
      }
      enum "five-gfp-mapping" {
        value 5;
        description
          "05 (GFP mapping)";
      }
      enum "six-virtual-concatenated-signal" {
        value 6;
        description
          "06 (Virtual Concatenated Signal)";
      }
      enum "seven-pcs-codeword-transparent-ethernet-mapping" {
        value 7;
        description
          "07 (PCS codeword transparent Ethernet mapping)";
      }
      enum "nine-gfp-mapping-into-opu2" {
        value 9;
        description
          "09 (GFP mapping into OPU2)";
      }
      enum "zero-astm1-mapping-into-opu0" {
        value 10;
        description
          "0A (STM1 mapping into OPU0)";
      }
      enum "zero-bstm4-mapping-into-opu0" {
        value 11;
        description
          "0B (STM4 mapping into OPU0)";
      }
      enum "twenty-odu-multiplex-structure-supporting-odt-ujk" {
        value 32;
        description
          "20 (ODU multiplex structure supporting ODTUjk)";
      }
      enum "twenty-one-odu-multiplex-structure-supporting-odt-ujk-and-odt-ukts" {
        value 33;
        description
          "21 (ODU multiplex structure supporting ODTUjk
           and ODTUk.ts)";
      }
    }
    description
      "Odu pt type et";
  }

  typedef Odu-resource-et {
    type enumeration {
      enum "resource-free" {
        value 0;
        description
          "ODU Resource Free";
      }
      enum "open-connection" {
        value 1;
        description
          "ODU Open Connection";
      }
      enum "cross-connection" {
        value 2;
        description
          "ODU Cross Connection";
      }
      enum "channelized" {
        value 3;
        description
          "ODU Channelized";
      }
      enum "loopbacked" {
        value 4;
        description
          "ODU Loopbacked";
      }
      enum "cross-connected-and-loopbacked" {
        value 5;
        description
          "ODU Cross Connection and Loopbacked";
      }
      enum "terminated" {
        value 6;
        description
          "ODU Terminated";
      }
      enum "invalid" {
        value 7;
        description
          "ODU Invalid";
      }
    }
    description
      "Odu resource et";
  }

  typedef Odu-user-et {
    type enumeration {
      enum "mp" {
        value 0;
        description
          "MP";
      }
      enum "gmpls" {
        value 1;
        description
          "GMPLS";
      }
      enum "all" {
        value 2;
        description
          "All";
      }
    }
    description
      "Odu user et";
  }

  typedef Odu-sec-state {
    type enumeration {
      enum "normal" {
        value 0;
        description
          "Normal";
      }
      enum "maintenance" {
        value 1;
        description
          "Maintenance";
      }
      enum "ains" {
        value 2;
        description
          "Automatic In Service";
      }
    }
    description
      "Odu sec state";
  }

  typedef Odu-der-state {
    type enumeration {
      enum "out-of-service" {
        value 0;
        description
          "Out Of Service";
      }
      enum "in-service" {
        value 1;
        description
          "In Service";
      }
      enum "maintenance" {
        value 2;
        description
          "Maintenance";
      }
      enum "ains" {
        value 3;
        description
          "Automatic In Service";
      }
    }
    description
      "Odu der state";
  }

  typedef Odu-tti-et {
    type enumeration {
      enum "ascii" {
        value 0;
        description
          "ASCII";
      }
      enum "hex" {
        value 1;
        description
          "HEX";
      }
      enum "full-ascii" {
        value 2;
        description
          "FULL ASCII";
      }
      enum "full-hex" {
        value 3;
        description
          "FULL HEX";
      }
    }
    description
      "Odu tti et";
  }

  typedef Odu-loop-back-mode {
    type enumeration {
      enum "none" {
        value 1;
        description
          "None";
      }
      enum "line" {
        value 2;
        description
          "Line";
      }
      enum "internal" {
        value 4;
        description
          "Internal";
      }
    }
    description
      "Odu loop back mode";
  }

  typedef Odu-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Odu state et";
  }

  typedef Odu-prbs-status {
    type enumeration {
      enum "locked" {
        value 0;
        description
          "Locked";
      }
      enum "unlocked" {
        value 1;
        description
          "Unlocked";
      }
      enum "not-applicable" {
        value 2;
        description
          "Not Applicable";
      }
    }
    description
      "Odu prbs status";
  }

  typedef Odu-prbs-pattern {
    type enumeration {
      enum "pn-none" {
        value 0;
        description
          "PNNONE";
      }
      enum "pn31" {
        value 1;
        description
          "PN31";
      }
      enum "pn23" {
        value 2;
        description
          "PN23";
      }
      enum "pn11" {
        value 4;
        description
          "PN11";
      }
      enum "inverted-pn31" {
        value 8;
        description
          "INVERTED PN31";
      }
      enum "inverted-pn11" {
        value 16;
        description
          "INVERTED PN11";
      }
    }
    description
      "Odu prbs pattern";
  }

  typedef Odu-prbs-mode {
    type enumeration {
      enum "invalid" {
        value 0;
        description
          "invalid";
      }
      enum "source" {
        value 1;
        description
          "Source";
      }
      enum "sink" {
        value 2;
        description
          "Sink";
      }
      enum "source-sink" {
        value 3;
        description
          "Source Sink";
      }
    }
    description
      "Odu prbs mode";
  }

  typedef Odu-prbs-test {
    type enumeration {
      enum "disable" {
        value 0;
        description
          "Disable";
      }
      enum "enable" {
        value 1;
        description
          "Enable";
      }
    }
    description
      "Odu prbs test";
  }

  grouping ODU-AINS-HW-INFO {
    description
      "ODU AINS information";
    leaf ains-state {
      type Odu-ains-state-et;
      description
        "AINS State";
    }
    leaf ains-timer-minutes {
      type uint32;
      units "minute";
      description
        "AINS Timer in Minutes";
    }
    leaf ains-remaining-secs {
      type uint32;
      units "second";
      description
        "AINS Remaining Seconds";
    }
  }

  grouping ODU-TERMINATE-ETHER-INFO {
    description
      "ODU termination information";
    leaf vether-ifhandle {
      type uint32;
      description
        "interface handle";
    }
    leaf ethernet-mapping {
      type Odu-ether-map-ping-et;
      description
        "ethernet mapping";
    }
    leaf ethernet-interface {
      type string;
      description
        "Ethernet interface name";
    }
  }

  grouping ODU-DELAY-INFO {
    description
      "ODU Delay";
    leaf mode {
      type uint8;
      description
        "Latency Mode";
    }
    leaf delay {
      type uint32;
      description
        "Delay Value";
    }
  }

  grouping ODU-TCM-INFO {
    description
      "ODU TCM";
    container tcmtti-mode {
      description
        "TTI";
      uses ODU-G709-TTI;
    }
    leaf tcmsf {
      type uint8;
      description
        "ODU TCM SF in the form of 1.0E - <SF>";
    }
    leaf tcmsd {
      type uint8;
      description
        "ODU TCM SD in the form of 1.0E - <SD>";
    }
    leaf tcm-state {
      type Odu-tcm-state-et;
      description
        "ODU TCM state";
    }
    leaf tcmper-mon {
      type Odu-tcm-per-mon;
      description
        "Performance Monitoring";
    }
    leaf tcm-mode {
      type Odu-tcm-mode;
      description
        "ODU TCM Mode";
    }
    leaf actual-tcm-mode {
      type Odu-tcm-mode;
      description
        "TCM Mode in H/W";
    }
    leaf tcmltc-state {
      type Odu-tcm-state-et;
      description
        "ODU TCM LTC CA state";
    }
    leaf tcmtim-state {
      type Odu-tcm-state-et;
      description
        "ODU TCM  TIM CAstate";
    }
    leaf tcm-delay {
      type uint32;
      description
        "ODU TCM DELAY";
    }
  }

  grouping OTM-MTE-VIF-PASSIVE-MATCH-INFO {
    description
      "MTE VIF Passive Match Information";
    leaf src-tid {
      type uint16;
      description
        "Src TId";
    }
    leaf src-rid {
      type uint32;
      description
        "Src RId";
    }
  }

  grouping OTM-S2L-FEC {
    description
      "S2L FEC Information";
    leaf s2l-fec-sub-group-id {
      type uint16;
      description
        "SubGroup Id";
    }
    leaf s2l-fec-lsp-id {
      type uint16;
      description
        "Lsp Id";
    }
    leaf s2l-fec-tunnel-id {
      type uint16;
      description
        "Tunnel Id";
    }
    leaf ext-tunnel-id {
      type uint32;
      description
        "Ext Tunnel Id";
    }
    leaf fec-source {
      type uint32;
      description
        "FEC Source";
    }
    leaf fec-dest {
      type uint32;
      description
        "FEC Dest";
    }
    leaf s2l-fec-p2mp-id {
      type uint32;
      description
        "P2MP Id";
    }
    leaf sub-group-origin-ator {
      type uint32;
      description
        "SubGroup Originator";
    }
    leaf fec-c-type {
      type Otm-mpls-lib-c;
      description
        "Ctype";
    }
  }

  grouping OTM-TE-TUNNEL-INFO-UNION {
    description
      "OTM TE TUNNEL INFO UNION";
    container lb-ctxt {
      when "../info-type = 'otm-te-info-s2l'" {
        description
          "../INFO_TYPE = 'OTM_TE_INFO_S2l'";
      }
      description
        "Lbl Ctxt";
      uses OTM-S2L-FEC;
    }
    container passive-match {
      when "../info-type = 'otm-te-info-passive-match'" {
        description
          "../INFO_TYPE = 'OTM_TE_INFO_PASSIVE_MATCH'";
      }
      description
        "Passive Match";
      uses OTM-MTE-VIF-PASSIVE-MATCH-INFO;
    }
    leaf info-type {
      type Otm-te-tunnel-info;
      description
        "INFO TYPE";
    }
    leaf tunnel-id {
      when "../info-type = 'otm-te-info-tunnel-id'" {
        description
          "../INFO_TYPE = 'OTM_TE_INFO_TUNNEL_ID'";
      }
      type uint32;
      description
        "Tunnel Id";
    }
  }

  grouping OTM-OPTICAL-RM-CTXT-DATA {
    description
      "TE Optical RM CTXT Data Information";
    container te-tunnel-info {
      description
        "Tunnel Information";
      uses OTM-TE-TUNNEL-INFO-UNION;
    }
    leaf gmpls-req-time {
      type uint32;
      description
        "Req Time";
    }
    leaf ctxt-type {
      type Otm-optical-rm-ctxt;
      description
        "Ctxt Type";
    }
    leaf rm-type {
      type Otm-optical-rm-ctxt-rm;
      description
        "Rm Type";
    }
  }

  grouping ODU-EDM-ALARM {
    description
      " ODU Alarm";
    leaf reporting-enabled {
      type boolean;
      description
        "Is reporting enabled?";
    }
    leaf is-detected {
      type boolean;
      description
        "Is defect detected?";
    }
    leaf is-asserted {
      type boolean;
      description
        "Is defect delared?";
    }
    leaf counter {
      type uint64;
      description
        "Alarm counter";
    }
  }

  grouping ODU-ALARM-INFO {
    description
      "ODU Alarm";
    container oci {
      description
        "Open Connection Indiction";
      uses ODU-EDM-ALARM;
    }
    container ais {
      description
        "Alarm Indication Signal";
      uses ODU-EDM-ALARM;
    }
    container lck {
      description
        "Upstream Connection Locked";
      uses ODU-EDM-ALARM;
    }
    container bdi {
      description
        "Backward Defect Indication";
      uses ODU-EDM-ALARM;
    }
    container eoc {
      description
        "GCC End of Channel";
      uses ODU-EDM-ALARM;
    }
    container ptim {
      description
        "Payload Type Identifier Mismatch";
      uses ODU-EDM-ALARM;
    }
    container tim {
      description
        "Trace Identifier Mismatch information";
      uses ODU-EDM-ALARM;
    }
    container iae {
      description
        "Incoming Alignment Error";
      uses ODU-EDM-ALARM;
    }
    container biae {
      description
        "Backward Incoming Alignment Error";
      uses ODU-EDM-ALARM;
    }
    container sf-ber {
      description
        "SF BER alarm";
      uses ODU-EDM-ALARM;
    }
    container sd-ber {
      description
        "SD BER alarm";
      uses ODU-EDM-ALARM;
    }
    container csf {
      description
        "Client Signal Failure";
      uses ODU-EDM-ALARM;
    }
    container tcm1-ais {
      description
        "TCM1 Alarm Indication Signal";
      uses ODU-EDM-ALARM;
    }
    container tcm1-ltc {
      description
        "TCM1 Loss of Tandem connection Monitoring";
      uses ODU-EDM-ALARM;
    }
    container tcm1-oci {
      description
        "TCM1 Open Connection Indiction";
      uses ODU-EDM-ALARM;
    }
    container tcm1-lck {
      description
        "TCM1  Upstream Connection Locked";
      uses ODU-EDM-ALARM;
    }
    container tcm1-iae {
      description
        "TCM1 Incoming Alignment Error";
      uses ODU-EDM-ALARM;
    }
    container tcm1-biae {
      description
        "TCM1 Backward Incoming Alignment Error";
      uses ODU-EDM-ALARM;
    }
    container tcm1-bdi {
      description
        "TCM1 Backward Defect Monitoring";
      uses ODU-EDM-ALARM;
    }
    container tcm1-tim {
      description
        "TCM1 Trail Trace Identifier Mismatch ";
      uses ODU-EDM-ALARM;
    }
    container tcm1-sf-ber {
      description
        "TCM1 SF BER alarm";
      uses ODU-EDM-ALARM;
    }
    container tcm1-sd-ber {
      description
        "TCM1 SD BER alarm";
      uses ODU-EDM-ALARM;
    }
    container tcm2-ais {
      description
        "TCM2 Alarm Indication Signal";
      uses ODU-EDM-ALARM;
    }
    container tcm2-ltc {
      description
        "TCM2 Loss of Tandem connection Monitoring";
      uses ODU-EDM-ALARM;
    }
    container tcm2-oci {
      description
        "TCM2 Open Connection Indiction";
      uses ODU-EDM-ALARM;
    }
    container tcm2-lck {
      description
        "TCM2  Upstream Connection Locked";
      uses ODU-EDM-ALARM;
    }
    container tcm2-iae {
      description
        "TCM2 Incoming Alignment Error";
      uses ODU-EDM-ALARM;
    }
    container tcm2-biae {
      description
        "TCM2 Backward Incoming Alignment Error";
      uses ODU-EDM-ALARM;
    }
    container tcm2-bdi {
      description
        "TCM2 Backward Defect Monitoring";
      uses ODU-EDM-ALARM;
    }
    container tcm2-tim {
      description
        "TCM2 Trail Trace Identifier Mismatch ";
      uses ODU-EDM-ALARM;
    }
    container tcm2-sf-ber {
      description
        "TCM2 SF BER alarm";
      uses ODU-EDM-ALARM;
    }
    container tcm2-sd-ber {
      description
        "TCM2 SD BER alarm";
      uses ODU-EDM-ALARM;
    }
    container tcm3-ais {
      description
        "TCM3 Alarm Indication Signal";
      uses ODU-EDM-ALARM;
    }
    container tcm3-ltc {
      description
        "TCM3 Loss of Tandem connection Monitoring";
      uses ODU-EDM-ALARM;
    }
    container tcm3-oci {
      description
        "TCM3 Open Connection Indiction";
      uses ODU-EDM-ALARM;
    }
    container tcm3-lck {
      description
        "TCM3  Upstream Connection Locked";
      uses ODU-EDM-ALARM;
    }
    container tcm3-iae {
      description
        "TCM3 Incoming Alignment Error";
      uses ODU-EDM-ALARM;
    }
    container tcm3-biae {
      description
        "TCM3 Backward Incoming Alignment Error";
      uses ODU-EDM-ALARM;
    }
    container tcm3-bdi {
      description
        "TCM3 Backward Defect Monitoring";
      uses ODU-EDM-ALARM;
    }
    container tcm3-tim {
      description
        "TCM3 Trail Trace Identifier Mismatch ";
      uses ODU-EDM-ALARM;
    }
    container tcm3-sf-ber {
      description
        "TCM3 SF BER alarm";
      uses ODU-EDM-ALARM;
    }
    container tcm3-sd-ber {
      description
        "TCM3 SD BER alarm";
      uses ODU-EDM-ALARM;
    }
    container tcm4-ais {
      description
        "TCM4 Alarm Indication Signal";
      uses ODU-EDM-ALARM;
    }
    container tcm4-ltc {
      description
        "TCM4 Loss of Tandem connection Monitoring";
      uses ODU-EDM-ALARM;
    }
    container tcm4-oci {
      description
        "TCM4 Open Connection Indiction";
      uses ODU-EDM-ALARM;
    }
    container tcm4-lck {
      description
        "TCM4  Upstream Connection Locked";
      uses ODU-EDM-ALARM;
    }
    container tcm4-iae {
      description
        "TCM4 Incoming Alignment Error";
      uses ODU-EDM-ALARM;
    }
    container tcm4-biae {
      description
        "TCM4 Backward Incoming Alignment Error";
      uses ODU-EDM-ALARM;
    }
    container tcm4-bdi {
      description
        "TCM4 Backward Defect Monitoring";
      uses ODU-EDM-ALARM;
    }
    container tcm4-tim {
      description
        "TCM4 Trail Trace Identifier Mismatch ";
      uses ODU-EDM-ALARM;
    }
    container tcm4-sf-ber {
      description
        "TCM4 SF BER alarm";
      uses ODU-EDM-ALARM;
    }
    container tcm4-sd-ber {
      description
        "TCM4 SD BER alarm";
      uses ODU-EDM-ALARM;
    }
    container tcm5-ais {
      description
        "TCM5 Alarm Indication Signal";
      uses ODU-EDM-ALARM;
    }
    container tcm5-ltc {
      description
        "TCM5 Loss of Tandem connection Monitoring";
      uses ODU-EDM-ALARM;
    }
    container tcm5-oci {
      description
        "TCM5 Open Connection Indiction";
      uses ODU-EDM-ALARM;
    }
    container tcm5-lck {
      description
        "TCM5  Upstream Connection Locked";
      uses ODU-EDM-ALARM;
    }
    container tcm5-iae {
      description
        "TCM5 Incoming Alignment Error";
      uses ODU-EDM-ALARM;
    }
    container tcm5-biae {
      description
        "TCM5 Backward Incoming Alignment Error";
      uses ODU-EDM-ALARM;
    }
    container tcm5-bdi {
      description
        "TCM5 Backward Defect Monitoring";
      uses ODU-EDM-ALARM;
    }
    container tcm5-tim {
      description
        "TCM5 Trail Trace Identifier Mismatch ";
      uses ODU-EDM-ALARM;
    }
    container tcm5-sf-ber {
      description
        "TCM5 SF BER alarm";
      uses ODU-EDM-ALARM;
    }
    container tcm5-sd-ber {
      description
        "TCM5 SD BER alarm";
      uses ODU-EDM-ALARM;
    }
    container tcm6-ais {
      description
        "TCM6 Alarm Indication Signal";
      uses ODU-EDM-ALARM;
    }
    container tcm6-ltc {
      description
        "TCM6 Loss of Tandem connection Monitoring";
      uses ODU-EDM-ALARM;
    }
    container tcm6-oci {
      description
        "TCM6 Open Connection Indiction";
      uses ODU-EDM-ALARM;
    }
    container tcm6-lck {
      description
        "TCM6  Upstream Connection Locked";
      uses ODU-EDM-ALARM;
    }
    container tcm6-iae {
      description
        "TCM6 Incoming Alignment Error";
      uses ODU-EDM-ALARM;
    }
    container tcm6-biae {
      description
        "TCM6 Backward Incoming Alignment Error";
      uses ODU-EDM-ALARM;
    }
    container tcm6-bdi {
      description
        "TCM6 Backward Defect Monitoring";
      uses ODU-EDM-ALARM;
    }
    container tcm6-tim {
      description
        "TCM6 Trail Trace Identifier Mismatch ";
      uses ODU-EDM-ALARM;
    }
    container tcm6-sf-ber {
      description
        "TCM6 SF BER alarm";
      uses ODU-EDM-ALARM;
    }
    container tcm6-sd-ber {
      description
        "TCM6 SD BER alarm";
      uses ODU-EDM-ALARM;
    }
    container gfp-lfd {
      description
        "Loss Of Frame Delineation";
      uses ODU-EDM-ALARM;
    }
    container gfp-locs {
      description
        "Loss Of Client Signal";
      uses ODU-EDM-ALARM;
    }
    container gfp-loccs {
      description
        "Loss Of Character Synchronization";
      uses ODU-EDM-ALARM;
    }
    container gfp-upm {
      description
        "User Payload Mismatch";
      uses ODU-EDM-ALARM;
    }
  }

  grouping ODU-CHILD-TS-INFO {
    description
      "ODU Child Ts";
    leaf intf-name {
      type string {
        length "0..64";
      }
      description
        "Child Interface Name";
    }
    leaf tpn-value {
      type uint8;
      description
        "Tpn Bitmap";
    }
    leaf ts-bitmap {
      type string {
        length "0..256";
      }
      description
        "Ts Bitmap";
    }
  }

  grouping ODU-FWD-REF-ODU-INFO {
    description
      "ODU FWD_REFERENCE ODU";
    leaf od-uuser {
      type Odu-user-et;
      description
        " ODU User";
    }
    leaf resource-state {
      type Odu-resource-et;
      description
        "Resource State";
    }
  }

  grouping ODU-TTI-ST {
    description
      "TTI Sapi Dapi";
    leaf-list sapi {
      type uint8;
      description
        "tx String";
    }
    leaf-list dapi {
      type uint8;
      description
        "exp String";
    }
    leaf-list operator-specific {
      type uint8;
      description
        "rec String";
    }
  }

  grouping ODU-G709-TTI {
    description
      "TTI";
    container tx {
      description
        "String Sent";
      uses ODU-TTI-ST;
    }
    container exp {
      description
        "String Expected";
      uses ODU-TTI-ST;
    }
    container rec {
      description
        "String Received";
      uses ODU-TTI-ST;
    }
    leaf g709tti-sent-mode {
      type Odu-tti-et;
      description
        "G709TTI Sent";
    }
    leaf g709tti-exp-mode {
      type Odu-tti-et;
      description
        "G709TTI Expected";
    }
    leaf g709tti-rec-mode {
      type Odu-tti-et;
      description
        "G709TTI Recieved";
    }
  }

  grouping OTN-ODU-REMOTE-INFO-VIA-TTI-T-RTRID-IFINDEX {
    description
      "otn odu remote info via tti t rtrid ifindex";
    leaf router-id {
      type uint32;
      description
        "Router ID";
    }
    leaf if-index {
      type uint32;
      description
        "IfIndex";
    }
  }

  grouping ODU-PER-PORT-INFO {
    description
      "ODU";
    container local {
      description
        "TTI";
      uses OTN-ODU-REMOTE-INFO-VIA-TTI-T-RTRID-IFINDEX;
    }
    container remote {
      description
        "Remote";
      uses OTN-ODU-REMOTE-INFO-VIA-TTI-T-RTRID-IFINDEX;
    }
    container tti-mode {
      description
        "TTI";
      uses ODU-G709-TTI;
    }
    container odu-fwd-ref {
      description
        "ODU fwd_ref ";
      uses ODU-FWD-REF-ODU-INFO;
    }
    container alarm {
      description
        "Alarm";
      uses ODU-ALARM-INFO;
    }
    container te-ctx-data {
      description
        "Label Get Data";
      uses OTM-OPTICAL-RM-CTXT-DATA;
    }
    container xc-add-ctx-data {
      description
        "Xconnect Add Data";
      uses OTM-OPTICAL-RM-CTXT-DATA;
    }
    container xc-rem-ctx-data {
      description
        "Xconnect Remove Data";
      uses OTM-OPTICAL-RM-CTXT-DATA;
    }
    container odu-delay {
      description
        "ODU Delay";
      uses ODU-DELAY-INFO;
    }
    container odu-terminate-ether {
      description
        "odu terminate ether";
      uses ODU-TERMINATE-ETHER-INFO;
    }
    container ains-info {
      description
        "AINS information";
      uses ODU-AINS-HW-INFO;
    }
    leaf state {
      type Odu-state-et;
      description
        "Admin State";
    }
    leaf sf {
      type uint8;
      description
        "SF in the form of 1.0E - <SF>";
    }
    leaf sd {
      type uint8;
      description
        "SD in the form of 1.0E - <SD>";
    }
    leaf loopback-mode {
      type Odu-loop-back-mode;
      description
        "Loopback";
    }
    leaf derived-mode {
      type Odu-der-state;
      description
        "Derived State";
    }
    leaf inherit-sec-state {
      type Odu-sec-state;
      description
        "Sec State ";
    }
    leaf config-sec-state {
      type Odu-sec-state;
      description
        "Sec State ";
    }
    leaf gcc-mode {
      type boolean;
      description
        "ODU GCC";
    }
    leaf child-name {
      type string {
        length "0..64";
      }
      description
        "Child Name";
    }
    leaf max-odu-child {
      type uint8;
      description
        "ODU maximum no of children";
    }
    leaf od-uuser {
      type Odu-user-et;
      description
        " ODU User";
    }
    leaf resource-state {
      type Odu-resource-et;
      description
        "Resource State";
    }
    leaf pt-type {
      type Odu-pt-type-et;
      description
        "PT type";
    }
    leaf flex-type {
      type Odu-flex-type-et;
      description
        "FLEX type";
    }
    leaf flex-bw {
      type uint32;
      description
        "FLEX bw";
    }
    leaf flex-tolerence {
      type uint16;
      description
        "FLEX tolerence";
    }
    leaf option {
      type uint8;
      description
        "Option";
    }
    leaf tpn-value {
      type uint8;
      description
        "TPN";
    }
    leaf num-ts {
      type uint8;
      description
        "Number of TS";
    }
    leaf ts-g {
      type Odu-ts-g-et;
      description
        "TS Granuality";
    }
    leaf ts-b {
      type string {
        length "0..256";
      }
      description
        "child ts bitmap";
    }
    leaf tpn-b {
      type string {
        length "0..256";
      }
      description
        "tpn bitmap";
    }
    leaf pts-b {
      type string {
        length "0..256";
      }
      description
        "ts bitmap";
    }
    leaf fwd-ref {
      type string {
        length "0..64";
      }
      description
        "fwd ref";
    }
    leaf xc-id {
      type uint32;
      description
        "Xconnect ID";
    }
    leaf xconnect-name {
      type string;
      description
        "Xconnect Name";
    }
    leaf fwd-ref-ifhandle {
      type uint32;
      description
        "fwd_ref ifhandle";
    }
    leaf no-parent-slot {
      type uint32;
      description
        "Number of parent slot";
    }
    leaf xc-resp-code {
      type Dp-programmed;
      description
        "Odu Xconnect Response code";
    }
    leaf performance-monitoring {
      type Odu-per-mon;
      description
        "Performance Monitoring";
    }
    leaf pmtimca {
      type Odu-pm-ca-et;
      description
        "PM TIM-CA state";
    }
    leaf pm-mode {
      type Odu-pm-mode;
      description
        "ODU PM Mode";
    }
    leaf nv-optical-support {
      type boolean;
      description
        "NV Optical support";
    }
    leaf gmpls-tti-mode {
      type Gmpls-tti-mode;
      description
        "tti mode";
    }
    leaf gmpls-tcm-id {
      type uint8;
      description
        "tcm id";
    }
    list odu {
      description
        "Child Ts";
      uses ODU-CHILD-TS-INFO;
    }
    list odutcm {
      description
        "ODU TCM";
      uses ODU-TCM-INFO;
    }
  }

  grouping ODU-PRBS-INFO {
    description
      "PRBS";
    leaf odu-prbs-test {
      type Odu-prbs-test;
      description
        "odu prbs test";
    }
    leaf odu-prbs-mode {
      type Odu-prbs-mode;
      description
        "odu prbs mode";
    }
    leaf odu-prbs-pattern {
      type Odu-prbs-pattern;
      description
        "odu prbs pattern";
    }
    leaf odu-prbs-status {
      type Odu-prbs-status;
      description
        "odu prbs status";
    }
  }
}
