module Cisco-IOS-XR-mpls-static-oper {
  namespace "http://cisco.com/ns/yang/Cisco-IOS-XR-mpls-static-oper";
  prefix mpls-static-oper;

  import Cisco-IOS-XR-types {
    prefix xr;
  }
  include Cisco-IOS-XR-mpls-static-oper-sub1 {
    revision-date 2017-05-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-static package operational data.
     
     This module contains definitions
     for the following management objects:
       mpls-static: MPLS STATIC operational data
     
     Copyright (c) 2013-2018 by Cisco Systems, Inc.
     All rights reserved.";

  revision 2017-05-01 {
    description
      "Fixing backward compatibility error in module.";
  }
  revision 2015-11-09 {
    description
      "IOS XR 6.0 revision.";
  }

  grouping LOCAL-LABEL-TABLE {
    description
      "Common node of mpls-static, vrf";
    container local-labels {
      description
        "data for static local-label table";
      list local-label {
        key "local-label-id";
        description
          "Data for static label";
        leaf local-label-id {
          type uint32 {
            range "16..1048575";
          }
          description
            "Local Label";
        }
        uses MPLS-STATIC-LBL-INFO;
      }
    }
  }

  container mpls-static {
    config false;
    description
      "MPLS STATIC operational data";
    container vrfs {
      description
        "VRF table";
      list vrf {
        key "vrf-name";
        description
          "VRF Name";
        container lsps {
          description
            "data for static lsp table";
          list lsp {
            key "lsp-name";
            description
              "Data for static lsp";
            leaf lsp-name {
              type xr:Cisco-ios-xr-string;
              description
                "LSP Name";
            }
            uses MPLS-STATIC-LSP-INFO;
          }
        }
        leaf vrf-name {
          type xr:Cisco-ios-xr-string;
          description
            "VRF Name";
        }
        uses LOCAL-LABEL-TABLE;
      }
    }
    container summary {
      description
        "MPLS STATIC summary data";
      uses MPLS-STATIC-SUMMARY;
    }
    uses LOCAL-LABEL-TABLE;
  }
}
