module cisco-xr-openconfig-transport-line-protection-deviations {
  namespace "http://cisco.com/ns/yang/cisco-xr-openconfig-transport-line-protection-deviations";
  prefix oc-line-protectdevs;

  import openconfig-transport-line-protection {
    prefix oc-line-protect;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for 
      
     openconfig-transport-line-protection.yang@2017-03-28 
     
     on Cisco IOS-XR devices.
     
     Copyright (c) 2017-2018 by Cisco Systems, Inc.
     All rights reserved.";

  revision 2018-07-06 {
    description
      "Initial revision applicable to IOS-XR 6.4.1";
  }

  deviation "/oc-line-protect:aps/oc-line-protect:aps-modules/oc-line-protect:aps-module/oc-line-protect:ports/oc-line-protect:line-primary-in/oc-line-protect:config/oc-line-protect:enabled" {
    deviate not-supported;
  }
  deviation "/oc-line-protect:aps/oc-line-protect:aps-modules/oc-line-protect:aps-module/oc-line-protect:ports/oc-line-protect:line-primary-in/oc-line-protect:state/oc-line-protect:enabled" {
    deviate not-supported;
  }
  deviation "/oc-line-protect:aps/oc-line-protect:aps-modules/oc-line-protect:aps-module/oc-line-protect:ports/oc-line-protect:line-primary-in/oc-line-protect:state/oc-line-protect:optical-power/oc-line-protect:interval" {
    deviate not-supported;
  }
  deviation "/oc-line-protect:aps/oc-line-protect:aps-modules/oc-line-protect:aps-module/oc-line-protect:ports/oc-line-protect:line-primary-in/oc-line-protect:state/oc-line-protect:optical-power/oc-line-protect:min-time" {
    deviate not-supported;
  }
  deviation "/oc-line-protect:aps/oc-line-protect:aps-modules/oc-line-protect:aps-module/oc-line-protect:ports/oc-line-protect:line-primary-in/oc-line-protect:state/oc-line-protect:optical-power/oc-line-protect:max-time" {
    deviate not-supported;
  }
  deviation "/oc-line-protect:aps/oc-line-protect:aps-modules/oc-line-protect:aps-module/oc-line-protect:ports/oc-line-protect:line-primary-out/oc-line-protect:state/oc-line-protect:optical-power/oc-line-protect:interval" {
    deviate not-supported;
  }
  deviation "/oc-line-protect:aps/oc-line-protect:aps-modules/oc-line-protect:aps-module/oc-line-protect:ports/oc-line-protect:line-primary-out/oc-line-protect:state/oc-line-protect:optical-power/oc-line-protect:min-time" {
    deviate not-supported;
  }
  deviation "/oc-line-protect:aps/oc-line-protect:aps-modules/oc-line-protect:aps-module/oc-line-protect:ports/oc-line-protect:line-primary-out/oc-line-protect:state/oc-line-protect:optical-power/oc-line-protect:max-time" {
    deviate not-supported;
  }
  deviation "/oc-line-protect:aps/oc-line-protect:aps-modules/oc-line-protect:aps-module/oc-line-protect:ports/oc-line-protect:line-secondary-in/oc-line-protect:config/oc-line-protect:enabled" {
    deviate not-supported;
  }
  deviation "/oc-line-protect:aps/oc-line-protect:aps-modules/oc-line-protect:aps-module/oc-line-protect:ports/oc-line-protect:line-secondary-in/oc-line-protect:state/oc-line-protect:enabled" {
    deviate not-supported;
  }
  deviation "/oc-line-protect:aps/oc-line-protect:aps-modules/oc-line-protect:aps-module/oc-line-protect:ports/oc-line-protect:line-secondary-in/oc-line-protect:state/oc-line-protect:optical-power/oc-line-protect:interval" {
    deviate not-supported;
  }
  deviation "/oc-line-protect:aps/oc-line-protect:aps-modules/oc-line-protect:aps-module/oc-line-protect:ports/oc-line-protect:line-secondary-in/oc-line-protect:state/oc-line-protect:optical-power/oc-line-protect:min-time" {
    deviate not-supported;
  }
  deviation "/oc-line-protect:aps/oc-line-protect:aps-modules/oc-line-protect:aps-module/oc-line-protect:ports/oc-line-protect:line-secondary-in/oc-line-protect:state/oc-line-protect:optical-power/oc-line-protect:max-time" {
    deviate not-supported;
  }
  deviation "/oc-line-protect:aps/oc-line-protect:aps-modules/oc-line-protect:aps-module/oc-line-protect:ports/oc-line-protect:line-secondary-out/oc-line-protect:state/oc-line-protect:optical-power/oc-line-protect:interval" {
    deviate not-supported;
  }
  deviation "/oc-line-protect:aps/oc-line-protect:aps-modules/oc-line-protect:aps-module/oc-line-protect:ports/oc-line-protect:line-secondary-out/oc-line-protect:state/oc-line-protect:optical-power/oc-line-protect:min-time" {
    deviate not-supported;
  }
  deviation "/oc-line-protect:aps/oc-line-protect:aps-modules/oc-line-protect:aps-module/oc-line-protect:ports/oc-line-protect:line-secondary-out/oc-line-protect:state/oc-line-protect:optical-power/oc-line-protect:max-time" {
    deviate not-supported;
  }
  deviation "/oc-line-protect:aps/oc-line-protect:aps-modules/oc-line-protect:aps-module/oc-line-protect:ports/oc-line-protect:common-in/oc-line-protect:config/oc-line-protect:enabled" {
    deviate not-supported;
  }
  deviation "/oc-line-protect:aps/oc-line-protect:aps-modules/oc-line-protect:aps-module/oc-line-protect:ports/oc-line-protect:common-in/oc-line-protect:config/oc-line-protect:target-attenuation" {
    deviate not-supported;
  }
  deviation "/oc-line-protect:aps/oc-line-protect:aps-modules/oc-line-protect:aps-module/oc-line-protect:ports/oc-line-protect:common-in/oc-line-protect:state/oc-line-protect:enabled" {
    deviate not-supported;
  }
  deviation "/oc-line-protect:aps/oc-line-protect:aps-modules/oc-line-protect:aps-module/oc-line-protect:ports/oc-line-protect:common-in/oc-line-protect:state/oc-line-protect:target-attenuation" {
    deviate not-supported;
  }
  deviation "/oc-line-protect:aps/oc-line-protect:aps-modules/oc-line-protect:aps-module/oc-line-protect:ports/oc-line-protect:common-in/oc-line-protect:state/oc-line-protect:attenuation" {
    deviate not-supported;
  }
  deviation "/oc-line-protect:aps/oc-line-protect:aps-modules/oc-line-protect:aps-module/oc-line-protect:ports/oc-line-protect:common-in/oc-line-protect:state/oc-line-protect:optical-power/oc-line-protect:instant" {
    deviate not-supported;
  }
  deviation "/oc-line-protect:aps/oc-line-protect:aps-modules/oc-line-protect:aps-module/oc-line-protect:ports/oc-line-protect:common-in/oc-line-protect:state/oc-line-protect:optical-power/oc-line-protect:avg" {
    deviate not-supported;
  }
  deviation "/oc-line-protect:aps/oc-line-protect:aps-modules/oc-line-protect:aps-module/oc-line-protect:ports/oc-line-protect:common-in/oc-line-protect:state/oc-line-protect:optical-power/oc-line-protect:min" {
    deviate not-supported;
  }
  deviation "/oc-line-protect:aps/oc-line-protect:aps-modules/oc-line-protect:aps-module/oc-line-protect:ports/oc-line-protect:common-in/oc-line-protect:state/oc-line-protect:optical-power/oc-line-protect:max" {
    deviate not-supported;
  }
  deviation "/oc-line-protect:aps/oc-line-protect:aps-modules/oc-line-protect:aps-module/oc-line-protect:ports/oc-line-protect:common-in/oc-line-protect:state/oc-line-protect:optical-power/oc-line-protect:interval" {
    deviate not-supported;
  }
  deviation "/oc-line-protect:aps/oc-line-protect:aps-modules/oc-line-protect:aps-module/oc-line-protect:ports/oc-line-protect:common-in/oc-line-protect:state/oc-line-protect:optical-power/oc-line-protect:min-time" {
    deviate not-supported;
  }
  deviation "/oc-line-protect:aps/oc-line-protect:aps-modules/oc-line-protect:aps-module/oc-line-protect:ports/oc-line-protect:common-in/oc-line-protect:state/oc-line-protect:optical-power/oc-line-protect:max-time" {
    deviate not-supported;
  }
  deviation "/oc-line-protect:aps/oc-line-protect:aps-modules/oc-line-protect:aps-module/oc-line-protect:ports/oc-line-protect:common-output/oc-line-protect:config/oc-line-protect:target-attenuation" {
    deviate not-supported;
  }
  deviation "/oc-line-protect:aps/oc-line-protect:aps-modules/oc-line-protect:aps-module/oc-line-protect:ports/oc-line-protect:common-output/oc-line-protect:state/oc-line-protect:target-attenuation" {
    deviate not-supported;
  }
  deviation "/oc-line-protect:aps/oc-line-protect:aps-modules/oc-line-protect:aps-module/oc-line-protect:ports/oc-line-protect:common-output/oc-line-protect:state/oc-line-protect:attenuation" {
    deviate not-supported;
  }
  deviation "/oc-line-protect:aps/oc-line-protect:aps-modules/oc-line-protect:aps-module/oc-line-protect:ports/oc-line-protect:common-output/oc-line-protect:state/oc-line-protect:optical-power/oc-line-protect:interval" {
    deviate not-supported;
  }
  deviation "/oc-line-protect:aps/oc-line-protect:aps-modules/oc-line-protect:aps-module/oc-line-protect:ports/oc-line-protect:common-output/oc-line-protect:state/oc-line-protect:optical-power/oc-line-protect:min-time" {
    deviate not-supported;
  }
  deviation "/oc-line-protect:aps/oc-line-protect:aps-modules/oc-line-protect:aps-module/oc-line-protect:ports/oc-line-protect:common-output/oc-line-protect:state/oc-line-protect:optical-power/oc-line-protect:max-time" {
    deviate not-supported;
  }
}
