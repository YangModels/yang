module Cisco-IOS-XR-ipv4-hsrp-oper {
  namespace "http://cisco.com/ns/yang/Cisco-IOS-XR-ipv4-hsrp-oper";
  prefix ipv4-hsrp-oper;

  import ietf-inet-types {
    prefix inet;
  }
  import Cisco-IOS-XR-types {
    prefix xr;
  }
  include Cisco-IOS-XR-ipv4-hsrp-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-hsrp package operational data.
     
     This module contains definitions
     for the following management objects:
       hsrp: HSRP operational data
     
     Copyright (c) 2013-2018 by Cisco Systems, Inc.
     All rights reserved.";

  revision 2017-09-07 {
    description
      "Fixed type translation error.";
  }
  revision 2015-11-09 {
    description
      "IOS XR 6.0 revision.";
  }

  container hsrp {
    config false;
    description
      "HSRP operational data";
    container ipv4 {
      description
        "IPv4 HSRP information";
      container groups {
        description
          "The HSRP standby group table";
        list group {
          key "interface-name group-number";
          description
            "An HSRP standby group";
          leaf interface-name {
            type xr:Interface-name;
            description
              "The interface name";
          }
          leaf group-number {
            type uint32;
            description
              "The HSRP group number";
          }
          uses STANDBY-GRP-INFO;
        }
      }
      container tracked-interfaces {
        description
          "The HSRP tracked interfaces table";
        list tracked-interface {
          key "interface-name group-number tracked-interface-name";
          description
            "An HSRP tracked interface entry";
          leaf interface-name {
            type xr:Interface-name;
            description
              "The interface name of the interface";
          }
          leaf group-number {
            type uint32;
            description
              "The HSRP group number";
          }
          leaf tracked-interface-name {
            type xr:Interface-name;
            description
              "The interface name of the interface being
               tracked";
          }
          uses STANDBY-TRACKEDIF-INFO;
        }
      }
      container interfaces {
        description
          "The HSRP interface information table";
        list interface {
          key "interface-name";
          description
            "A HSRP interface entry";
          leaf interface-name {
            type xr:Interface-name;
            description
              "The interface name";
          }
          uses STANDBY-IF-INFO;
        }
      }
    }
    container mgo-sessions {
      description
        "HSRP MGO session table";
      list mgo-session {
        key "session-name";
        description
          "HSRP MGO session";
        leaf session-name {
          type xr:Cisco-ios-xr-string;
          description
            "HSRP MGO session name";
        }
        uses HSRP-MGO-INFO;
      }
    }
    container ipv6 {
      description
        "IPv6 HSRP information";
      container tracked-interfaces {
        description
          "The HSRP tracked interfaces table";
        list tracked-interface {
          key "interface-name group-number tracked-interface-name";
          description
            "An HSRP tracked interface entry";
          leaf interface-name {
            type xr:Interface-name;
            description
              "The interface name of the interface";
          }
          leaf group-number {
            type uint32;
            description
              "The HSRP group number";
          }
          leaf tracked-interface-name {
            type xr:Interface-name;
            description
              "The interface name of the interface being
               tracked";
          }
          uses STANDBY-TRACKEDIF-INFO;
        }
      }
      container groups {
        description
          "The HSRP standby group table";
        list group {
          key "interface-name group-number";
          description
            "An HSRP standby group";
          leaf interface-name {
            type xr:Interface-name;
            description
              "The interface name";
          }
          leaf group-number {
            type uint32;
            description
              "The HSRP group number";
          }
          uses STANDBY-GRP-INFO;
        }
      }
      container interfaces {
        description
          "The HSRP interface information table";
        list interface {
          key "interface-name";
          description
            "A HSRP interface entry";
          leaf interface-name {
            type xr:Interface-name;
            description
              "The interface name";
          }
          uses STANDBY-IF-INFO;
        }
      }
    }
    container bfd-sessions {
      description
        "The table of HSRP BFD Sessions";
      list bfd-session {
        key "interface-name ip-address";
        description
          "An HSRP BFD Session";
        leaf interface-name {
          type xr:Interface-name;
          description
            "The interface name";
        }
        leaf ip-address {
          type inet:ip-address-no-zone;
          description
            "Destination IP Address of BFD Session";
        }
        uses STANDBY-BFD-INFO;
      }
    }
    container summary {
      description
        "HSRP summary statistics";
      uses HSRP-SUMMARY-INFO;
    }
  }
}
