submodule Cisco-IOS-XR-spirit-install-instmgr-oper-sub2 {
  belongs-to Cisco-IOS-XR-spirit-install-instmgr-oper {
    prefix Cisco-IOS-XR-spirit-install-instmgr-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR spirit-install-instmgr package operational data.
     
     Copyright (c) 2013-2018 by Cisco Systems, Inc.
     All rights reserved.";

  revision 2019-08-24 {
    description
      "Changed model structure for software version and deprecated img-info node.";
  }
  revision 2017-09-07 {
    description
      "Fixed type translation error.";
  }
  revision 2017-07-24 {
    description
      "Fixing backward compatibility error in module.";
  }
  revision 2015-11-09 {
    description
      "IOS XR 6.0 revision.";
  }

  typedef Install-bag-optional-string {
    type string;
    description
      "Install bag optional string";
  }

  grouping CURRENT-INSTALL-OPERATION {
    description
      "Show install request info";
    leaf curr-inst-oper {
      type string;
      description
        "CurrInstOper";
    }
  }

  grouping VERSION-PACKAGE-LIST {
    description
      "creation of list of packages for show version";
    leaf name {
      type string;
      description
        "Name";
    }
    leaf version {
      type string;
      description
        "Running version";
    }
    leaf built-by {
      type string;
      description
        "User built by";
    }
    leaf built-on {
      type string;
      description
        "Time built";
    }
    leaf build-host {
      type string;
      description
        "Build host";
    }
    leaf workspace {
      type string;
      description
        "Workspace built in";
    }
  }

  grouping SHOW-VERSION-INFO {
    description
      "Show version info";
    leaf location {
      type Install-bag-optional-string;
      description
        "Path where all cisco packages are installed";
    }
    leaf label {
      type Install-bag-optional-string;
      description
        "label name";
    }
    leaf copyright-info {
      type string;
      description
        "copyright info";
    }
    leaf hardware-info {
      type string;
      description
        "hardware info of the router";
    }
    leaf system-uptime {
      type string;
      description
        "duration since when system is up";
    }
    leaf img-info {
      type string;
      description
        "this tag is deprecated";
    }
    list package {
      description
        "package";
      uses VERSION-PACKAGE-LIST;
    }
  }

  grouping INST-STRING-PTR {
    description
      "inst string ptr";
    leaf package {
      type string;
      description
        "package";
    }
  }

  grouping INSTMGR-SHOW-INSTALL-PREPARE {
    description
      "show install prepare";
    leaf no-prepare-done {
      type string;
      description
        "NoPrepareDone";
    }
    leaf prepared-boot-image {
      type string;
      description
        "PreparedBootImage";
    }
    leaf prepared-boot-partition {
      type string;
      description
        "PreparedBootPartition";
    }
    leaf restart-type {
      type string;
      description
        "RestartType";
    }
    leaf activate-message {
      type string;
      description
        "ActivateMessage";
    }
    leaf prepare-clean-message {
      type string;
      description
        "PrepareCleanMessage";
    }
    list rpm {
      description
        "rpm";
      uses INST-STRING-PTR;
    }
    list package {
      description
        "package";
      uses INST-STRING-PTR;
    }
  }

  grouping INSTMGR-CALV-SHOW-INST-ACT-ROW {
    description
      "calvados show install active";
    leaf error-message {
      type string;
      description
        "ErrorMessage";
    }
    leaf location {
      type string;
      description
        "Location";
    }
    leaf node-type {
      type string;
      description
        "NodeType";
    }
    leaf boot-partition-name {
      type string;
      description
        "BootPartitionName";
    }
    leaf number-of-active-packages {
      type uint32;
      description
        "NumberOfActivePackages";
    }
    leaf active-packages {
      type string;
      description
        "ActivePackages";
    }
  }

  grouping INSTMGR-CALV-SHOW-INST-ACT {
    description
      "Calvados show install active info";
    list active-package-info {
      description
        "active package info";
      uses INSTMGR-CALV-SHOW-INST-ACT-ROW;
    }
  }

  grouping INSTMGR-CALV-SHOW-INST-COMMIT-ROW {
    description
      "calvados show install committed";
    leaf error-message {
      type string;
      description
        "ErrorMessage";
    }
    leaf location {
      type string;
      description
        "Location";
    }
    leaf node-type {
      type string;
      description
        "NodeType";
    }
    leaf boot-partition-name {
      type string;
      description
        "BootPartitionName";
    }
    leaf number-of-committed-packages {
      type uint32;
      description
        "NumberOfCommittedPackages";
    }
    leaf committed-packages {
      type string;
      description
        "CommittedPackages";
    }
  }

  grouping INSTMGR-CALV-SHOW-INST-COMMIT {
    description
      "Calvados show install commit info";
    list committed-package-info {
      description
        "committed package info";
      uses INSTMGR-CALV-SHOW-INST-COMMIT-ROW;
    }
  }

  grouping INSTMGR-SHOW-INST-SUP-ROW {
    description
      "show install superseded";
    leaf error-message {
      type string;
      description
        "ErrorMessage";
    }
    leaf location {
      type string;
      description
        "Location";
    }
    leaf node-type {
      type string;
      description
        "NodeType";
    }
    leaf boot-partition-name {
      type string;
      description
        "BootPartitionName";
    }
    leaf superseded-packages {
      type string;
      description
        "SupersededPackages";
    }
    leaf number-of-packages {
      type uint32;
      description
        "NumberOfPackages";
    }
  }

  grouping INSTMGR-SHOW-INST-SUP {
    description
      " show install superseded info";
    list superseded-package-info {
      description
        "superseded package info";
      uses INSTMGR-SHOW-INST-SUP-ROW;
    }
  }

  grouping INSTALL-LOG {
    description
      "Install Log";
    leaf log {
      type string;
      description
        "log";
    }
  }
}
