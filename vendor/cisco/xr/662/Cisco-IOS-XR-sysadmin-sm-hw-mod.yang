module Cisco-IOS-XR-sysadmin-sm-hw-mod {
  namespace "http://www.cisco.com/ns/yang/Cisco-IOS-XR-sysadmin-sm-hw-mod";
  prefix shelf_sm_hw_mod;

  import tailf-common {
    prefix tailf;
  }
  import Cisco-IOS-XR-sysadmin-types {
    prefix calvados;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module holds Shelf Management HW module data.
     
     Copyright(c) 2012-2017 by Cisco Systems, Inc.
     All rights reserved.
     
     Copyright (c) 2012-2018 by Cisco Systems, Inc.
     All rights reserved.";

  revision 2017-04-12 {
    description
      "Changed namespace and module name";
  }

  grouping hw-module-config-group {
    uses hw-module-shutdown-config-group;
    uses hw-module-reset-auto-disable-config-group;
    uses hw-module-offline-config-group;
  }

  grouping hw-module-shutdown-config-group {
    container shutdown {
      list location {
        key "location";
        leaf location {
          type calvados:location-id;
          mandatory true;
        }
      }
    }
  }

  grouping hw-module-reset-auto-disable-config-group {
    container reset {
      container auto {
        container disable {
          list location {
            key "location";
            leaf location {
              type calvados:location-id;
              mandatory true;
            }
          }
        }
      }
    }
  }

  grouping hw-module-offline-config-group {
    container offline {
      list location {
        key "location";
        leaf location {
          type calvados:location-id;
          mandatory true;
        }
      }
    }
  }

  grouping hw-module-action-group {
    uses hw-module-reload-action-group;
    uses hw-module-bootmedia-action-group;
    uses hw-module-shutdown-action-group;
    uses hw-module-offline-action-group;
    uses hw-module-online-action-group;
  }

  grouping hw-module-bootmedia-action-group {
    container cbootmedia {
      config false;
      list bootmedia {
        key "bootmedium";
        config false;
        leaf bootmedium {
          type string;
        }
        tailf:action "reload" {
          output {
            leaf result {
              type string;
              mandatory true;
            }
          }
        }
      }
    }
  }

  grouping hw-module-reload-action-group {
    tailf:action "reload" {
      input {
        leaf force {
          type empty;
          mandatory false;
        }
        leaf noprompt {
          type empty;
          mandatory false;
        }
        leaf warm {
          type empty;
          mandatory false;
        }
      }
      output {
        leaf result {
          type string;
          mandatory true;
        }
      }
    }
  }

  grouping hw-module-shutdown-action-group {
    tailf:action "shutdown" {
      input {
        choice shutdown_polarity {
          mandatory false;
          case shutdown {
            leaf force {
              type empty;
              mandatory false;
            }
          }
          case powerup {
            leaf disable {
              type empty;
              mandatory false;
            }
          }
        }
      }
      output {
        leaf result {
          type string;
          mandatory true;
        }
      }
    }
  }

  grouping hw-module-offline-action-group {
    tailf:action "offline" {
      output {
        leaf result {
          type string;
          mandatory true;
        }
      }
    }
  }

  grouping hw-module-online-action-group {
    tailf:action "online" {
      output {
        leaf result {
          type string;
          mandatory true;
        }
      }
    }
  }
}
