module Cisco-IOS-XR-subscriber-srg-cfg {
  namespace "http://cisco.com/ns/yang/Cisco-IOS-XR-subscriber-srg-cfg";
  prefix subscriber-srg-cfg;

  import ietf-inet-types {
    prefix inet;
  }
  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-srg package configuration.
     
     This module contains definitions
     for the following management objects:
       subscriber-redundancy: Subscriber Redundancy configuration
     
     Copyright (c) 2013-2018 by Cisco Systems, Inc.
     All rights reserved.";

  revision 2017-09-07 {
    description
      "Fixed type translation error.";
  }
  revision 2015-11-09 {
    description
      "IOS XR 6.0 revision.";
  }

  typedef Subscriber-redundancy-group-slave-mode {
    type enumeration {
      enum "warm" {
        value 1;
        description
          "Warm Mode";
      }
      enum "hot" {
        value 2;
        description
          "Hot Mode";
      }
    }
    description
      "Subscriber redundancy group slave mode";
  }

  typedef Subscriber-redundancy-group-role {
    type enumeration {
      enum "master" {
        value 1;
        description
          "Master Role";
      }
      enum "slave" {
        value 2;
        description
          "Slave Role";
      }
    }
    description
      "Subscriber redundancy group role";
  }

  typedef Srg-addr-family {
    type enumeration {
      enum "ipv4" {
        value 2;
        description
          "IPv4";
      }
      enum "ipv6" {
        value 26;
        description
          "IPv6";
      }
    }
    description
      "Srg addr family";
  }

  container subscriber-redundancy {
    presence "Indicates a subscriber-redundancy node is configured.";
    description
      "Subscriber Redundancy configuration";
    container groups {
      description
        "Table of Group";
      list group {
        key "group-id";
        description
          "Redundancy Group configuration";
        container interface-list {
          presence "Indicates a interface-list node is configured.";
          description
            "List of Interfaces for this Group";
          container interfaces {
            description
              "Table of Interface";
            list interface {
              key "interface-name";
              description
                "Interface for this Group";
              leaf interface-name {
                type xr:Interface-name;
                description
                  "Interface name";
              }
              leaf interface-id {
                type uint32 {
                  range "1..65535";
                }
                mandatory true;
                description
                  "Interface Id for the interface";
              }
            }
          }
          container interface-ranges {
            description
              "Table of InterfaceRange";
            list interface-range {
              key "interface-name sub-interface-range-start sub-interface-range-end";
              description
                "Interface for this Group";
              leaf interface-name {
                type xr:Interface-name;
                description
                  "Interface name";
              }
              leaf sub-interface-range-start {
                type uint32 {
                  range "0..2147483647";
                }
                description
                  "Sub Interface Start Range";
              }
              leaf sub-interface-range-end {
                type uint32 {
                  range "0..2147483647";
                }
                description
                  "Sub Interface End Range";
              }
              leaf interface-id-range-start {
                type uint32 {
                  range "1..65535";
                }
                description
                  "Interface ID Start Range";
              }
              leaf interface-id-range-end {
                type uint32 {
                  range "1..65535";
                }
                description
                  "Interface ID End Range";
              }
            }
          }
          leaf enable {
            type empty;
            mandatory true;
            description
              "Enable List of Interfaces for this Group.
               Deletion of this object also causes deletion
               of all associated objects under InterfaceList
               .";
          }
        }
        container peer {
          description
            "None";
          container ipaddress {
            description
              "IPv4 or IPv6 Address of SRG Peer";
            leaf address-family {
              type Srg-addr-family;
              description
                "Type of IPv4/IPv6 address";
            }
            leaf prefix-string {
              type inet:ip-address-no-zone;
              description
                "IPv4/IPv6 address";
            }
          }
          leaf route-add-disable {
            type empty;
            description
              "Set Route add disable";
          }
        }
        container revertive-timer {
          description
            "None";
          leaf max-value {
            type uint32 {
              range "1..65535";
            }
            description
              "Value of MAX Revertive Timer";
          }
          leaf value {
            type uint32 {
              range "1..65535";
            }
            units "minute";
            description
              "Value of revertive time in minutes";
          }
        }
        container virtual-mac {
          description
            "Virtual MAC Address for this Group";
          leaf address {
            type yang:mac-address;
            description
              "Virtual MAC Address for this Group";
          }
          leaf disable {
            type empty;
            description
              "Disable Virtual MAC Address for this Group";
          }
        }
        container state-control-route {
          description
            "None";
          container ipv4-routes {
            description
              "Table of IPv4Route";
            list ipv4-route {
              key "vrfname prefix-length prefix-string";
              description
                "None";
              leaf vrfname {
                type xr:Cisco-ios-xr-string;
                description
                  "VRF name";
              }
              leaf prefix-length {
                type uint32;
                description
                  "Prefix of the IP Address";
              }
              leaf prefix-string {
                type inet:ip-address-no-zone;
                description
                  "IPv4 address with prefix-length";
              }
              leaf tagvalue {
                type uint32 {
                  range "1..4294967295";
                }
                mandatory true;
                description
                  "Tag value";
              }
            }
          }
          container ipv6-route {
            description
              "None";
            container ipv6na-routes {
              description
                "Table of IPv6NARoute";
              list ipv6na-route {
                key "vrfname prefix-length prefix-string";
                description
                  "None";
                leaf vrfname {
                  type xr:Cisco-ios-xr-string;
                  description
                    "VRF name";
                }
                leaf prefix-length {
                  type uint32;
                  description
                    "Prefix of the IP Address";
                }
                leaf prefix-string {
                  type inet:ip-address-no-zone;
                  description
                    "IPv6 address with prefix-length";
                }
                leaf tagvalue {
                  type uint32 {
                    range "1..4294967295";
                  }
                  mandatory true;
                  description
                    "Tag value";
                }
              }
            }
            container ipv6pd-routes {
              description
                "Table of IPv6PDRoute";
              list ipv6pd-route {
                key "vrfname prefix-length prefix-string";
                description
                  "None";
                leaf vrfname {
                  type xr:Cisco-ios-xr-string;
                  description
                    "VRF name";
                }
                leaf prefix-length {
                  type uint32;
                  description
                    "Prefix of the IP Address";
                }
                leaf prefix-string {
                  type inet:ip-address-no-zone;
                  description
                    "IPv6 address with prefix-length";
                }
                leaf tagvalue {
                  type uint32 {
                    range "1..4294967295";
                  }
                  mandatory true;
                  description
                    "Tag value";
                }
              }
            }
          }
        }
        leaf disable-tracking-object {
          type empty;
          description
            "Disable Tracking Object for this Group";
        }
        leaf core-tracking-object {
          type string;
          description
            "Core Tracking Object for this Group";
        }
        leaf enable {
          type empty;
          mandatory true;
          description
            "Enable Redundancy Group configuration.
             Deletion of this object also causes deletion
             of all associated objects under Group.";
        }
        leaf preferred-role {
          type Subscriber-redundancy-group-role;
          description
            "Set preferred role";
        }
        leaf description {
          type string;
          description
            "Description for this Group";
        }
        leaf l2tp-source-ip-address {
          type inet:ipv4-address-no-zone;
          description
            "Enter an IP address";
        }
        leaf slave-mode {
          type Subscriber-redundancy-group-slave-mode;
          description
            "Set Slave Mode";
        }
        leaf hold-timer {
          type uint32 {
            range "1..65535";
          }
          units "minute";
          description
            "Set hold time (in Minutes)";
        }
        leaf access-tracking-object {
          type string;
          description
            "Access Tracking Object for this Group";
        }
        leaf enable-fast-switchover {
          type empty;
          description
            "Enable fast switchover for this Group";
        }
        leaf redundancy-disable {
          type empty;
          description
            "Disable";
        }
        leaf group-id {
          type uint32 {
            range "1..4000";
          }
          description
            "Group ID";
        }
      }
    }
    container revertive-timer {
      description
        "None";
      leaf max-value {
        type uint32 {
          range "1..65535";
        }
        description
          "Value of MAX Revertive Timer";
      }
      leaf value {
        type uint32 {
          range "1..65535";
        }
        units "minute";
        description
          "Value of revertive time in minutes";
      }
    }
    leaf enable {
      type empty;
      mandatory true;
      description
        "Enable Subscriber Redundancy configuration.
         Deletion of this object also causes deletion of
         all associated objects under
         SubscriberRedundancy.";
    }
    leaf virtual-mac-prefix {
      type yang:mac-address;
      description
        "Virtual MAC Prefix for Subscriber Redundancy";
    }
    leaf preferred-role {
      type Subscriber-redundancy-group-role;
      description
        "Set preferred role";
    }
    leaf source-interface {
      type xr:Interface-name;
      description
        "Source Interface for Redundancy Peer
         Communication";
    }
    leaf slave-mode {
      type Subscriber-redundancy-group-slave-mode;
      description
        "Set slave";
    }
    leaf hold-timer {
      type uint32 {
        range "1..65535";
      }
      units "minute";
      description
        "Set hold time (in Minutes)";
    }
    leaf sync-timer {
      type uint32 {
        range "1..255";
      }
      units "minute";
      description
        "Set sync time (in Minutes)";
    }
    leaf redundancy-disable {
      type empty;
      description
        "Disable";
    }
  }
}
