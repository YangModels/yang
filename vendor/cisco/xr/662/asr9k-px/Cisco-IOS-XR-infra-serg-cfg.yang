module Cisco-IOS-XR-infra-serg-cfg {
  namespace "http://cisco.com/ns/yang/Cisco-IOS-XR-infra-serg-cfg";
  prefix infra-serg-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-serg package configuration.
     
     This module contains definitions
     for the following management objects:
       session-redundancy: Session Redundancy configuration
     
     Copyright (c) 2013-2018 by Cisco Systems, Inc.
     All rights reserved.";

  revision 2018-01-31 {
    description
      "Added pool-name support.";
  }
  revision 2015-11-09 {
    description
      "IOS XR 6.0 revision.";
  }

  typedef Session-redundancy-group-role {
    type enumeration {
      enum "master" {
        value 1;
        description
          "Master Role";
      }
      enum "slave" {
        value 2;
        description
          "Slave Role";
      }
    }
    description
      "Session redundancy group role";
  }

  typedef Serg-addr-family {
    type enumeration {
      enum "ipv4" {
        value 2;
        description
          "IPv4";
      }
      enum "ipv6" {
        value 26;
        description
          "IPv6";
      }
    }
    description
      "Serg addr family";
  }

  container session-redundancy {
    description
      "Session Redundancy configuration";
    container groups {
      description
        "Table of Group";
      list group {
        key "group-id";
        description
          "Redundancy Group configuration";
        container peer {
          description
            "None";
          container ipaddress {
            description
              "IPv4 or IPv6 Address of SERG Peer";
            leaf address-family {
              type Serg-addr-family;
              description
                "Type of IPv4/IPv6 address";
            }
            leaf prefix-string {
              type inet:ip-address-no-zone;
              description
                "IPv4/IPv6 address";
            }
          }
        }
        container revertive-timer {
          description
            "None";
          leaf max-value {
            type uint32 {
              range "1..65535";
            }
            description
              "Value of MAX Revertive Timer";
          }
          leaf value {
            type uint32 {
              range "1..65535";
            }
            units "minute";
            description
              "Value of revertive time in minutes";
          }
        }
        container interface-list {
          description
            "List of Interfaces for this Group";
          container interface-ranges {
            description
              "Table of InterfaceRange";
            list interface-range {
              key "interface-name sub-interface-range-start sub-interface-range-end";
              description
                "Interface for this Group";
              leaf interface-name {
                type xr:Interface-name;
                description
                  "Interface name";
              }
              leaf sub-interface-range-start {
                type uint32 {
                  range "0..2147483647";
                }
                description
                  "Sub Interface Start Range";
              }
              leaf sub-interface-range-end {
                type uint32 {
                  range "0..2147483647";
                }
                description
                  "Sub Interface End Range";
              }
              leaf interface-id-range-start {
                type uint32 {
                  range "1..65535";
                }
                description
                  "Interface ID Start Range";
              }
              leaf interface-id-range-end {
                type uint32 {
                  range "1..65535";
                }
                description
                  "Interface ID End Range";
              }
            }
          }
          container interfaces {
            description
              "Table of Interface";
            list interface {
              key "interface-name";
              description
                "Interface for this Group";
              leaf interface-name {
                type xr:Interface-name;
                description
                  "Interface name";
              }
              leaf interface-id {
                type uint32 {
                  range "1..65535";
                }
                mandatory true;
                description
                  "Interface Id for the interface";
              }
            }
          }
          leaf enable {
            type empty;
            description
              "Enable List of Interfaces for this Group.
               Deletion of this object also causes deletion
               of all associated objects under InterfaceList
               .";
          }
        }
        container pool-list {
          description
            "List of Pool-names for this Group";
          container pool-names {
            description
              "Table of PoolName";
            list pool-name {
              key "pool-name";
              description
                "Address Pool Name";
              leaf pool-name {
                type xr:Cisco-ios-xr-string;
                description
                  "Pool name";
              }
            }
          }
          leaf enable {
            type empty;
            description
              "Enable List of Pool-names for this Group.
               Deletion of this object also causes deletion
               of all associated objects under PoolList.";
          }
        }
        leaf core-tracking-object {
          type string;
          description
            "Core Tracking Object for this Group";
        }
        leaf disable-tracking-object {
          type empty;
          description
            "Disable Tracking Object for this Group";
        }
        leaf redundancy-disable {
          type empty;
          description
            "Disable";
        }
        leaf enable {
          type empty;
          description
            "Enable Redundancy Group configuration.
             Deletion of this object also causes deletion
             of all associated objects under Group.";
        }
        leaf description {
          type string;
          description
            "Description for this Group";
        }
        leaf access-tracking-object {
          type string;
          description
            "Access Tracking Object for this Group";
        }
        leaf preferred-role {
          type Session-redundancy-group-role;
          description
            "Set preferred role";
        }
        leaf hold-timer {
          type uint32 {
            range "1..65535";
          }
          units "minute";
          description
            "Set hold time (in Minutes)";
        }
        leaf mode-active {
          type empty;
          description
            "Set operation mode";
        }
        leaf group-id {
          type uint32 {
            range "1..500";
          }
          description
            "Group ID";
        }
      }
    }
    container revertive-timer {
      description
        "None";
      leaf max-value {
        type uint32 {
          range "1..65535";
        }
        description
          "Value of MAX Revertive Timer";
      }
      leaf value {
        type uint32 {
          range "1..65535";
        }
        units "minute";
        description
          "Value of revertive time in minutes";
      }
    }
    leaf redundancy-disable {
      type empty;
      description
        "Disable";
    }
    leaf enable {
      type empty;
      description
        "Enable Session Redundancy configuration.
         Deletion of this object also causes deletion of
         all associated objects under SessionRedundancy.";
    }
    leaf source-interface {
      type xr:Interface-name;
      description
        "Source Interface for Redundancy Peer
         Communication";
    }
    leaf preferred-role {
      type Session-redundancy-group-role;
      description
        "Set preferred role";
    }
    leaf hold-timer {
      type uint32 {
        range "1..65535";
      }
      units "minute";
      description
        "Set hold time (in Minutes)";
    }
  }
}
