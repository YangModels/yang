module openconfig-platform-fan {
  yang-version 1;
  namespace "http://openconfig.net/yang/platform/fan";
  prefix oc-fan;

  import openconfig-platform {
    prefix oc-platform;
  }
  import openconfig-extensions {
    prefix oc-ext;
  }

  organization
    "OpenConfig working group";
  contact
    "OpenConfig working group
     www.openconfig.net";
  description
    "This module defines data related to FAN components in the
     OpenConfig platform model.";

  revision 2018-01-18 {
    description
      "Initial revision";
    reference "0.1.0";
  }

  grouping fan-state {
    description
      "Operational state data for fan components";
    leaf speed {
      type uint32;
      units "rpm";
      description
        "Current (instantaneous) fan speed";
    }
  }

  augment "/oc-platform:components/oc-platform:component/oc-platform:fan/oc-platform:state" {
    description
      "Adding fan data to component model";
    uses fan-state;
  }
  oc-ext:openconfig-version "0.1.0";
}
