module Cisco-IOS-XR-ikev2-cfg {
  namespace "http://cisco.com/ns/yang/Cisco-IOS-XR-ikev2-cfg";
  prefix ikev2-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ikev2 package configuration.
     
     This module contains definitions
     for the following management objects:
       ikev2: Internet key exchange(IKEv2) config commands
     
     Copyright (c) 2013-2018 by Cisco Systems, Inc.
     All rights reserved.";

  revision 2015-11-09 {
    description
      "IOS XR 6.0 revision.";
  }

  container ikev2 {
    description
      "Internet key exchange(IKEv2) config commands";
    container keyring-names {
      description
        "IKEv2 keyring config commands";
      list keyring-name {
        key "name";
        description
          "IKEv2 keyring name";
        container peer-names {
          description
            "IKEv2 keyring peer config commands";
          list peer-name {
            key "name";
            description
              "IKEv2 keyring peer name";
            container address {
              description
                "IP Address to identify the peer";
              leaf ip {
                type inet:ipv4-address-no-zone;
                description
                  "IP Address";
              }
              leaf subnet {
                type inet:ipv4-address-no-zone;
                description
                  "Subnet";
              }
            }
            container psk {
              description
                "Pre-shared key for peer";
              container local-remote-key {
                description
                  "Local/Remote pre-shared key for the peer";
                leaf string-xr {
                  type xr:Proprietary-password;
                  description
                    "Local pre-shared key";
                }
                leaf string {
                  type xr:Proprietary-password;
                  description
                    "Remote pre-shared key";
                }
              }
              leaf both-key {
                type xr:Proprietary-password;
                description
                  "Both pre-shared key for the peer";
              }
            }
            leaf peer-sub {
              type empty;
              description
                "This indicates existence of keyring-peer";
            }
            leaf name {
              type xr:Cisco-ios-xr-string {
                length "1..32";
              }
              description
                "Name of the keyring-peer";
            }
          }
        }
        leaf keyring-sub {
          type empty;
          description
            "This indicated existence of keyring";
        }
        leaf name {
          type xr:Cisco-ios-xr-string {
            length "1..32";
          }
          description
            "Name of the keyring";
        }
      }
    }
    container profile-names {
      description
        "IKEv2 profile config commands";
      list profile-name {
        key "name";
        description
          "IKEv2 profile name";
        container match-identity {
          description
            "Match a profile based on remote identity";
          container address-subs {
            description
              "Match a profile based on remote identity
               address";
            list address-sub {
              key "address";
              description
                "Remote ip address for matching identity";
              leaf address-sub-val {
                type empty;
                description
                  "This indicates existence of remote ip
                   address";
              }
              leaf address {
                type inet:ipv4-address-no-zone;
                description
                  "Address";
              }
              leaf mask {
                type inet:ipv4-address-no-zone;
                description
                  "Mask";
              }
            }
          }
          leaf any {
            type empty;
            description
              "Match any peer identity";
          }
        }
        container dpd {
          description
            "Enable IKEv2 liveliness for peers";
          leaf interval {
            type uint32 {
              range "10..3600";
            }
            description
              "Interval(in sec)";
          }
          leaf retry-time {
            type uint32 {
              range "2..60";
            }
            description
              "Retry interval(in sec)";
          }
        }
        leaf profile-sub {
          type empty;
          description
            "This indicates existence of profile";
        }
        leaf lifetime {
          type uint32 {
            range "120..86400";
          }
          description
            "Lifetime(in sec) for IKEv2 SA";
        }
        leaf keyring-in-profile {
          type xr:Cisco-ios-xr-string {
            length "1..32";
          }
          description
            "Keyring to use with local/remote
             authentication method";
        }
        leaf name {
          type xr:Cisco-ios-xr-string {
            length "1..32";
          }
          description
            "Name of the profile";
        }
      }
    }
    container policy-names {
      description
        "Configure IKEv2 policies";
      list policy-name {
        key "name";
        description
          "IKEv2 policy name";
        container address-vals {
          description
            "Match a policy based on address";
          list address-val {
            key "address";
            description
              "local address used to match policy";
            leaf address {
              type inet:ipv4-address-no-zone;
              description
                "Address";
            }
          }
        }
        leaf proposal-in-policy {
          type xr:Cisco-ios-xr-string {
            length "1..32";
          }
          description
            "Proposal to use with configured policy";
        }
        leaf policy-sub {
          type empty;
          description
            "This indicates existence of policy";
        }
        leaf name {
          type xr:Cisco-ios-xr-string {
            length "1..32";
          }
          description
            "Policy name";
        }
      }
    }
    container proposal-names {
      description
        "Configure IKEv2 proposals";
      list proposal-name {
        key "name";
        description
          "IKEv2 proposal name";
        container prfses {
          description
            "Specify one or more transforms of prf";
          leaf-list prfs {
            type string {
              length "1..8";
            }
            max-elements "4";
            description
              "PRF Algorithm";
          }
        }
        container groups {
          description
            "Specify one or more transforms of group";
          leaf-list group {
            type string {
              length "1..3";
            }
            max-elements "8";
            description
              "Encryption Algorithm";
          }
        }
        container integrities {
          description
            "Specify one or more transforms of integrity";
          leaf-list integrity {
            type string {
              length "1..8";
            }
            max-elements "4";
            description
              "Integrity Algorithm";
          }
        }
        container encryptions {
          description
            "Specify one or more transforms of encryption";
          leaf-list encryption {
            type string {
              length "1..12";
            }
            max-elements "5";
            description
              "Encryption Algorithm";
          }
        }
        leaf proposal-sub {
          type empty;
          description
            "This indicates existence of proposal";
        }
        leaf name {
          type xr:Cisco-ios-xr-string {
            length "1..32";
          }
          description
            "Proposal name";
        }
      }
    }
  }
}
