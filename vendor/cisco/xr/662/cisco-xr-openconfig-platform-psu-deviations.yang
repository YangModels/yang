module cisco-xr-openconfig-platform-psu-deviations {
  namespace "http://cisco.com/ns/yang/cisco-xr-openconfig-platform-psu-deviations";
  prefix oc-platform-psudevs;

  import openconfig-platform-psu {
    prefix oc-platform-psu;
  }
  import openconfig-platform {
    prefix oc-platform;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for 
      
     openconfig-platform-psu.yang@2018-01-16 
     
     on Cisco IOS-XR devices.
     
     Copyright (c) 2017-2019 by Cisco Systems, Inc.
     All rights reserved.";

  revision 2018-12-10 {
    description
      "Initial revision applicable to IOS-XR 6.6.1";
  }

  deviation "/oc-platform:components/oc-platform:component/oc-platform:power-supply/oc-platform:config/oc-platform-psu:enabled" {
    deviate not-supported;
  }
}
