submodule Cisco-IOS-XR-ipv4-ospf-oper-sub3 {
  belongs-to Cisco-IOS-XR-ipv4-ospf-oper {
    prefix Cisco-IOS-XR-ipv4-ospf-oper;
  }

  import ietf-inet-types {
    prefix inet;
  }
  import ietf-yang-types {
    prefix yang;
  }
  import Cisco-IOS-XR-types {
    prefix xr;
  }
  include Cisco-IOS-XR-ipv4-ospf-oper-sub2 {
    revision-date 2018-04-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-ospf package operational data.
     
     Copyright (c) 2013-2018 by Cisco Systems, Inc.
     All rights reserved.";

  revision 2018-04-18 {
    description
      "Added keychain name to be displayed in show ospf interface bag";
  }
  revision 2017-10-26 {
    description
      "Fixed some field name and values for better interpretation";
  }
  revision 2017-09-07 {
    description
      "Fixed type translation error.";
  }
  revision 2017-05-01 {
    description
      "Fixing backward compatibility error in module.";
  }
  revision 2017-01-02 {
    description
      "IOS XR 6.2.1 revision.";
  }
  revision 2015-11-09 {
    description
      "IOS XR 6.0 revision.";
  }

  typedef Ospf-string-array {
    type string;
    description
      "Ospf string array";
  }

  grouping OSPF-SH-IF-STATS-ENTRY {
    description
      "OSPF interface entry for statistics";
    leaf madj-intf {
      type boolean;
      description
        "OSPF madj interface";
    }
    leaf area-id {
      type uint32;
      description
        "OSPF area id";
    }
    leaf area-id-str {
      type string;
      description
        "OSPF aread id string";
    }
    list if-stat {
      description
        "OSPF interface statistics";
      leaf entry {
        type uint32;
        description
          "OSPF interface statistics";
      }
    }
  }

  grouping OSPF-SH-IF-STATS {
    description
      "OSPF interface statistics";
    leaf handle {
      type xr:Interface-name;
      description
        "interface handle type";
    }
    leaf if-name-str {
      type string;
      description
        "interface name";
    }
    list if-entry {
      description
        "interface entry";
      uses OSPF-SH-IF-STATS-ENTRY;
    }
  }

  grouping OSPF-SH-RAW-STATS {
    description
      "OSPF SH RAW STATS";
    leaf out-sent {
      type uint32;
      description
        "out sent";
    }
    leaf out-bytes-sent {
      type uint32;
      description
        "out bytes sent";
    }
    leaf out-no-conn-discarded {
      type uint32;
      description
        "out no conn discarded";
    }
    leaf out-null-src-discarded {
      type uint32;
      description
        "out null src discarded";
    }
    leaf out-no-pak-discarded {
      type uint32;
      description
        "out no pak discarded";
    }
    leaf out-ipv4-hdr-err-discarded {
      type uint32;
      description
        "out ipv4 hdr err discarded";
    }
    leaf out-send-pak-err-discarded {
      type uint32;
      description
        "out send pak err discarded";
    }
    leaf in-rcv {
      type uint32;
      description
        "in rcv";
    }
    leaf in-bytes-rcv {
      type uint32;
      description
        "in bytes rcv";
    }
    leaf in-short-msg-discarded {
      type uint32;
      description
        "in short msg discarded";
    }
    leaf in-no-mem-discarded {
      type uint32;
      description
        "in no mem discarded";
    }
    leaf in-raw-event {
      type uint32;
      description
        "in raw event";
    }
    leaf disconnects {
      type uint32;
      description
        "disconnects";
    }
    leaf in-standby-discarded {
      type uint32;
      description
        "in standby discarded";
    }
    leaf nsr-not-ready-discarded {
      type uint32;
      description
        "nsr not ready discarded";
    }
    leaf raw-connected {
      type boolean;
      description
        "raw connected";
    }
    leaf sl-raw-connected {
      type boolean;
      description
        "sl raw connected";
    }
  }

  grouping OSPF-SH-PROTOPKT-STATS {
    description
      "OSPF SH PROTOPKT STATS";
    leaf inputs {
      type uint32;
      description
        "inputs";
    }
    leaf input-hello {
      type uint32;
      description
        "input hello";
    }
    leaf input-dbdes {
      type uint32;
      description
        "input dbdes";
    }
    leaf input-dbdes-lsa {
      type uint32;
      description
        "input dbdes lsa";
    }
    leaf input-req {
      type uint32;
      description
        "input req";
    }
    leaf input-req-lsa {
      type uint32;
      description
        "input req lsa";
    }
    leaf input-lsupd {
      type uint32;
      description
        "input lsupd";
    }
    leaf input-lsupd-lsa {
      type uint32;
      description
        "input lsupd lsa";
    }
    leaf input-ack {
      type uint32;
      description
        "input ack";
    }
    leaf input-ack-lsa {
      type uint32;
      description
        "input ack lsa";
    }
    leaf checksumerr {
      type uint32;
      description
        "checksumerr";
    }
    leaf input-autherr {
      type uint32;
      description
        "input autherr";
    }
    leaf outputs {
      type uint32;
      description
        "outputs";
    }
    leaf output-hello {
      type uint32;
      description
        "output hello";
    }
    leaf output-dbdes {
      type uint32;
      description
        "output dbdes";
    }
    leaf output-dbdes-lsa {
      type uint32;
      description
        "output dbdes lsa";
    }
    leaf output-req {
      type uint32;
      description
        "output req";
    }
    leaf output-req-lsa {
      type uint32;
      description
        "output req lsa";
    }
    leaf output-lsupd {
      type uint32;
      description
        "output lsupd";
    }
    leaf output-lsupd-lsa {
      type uint32;
      description
        "output lsupd lsa";
    }
    leaf output-ack {
      type uint32;
      description
        "output ack";
    }
    leaf output-ack-lsa {
      type uint32;
      description
        "output ack lsa";
    }
    leaf output-autherr {
      type uint32;
      description
        "output autherr";
    }
    leaf h-input-dbdes {
      type uint32;
      description
        "h input dbdes";
    }
    leaf h-input-req {
      type uint32;
      description
        "h input req";
    }
    leaf h-input-lsupd {
      type uint32;
      description
        "h input lsupd";
    }
    leaf h-input-ack {
      type uint32;
      description
        "h input ack";
    }
  }

  grouping OSPF-SH-TE-STATS {
    description
      "OSPF SH TE STATS";
    leaf te-connected {
      type boolean;
      description
        "te connected";
    }
    leaf control-disconnects {
      type uint32;
      description
        "control disconnects";
    }
    leaf te-disconnects {
      type uint32;
      description
        "te disconnects";
    }
    leaf adj-gets {
      type uint32;
      description
        "adj gets";
    }
    leaf link-floods {
      type uint32;
      description
        "link floods";
    }
    leaf link-fragment-floods {
      type uint32;
      description
        "link fragment floods";
    }
    leaf lsp-gets {
      type uint32;
      description
        "lsp gets";
    }
    leaf tunnel-announces {
      type uint32;
      description
        "tunnel announces";
    }
    leaf total-tunnels {
      type uint32;
      description
        "total tunnels";
    }
    leaf control-batch-reads {
      type uint32;
      description
        "control batch reads";
    }
    leaf control-batch-writes {
      type uint32;
      description
        "control batch writes";
    }
    leaf link-batch-reads {
      type uint32;
      description
        "link batch reads";
    }
    leaf link-batch-writes {
      type uint32;
      description
        "link batch writes";
    }
    leaf adj-changes {
      type uint32;
      description
        "adj changes";
    }
    leaf fragment-deletes {
      type uint32;
      description
        "fragment deletes";
    }
    leaf fragment-announces {
      type uint32;
      description
        "fragment announces";
    }
    leaf data-trans-completes {
      type uint32;
      description
        "data trans completes";
    }
    leaf pce-listen {
      type uint32;
      description
        "pce listen";
    }
    leaf pce-stoplisten {
      type uint32;
      description
        "pce stoplisten";
    }
    leaf pce-flood {
      type uint32;
      description
        "pce flood";
    }
    leaf pce-get {
      type uint32;
      description
        "pce get";
    }
    leaf pce-br-lookup {
      type uint32;
      description
        "pce br lookup";
    }
    leaf pce-br-lkup-num-dests {
      type uint32;
      description
        "pce br lkup num dests";
    }
    leaf pce-br-resp-fails {
      type uint32;
      description
        "pce br resp fails";
    }
    leaf pce-node-announce-batches {
      type uint32;
      description
        "pce node announce batches";
    }
    leaf pce-node-delete-batches {
      type uint32;
      description
        "pce node delete batches";
    }
    leaf pce-num-node-announce {
      type uint32;
      description
        "pce num node announce";
    }
    leaf pce-num-node-delete {
      type uint32;
      description
        "pce num node delete";
    }
    leaf pce-node-send-fails {
      type uint32;
      description
        "pce node send fails";
    }
    leaf te-sr-path-reg-idt-recvd {
      type boolean;
      description
        "te sr path reg idt recvd";
    }
    leaf te-sr-idt-sent {
      type boolean;
      description
        "te sr idt sent";
    }
    leaf sr-num-area-enabled {
      type uint32;
      description
        "sr num area enabled";
    }
  }

  grouping OSPF-SH-IPFRR-STATS {
    description
      "OSPF SH IPFRR STATS";
    leaf fs-paths {
      type uint32;
      description
        "Number of IPFRR paths";
    }
    leaf fs-paths-eligible {
      type uint32;
      description
        "Number of paths enabled for protection";
    }
    leaf fs-paths-protected {
      type uint32;
      description
        "Number of paths protected";
    }
  }

  grouping NSR-PL-RECV-DROP-ARRAY {
    description
      "NSR PL RECV DROP ARRAY";
    list nsr-pl-recv-drop-array {
      max-elements "16";
      description
        "nsr pl recv drop array";
      leaf entry {
        type uint32;
        description
          "nsr pl recv drop array";
      }
    }
  }

  grouping NSR-PL-SEND-DROP-ARRAY {
    description
      "NSR PL SEND DROP ARRAY";
    list nsr-pl-send-drop-array {
      max-elements "7";
      description
        "nsr pl send drop array";
      leaf entry {
        type uint32;
        description
          "nsr pl send drop array";
      }
    }
  }

  grouping NSR-PL-CLIENT-STATS-TYPE {
    description
      "NSR PL stats information";
    list num-sent {
      max-elements "5";
      description
        "Total sent";
      leaf entry {
        type uint64;
        description
          "Total sent";
      }
    }
    list num-recv {
      max-elements "6";
      description
        "Total recvd";
      leaf entry {
        type uint64;
        description
          "Total recvd";
      }
    }
    list num-sent-drop {
      max-elements "5";
      description
        "Sent Error/drops";
      uses NSR-PL-SEND-DROP-ARRAY;
    }
    list num-recv-drop {
      max-elements "6";
      description
        "Recv Errors/drops";
      uses NSR-PL-RECV-DROP-ARRAY;
    }
  }

  grouping OSPF-SH-NCD-STATS {
    description
      "OSPF SH NCD STATS";
    list ncd-pri {
      max-elements "2";
      description
        "ncd pri";
      uses NSR-PL-CLIENT-STATS-TYPE;
    }
  }

  grouping OSPF-SH-STATS-RIB-THREAD {
    description
      "OSPF SH STATS RIB THREAD";
    container rib-base-time {
      description
        "rib base time";
      uses BAG-TIMESPEC;
    }
    leaf wq-thread-active {
      type boolean;
      description
        "wq thread active";
    }
    leaf wq-dqtime {
      type uint64;
      description
        "wq dqtime";
    }
    leaf wqe-qtime {
      type uint64;
      description
        "wqe qtime";
    }
    leaf wq-len-cur {
      type int32;
      description
        "wq len cur";
    }
    leaf wq-len-max {
      type int32;
      description
        "wq len max";
    }
    leaf wq-total-queued {
      type uint32;
      description
        "wq total queued";
    }
    leaf wq-total-dequeued {
      type uint32;
      description
        "wq total dequeued";
    }
    leaf rib-version {
      type uint32;
      description
        "rib version";
    }
    leaf rib-pkts-sent {
      type uint32;
      description
        "rib pkts sent";
    }
    leaf rib-signals {
      type uint32;
      description
        "rib signals";
    }
    leaf rib-send-errs {
      type uint32;
      description
        "rib send errs";
    }
    leaf rib-queue-errs {
      type uint32;
      description
        "rib queue errs";
    }
    leaf rib-pfx-limit-errs {
      type uint32;
      description
        "rib pfx limit errs";
    }
    leaf rib-dequeue-errs {
      type uint32;
      description
        "rib dequeue errs";
    }
    leaf rib-empty-batches {
      type uint32;
      description
        "rib empty batches";
    }
    leaf rib-drop-before {
      type uint32;
      description
        "rib drop before";
    }
    leaf rib-drop-after {
      type uint32;
      description
        "rib drop after";
    }
    leaf rib-drop-conn {
      type uint32;
      description
        "rib drop conn";
    }
    leaf rib-table-not-created {
      type uint32;
      description
        "rib table not created";
    }
    leaf priority-level {
      type string {
        length "0..40";
      }
      description
        "priority level";
    }
    leaf rib-base-clock {
      type uint64;
      description
        "rib base clock";
    }
  }

  grouping OSPF-SH-STATS-WORK-QUEUES {
    description
      "OSPF SH STATS WORK QUEUES";
    container internalwq {
      description
        "internalwq";
      uses OSPF-SH-STATS-RIB-THREAD;
    }
    list ribqueue {
      max-elements "8";
      description
        "ribqueue";
      uses OSPF-SH-STATS-RIB-THREAD;
    }
  }

  grouping BAG-TIMESPEC {
    description
      "BAG TIMESPEC";
    leaf second {
      type uint32;
      description
        "Second";
    }
    leaf nanosecond {
      type uint32;
      description
        "Nanosecond";
    }
  }

  grouping OSPF-NSR-ERR-INFO-BAG {
    description
      "OSPF NSR ERR INFO BAG";
    container last-err-time {
      description
        "Time this error was last hit";
      uses BAG-TIMESPEC;
    }
    leaf err-count {
      type int32;
      description
        "Count this error hit during the Nsr Revision";
    }
    leaf err-info-string {
      type string;
      description
        "Error Information";
    }
  }

  grouping OSPF-NSR-ERR-BLOCK-BAG {
    description
      "OSPF NSR ERR BLOCK BAG";
    leaf nsr-revisionversion {
      type uint32;
      description
        "Nsr Revision version";
    }
    leaf total-errors {
      type int32;
      description
        "Total errors for this nsr revision version";
    }
    list nsr-error-info {
      description
        "List of erros";
      uses OSPF-NSR-ERR-INFO-BAG;
    }
  }

  grouping OSPF-ISSU-MILESTONE-BAG {
    description
      "OSPF ISSU MILESTONE BAG";
    leaf milestone-name {
      type string;
      description
        "Milestone Name";
    }
    leaf milestone-status {
      type string;
      description
        "Milestone Status";
    }
  }

  grouping OSPF-SH-NSR-STATS-PRI {
    description
      "OSPF SH NSR STATS PRI";
    leaf nsr-sched-pri {
      type uint32;
      description
        "nsr sched pri";
    }
    leaf nsr-sched-quant {
      type uint8;
      description
        "nsr sched quant";
    }
    leaf nsr-sched-remain-quant {
      type uint8;
      description
        "nsr sched remain quant";
    }
    leaf nsr-sched-evs-in-q {
      type uint16;
      description
        "nsr sched evs in q";
    }
    leaf nsr-sched-max-evs {
      type uint16;
      description
        "nsr sched max evs";
    }
    leaf nsr-sched-peak-q-len {
      type uint16;
      description
        "nsr sched peak q len";
    }
    leaf nsr-sched-evs-qd {
      type uint64;
      description
        "nsr sched evs qd";
    }
    leaf nsr-sched-enq-fails {
      type uint64;
      description
        "nsr sched enq fails";
    }
    leaf nsr-sched-evs-deqd {
      type uint64;
      description
        "nsr sched evs deqd";
    }
  }

  grouping OSPF-SH-NSR-SCHED-STATS {
    description
      "OSPF SH NSR SCHED STATS";
    leaf nsr-pulse-quant {
      type int32;
      description
        "nsr pulse quant";
    }
    leaf nsr-events-in-q {
      type uint32;
      description
        "nsr events in q";
    }
    leaf nsr-events-tx {
      type uint64;
      description
        "nsr events tx";
    }
    leaf nsr-events-rx {
      type uint64;
      description
        "nsr events rx";
    }
    leaf nsr-bad-pulses-rx {
      type uint64;
      description
        "nsr bad pulses rx";
    }
    leaf nsr-good-pulses-rx {
      type uint64;
      description
        "nsr good pulses rx";
    }
    leaf nsr-pulses-tx {
      type uint64;
      description
        "nsr pulses tx";
    }
    leaf nsr-pulse-tx-fails {
      type uint64;
      description
        "nsr pulse tx fails";
    }
    list nsr-pri {
      max-elements "3";
      description
        "nsr pri";
      uses OSPF-SH-NSR-STATS-PRI;
    }
  }

  grouping OSPF-SH-NSR-STATS {
    description
      "OSPF SH NSR STATS";
    container nsr-thd-sched {
      description
        "nsr thd sched";
      uses OSPF-SH-NSR-SCHED-STATS;
    }
    container nsr-rtr-thd-sched {
      description
        "nsr rtr thd sched";
      uses OSPF-SH-NSR-SCHED-STATS;
    }
    leaf nsr-rev {
      type int32;
      description
        "nsr rev";
    }
    leaf nsr-fsm-state {
      type int32;
      description
        "nsr fsm state";
    }
    leaf nsr-version {
      type uint32;
      description
        "nsr version";
    }
    leaf nsr-nodeid {
      type uint32;
      description
        "nsr nodeid";
    }
    leaf nsr-peer-version {
      type uint32;
      description
        "nsr peer version";
    }
    leaf nsr-peer-nodeid {
      type uint32;
      description
        "nsr peer nodeid";
    }
    leaf nsr-peer-ep-len {
      type uint32;
      description
        "nsr peer ep len";
    }
    leaf nsr-peer-ep-version {
      type uint32;
      description
        "nsr peer ep version";
    }
    leaf nsr-local-ep-len {
      type uint32;
      description
        "nsr local ep len";
    }
    leaf nsr-local-ep-version {
      type uint32;
      description
        "nsr local ep version";
    }
    leaf nsr-fabric-mtu {
      type uint32;
      description
        "nsr fabric mtu";
    }
    leaf nsr-nbr-qad-qid {
      type uint32;
      description
        "nsr nbr qad qid";
    }
    leaf nsr-lsa-qad-qid {
      type uint32;
      description
        "nsr lsa qad qid";
    }
    leaf nsr-nbr-qad-mdata-count {
      type uint32;
      description
        "nsr nbr qad mdata count";
    }
    leaf nsr-lsa-qad-mdata-count {
      type uint32;
      description
        "nsr lsa qad mdata count";
    }
    leaf nsr-nbr-init-sync-pend-count {
      type int32;
      description
        "nsr nbr init sync pend count";
    }
    leaf nsr-lsa-init-sync-pend-count {
      type int32;
      description
        "nsr lsa init sync pend count";
    }
    leaf nsr-nbr-seq-no {
      type uint32;
      description
        "nsr nbr seq no";
    }
    leaf nsr-intf-seq-no {
      type uint32;
      description
        "nsr intf seq no";
    }
    leaf nsr-tmr-quant {
      type int32;
      description
        "nsr tmr quant";
    }
    leaf nsr-peer-ds-hdl {
      type uint64;
      description
        "nsr peer ds hdl";
    }
    leaf nsr-local-ds-hdl {
      type uint64;
      description
        "nsr local ds hdl";
    }
    leaf nsr-conn-to-active-attempts {
      type uint64;
      description
        "nsr conn to active attempts";
    }
    leaf nsr-conn-to-active-fails {
      type uint64;
      description
        "nsr conn to active fails";
    }
    leaf nsr-conn-to-active-opens {
      type uint64;
      description
        "nsr conn to active opens";
    }
    leaf nsr-conn-to-active-closes {
      type uint64;
      description
        "nsr conn to active closes";
    }
    leaf nsr-conn-to-active-errors {
      type uint64;
      description
        "nsr conn to active errors";
    }
    leaf nsr-peer-ep {
      type yang:hex-string;
      description
        "nsr peer ep";
    }
    leaf nsr-local-ep {
      type yang:hex-string;
      description
        "nsr local ep";
    }
    list nsr-fsm-flag {
      description
        "Nsr Fsm Flags information";
      leaf entry {
        type Ospf-string-array;
        description
          "Nsr Fsm Flags information";
      }
    }
    list nsr-fsm-running-timer {
      description
        "Nsr Fsm Running Timers";
      leaf entry {
        type Ospf-string-array;
        description
          "Nsr Fsm Running Timers";
      }
    }
    list nsr-issu-milestone {
      description
        "Nsr Issu Milestones";
      uses OSPF-ISSU-MILESTONE-BAG;
    }
    list nsr-err-history {
      description
        "Nsr Error History List";
      uses OSPF-NSR-ERR-BLOCK-BAG;
    }
  }

  grouping OSPF-SH-RIB-BATCH {
    description
      "OSPF SH RIB BATCH";
    leaf batches-sent {
      type uint32;
      description
        "batches sent";
    }
    leaf routes-sent {
      type uint32;
      description
        "routes sent";
    }
    leaf routes-pending {
      type uint32;
      description
        "routes pending";
    }
    leaf max-routes {
      type uint32;
      description
        "max routes";
    }
    leaf paths-sent {
      type uint32;
      description
        "paths sent";
    }
    leaf paths-pending {
      type uint32;
      description
        "paths pending";
    }
    leaf paths-add {
      type uint32;
      description
        "paths add";
    }
    leaf paths-add-errs {
      type uint32;
      description
        "paths add errs";
    }
    leaf paths-del {
      type uint32;
      description
        "paths del";
    }
    leaf paths-del-errs {
      type uint32;
      description
        "paths del errs";
    }
    leaf lfas-pending {
      type uint32;
      description
        "lfas pending";
    }
    leaf lfas-add {
      type uint32;
      description
        "lfas add";
    }
    leaf lfas-del {
      type uint32;
      description
        "lfas del";
    }
    leaf lfas-sent {
      type uint32;
      description
        "lfas sent";
    }
    leaf priority-level {
      type string {
        length "0..40";
      }
      description
        "priority level";
    }
  }

  grouping OSPF-SH-RIB-BATCH-PRIORITY-QUEUES {
    description
      "OSPF SH RIB BATCH PRIORITY QUEUES";
    list priority-batch {
      max-elements "8";
      description
        "priority batch";
      uses OSPF-SH-RIB-BATCH;
    }
  }

  grouping OSPF-EDM-AREA-SUMM {
    description
      "OSPF EDM AREA SUMM";
    leaf area-id {
      type uint32;
      description
        "area id";
    }
    leaf spf-count {
      type uint32;
      description
        "spf count";
    }
  }

  grouping OSPF-HEADER-INFO {
    description
      "OSPF HEADER INFO";
    leaf router-id {
      type inet:ipv4-address;
      description
        "router id";
    }
    leaf spf-count {
      type uint32;
      description
        "spf count";
    }
    list area-summ {
      description
        "area summ";
      uses OSPF-EDM-AREA-SUMM;
    }
  }

  grouping OSPF-EDM-SPF-AREA-STATS {
    description
      "OSPF EDM SPF AREA STATS";
    container spf-time {
      description
        "spf time";
      uses OSPF-SPF-TIME;
    }
    leaf area-id {
      type uint32;
      description
        "area id";
    }
    list lsa-type-cnt {
      max-elements "7";
      description
        "lsa type cnt";
      leaf entry {
        type uint32;
        description
          "lsa type cnt";
      }
    }
  }

  grouping OSPF-LSA-CHANGE {
    description
      "OSPF LSA CHANGE";
    leaf area-id {
      type uint32;
      description
        "area id";
    }
    leaf adv-rtr {
      type inet:ipv4-address;
      description
        "adv rtr";
    }
    leaf id {
      type inet:ipv4-address;
      description
        "id";
    }
    leaf type {
      type uint8;
      description
        "type";
    }
    leaf flush {
      type boolean;
      description
        "flush";
    }
  }

  grouping OSPF-SPF-TIME {
    description
      "OSPF SPF TIME";
    leaf spf-dijkstra {
      type uint32;
      description
        "spf dijkstra";
    }
    leaf spf-intra-prefix {
      type uint32;
      description
        "spf intra prefix";
    }
    leaf spf-intra-prefix-del {
      type uint32;
      description
        "spf intra prefix del";
    }
    leaf spf-inter-prefix {
      type uint32;
      description
        "spf inter prefix";
    }
    leaf spf-inter-prefix-del {
      type uint32;
      description
        "spf inter prefix del";
    }
    leaf spf-ext-prefix {
      type uint32;
      description
        "spf ext prefix";
    }
    leaf spf-ext-prefix-del {
      type uint32;
      description
        "spf ext prefix del";
    }
  }

  grouping OSPF-RUNTIME-STATS {
    description
      "OSPF RUNTIME STATS";
    container gbl-spf-time {
      description
        "gbl spf time";
      uses OSPF-SPF-TIME;
    }
    leaf spf-start-time {
      type uint32;
      description
        "spf start time";
    }
    leaf lsa-change-cnt {
      type int16;
      description
        "lsa change cnt";
    }
    list lsa-info {
      max-elements "5";
      description
        "lsa info";
      uses OSPF-LSA-CHANGE;
    }
    list area-stat {
      description
        "area stat";
      uses OSPF-EDM-SPF-AREA-STATS;
    }
  }

  grouping OSPF-SH-STAT-PARTIAL {
    description
      "OSPF SH STAT PARTIAL";
    container sp-start-time {
      description
        "sp start time";
      uses OSPF-SH-TIME;
    }
    container sp-duration {
      description
        "sp duration";
      uses OSPF-SH-TIME;
    }
    leaf sp-adv-rtr-id {
      type uint32;
      description
        "sp adv rtr id";
    }
    leaf sp-dest-count {
      type uint32;
      description
        "sp dest count";
    }
    leaf sp-dest-addr {
      type uint32;
      description
        "sp dest addr";
    }
  }

  grouping OSPF-SH-STAT-INTRA {
    description
      "OSPF SH STAT INTRA";
    container si-start-time {
      description
        "si start time";
      uses OSPF-SH-TIME;
    }
    container si-duration {
      description
        "si duration";
      uses OSPF-SH-TIME;
    }
    leaf si-area-id-str {
      type string;
      description
        "si area id str";
    }
    leaf si-change-flags {
      type uint16;
      description
        "si change flags";
    }
  }

  grouping OSPF-SH-STATS-SPF {
    description
      "OSPF SH STATS SPF";
    container spf-header {
      description
        "spf header";
      uses OSPF-HEADER-INFO;
    }
    list os-runtime {
      description
        "os runtime";
      uses OSPF-SH-STAT-INTRA;
    }
    list os-sum-runtime {
      description
        "os sum runtime";
      uses OSPF-SH-STAT-PARTIAL;
    }
    list os-ex-runtime {
      description
        "os ex runtime";
      uses OSPF-SH-STAT-PARTIAL;
    }
    list runtime {
      description
        "runtime";
      uses OSPF-RUNTIME-STATS;
    }
  }
}
