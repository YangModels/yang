submodule Cisco-IOS-XR-asr9k-sc-envmon-oper-sub1 {
  belongs-to Cisco-IOS-XR-asr9k-sc-envmon-oper {
    prefix Cisco-IOS-XR-asr9k-sc-envmon-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-sc-envmon package operational data.
     
     Copyright (c) 2013-2018 by Cisco Systems, Inc.
     All rights reserved.";

  revision 2017-01-19 {
    description
      "IOS-XR 6.2.1 revision.";
  }
  revision 2015-11-09 {
    description
      "IOS XR 6.0 revision.";
  }

  grouping ENVMON-POWER-INFO {
    description
      "Power Info bag";
    leaf power-value {
      type int32;
      description
        "Current Power Value of the Unit";
    }
    leaf power-max-value {
      type int32;
      description
        "Max Power Value of the Unit";
    }
    leaf power-unit-multiplier {
      type uint32;
      description
        "Unit Multiplier of Power";
    }
    leaf power-accuracy {
      type uint32;
      description
        "Accuracy of the Power Value";
    }
    leaf power-measure-caliber {
      type uint32;
      description
        "Measure Caliber";
    }
    leaf power-current-type {
      type uint32;
      description
        "Current Type of the Unit";
    }
    leaf power-origin {
      type uint32;
      description
        "The Power Origin of the Unit";
    }
    leaf power-admin-state {
      type uint32;
      description
        "Admin Status of the Unit";
    }
    leaf power-oper-state {
      type uint32;
      description
        "Oper Status of the Unit";
    }
    leaf power-state-enter-reason {
      type string {
        length "0..50";
      }
      description
        "Enter Reason for the State";
    }
  }

  grouping ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type uint32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }

  grouping ENVMON-SENSOR-INFO {
    description
      "ENVMON sensor Info";
    leaf field-validity-bitmap {
      type uint32;
      description
        "Sensor valid bitmap";
    }
    leaf device-description {
      type string {
        length "0..50";
      }
      description
        "Device Name";
    }
    leaf units {
      type string {
        length "0..50";
      }
      description
        "Units of variable being read";
    }
    leaf device-id {
      type uint32;
      description
        "Identifier for this device";
    }
    leaf value {
      type uint32;
      description
        "Current reading of sensor";
    }
    leaf alarm-type {
      type uint32;
      description
        "Indicates threshold violation";
    }
    leaf data-type {
      type uint32;
      description
        "Sensor data type enums";
    }
    leaf scale {
      type uint32;
      description
        "Sensor scale enums";
    }
    leaf precision {
      type uint32;
      description
        "Sensor precision range";
    }
    leaf status {
      type uint32;
      description
        "Sensor operation state enums";
    }
    leaf age-time-stamp {
      type uint32;
      description
        "Age of the sensor value; set to the current time
         if directly access the value from sensor";
    }
    leaf update-rate {
      type uint32;
      description
        "Sensor value update rate;set to 0 if sensor
         value is updated and evaluated immediately";
    }
    leaf average {
      type int32;
      description
        "Average sensor value over time interval";
    }
    leaf minimum {
      type int32;
      description
        "Minimum Sensor value over time interval";
    }
    leaf maximum {
      type int32;
      description
        "Maximum Sensor value over time interval";
    }
    leaf interval {
      type int32;
      description
        "Time Interval over which sensor value is
         monitored";
    }
  }
}
