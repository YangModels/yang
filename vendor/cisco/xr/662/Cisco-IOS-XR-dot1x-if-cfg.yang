module Cisco-IOS-XR-dot1x-if-cfg {
  namespace "http://cisco.com/ns/yang/Cisco-IOS-XR-dot1x-if-cfg";
  prefix dot1x-if-cfg;

  import ietf-yang-types {
    prefix yang;
  }
  import Cisco-IOS-XR-types {
    prefix xr;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dot1x-if package configuration.
     
     This YANG module augments the
       Cisco-IOS-XR-ifmgr-cfg
     module with configuration data.
     
     Copyright (c) 2013-2018 by Cisco Systems, Inc.
     All rights reserved.";

  revision 2015-11-09 {
    description
      "IOS XR 6.0 revision.";
  }

  augment "/a1:interface-configurations/a1:interface-configuration" {
    description
      "This augment extends the configuration data of
       'Cisco-IOS-XR-ifmgr-cfg'";
    container dot1x-interface {
      description
        "Interface Specific Dot1x Configuration";
      leaf eapol-dest-addr {
        type yang:mac-address;
        description
          "Destination address for EAPoL frames
           transmission";
      }
      leaf dot1x-profile {
        type xr:Cisco-ios-xr-string {
          length "1..63";
        }
        description
          "Name of Dot1x profile";
      }
    }
  }
}
