module Cisco-IOS-XR-sysadmin-show-obfl {
  namespace "http://www.cisco.com/ns/yang/Cisco-IOS-XR-sysadmin-show-obfl";
  prefix shobfl;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module holds OBFL data.
     
     Copyright (c) 2012-2018 by Cisco Systems, Inc.
     All rights reserved.";

  revision 2018-10-05 {
    description
      "Added np container";
  }

  grouping obfl_data {
    container uptime {
      config false;
      list location {
        key "location";
        leaf location {
          type string;
        }
        container uptime {
          leaf-list uptime_values {
            type string;
          }
        }
      }
    }
    container nvram {
      config false;
      list location {
        key "location";
        leaf location {
          type string;
        }
        container nvram {
          leaf-list nvram_values {
            type string;
          }
        }
      }
    }
    container fia_asic_init_fail {
      config false;
      list location {
        key "location";
        leaf location {
          type string;
        }
        container fia_asic_init_fail {
          leaf-list fia_asic_init_fail_values {
            type string;
          }
        }
      }
    }
    container inventory {
      config false;
      list location {
        key "location";
        leaf location {
          type string;
        }
        container inventory {
          leaf-list inventory_values {
            type string;
          }
        }
      }
    }
    container temperature {
      config false;
      list location {
        key "location";
        leaf location {
          type string;
        }
        container temperature {
          leaf-list temp_values {
            type string;
          }
        }
      }
    }
    container voltage {
      config false;
      list location {
        key "location";
        leaf location {
          type string;
        }
        container voltage {
          leaf-list volt_values {
            type string;
          }
        }
      }
    }
    container fpd {
      config false;
      list location {
        key "location";
        leaf location {
          type string;
        }
        container fpd {
          leaf-list fpd_values {
            type string;
          }
        }
      }
    }
    container diag_result {
      config false;
      list location {
        key "location";
        leaf location {
          type string;
        }
        container diag_result {
          leaf-list diag_result_values {
            type string;
          }
        }
      }
    }
    container diag_log {
      config false;
      list location {
        key "location";
        leaf location {
          type string;
        }
        container diag_log {
          leaf-list diag_log_values {
            type string;
          }
        }
      }
    }
    container fmea {
      config false;
      list location {
        key "location";
        leaf location {
          type string;
        }
        container fmea {
          leaf-list fmea_values {
            type string;
          }
        }
      }
    }
    container fabric {
      config false;
      list location {
        key "location";
        leaf location {
          type string;
        }
        container fabric {
          leaf-list fabric_values {
            type string;
          }
        }
      }
    }
    container prm {
      config false;
      list location {
        key "location";
        leaf location {
          type string;
        }
        container prm {
          leaf-list prm_values {
            type string;
          }
        }
      }
    }
    container np {
      config false;
      list location {
        key "location";
        leaf location {
          type string;
        }
        container np {
          leaf-list np_values {
            type string;
          }
        }
      }
    }
  }

  grouping obfl-show-grp {
    container onboard {
      uses obfl_data;
    }
  }
}
