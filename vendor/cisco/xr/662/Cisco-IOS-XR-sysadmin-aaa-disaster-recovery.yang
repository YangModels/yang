module Cisco-IOS-XR-sysadmin-aaa-disaster-recovery {
  namespace "http://www.cisco.com/ns/yang/Cisco-IOS-XR-sysadmin-aaa-disaster-recovery";
  prefix disaster-recovery;

  import tailf-common {
    prefix tailf;
  }
  import tailf-aaa {
    prefix aaa;
  }

  organization
    "Cisco Systems Inc.";
  contact
    "clos-mgbl@cisco.com";
  description
    "This module contains definitions
     for the Calvados model objects.
     
     This module defines the system users authentication 
     credentials and virtual IP that can be modified in 
     runtime.
     
     Copyright (c) 2012-2018 by Cisco Systems, Inc.
     All rights reserved.";

  revision 2017-05-10 {
    description
      "Namespace changed from disaster-recovery to Cisco-IOS-XR-sysadmin-aaa-disaster-recovery";
  }

  augment "/aaa:aaa" {
    container disaster-recovery {
      leaf username {
        type leafref {
          path "/aaa:aaa/aaa:authentication/aaa:users/aaa:user/aaa:name";
        }
      }
      leaf password {
        type tailf:md5-digest-string;
      }
    }
  }
}
