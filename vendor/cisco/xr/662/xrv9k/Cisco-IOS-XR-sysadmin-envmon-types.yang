module Cisco-IOS-XR-sysadmin-envmon-types {
  namespace "http://www.cisco.com/ns/Cisco-IOS-XR-sysadmin-envmon-types";
  prefix envmon-types;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2018 by Cisco Systems, Inc.
     All rights reserved.";

  revision 2017-11-27 {
    description
      "Add graceful shutdown disable CLI.";
  }

  typedef num_pm {
    type uint32 {
      range "0..1";
    }
  }

  grouping fan-speed-group {
    leaf raise-fan-speed {
      type uint32 {
        range "0..100";
      }
      config false;
    }
  }

  grouping fan-ctrl-optics-group {
    leaf fan-ctrl-optics {
      type uint32 {
        range "0..1";
      }
      config false;
    }
  }

  grouping vin-uv-shut-group {
    leaf graceful-shutdown {
      type uint32 {
        range "0..1";
      }
      config false;
    }
  }
}
