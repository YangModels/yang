module cisco-xr-openconfig-platform-cpu-deviations {
  namespace "http://cisco.com/ns/yang/cisco-xr-openconfig-platform-cpu-deviations";
  prefix oc-cpudevs;

  import openconfig-platform-cpu {
    prefix oc-cpu;
  }
  import openconfig-platform {
    prefix oc-platform;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for 
      
     openconfig-platform-cpu.yang@2018-01-30 
     
     on Cisco IOS-XR devices.
     
     Copyright (c) 2017-2019 by Cisco Systems, Inc.
     All rights reserved.";

  revision 2018-12-10 {
    description
      "Initial revision applicable to IOS-XR 6.6.1";
  }

  deviation "/oc-platform:components/oc-platform:component/oc-platform:cpu/oc-cpu:utilization/oc-cpu:state/oc-cpu:instant" {
    deviate not-supported;
  }
  deviation "/oc-platform:components/oc-platform:component/oc-platform:cpu/oc-cpu:utilization/oc-cpu:state/oc-cpu:avg" {
    deviate not-supported;
  }
  deviation "/oc-platform:components/oc-platform:component/oc-platform:cpu/oc-cpu:utilization/oc-cpu:state/oc-cpu:min" {
    deviate not-supported;
  }
  deviation "/oc-platform:components/oc-platform:component/oc-platform:cpu/oc-cpu:utilization/oc-cpu:state/oc-cpu:max" {
    deviate not-supported;
  }
  deviation "/oc-platform:components/oc-platform:component/oc-platform:cpu/oc-cpu:utilization/oc-cpu:state/oc-cpu:interval" {
    deviate not-supported;
  }
  deviation "/oc-platform:components/oc-platform:component/oc-platform:cpu/oc-cpu:utilization/oc-cpu:state/oc-cpu:min-time" {
    deviate not-supported;
  }
  deviation "/oc-platform:components/oc-platform:component/oc-platform:cpu/oc-cpu:utilization/oc-cpu:state/oc-cpu:max-time" {
    deviate not-supported;
  }
}
