submodule Cisco-IOS-XR-aaa-locald-oper-sub1 {
  belongs-to Cisco-IOS-XR-aaa-locald-oper {
    prefix Cisco-IOS-XR-aaa-locald-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR aaa-locald package operational data.
     
     Copyright (c) 2013-2018 by Cisco Systems, Inc.
     All rights reserved.";

  revision 2015-11-09 {
    description
      "IOS XR 6.0 revision.";
  }

  typedef String1 {
    type string;
    description
      "String1";
  }

  grouping USERGROUP-DET {
    description
      "Detailed information regarding a usergroup";
    container task-map {
      description
        "Computed task map";
      uses TASKMAP;
    }
    list taskgroup {
      description
        "Component taskgroups";
      uses TASKGROUP-DET;
    }
  }

  grouping PP-DURATION {
    description
      "Information about time duration";
    leaf years {
      type uint8;
      description
        "years";
    }
    leaf months {
      type uint8;
      description
        "months";
    }
    leaf days {
      type uint8;
      description
        "days";
    }
    leaf hours {
      type uint8;
      description
        "hours";
    }
    leaf mins {
      type uint8;
      description
        "mins";
    }
    leaf secs {
      type uint8;
      description
        "secs";
    }
  }

  grouping PP-DET {
    description
      "Detailed information about a single Password
       Policy";
    container life-time {
      description
        "Lifetime of the policy";
      uses PP-DURATION;
    }
    container lock-out-time {
      description
        "Lockout time of the policy";
      uses PP-DURATION;
    }
    leaf min-len {
      type uint8;
      description
        "Min Length";
    }
    leaf max-len {
      type uint8;
      description
        "Max Length";
    }
    leaf spl-char {
      type uint8;
      description
        "Special Character length";
    }
    leaf upper-case {
      type uint8;
      description
        "UpperCase Character length";
    }
    leaf lower-case {
      type uint8;
      description
        "LowerCase Character length";
    }
    leaf numeric {
      type uint8;
      description
        "Numeric Character length";
    }
    leaf min-char-change {
      type uint8;
      description
        "Number of different characters";
    }
    leaf num-of-users {
      type uint8;
      description
        "Number of users with this policy";
    }
    leaf max-fail-attempts {
      type uint32;
      description
        "Maximum Failure Attempts allowed";
    }
    leaf usr-count {
      type uint8;
      description
        "Count of users";
    }
    leaf err-count {
      type uint8;
      description
        "Error Count";
    }
    leaf lock-out-count {
      type uint8;
      description
        "Lock Out Count";
    }
  }

  grouping USER-DET {
    description
      "Detailed information about a single user";
    container task-map {
      description
        "Computed taskmap";
      uses TASKMAP;
    }
    leaf admin-user {
      type boolean;
      description
        "Is admin plane user ?";
    }
    leaf first-user {
      type boolean;
      description
        "Is first user ?";
    }
    leaf-list usergroup {
      type String1;
      description
        "Member usergroups";
    }
  }

  grouping TASKID {
    description
      "Information about a single Task ID";
    leaf task-id {
      type string;
      description
        "Name of the task-id";
    }
    leaf read {
      type boolean;
      description
        "Is read permitted?";
    }
    leaf write {
      type boolean;
      description
        "Is write permitted?";
    }
    leaf execute {
      type boolean;
      description
        "Is execute permitted?";
    }
    leaf debug {
      type boolean;
      description
        "Is debug permitted?";
    }
  }

  grouping TASKMAP {
    description
      "Computed taskmap of a user/usergroup/taskgroup or
       Task IDs included in a taskgroup";
    list tasks {
      description
        "List of permitted tasks";
      uses TASKID;
    }
  }

  grouping TASKGROUP-DET {
    description
      "Detailed information regarding a taskgroup";
    container included-task-ids {
      description
        "Task-ids included";
      uses TASKMAP;
    }
    container task-map {
      description
        "Computed task map";
      uses TASKMAP;
    }
  }

  grouping REMOTEUSR-DET {
    description
      "Detailed information regarding a usergroup";
    leaf name {
      type string;
      description
        "Name of the usergroup";
    }
    leaf shelltype {
      type string;
      description
        "Shell-type of user";
    }
    leaf directory {
      type string;
      description
        "Directory of user";
    }
    leaf authenmethod {
      type int32;
      description
        "Authentication method";
    }
    leaf-list usergroup {
      type String1;
      description
        "Component usergroups";
    }
    leaf-list taskmap {
      type String1;
      description
        "Task map details";
    }
  }

  grouping SYSTEM-SUPPORTED-TASKS {
    description
      "List of all tasks available in the system";
    leaf-list task-id {
      type String1;
      description
        "Names of available task-ids";
    }
  }
}
