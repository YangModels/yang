module Cisco-IOS-XR-lib-keychain-oper {
  namespace "http://cisco.com/ns/yang/Cisco-IOS-XR-lib-keychain-oper";
  prefix lib-keychain-oper;

  import Cisco-IOS-XR-types {
    prefix xr;
  }
  include Cisco-IOS-XR-lib-keychain-oper-sub1 {
    revision-date 2018-01-31;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lib-keychain package operational data.
     
     This module contains definitions
     for the following management objects:
       keychain: Keychain operational data
     
     Copyright (c) 2013-2018 by Cisco Systems, Inc.
     All rights reserved.";

  revision 2018-01-31 {
    description
      "Fixed incorrect plural rendering.";
  }
  revision 2015-01-07 {
    description
      "IOS XR 5.3.1 revision.";
  }

  container keychain {
    config false;
    description
      "Keychain operational data";
    container keys {
      description
        "List of configured key names";
      list key {
        key "key-name";
        description
          "Configured key name";
        leaf key-name {
          type xr:Cisco-ios-xr-string;
          description
            "Key name";
        }
        uses KEY-CHAIN;
      }
    }
  }
}
