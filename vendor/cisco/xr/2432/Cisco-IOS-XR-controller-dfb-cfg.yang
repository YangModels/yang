module Cisco-IOS-XR-controller-dfb-cfg {
  namespace "http://cisco.com/ns/yang/Cisco-IOS-XR-controller-dfb-cfg";
  prefix controller-dfb-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-dfb package configuration.
     
     This YANG module augments the
       Cisco-IOS-XR-ifmgr-cfg
     module with configuration data.
     
     Copyright (c) 2013-2022 by Cisco Systems, Inc.
     All rights reserved.";

  revision 2022-12-28 {
    description
      "dfb-tx-voa-attenuation datatype is changed to signed int32";
    semver:module-version "1.0.0";
  }
  revision 2022-03-21 {
    description
      "Name of the enum ThresholdType is changed to DfbThresholdType";
  }
  revision 2020-10-16 {
    description
      "New Cfg Model Added for Dfb Controller";
  }
  revision 2019-04-05 {
    description
      "Establish semantic version baseline.";
  }
  revision 2015-11-09 {
    description
      "IOS XR 6.0 revision.";
  }

  typedef Dfb-threshold {
    type enumeration {
      enum "low" {
        value 1;
        description
          "Low Threshold";
      }
      enum "high" {
        value 2;
        description
          "High Threshold";
      }
    }
    description
      "Dfb threshold";
  }

  augment "/a1:interface-configurations/a1:interface-configuration" {
    description
      "This augment extends the configuration data of
       'Cisco-IOS-XR-ifmgr-cfg'";
    container dfb {
      description
        "Dfb controller configuration";
      container tx-thresholds {
        description
          "Configure TX threshold";
        list tx-threshold {
          key "tx-threshold-type";
          description
            "Configure transponder transmit power threshold";
          leaf tx-threshold-type {
            type Dfb-threshold;
            description
              "Low or high tx threshold";
          }
          leaf tx-threshold {
            type int32 {
              range "-400..300";
            }
            mandatory true;
            description
              "Select power level (in units of 0.1dBm";
          }
        }
      }
      container rx-thresholds {
        description
          "Configure RX threshold";
        list rx-threshold {
          key "rx-threshold-type";
          description
            "Configure transponder receive power threshold";
          leaf rx-threshold-type {
            type Dfb-threshold;
            description
              "Low or high rx threshold";
          }
          leaf rx-threshold {
            type int32 {
              range "-400..300";
            }
            mandatory true;
            description
              "Select power level (in units of 0.1dBm)";
          }
        }
      }
      leaf dfb-tx-voa-attenuation {
        type int32 {
          range "0..200";
        }
        description
          "Select Tx Voa Attenuation Level (in units of 0
           .1dB)";
      }
      leaf dfb-transmit-power {
        type int32 {
          range "-190..50";
        }
        description
          "Select Power Level (in units of 0.1dBm)";
      }
      leaf dfb-transmit-shutdown {
        type boolean;
        description
          "Configure Dfb transmit laser shutdown";
      }
    }
  }
}
