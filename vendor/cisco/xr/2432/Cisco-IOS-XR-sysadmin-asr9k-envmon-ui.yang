module Cisco-IOS-XR-sysadmin-asr9k-envmon-ui {
  namespace "http://www.cisco.com/ns/yang/Cisco-IOS-XR-sysadmin-asr9k-envmon-ui";
  prefix envmon;

  import Cisco-IOS-XR-sysadmin-show-trace {
    prefix show_trace;
  }
  import tailf-xsd-types {
    prefix xs;
  }
  import Cisco-IOS-XR-sysadmin-types {
    prefix calvados;
  }
  import Cisco-IOS-XR-sysadmin-asr9k-envmon-types {
    prefix envmon-types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module holds chassis, cards Enviroment data.
     
     Copyright (c) 2012-2020 by Cisco Systems, Inc.
     All rights reserved.";

  revision 2020-05-12 {
    description
      "Required changes to add single mode config location specific";
    semver:module-version "1.1.0";
  }
  revision 2020-05-05 {
    description
      "Adjusting power consumed due to multi output for 9903";
  }
  revision 2019-04-15 {
    description
      "Establish semantic version baseline.";
  }
  revision 2018-04-09 {
    description
      "Required changes for ConfD 6.4.5";
  }
  revision 2018-02-06 {
    description
      "Adding CLI input validation for LC priority shutdown feature";
  }
  revision 2018-01-25 {
    description
      "Initial revision of LC priority shutdown feature";
  }
  revision 2017-11-27 {
    description
      "Add graceful shutdown disable CLI.";
  }
  revision 2017-07-31 {
    description
      "Changing the namespace to follow Cisco guidelines on naming convention";
  }
  revision 2017-04-10 {
    description
      "Adding the source leaf to altitude value,
         this is to distinguish the source of the altitude value ";
  }
  revision 2017-03-31 {
    description
      "Renamed module and namespace";
  }
  revision 2017-03-30 {
    description
      "commenting the sensor_attributes callpoints for the oper sensors,
         using only the location based callpoints for sensor_attributes ";
  }
  revision 2016-10-12 {
    description
      "unhide commands and configs. moved to advanced-grp";
  }
  revision 2011-11-24 {
    description
      "Initial revision of show environment commands";
  }

  grouping pm-location {
    description
      "Power module data";
    leaf all {
      type empty;
      description
        " All Power modules";
    }
    list location {
      key "pmId";
      description
        "Power module location Name";
      leaf pmId {
        type string {
          pattern "0/PT[0-3]-PM[0-3]";
        }
        description
          "Power module Id";
      }
    }
  }

  grouping temp-data {
    container temperatures {
      config false;
      description
        "Environmental operational temperature data";
      list location {
        key "location";
        description
          "Location";
        leaf location {
          type string;
          description
            "Location Name";
        }
        list sensor_attributes {
          key "sensor";
          description
            "temperature sensor attributes";
          leaf sensor {
            type string;
            description
              "Sensor Name";
          }
          leaf sensor_id {
            type string;
            description
              "sensor id (unique for location)";
          }
          leaf loc_header {
            type boolean;
            default "false";
            description
              "Entry to customize the show-template for CLI";
          }
          leaf print_header {
            type boolean;
            default "false";
            description
              "Expandable entry for cli-template-string to print the header for sensor table";
          }
          leaf location {
            type string;
            description
              "Location Name";
          }
          leaf alarm {
            type string;
            description
              "Alarm Name";
          }
          leaf temperature_value {
            type string;
            description
              "temperature sensor value in degree Celsius";
          }
          leaf value {
            type int32;
            description
              "temperature value in degree Celsius";
          }
          leaf critical_lo {
            type int32;
            description
              "Critical Low Threshold Value, interpret -32768 value as N/A";
          }
          leaf major_lo {
            type int32;
            description
              "Major Low Threshold Value, interpret -32768 value as N/A";
          }
          leaf minor_lo {
            type int32;
            description
              "Minor Low Threshold Value, interpret -32768 value as N/A";
          }
          leaf minor_hi {
            type int32;
            description
              "Minor High Threshold Value, interpret 32768 value as N/A";
          }
          leaf major_hi {
            type int32;
            description
              "Major High Threshold Value, interpret 32768 value as N/A";
          }
          leaf critical_hi {
            type int32;
            description
              "Critical High Threshold Value, interpret 32768 value as N/A";
          }
        }
      }
    }
  }

  grouping all-temp-data {
    description
      "all environmental temperature data";
    list temperatures {
      key "loc_iden";
      config false;
      description
        "environmental parameter temperature data";
      leaf loc_iden {
        type string;
        description
          "temperature sensor location";
      }
      leaf print_header {
        type boolean;
        default "false";
        description
          "Entry to customize the temp table in show-template for CLI";
      }
      list sensor_attributes {
        key "sensor";
        description
          "temperature sensor attributes";
        leaf sensor {
          type string;
          description
            "temperature sensor name";
        }
        leaf sensor_id {
          type string;
          description
            "temperature sensor id unique for location";
        }
        leaf alarm {
          type string;
          description
            "alarm name";
        }
        leaf temperature_value {
          type string;
          description
            "temperature sensor value in degree Celsius";
        }
        leaf value {
          type int32;
          description
            "temperature value in degree Celsius";
        }
        leaf critical_lo {
          type int32;
          description
            "Critical Low Threshold Value, interpret -32768 value as N/A";
        }
        leaf major_lo {
          type int32;
          description
            "Major Low Threshold Value, interpret -32768 value as N/A";
        }
        leaf minor_lo {
          type int32;
          description
            "Minor Low Threshold Value, interpret -32768 value as N/A";
        }
        leaf minor_hi {
          type int32;
          description
            "Minor High Threshold Value, interpret 32768 value as N/A";
        }
        leaf major_hi {
          type int32;
          description
            "Major High Threshold Value, interpret 32768 value as N/A";
        }
        leaf critical_hi {
          type int32;
          description
            "Critical High Threshold Value, interpret 32768 value as N/A";
        }
      }
    }
  }

  grouping volt-data {
    description
      "environmental operational voltages data";
    container voltages {
      config false;
      description
        "environmental parameter voltages";
      list location {
        key "location";
        description
          "locations of the voltage sensors";
        leaf location {
          type string;
          description
            "voltage sensor location";
        }
        list sensor_attributes {
          key "sensor";
          description
            "voltage sensor attributes";
          leaf sensor {
            type string;
            description
              "voltage sensor name";
          }
          leaf sensor_id {
            type string;
            description
              "voltage sensor id (unique for location)";
          }
          leaf loc_header {
            type boolean;
            default "false";
            description
              "Entry to customize to show voltage sensor for CLI";
          }
          leaf print_header {
            type boolean;
            default "false";
            description
              "Entry to customize to show voltage sensor for CLI";
          }
          leaf location {
            type string;
            description
              "Location Name";
          }
          leaf alarm {
            type string;
            description
              "Alarm Name";
          }
          leaf value {
            type string;
            description
              "voltage sensor value in mV";
          }
          leaf temperature_value {
            type int32;
            description
              "temperature value in degree Celsius";
          }
          leaf critical_lo {
            type int32;
            description
              "Critical Low Threshold Value, interpret -32768 value as N/A";
          }
          leaf major_lo {
            type int32;
            description
              "Major Low Threshold Value, interpret -32768 value as N/A";
          }
          leaf minor_lo {
            type int32;
            description
              "Minor Low Threshold Value, interpret -32768 value as N/A";
          }
          leaf minor_hi {
            type int32;
            description
              "Minor High Threshold Value, interpret -32768 value as N/A";
          }
          leaf major_hi {
            type int32;
            description
              "Major High Threshold Value, interpret -32768 value as N/A";
          }
          leaf critical_hi {
            type int32;
            description
              "Critical High Threshold Value, interpret -32768 value as N/A";
          }
        }
      }
    }
  }

  grouping all-volt-data {
    description
      "all environmental voltages data";
    list voltages {
      key "loc_iden";
      config false;
      description
        "environmental parameter voltage";
      leaf loc_iden {
        type string;
        description
          "voltage sensor locations";
      }
      leaf print_header {
        type boolean;
        default "false";
        description
          "Entry to customize the show-template for CLI";
      }
      list sensor_attributes {
        key "sensor";
        description
          "voltage sensor attributes";
        leaf sensor {
          type string;
          description
            "voltage sensor name";
        }
        leaf sensor_id {
          type string;
          description
            "voltage sensor id (unique for location)";
        }
        leaf alarm {
          type string;
          description
            "Alarm Name";
        }
        leaf value {
          type string;
          description
            "voltage sensor value in mV";
        }
        leaf temperature_value {
          type int32;
          description
            "temperature vlaue in degree Celsius";
        }
        leaf critical_lo {
          type int32;
          description
            "Critical Low Threshold Value, interpret -32768 value as N/A";
        }
        leaf major_lo {
          type int32;
          description
            "Major Low Threshold Value, interpret -32768 value as N/A";
        }
        leaf minor_lo {
          type int32;
          description
            "Minor Low Threshold Value, interpret -32768 value as N/A";
        }
        leaf minor_hi {
          type int32;
          description
            "Minor High Threshold Value, interpret -32768 value as N/A";
        }
        leaf major_hi {
          type int32;
          description
            "Major High Threshold Value, interpret -32768 value as N/A";
        }
        leaf critical_hi {
          type int32;
          description
            "Critical High Threshold Value, interpret -32768 value as N/A";
        }
      }
    }
  }

  grouping current-data {
    description
      "environmental operational current sensor data";
    container current {
      config false;
      description
        "environmental parameter current";
      list location {
        key "location";
        description
          "sensor location";
        leaf location {
          type string;
          description
            "sensor location";
        }
        list sensor_attributes {
          key "sensor";
          description
            "current sensor attributes";
          leaf loc_header {
            type boolean;
            default "false";
            description
              "Entry to customize the show-template for CLI";
          }
          leaf print_header {
            type boolean;
            default "false";
            description
              "Entry to customize the show-template for CLI";
          }
          leaf location {
            type string;
            description
              "current sensor location name";
          }
          leaf sensor {
            type string;
            description
              "current sensor name";
          }
          leaf sensor_id {
            type string;
            description
              "current sensor id (unique for location)";
          }
          leaf alarm {
            type string;
            description
              "Alarm name";
          }
          leaf value {
            type string;
            description
              "current sensor value in mA";
          }
          leaf temperature_value {
            type int32;
            description
              "temperature value in degree Celsius";
          }
        }
      }
    }
  }

  grouping all-current-data {
    description
      "all environmental current sensor data";
    list current {
      key "loc_iden";
      config false;
      description
        "environmental parameter current";
      leaf loc_iden {
        type string;
        description
          "Loc Iden";
      }
      leaf print_header {
        type boolean;
        default "false";
        description
          "Entry to customize the show-template for CLI";
      }
      list sensor_attributes {
        key "sensor";
        description
          "current sensor attributes";
        leaf sensor {
          type string;
          description
            "current sensor name";
        }
        leaf sensor_id {
          type string;
          description
            "current sensor id (unique for location)";
        }
        leaf value {
          type string;
          description
            "current sensor value in mA";
        }
      }
    }
  }

  grouping fan-data {
    description
      "environmental operational fan data";
    container fan {
      config false;
      description
        "environmental parameter fan";
      list location {
        key "location";
        description
          "Location Number";
        leaf location {
          type string;
          description
            "fan location";
        }
        leaf print_header {
          type boolean;
          default "false";
          description
            "Entry to customize the show-template for CLI";
        }
        leaf loc_header {
          type uint32;
          description
            "Entry to customize the show-template for CLI";
        }
        list fan_attributes {
          key "logical_slot";
          description
            "Fan Attributes";
          leaf print_fan_header {
            type string;
            description
              "Entry to customize the show-template for CLI";
          }
          leaf location {
            type string;
            description
              "fan location name";
          }
          leaf logical_slot {
            type string;
            description
              "fan logical slot";
          }
          leaf fru_PID {
            type string;
            description
              "Fru PID";
          }
          leaf fans_speed {
            type string;
            description
              "Fan Speed in rpm";
          }
          leaf fan_header {
            type uint32;
            description
              "Entry to customize the show-template for CLI";
          }
          leaf speed_space {
            type uint32;
            description
              "fan speed space";
          }
        }
      }
    }
  }

  grouping all-fan-data {
    list fan {
      key "loc_iden";
      config false;
      description
        "all environmental fan data";
      leaf loc_iden {
        type string;
        description
          "fan location";
      }
      list fan_attributes {
        key "logical_slot";
        description
          "Fan Attributes";
        leaf print_fan_header {
          type string;
          description
            "Entry to customize the show-template for CLI";
        }
        leaf location {
          type string;
          description
            "Location";
        }
        leaf logical_slot {
          type string;
          description
            "Fan Logical Slot";
        }
        leaf fru_PID {
          type string;
          description
            "Fru PID";
        }
        leaf fans_speed {
          type string;
          description
            "fan speed in rpm";
        }
        leaf fan_header {
          type uint32;
          description
            "Entry to customize the show-template for CLI";
        }
        leaf speed_space {
          type uint32;
          description
            "Fan speed space";
        }
      }
    }
  }

  grouping power-data {
    description
      "environmental operational power data";
    container power {
      config false;
      description
        "environmental parameter power";
      list location {
        key "location";
        description
          "Power Location";
        leaf location {
          type string;
          description
            "Power Location";
        }
        list pem_attributes {
          key "pem";
          description
            "power module attributes";
          leaf pem {
            type string;
            description
              "power module name";
          }
          leaf pem_id {
            type string;
            description
              "power module id";
          }
          leaf card_type {
            type string;
            description
              "power card type";
          }
          leaf ps_type {
            type string;
            description
              "power supply type";
          }
          leaf shelf_num {
            type uint16;
            description
              "power shelf number";
          }
          leaf supply_type {
            type string;
            description
              "power supply type";
          }
          leaf input_voltage {
            type string;
            description
              "input voltage in volts";
          }
          leaf input_current {
            type string;
            description
              "input current in Amps";
          }
          leaf output_voltage {
            type xs:double;
            description
              "output voltage in volts";
          }
          leaf output_current {
            type xs:double;
            description
              "output current in Amps";
          }
          leaf status {
            type string;
            description
              "power status";
          }
          leaf input_power_to_ps {
            type uint32;
            description
              "input power to power supply in Watts";
          }
          leaf input_current_to_ps {
            type string;
            description
              "input current to ps in Amps";
          }
          leaf output_power_from_ps {
            type uint32;
            description
              "Output Power from PS in Watts";
          }
          leaf output_current_from_ps {
            type xs:double;
            description
              "Output Current from PS in Amps";
          }
          leaf power_allocated {
            type uint32;
            description
              "Allocated Power in Watts";
          }
          leaf power_consumed {
            type string;
            description
              "Consumed power in Watts";
          }
          leaf power_status {
            type string;
            description
              "Power Status";
          }
          leaf confgd_power_redundancy_mode {
            type string;
            description
              "configured power redundancy mode";
          }
          leaf usable_power_capacity {
            type uint32;
            description
              "Usable Power Capacity in Watts";
          }
          leaf protection_power_capacity {
            type uint32;
            description
              "Protection Power Capacity";
          }
          leaf power_resrv_and_alloc {
            type uint32;
            description
              "Power Resrv and Alloc";
          }
          leaf system_power_used {
            type uint32;
            description
              "Used System Power";
          }
          leaf system_power_input {
            type uint32;
            description
              "Sysyem Power Input";
          }
          leaf power_level {
            type uint16;
            description
              "Power level";
          }
          leaf output_header {
            type uint16;
            description
              "Power output header";
          }
          leaf output_footer {
            type uint16;
            description
              "Power output footer";
          }
          leaf ps_sum_footer {
            type uint16;
            description
              "power ps sum footer";
          }
        }
      }
    }
  }

  grouping all-power-data {
    description
      "all environmental power data";
    list power {
      key "loc_iden";
      config false;
      description
        "environmental parameter power";
      leaf loc_iden {
        type string;
        description
          "power location";
      }
      list pem_attributes {
        key "pem";
        description
          "Power pem Attributes";
        leaf pem {
          type string;
          description
            "Pem Name";
        }
        leaf pem_id {
          type string;
          description
            "Pem ID";
        }
        leaf card_type {
          type string;
          description
            "Power card type";
        }
        leaf ps_type {
          type string;
          description
            "Power ps type";
        }
        leaf shelf_num {
          type uint16;
          description
            "Power shelf number";
        }
        leaf supply_type {
          type string;
          description
            "power supply type";
        }
        leaf input_voltage {
          type string;
          description
            "input voltage in volts";
        }
        leaf input_current {
          type string;
          description
            "input current in Amps";
        }
        leaf output_voltage {
          type xs:double;
          description
            "output voltage in volts";
        }
        leaf output_current {
          type xs:double;
          description
            "output current in Amps";
        }
        leaf status {
          type string;
          description
            "power status name";
        }
        leaf input_power_to_ps {
          type uint32;
          description
            "input power to ps";
        }
        leaf input_current_to_ps {
          type string;
          description
            "intput current to ps";
        }
        leaf output_power_from_ps {
          type uint32;
          description
            "output power from ps";
        }
        leaf output_current_from_ps {
          type xs:double;
          description
            "output current from ps";
        }
        leaf power_allocated {
          type uint32;
          description
            "allocated power in Watts";
        }
        leaf power_consumed {
          type string;
          description
            "consumed power in Watts";
        }
        leaf power_status {
          type string;
          description
            "status of the power";
        }
        leaf confgd_power_redundancy_mode {
          type string;
          description
            "confgd power redundancy mode";
        }
        leaf usable_power_capacity {
          type uint32;
          description
            "usable power capacity";
        }
        leaf protection_power_capacity {
          type uint32;
          description
            "protection power capacity";
        }
        leaf power_resrv_and_alloc {
          type uint32;
          description
            "resrv and allocatd power";
        }
        leaf system_power_used {
          type uint32;
          description
            "used system power";
        }
        leaf system_power_input {
          type uint32;
          description
            "used system power";
        }
        leaf power_level {
          type uint16;
          description
            "power level";
        }
        leaf output_header {
          type uint16;
          description
            "Entry to customise the PM table header cli display";
        }
        leaf output_footer {
          type uint16;
          description
            "Entry to customise the Footer of PM table cli display";
        }
        leaf ps_sum_footer {
          type uint16;
          description
            "Entry to customise  show-template CLI, but not used";
        }
      }
    }
  }

  grouping altitude-data {
    description
      "operational environmental altitude data";
    container altitude {
      config false;
      description
        "environmental parameter altitude";
      list location {
        key "location";
        description
          "sensor location";
        leaf location {
          type string;
          description
            "Location Name";
        }
        list alt_attributes {
          key "sensor";
          description
            "Name of Altitude Sensor Attributes";
          leaf sensor {
            type string;
            description
              "source name";
          }
          leaf rack {
            type uint32;
            description
              "Rack value";
          }
          leaf sensor_value {
            type string;
            description
              "Value of Sensor";
          }
          leaf source {
            type string;
            description
              "Source name";
          }
          leaf print_header {
            type boolean;
            default "false";
            description
              "Entry to customise the altitude table header cli display";
          }
        }
      }
    }
  }

  grouping all-altitude-data {
    description
      "all environmental altitude data";
    list altitude {
      key "loc_iden";
      config false;
      description
        "environmental parameter altitude";
      leaf loc_iden {
        type string;
        description
          "sensor location";
      }
      list alt_attributes {
        key "sensor";
        description
          "altitude attributes";
        leaf print_header {
          type boolean;
          default "false";
          description
            "Entry to customise the altitude attributes header cli display";
        }
        leaf sensor {
          type string;
          description
            "Sensor Name";
        }
        leaf rack {
          type uint32;
          description
            "Rack value";
        }
        leaf sensor_value {
          type string;
          description
            "Sensor value";
        }
        leaf source {
          type string;
          description
            "Source name";
        }
      }
    }
  }

  grouping rack-location {
    description
      "rack location";
    leaf all {
      type empty;
      description
        "all racks";
    }
    list location {
      key "rackId";
      description
        "location name";
      leaf rackId {
        type calvados:rack-id;
        description
          "rack id";
      }
    }
  }

  grouping router-group {
    description
      "environmnetal config router group";
    container router {
      description
        "environmnetal config router";
      container altitude {
        description
          "environmnetal config altitude";
        container all {
          description
            "all environmnetal config altitude";
          leaf num_meters {
            type uint32 {
              range "1..4000";
            }
            description
              "configured altitude value in mtr, negative value not allowed";
          }
        }
        container rack_loc {
          description
            "environmnetal config rack location";
          list location {
            key "rackId";
            description
              "Location Name";
            leaf rackId {
              type calvados:rack-id;
              description
                "Rack ID";
            }
            leaf num_meters {
              type uint32 {
                range "1..4000";
              }
              description
                "Num Meters";
            }
          }
        }
      }
    }
  }

  grouping air-filter-group {
    description
      "environmnetal config air filter";
    container air-filter {
      description
        "environmnetal configuration air filter";
      container replaced {
        description
          "Air Filter replaced date";
        container all {
          description
            "all environmnetal configuration air filter";
          leaf date {
            type xs:date;
            description
              "Date";
          }
        }
        container rack_loc {
          description
            "Rack Location";
          list location {
            key "rackId";
            description
              "Location";
            leaf rackId {
              type calvados:rack-id;
              description
                "environmental air filter rack id";
            }
            leaf date {
              type xs:date;
              description
                "air filter replaced rack location date";
            }
          }
        }
      }
    }
  }

  grouping fan-ctrl-group {
    description
      "environmental config fan control group";
    container fan-ctrl {
      description
        "environmental config fan control";
      container disable {
        description
          "environmental config fan control disable";
        container rack_loc {
          description
            "environmental config fan control rack location";
          uses rack-location;
        }
      }
    }
  }

  grouping temp-monitor-group {
    description
      "environmental config temperature monitor";
    container temperature {
      description
        "temperature monitoring";
      container disable {
        description
          "environmental monitoring disable";
        container rack_loc {
          description
            "environmental monitoring rack location";
          uses rack-location;
        }
      }
    }
  }

  grouping env-monitor-group {
    description
      "environmental monitoring group";
    container monitoring {
      description
        "Environment monitoring";
      container disable {
        description
          "environmental monitoring disable";
        container rack_loc {
          description
            "environmental monitoring rack location";
          uses rack-location;
        }
      }
    }
  }

  grouping power-mgmt-group {
    description
      "environmental power management config";
    container action {
      description
        "power management action";
      container disable {
        description
          "power management action disable";
        container rack_loc {
          description
            "power management rack location";
          uses rack-location;
        }
      }
    }
    container single-feed-mode {
      description
        "Action for suppressing alarms for missing feed";
      container enable {
        description
          "Suppression of alarms State";
        container pm_loc {
          description
            "Single feed mode pm location";
          uses pm-location;
        }
      }
    }
    container extended-temp {
      description
        "Action for setting power budget for extended temp mode";
      container enable {
        description
          "enable extended temperature";
        container rack_loc {
          description
            "enable extended temperature rack location";
          uses rack-location;
        }
      }
    }
    container redundancy-num-pms {
      description
        "Power management redundancy of power modules Attributes";
      container all {
        description
          "all redundancy number power modules name";
        leaf num_pm {
          type envmon-types:num_pm;
          description
            "redundancy number power modules";
        }
      }
      container rack_loc {
        description
          "Rack Location";
        list location {
          key "rackId";
          description
            "Location Name";
          leaf rackId {
            type calvados:rack-id;
            description
              "Rack ID";
          }
          leaf num_pm {
            type envmon-types:num_pm;
            description
              "Power module Number";
          }
        }
      }
    }
    container progressive {
      description
        "Action for setting LC shutdown order";
      list enable {
        key "enabled";
        description
          "Enable";
        leaf enabled {
          type enumeration {
            enum "enable";
          }
          config true;
          description
            "Enable the progressive behavior";
        }
        leaf syslog-threshold {
          type uint32 {
            range "3000 .. 72000";
          }
          config true;
          description
            "CLI input validation for LC priority shutdown feature,syslog-threshold <= shutdown threshold";
        }
        leaf shutdown-threshold {
          type uint32 {
            range "3000 .. 72000";
          }
          config true;
          description
            "CLI input validation for LC priority shutdown feature,syslog-threshold <= shutdown threshold";
        }
        container priority {
          description
            "Priority node location";
          list location {
            key "loc";
            description
              "Location of the node";
            leaf loc {
              type string {
                pattern "0/([0-9]|1[0-9])";
              }
              description
                "Location";
            }
            leaf prior {
              type uint32 {
                range "0 .. 19";
              }
              description
                "Priority";
            }
          }
        }
      }
    }
  }

  grouping cmd_types {
    description
      "operational environmental data";
    container oper {
      config false;
      description
        "environment operational (show) data";
      uses temp-data;
      uses volt-data;
      uses current-data;
      uses fan-data;
      uses power-data;
      uses altitude-data;
    }
    container all {
      config false;
      description
        "All environment monitor parameters";
      list location {
        key "location";
        description
          "environment location";
        leaf location {
          type string;
          description
            "Location";
        }
        uses all-temp-data;
        uses all-volt-data;
        uses all-current-data;
        uses all-fan-data;
        uses all-power-data;
        uses all-altitude-data;
      }
    }
    container config {
      description
        "environment configurational data";
      uses router-group;
      uses air-filter-group;
      uses fan-ctrl-group;
      uses temp-monitor-group;
      uses env-monitor-group;
      uses envmon-types:fan-speed-group;
      uses envmon-types:fan-ctrl-optics-group;
      uses envmon-types:vin-uv-shut-group;
    }
  }

  container environment {
    description
      "Environmental Monitoring ui data space";
    uses cmd_types;
    uses show_trace:traceable;
  }
  container power-mgmt {
    description
      "Manage Chassis Power Trays and PEMs";
    container config {
      description
        "Power Trays and PEMs configurational data";
      uses power-mgmt-group;
    }
  }
}
