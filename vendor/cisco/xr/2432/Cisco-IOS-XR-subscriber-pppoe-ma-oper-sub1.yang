submodule Cisco-IOS-XR-subscriber-pppoe-ma-oper-sub1 {
  belongs-to Cisco-IOS-XR-subscriber-pppoe-ma-oper {
    prefix Cisco-IOS-XR-subscriber-pppoe-ma-oper;
  }

  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-pppoe-ma package operational data.
     
     Copyright (c) 2013-2023 by Cisco Systems, Inc.
     All rights reserved.";

  revision 2023-07-20 {
    description
      "Changed description of the model
       2022-03-03
         Introduced an new bag element to display HA state";
    semver:module-version "4.0.0";
  }
  revision 2021-07-01 {
    description
      "Introduced an new enum in cleanup count";
    semver:module-version "3.0.0";
  }
  revision 2019-10-07 {
    description
      "Introduced an new cli pppoe bba-group padi host-uniq-disconnect";
    semver:module-version "2.0.0";
  }
  revision 2019-04-05 {
    description
      "Establish semantic version baseline.";
    semver:module-version "1.0.0";
  }
  revision 2015-11-09 {
    description
      "IOS XR 6.0 revision.";
  }

  typedef Pppoe-ma-throttle-state {
    type enumeration {
      enum "idle" {
        value 0;
        description
          "Idle State";
      }
      enum "monitor" {
        value 1;
        description
          "Monitor State";
      }
      enum "block" {
        value 2;
        description
          "Block State";
      }
    }
    description
      "Pppoe ma throttle state";
  }

  typedef Pppoe-ma-limit-state {
    type enumeration {
      enum "ok" {
        value 0;
        description
          "OK State";
      }
      enum "warning" {
        value 1;
        description
          "Warn State";
      }
      enum "block" {
        value 2;
        description
          "Block State";
      }
    }
    description
      "Pppoe ma limit state";
  }

  typedef Pppoe-ma-bag-optional-string {
    type string;
    description
      "String which may be optionally present.";
  }

  typedef Im-state {
    type uint32;
    description
      "Im state";
  }

  typedef Pppoe-ma-session-trig {
    type enumeration {
      enum "pppoe-ma-session-trig-error" {
        value 0;
        description
          "pppoe ma session trig error";
      }
      enum "pppoe-ma-session-trig-publish-encaps-attr-fail" {
        value 1;
        description
          "pppoe ma session trig publish encaps attr fail";
      }
      enum "pppoe-ma-session-trig-if-create-fail" {
        value 2;
        description
          "pppoe ma session trig if create fail";
      }
      enum "pppoe-ma-session-trig-iedge-session-start-fail" {
        value 3;
        description
          "pppoe ma session trig iedge session start fail";
      }
      enum "pppoe-ma-session-trig-iedge-session-update-fail" {
        value 4;
        description
          "pppoe ma session trig iedge session update fail";
      }
      enum "pppoe-ma-session-trig-sub-db-activate-fail" {
        value 5;
        description
          "pppoe ma session trig sub db activate fail";
      }
      enum "pppoe-ma-session-trig-in-flight-timeout" {
        value 6;
        description
          "pppoe ma session trig in flight timeout";
      }
      enum "pppoe-ma-session-trig-down" {
        value 7;
        description
          "pppoe ma session trig down";
      }
      enum "pppoe-ma-session-trig-parent" {
        value 8;
        description
          "pppoe ma session trig parent";
      }
      enum "pppoe-ma-session-trig-padt" {
        value 9;
        description
          "pppoe ma session trig padt";
      }
      enum "pppoe-ma-session-trig-session-pak" {
        value 10;
        description
          "pppoe ma session trig session pak";
      }
      enum "pppoe-ma-session-trig-final" {
        value 11;
        description
          "pppoe ma session trig final";
      }
      enum "pppoe-ma-session-trig-no-im-or" {
        value 12;
        description
          "pppoe ma session trig no im or";
      }
      enum "pppoe-ma-session-trig-restart" {
        value 13;
        description
          "pppoe ma session trig restart";
      }
      enum "pppoe-ma-session-trig-admissions-config-change" {
        value 14;
        description
          "pppoe ma session trig admissions config change";
      }
      enum "pppoe-ma-session-trig-iedge-disconnect" {
        value 15;
        description
          "pppoe ma session trig iedge disconnect";
      }
      enum "pppoe-ma-session-trig-invalid-vlan-tags" {
        value 16;
        description
          "pppoe ma session trig invalid vlan tags";
      }
      enum "pppoe-ma-session-trig-port-limit-disconnect" {
        value 17;
        description
          "pppoe ma session trig port limit disconnect";
      }
      enum "pppoe-ma-session-trig-srg-disconnect" {
        value 18;
        description
          "pppoe ma session trig srg disconnect";
      }
      enum "pppoe-ma-session-trig-srg-sweep" {
        value 19;
        description
          "pppoe ma session trig srg sweep";
      }
      enum "pppoe-ma-session-trig-renegotiation" {
        value 20;
        description
          "pppoe ma session trig renegotiation";
      }
      enum "pppoe-ma-session-trig-destroy-ing-cleanup-timer" {
        value 21;
        description
          "pppoe ma session trig destroy ing cleanup timer";
      }
      enum "pppoe-ma-session-trig-stopping-cleanup-timer" {
        value 22;
        description
          "pppoe ma session trig stopping cleanup timer";
      }
      enum "pppoe-ma-session-trig-deleting-cleanup-timer" {
        value 23;
        description
          "pppoe ma session trig deleting cleanup timer";
      }
      enum "pppoe-ma-session-trig-host-uniq-insert-fail" {
        value 24;
        description
          "pppoe ma session trig host uniq insert fail";
      }
      enum "pppoe-ma-session-trig-count" {
        value 25;
        description
          "pppoe ma session trig count";
      }
    }
    description
      "Pppoe ma session trig";
  }

  typedef Pppoe-ma-session-idb-srg-state {
    type enumeration {
      enum "none" {
        value 0;
        description
          "SRG-None state";
      }
      enum "active" {
        value 1;
        description
          "SRG-Active state";
      }
      enum "standby" {
        value 2;
        description
          "SRG-Standby state";
      }
    }
    description
      "Pppoe ma session idb srg state";
  }

  typedef Pppoe-ma-session-state {
    type enumeration {
      enum "destroying" {
        value 0;
        description
          "Destroying session";
      }
      enum "deleting" {
        value 1;
        description
          "Deleting interface";
      }
      enum "initializing" {
        value 2;
        description
          "Initializing";
      }
      enum "created" {
        value 3;
        description
          "Interface created";
      }
      enum "stopping" {
        value 4;
        description
          "Stopping AAA session";
      }
      enum "started" {
        value 5;
        description
          "AAA session started";
      }
      enum "activated" {
        value 6;
        description
          "SubDB Config activated";
      }
      enum "complete" {
        value 7;
        description
          "Complete";
      }
    }
    description
      "Pppoe ma session state";
  }

  grouping PPPOE-MA-SUMMARY-TOTAL-INFO {
    description
      "PPPoE MA Summary Total information";
    leaf ready-access-interfaces {
      type uint32;
      description
        "Ready Access Interface Count";
    }
    leaf not-ready-access-interfaces {
      type uint32;
      description
        "Not Ready Access Interface Count";
    }
    leaf complete-sessions {
      type uint32;
      description
        "Complete Session Count";
    }
    leaf incomplete-sessions {
      type uint32;
      description
        "Incomplete Session Count";
    }
    leaf flow-control-limit {
      type uint32;
      description
        "Flow Control credit limit";
    }
    leaf flow-control-in-flight-sessions {
      type uint32;
      description
        "Flow Control In-Flight Count";
    }
    leaf flow-control-dropped-sessions {
      type uint64;
      description
        "Flow Control Drop Count";
    }
    leaf flow-control-disconnected-sessions {
      type uint64;
      description
        "Flow Control Disconnected Count";
    }
    leaf flow-control-successful-sessions {
      type uint64;
      description
        "Flow Control Success Count, sessions completing
         call flow";
    }
    leaf pppoema-subscriber-infra-flow-control {
      type uint32;
      description
        "PPPoEMASubscriberInfraFlowControl";
    }
  }

  grouping PPPOE-MA-THROTTLE-CONFIG-SINGLE {
    description
      "PPPoE MA Single Throttle Config Information";
    leaf limit {
      type uint32;
      description
        "Limit";
    }
    leaf request-period {
      type uint32;
      description
        "PPPoE throttle request period";
    }
    leaf blocking-period {
      type uint32;
      description
        "PPPoE throttle blocking period";
    }
  }

  grouping PPPOE-MA-THROTTLE-CONFIG-INFO {
    description
      "PPPoE MA Throttle Config Information";
    container mac {
      description
        "MAC";
      uses PPPOE-MA-THROTTLE-CONFIG-SINGLE;
    }
    container mac-access-interface {
      description
        "MAC Access Interface";
      uses PPPOE-MA-THROTTLE-CONFIG-SINGLE;
    }
    container mac-iwf-access-interface {
      description
        "MAC IWF Access Interface";
      uses PPPOE-MA-THROTTLE-CONFIG-SINGLE;
    }
    container circuit-id {
      description
        "Circuit ID";
      uses PPPOE-MA-THROTTLE-CONFIG-SINGLE;
    }
    container remote-id {
      description
        "Remote ID";
      uses PPPOE-MA-THROTTLE-CONFIG-SINGLE;
    }
    container circuit-id-and-remote-id {
      description
        "Circuit ID and Remote ID";
      uses PPPOE-MA-THROTTLE-CONFIG-SINGLE;
    }
    container outer-vlan-id {
      description
        "Outer VLAN ID";
      uses PPPOE-MA-THROTTLE-CONFIG-SINGLE;
    }
    container inner-vlan-id {
      description
        "Inner VLAN ID";
      uses PPPOE-MA-THROTTLE-CONFIG-SINGLE;
    }
    container vlan-id {
      description
        "VLAN ID";
      uses PPPOE-MA-THROTTLE-CONFIG-SINGLE;
    }
  }

  grouping PPPOE-MA-THROTTLE-INFO {
    description
      "PPPoE MA Throttle information";
    leaf state {
      type Pppoe-ma-throttle-state;
      description
        "State";
    }
    leaf time-left {
      type uint32;
      units "second";
      description
        "Time left in seconds";
    }
    leaf since-reset {
      type uint32;
      units "second";
      description
        "Number of seconds since counters reset";
    }
    leaf padi-count {
      type uint32;
      description
        "PADI Count";
    }
    leaf padr-count {
      type uint32;
      description
        "PADR Count";
    }
  }

  grouping PPPOE-MA-LIMIT-INFO {
    description
      "PPPoE MA Limit information";
    leaf state {
      type Pppoe-ma-limit-state;
      description
        "State";
    }
    leaf session-count {
      type uint32;
      description
        "Total PPPoE subscriber session Count";
    }
    leaf radius-override-set {
      type int32;
      description
        "Overridden limit has been set";
    }
    leaf override-limit {
      type uint32;
      description
        "Overridden limit if set";
    }
  }

  grouping PPPOE-MA-LIMIT-CONFIG-SINGLE {
    description
      "PPPoE MA Single Limit Config information";
    leaf max-limit {
      type uint32;
      description
        "Max Limit";
    }
    leaf threshold {
      type uint32;
      description
        "Configured PPPoE sessions threshold value";
    }
    leaf radius-override-enabled {
      type int32;
      description
        "Radius override configuration is enabled";
    }
  }

  grouping PPPOE-MA-LIMIT-CONFIG-INFO {
    description
      "PPPoE MA Limit Configuration Information";
    container card {
      description
        "Card";
      uses PPPOE-MA-LIMIT-CONFIG-SINGLE;
    }
    container access-intf {
      description
        "Access Interface";
      uses PPPOE-MA-LIMIT-CONFIG-SINGLE;
    }
    container mac {
      description
        "MAC";
      uses PPPOE-MA-LIMIT-CONFIG-SINGLE;
    }
    container mac-iwf {
      description
        "MAC IWF";
      uses PPPOE-MA-LIMIT-CONFIG-SINGLE;
    }
    container mac-access-interface {
      description
        "MAC Access Interface";
      uses PPPOE-MA-LIMIT-CONFIG-SINGLE;
    }
    container mac-iwf-access-interface {
      description
        "MAC IWF Access Interface";
      uses PPPOE-MA-LIMIT-CONFIG-SINGLE;
    }
    container circuit-id {
      description
        "Circuit ID";
      uses PPPOE-MA-LIMIT-CONFIG-SINGLE;
    }
    container remote-id {
      description
        "Remote ID";
      uses PPPOE-MA-LIMIT-CONFIG-SINGLE;
    }
    container circuit-id-and-remote-id {
      description
        "Circuit ID and Remote ID";
      uses PPPOE-MA-LIMIT-CONFIG-SINGLE;
    }
    container outer-vlan-id {
      description
        "Outer VLAN ID";
      uses PPPOE-MA-LIMIT-CONFIG-SINGLE;
    }
    container inner-vlan-id {
      description
        "Inner VLAN ID";
      uses PPPOE-MA-LIMIT-CONFIG-SINGLE;
    }
    container vlan-id {
      description
        "VLAN ID";
      uses PPPOE-MA-LIMIT-CONFIG-SINGLE;
    }
  }

  grouping PPPOE-MA-TAGS-INFO {
    description
      "Tags information";
    container access-loop-encapsulation {
      description
        "Access Loop Encapsulation";
      uses PPPOE-MA-TAGS-ALE-INFO;
    }
    leaf service-name {
      type Pppoe-ma-bag-optional-string;
      description
        "Service Name";
    }
    leaf max-payload {
      type uint16;
      description
        "Max Payload";
    }
    leaf host-uniq {
      type yang:hex-string;
      description
        "Host Uniq";
    }
    leaf relay-session-id {
      type yang:hex-string;
      description
        "Relay Session ID";
    }
    leaf remote-id {
      type Pppoe-ma-bag-optional-string;
      description
        "Remote ID";
    }
    leaf circuit-id {
      type Pppoe-ma-bag-optional-string;
      description
        "Circuit ID";
    }
    leaf is-iwf {
      type int32;
      description
        "Is IWF";
    }
    leaf dsl-actual-up {
      type uint32;
      description
        "DSL Actual Up";
    }
    leaf dsl-actual-down {
      type uint32;
      description
        "DSL Actual Down";
    }
    leaf dsl-min-up {
      type uint32;
      description
        "DSL Min Up";
    }
    leaf dsl-min-down {
      type uint32;
      description
        "DSL Min Down";
    }
    leaf dsl-attain-up {
      type uint32;
      description
        "DSL Attain Up";
    }
    leaf dsl-attain-down {
      type uint32;
      description
        "DSL Attain Down";
    }
    leaf dsl-max-up {
      type uint32;
      description
        "DSL Max Up";
    }
    leaf dsl-max-down {
      type uint32;
      description
        "DSL Max Down";
    }
    leaf dsl-min-up-low {
      type uint32;
      description
        "DSL Min Up Low";
    }
    leaf dsl-min-down-low {
      type uint32;
      description
        "DSL Min Down Low";
    }
    leaf dsl-max-delay-up {
      type uint32;
      description
        "DSL Max Delay Up";
    }
    leaf dsl-actual-delay-up {
      type uint32;
      description
        "DSL Actual Delay Up";
    }
    leaf dsl-max-delay-down {
      type uint32;
      description
        "DSL Max Delay Down";
    }
    leaf dsl-actual-delay-down {
      type uint32;
      description
        "DSL Actual Delay Down";
    }
  }

  grouping PPPOE-MA-INTERFACE-INFO {
    description
      "PPPoE MA interface information";
    container tags {
      description
        "Tags";
      uses PPPOE-MA-TAGS-INFO;
    }
    leaf interface-name-xr {
      type xr:Interface-name;
      description
        "Interface";
    }
    leaf access-interface-name {
      type xr:Interface-name;
      description
        "Access Interface";
    }
    leaf bba-group-name {
      type string;
      description
        "BBA Group";
    }
    leaf session-id {
      type uint16;
      description
        "Session ID";
    }
    leaf local-mac-address {
      type yang:mac-address;
      description
        "PPPoE subscriber interface local mac-address";
    }
    leaf peer-mac-address {
      type yang:mac-address;
      description
        "PPPoE subscriber peer mac-address";
    }
    leaf is-complete {
      type int32;
      description
        "Is Complete";
    }
    leaf vlan-outer-id {
      type uint16;
      description
        "VLAN Outer ID";
    }
    leaf vlan-inner-id {
      type uint16;
      description
        "VLAN Inner ID";
    }
    leaf srg-state {
      type Pppoe-ma-session-idb-srg-state;
      description
        "SRG state";
    }
  }

  grouping PPPOE-MA-ACCESS-INTERFACE-INFO {
    description
      "PPPoE MA Access interface information";
    leaf interface-name-xr {
      type xr:Interface-name;
      description
        "Interface";
    }
    leaf interface-state {
      type Im-state;
      description
        "PPPoE access interface state";
    }
    leaf mac-address {
      type yang:mac-address;
      description
        "PPPPoE access interface mac-address";
    }
    leaf bba-group-name {
      type string;
      description
        "BBA Group";
    }
    leaf is-ready {
      type int32;
      description
        "Is Ready";
    }
    leaf sessions {
      type uint32;
      description
        "Session Count";
    }
    leaf incomplete-sessions {
      type uint32;
      description
        "Incomplete Session Count";
    }
  }

  grouping PPPOE-MA-PACKET-ERROR-COUNTS {
    description
      "PPPoE MA Packet Error Counts";
    leaf no-interface-handle {
      type uint32;
      description
        "Total count of No interface handle errors";
    }
    leaf no-packet-payload {
      type uint32;
      description
        "Total count of No packet payload errors";
    }
    leaf no-packet-mac-address {
      type uint32;
      description
        "Total count of No packet mac-address errors";
    }
    leaf invalid-version-type-value {
      type uint32;
      description
        "Total count of Invalid version-type value errors";
    }
    leaf bad-packet-length {
      type uint32;
      description
        "Total count of bad packet length errors";
    }
    leaf unknown-interface {
      type uint32;
      description
        "Total count of unknown interface errors";
    }
    leaf pado-received {
      type uint32;
      description
        "PADO received";
    }
    leaf pads-received {
      type uint32;
      description
        "PADS received";
    }
    leaf unknown-packet-type-received {
      type uint32;
      description
        "Total count of unknown packet type received
         errors";
    }
    leaf unexpected-session-id-in-packet {
      type uint32;
      description
        "Total count of unexpected Session-ID in packet
         errors";
    }
    leaf no-service-name-tag {
      type uint32;
      description
        "Total count of No Service-Name Tag errors";
    }
    leaf padt-for-unknown-session {
      type uint32;
      description
        "Total count of PADT for unknown session errors";
    }
    leaf padt-with-wrong-peer-mac {
      type uint32;
      description
        "Total count of PADT with wrong peer-mac errors";
    }
    leaf padt-with-wrong-vlan-tags {
      type uint32;
      description
        "PADT with wrong VLAN tags";
    }
    leaf zero-length-host-uniq {
      type uint32;
      description
        "Zero-length Host-Uniq tag";
    }
    leaf padt-before-pads-sent {
      type uint32;
      description
        "PADT before PADS sent";
    }
    leaf session-stage-packet-for-unknown-session {
      type uint32;
      description
        "Session-stage packet for unknown session";
    }
    leaf session-stage-packet-with-wrong-mac {
      type uint32;
      description
        "Total count of Session-stage packet with wrong
         mac errors";
    }
    leaf session-stage-packet-with-wrong-vlan-tags {
      type uint32;
      description
        "Total count of Session-stage packet with wrong
         VLAN tags errors";
    }
    leaf session-stage-packet-with-no-error {
      type uint32;
      description
        "Total count of Session-stage packet with no
         error";
    }
    leaf tag-too-short {
      type uint32;
      description
        "Total count of packets With too short tag";
    }
    leaf bad-tag-length-field {
      type uint32;
      description
        "Total count of packets with bad tag-length field";
    }
    leaf multiple-service-name-tags {
      type uint32;
      description
        "Total count of packets with multiple
         service-Name tags";
    }
    leaf multiple-max-payload-tags {
      type uint32;
      description
        "Total count of packets with multiple max-payload
         tags";
    }
    leaf invalid-max-payload-tag {
      type uint32;
      description
        "Total count of packets with invalid max-payload
         tag";
    }
    leaf multiple-vendor-specific-tags {
      type uint32;
      description
        "Total count of packets with multiple
         vendor-specific tags";
    }
    leaf unexpected-ac-name-tag {
      type uint32;
      description
        "Total count of packets with Unexpected AC-Name
         tag";
    }
    leaf unexpected-error-tags {
      type uint32;
      description
        "Total count of packets with Unexpected error
         tags";
    }
    leaf unknown-tag-received {
      type uint32;
      description
        "Total count of packets with Unknown tag received";
    }
    leaf no-iana-code-invendor-tag {
      type uint32;
      description
        "Total count of packets with No IANA code in
         vendor tag";
    }
    leaf invalid-iana-code-invendor-tag {
      type uint32;
      description
        "Total count of packets with Invalid IANA code in
         vendor tag";
    }
    leaf vendor-tag-too-short {
      type uint32;
      description
        "Total count of packets with too short Vendor Tag";
    }
    leaf bad-vendor-tag-length-field {
      type uint32;
      description
        "Total count of packets with bad vendor tag
         length field";
    }
    leaf multiple-host-uniq-tags {
      type uint32;
      description
        "Total count of packets with multiple Host-Uniq
         tags";
    }
    leaf multiple-relay-session-id-tags {
      type uint32;
      description
        "Total count of packets with multiple
         relay-session-id tags";
    }
    leaf multiple-circuit-id-tags {
      type uint32;
      description
        "Total count of packets with multiple circuit-ID
         tags";
    }
    leaf multiple-remote-id-tags {
      type uint32;
      description
        "Total count of packets with multiple Remote-ID
         tags";
    }
    leaf invalid-dsl-tag {
      type uint32;
      description
        "Total count of packets with invalid DSL tag";
    }
    leaf multiple-of-the-same-dsl-tag {
      type uint32;
      description
        "Total count of packets with multiple same DSL
         tag";
    }
    leaf invalid-iwf-tag {
      type uint32;
      description
        "Total count of packets with invalid IWF tag";
    }
    leaf multiple-iwf-tags {
      type uint32;
      description
        "Total count of packets with multiple IWF tags";
    }
    leaf unknownvendor-tag {
      type uint32;
      description
        "Total count of packets with Unknown vendor-tag";
    }
    leaf no-space-left-in-packet {
      type uint32;
      description
        "Total count of No space left in packet error";
    }
    leaf duplicate-host-uniq-tag-received {
      type uint32;
      description
        "Total count of packets with duplicate Host-Uniq
         tag received";
    }
    leaf duplicate-relay-session-id-tag-received {
      type uint32;
      description
        "Total count of packets with duplicate relay
         session ID tag received";
    }
    leaf packet-too-long {
      type uint32;
      description
        "Total count of packet too long";
    }
    leaf invalid-ale-tag {
      type uint32;
      description
        "Total count of packets with invalid ALE tag";
    }
    leaf multiple-ale-tags {
      type uint32;
      description
        "Total count of packets with multiple ALE tags";
    }
    leaf invalid-service-name {
      type uint32;
      description
        "Invalid Service Name";
    }
    leaf invalid-peer-mac {
      type uint32;
      description
        "Total count of packets with invalid peer MAC";
    }
    leaf invalid-vlan-tags {
      type uint32;
      description
        "Total count of packets with invalid VLAN tags";
    }
    leaf packet-on-srg-slave {
      type uint32;
      description
        "Total count of packets Received on SRG slave";
    }
  }

  grouping PPPOE-MA-TOTAL-STATS-INFO {
    description
      "PPPoE MA Total Statistics Information";
    container packet-counts {
      description
        "Total PPPoE packet count";
      uses PPPOE-MA-PACKET-COUNTS;
    }
    container packet-error-counts {
      description
        "Total PPPoE packet error Count";
      uses PPPOE-MA-PACKET-ERROR-COUNTS;
    }
  }

  grouping PPPOE-MA-DISC-HISTORY-UNIQUE {
    description
      "Wrapping history of disconnected subscribers";
    leaf-list disconnect-count {
      type uint32;
      max-elements "25";
      description
        "The total number of disconnects";
    }
    list entry {
      max-elements "25";
      description
        "Array of disconnected subscribers";
      uses PPPOE-MA-DISC-ENTRY;
    }
  }

  grouping PPPOE-MA-VLAN-TAG-TYPE {
    description
      "VLAN Tag Information";
    leaf ether-type {
      type uint16;
      description
        "Ethertype. See IEEE 802.1Q for more information.";
    }
    leaf user-priority {
      type uint8;
      description
        "VLAN user priority";
    }
    leaf cfi {
      type uint8;
      description
        "CFI";
    }
    leaf vlan-id {
      type uint16;
      description
        "VLAN ID";
    }
  }

  grouping PPPOE-MA-TAGS-ALE-INFO {
    description
      "Access-Loop-Encapsulation tag. See RFC-4679 for
       more detail";
    leaf data-link {
      type uint8;
      description
        "Data Link";
    }
    leaf encaps1 {
      type uint8;
      description
        "Encaps 1";
    }
    leaf encaps2 {
      type uint8;
      description
        "Encaps 2";
    }
  }

  grouping PPPOE-MA-INTERNAL-TAGS-INFO {
    description
      "Tags information";
    container access-loop-encapsulation {
      description
        "PPPoE access loop encapsulation tag";
      uses PPPOE-MA-TAGS-ALE-INFO;
    }
    leaf is-service-name {
      type int32;
      description
        "Is Service Name";
    }
    leaf is-max-payload {
      type int32;
      description
        "Is Max Payload";
    }
    leaf is-host-uniq {
      type int32;
      description
        "Is Host Uniq";
    }
    leaf is-relay-session-id {
      type int32;
      description
        "Is Relay Session ID";
    }
    leaf is-vendor-specific {
      type int32;
      description
        "This indicates if tag is vendor-specific.";
    }
    leaf is-iwf {
      type int32;
      description
        "Is IWF";
    }
    leaf is-remote-id {
      type int32;
      description
        "Is Remote ID";
    }
    leaf is-circuit-id {
      type int32;
      description
        "Is Circuit ID";
    }
    leaf is-dsl-tag {
      type int32;
      description
        "Is DSL Tag";
    }
    leaf service-name {
      type string;
      description
        "PPPoE service name tag";
    }
    leaf max-payload {
      type uint32;
      description
        "PPPoE max Payload tag";
    }
    leaf host-uniq {
      type yang:hex-string;
      description
        "Host Uniq";
    }
    leaf relay-session-id {
      type yang:hex-string;
      description
        "Relay Session ID";
    }
    leaf remote-id {
      type string;
      description
        "Remote ID";
    }
    leaf circuit-id {
      type string;
      description
        "Circuit ID";
    }
    leaf is-dsl-actual-up {
      type int32;
      description
        "Is DSL Actual Up";
    }
    leaf is-dsl-actual-down {
      type int32;
      description
        "Is DSL Actual Down";
    }
    leaf is-dsl-min-up {
      type int32;
      description
        "Is DSL Min Up";
    }
    leaf is-dsl-min-down {
      type int32;
      description
        "Is DSL Min Down";
    }
    leaf is-dsl-attain-up {
      type int32;
      description
        "Is DSL Attain Up";
    }
    leaf is-dsl-attain-down {
      type int32;
      description
        "Is DSL Attain Down";
    }
    leaf is-dsl-max-up {
      type int32;
      description
        "Is DSL Max Up";
    }
    leaf is-dsl-max-down {
      type int32;
      description
        "Is DSL Max Down";
    }
    leaf is-dsl-min-up-low {
      type int32;
      description
        "Is DSL Min Up Low";
    }
    leaf is-dsl-min-down-low {
      type int32;
      description
        "Is DSL Min Down Low";
    }
    leaf is-dsl-max-delay-up {
      type int32;
      description
        "Is DSL Max Delay Up";
    }
    leaf is-dsl-actual-delay-up {
      type int32;
      description
        "Is DSL Actual Delay Up";
    }
    leaf is-dsl-max-delay-down {
      type int32;
      description
        "Is DSL Max Delay Down";
    }
    leaf is-dsl-actual-delay-down {
      type int32;
      description
        "Is DSL Actual Delay Down";
    }
    leaf is-access-loop-encapsulation {
      type int32;
      description
        "This indicates if tag is access loop
         encapsulation specific";
    }
    leaf dsl-actual-up {
      type uint32;
      description
        "DSL Actual Up";
    }
    leaf dsl-actual-down {
      type uint32;
      description
        "DSL Actual Down";
    }
    leaf dsl-min-up {
      type uint32;
      description
        "DSL Min Up";
    }
    leaf dsl-min-down {
      type uint32;
      description
        "DSL Min Down";
    }
    leaf dsl-attain-up {
      type uint32;
      description
        "DSL Attain Up";
    }
    leaf dsl-attain-down {
      type uint32;
      description
        "DSL Attain Down";
    }
    leaf dsl-max-up {
      type uint32;
      description
        "DSL Max Up";
    }
    leaf dsl-max-down {
      type uint32;
      description
        "DSL Max Down";
    }
    leaf dsl-min-up-low {
      type uint32;
      description
        "DSL Min Up Low";
    }
    leaf dsl-min-down-low {
      type uint32;
      description
        "DSL Min Down Low";
    }
    leaf dsl-max-delay-up {
      type uint32;
      description
        "DSL Max Delay Up";
    }
    leaf dsl-actual-delay-up {
      type uint32;
      description
        "DSL Actual Delay Up";
    }
    leaf dsl-max-delay-down {
      type uint32;
      description
        "DSL Max Delay Down";
    }
    leaf dsl-actual-delay-down {
      type uint32;
      description
        "DSL Actual Delay Down";
    }
  }

  grouping PPPOE-MA-SESSION-IDB-INFO {
    description
      "PPPoE MA Session IDB information";
    container tags {
      description
        "Tags";
      uses PPPOE-MA-INTERNAL-TAGS-INFO;
    }
    container vlan-outer-tag {
      description
        "VLAN Outer Tag";
      uses PPPOE-MA-VLAN-TAG-TYPE;
    }
    container vlan-inner-tag {
      description
        "VLAN Inner Tag";
      uses PPPOE-MA-VLAN-TAG-TYPE;
    }
    leaf interface {
      type xr:Interface-name;
      description
        "PPPoE subscriber interface";
    }
    leaf access-interface {
      type xr:Interface-name;
      description
        "PPPoE subscriber access interface";
    }
    leaf session-id {
      type uint16;
      description
        "Session ID";
    }
    leaf sub-label {
      type uint32;
      description
        "Sub Label";
    }
    leaf peer-mac-address {
      type yang:mac-address;
      description
        "PPPoE subscriber peer mac-address";
    }
    leaf state {
      type Pppoe-ma-session-state;
      description
        "State";
    }
    leaf cdm-object-handle {
      type uint32;
      description
        "CDM Object Handle";
    }
    leaf chkpt-id {
      type uint32;
      description
        "Chkpt ID";
    }
    leaf punted-count {
      type uint32;
      description
        "Total number of punted packets";
    }
    leaf port-limit {
      type uint32;
      description
        "Port Limit";
    }
    leaf is-counted {
      type int32;
      description
        "Is BBA Counted";
    }
    leaf is-vlan-outer-tag {
      type int32;
      description
        "Is VLAN Outer Tag";
    }
    leaf is-vlan-inner-tag {
      type int32;
      description
        "Is VLAN Inner Tag";
    }
    leaf is-cleanup-pending {
      type int32;
      description
        "PPPoE subscriber cleanup pending status";
    }
    leaf is-disconnect-done-pending {
      type int32;
      description
        "PPPoE subscriber disconnect done pending status";
    }
    leaf is-delete-done-pending {
      type int32;
      description
        "PPPoE subscriber delete done pending status";
    }
    leaf is-intf-create-callback-pending {
      type int32;
      description
        "PPPoE subscriber interface create callback
         pending status";
    }
    leaf is-publish-encaps-attr-pending {
      type int32;
      description
        "PPPoE subscriber publish encaps attr pending
         status";
    }
    leaf is-publish-encaps-attr-cb-pending {
      type int32;
      description
        "Publish encaps attr callback pending status";
    }
    leaf is-intf-delete-callback-pending {
      type int32;
      description
        "PPPoE subscriber interface delete callback
         pending status";
    }
    leaf is-intf-delete-pending {
      type int32;
      description
        "Indicates if interface delete is pending";
    }
    leaf is-im-owned-resource {
      type int32;
      description
        "IM owned resource indicator";
    }
    leaf is-im-final-received {
      type int32;
      description
        "IM final received status";
    }
    leaf is-im-owned-resource-missing {
      type int32;
      description
        "IM owned resource notification is missing status";
    }
    leaf is-aaa-start-request-callback-pending {
      type int32;
      description
        "AAA session start request callback pending
         status";
    }
    leaf is-aaa-owned-resource {
      type int32;
      description
        "AAA owned resource indicator";
    }
    leaf is-aaa-disconnect-requested {
      type int32;
      description
        "AAA disconnect is requested status";
    }
    leaf is-aaa-disconnect-received {
      type int32;
      description
        "AAA disconnect is received status";
    }
    leaf is-sub-db-activate-callback-pending {
      type int32;
      description
        "SubDB Session Activate callback pending status";
    }
    leaf is-pads-sent {
      type int32;
      description
        "PADS sent status";
    }
    leaf is-padt-received {
      type int32;
      description
        "PADT received status";
    }
    leaf is-in-flight {
      type int32;
      description
        "Session in flight status";
    }
    leaf is-radius-override {
      type int32;
      description
        "RADIUS override enabled status";
    }
    leaf expected-notifications {
      type uint8;
      description
        "Total number of expected Notifications";
    }
    leaf received-notifications {
      type uint8;
      description
        "Total number of received Notifications";
    }
    leaf srg-state {
      type Pppoe-ma-session-idb-srg-state;
      description
        "SRG state";
    }
    leaf is-srg-data-received {
      type int32;
      description
        "SRG data received status";
    }
    leaf is-iedge-data-received {
      type int32;
      description
        "IEDGE data received status";
    }
  }

  grouping PPPOE-MA-DISC-ENTRY {
    description
      "PPPoE disconnected subscriber information";
    container session-idb {
      description
        "Session IDB";
      uses PPPOE-MA-SESSION-IDB-INFO;
    }
    leaf timestamp {
      type uint64;
      description
        "Time when disconnected";
    }
    leaf ifname {
      type string;
      description
        "Interface name";
    }
    leaf trigger {
      type Pppoe-ma-session-trig;
      description
        "Disconnect Trigger";
    }
  }

  grouping PPPOE-MA-DISC-HISTORY {
    description
      "Wrapping history of disconnected subscribers";
    leaf current-idx {
      type uint32;
      description
        "Current index of history";
    }
    list entry {
      description
        "Array of disconnected subscribers";
      uses PPPOE-MA-DISC-ENTRY;
    }
  }

  grouping PPPOE-MA-PACKET-TYPE-COUNTS {
    description
      "PPPoE MA Packet type counts";
    leaf sent {
      type uint32;
      description
        "Total number of packets sent";
    }
    leaf received {
      type uint32;
      description
        "Total number of packets received";
    }
    leaf dropped {
      type uint32;
      description
        "Total number of packets dropped";
    }
  }

  grouping PPPOE-MA-PACKET-COUNTS {
    description
      "PPPoE MA Packet Counts";
    container padi {
      description
        "PADI counts";
      uses PPPOE-MA-PACKET-TYPE-COUNTS;
    }
    container pado {
      description
        "PADO counts";
      uses PPPOE-MA-PACKET-TYPE-COUNTS;
    }
    container padr {
      description
        "PADR counts";
      uses PPPOE-MA-PACKET-TYPE-COUNTS;
    }
    container pads-success {
      description
        "PADS Success counts";
      uses PPPOE-MA-PACKET-TYPE-COUNTS;
    }
    container pads-error {
      description
        "PADS Error counts";
      uses PPPOE-MA-PACKET-TYPE-COUNTS;
    }
    container padt {
      description
        "PADT counts";
      uses PPPOE-MA-PACKET-TYPE-COUNTS;
    }
    container session-state {
      description
        "Session Stage counts";
      uses PPPOE-MA-PACKET-TYPE-COUNTS;
    }
    container other {
      description
        "Other counts";
      uses PPPOE-MA-PACKET-TYPE-COUNTS;
    }
  }

  grouping PPPOE-MA-ACCESS-INTERFACE-STATS-INFO {
    description
      "PPPoE MA Access Interface Statistics Information";
    container packet-counts {
      description
        "Total packet counts for PPPoE access interface";
      uses PPPOE-MA-PACKET-COUNTS;
    }
  }
}
