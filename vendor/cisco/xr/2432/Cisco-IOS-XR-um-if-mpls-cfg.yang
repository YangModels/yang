module Cisco-IOS-XR-um-if-mpls-cfg {
  namespace "http://cisco.com/ns/yang/Cisco-IOS-XR-um-if-mpls-cfg";
  prefix um-if-mpls-cfg;

  import cisco-semver {
    prefix semver;
  }
  import Cisco-IOS-XR-um-interface-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-mpls package configuration.
     
     This YANG module augments the
     modules with configuration data.
     
     Copyright (c) 2019-2022 by Cisco Systems, Inc.
     All rights reserved.";

  revision 2022-07-11 {
    description
      "Added missing description statement to nodes";
    semver:module-version "1.1.0";
  }
  revision 2019-06-10 {
    description
      "Establish semantic version baseline.";
    semver:module-version "1.0.1";
  }
  revision 2019-03-30 {
    description
      "Initial version";
  }

  grouping GROUP-MPLS {
    description
      "Grouping for mpls";
    container mpls {
      description
        "MPLS interface subcommands";
      leaf mtu {
        type uint32 {
          range "68..65535" {
            description
              " MTU size in bytes";
          }
        }
        description
          "Set the MPLS MTU for the interface";
      }
      container label-security {
        description
          "MPLS label-security for the interface";
        container rpf {
          presence "Indicates a rpf node is configured.";
          description
            "MPLS RPF for incoming packets";
        }
        container multi-label-packet {
          description
            "Handling incoming packets with multiple labels on the stack";
          container drop {
            presence "Indicates a drop node is configured.";
            description
              "Drop packets with multiple labels on the stack";
          }
        }
      }
    }
  }

  augment "/a1:interfaces/a1:interface" {
    description
      "This augment extends active nodes configuration";
    uses GROUP-MPLS;
  }
  augment "/a1:interfaces/a1:interface-preconfigure" {
    description
      "This augment extends preconfigured nodes
       configuration";
    uses GROUP-MPLS;
  }
}
