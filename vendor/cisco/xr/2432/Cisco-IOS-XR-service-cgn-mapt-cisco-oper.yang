module Cisco-IOS-XR-service-cgn-mapt-cisco-oper {
  namespace "http://cisco.com/ns/yang/Cisco-IOS-XR-service-cgn-mapt-cisco-oper";
  prefix service-cgn-mapt-cisco-oper;

  import Cisco-IOS-XR-types {
    prefix xr;
  }
  import cisco-semver {
    prefix semver;
  }
  include Cisco-IOS-XR-service-cgn-mapt-cisco-oper-sub1 {
    revision-date 2023-11-21;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR service-cgn-mapt-cisco package operational data.
     
     This module contains definitions
     for the following management objects:
       cgn: STATS data for CGN
       cgn-stats: Operational data for CGN
     
     Copyright (c) 2013-2023 by Cisco Systems, Inc.
     All rights reserved.";

  revision 2023-11-21 {
    description
      "Added mapt-cisco Yang Model.";
    semver:module-version "1.0.0";
  }
  revision 2019-04-05 {
    description
      "Establish semantic version baseline.";
  }
  revision 2015-11-09 {
    description
      "IOS XR 6.0 revision.";
  }

  container cgn {
    config false;
    description
      "STATS data for CGN";
    list mapt-remote-id {
      key "remote-id";
      description
        "Mapt instance translations operational data";
      container service-stats {
        description
          "Statistics of a MAPT statless instance";
        uses MAP-T-CISCO-STATS-SUMMARY;
      }
      leaf remote-id {
        type uint32;
        description
          "Remote Identifier";
      }
    }
  }
  container cgn-stats {
    config false;
    description
      "Operational data for CGN";
    list mapt-table {
      key "mapt-name";
      description
        "Mapt instance translations operational data";
      container statistics {
        description
          "Statistics of a MAPT statless instance";
        uses MAP-T-CISCO-STATS-SUMMARY;
      }
      leaf mapt-name {
        type xr:Cisco-ios-xr-string {
          length "1..24";
        }
        description
          "MAPT instance name";
      }
    }
  }
}
