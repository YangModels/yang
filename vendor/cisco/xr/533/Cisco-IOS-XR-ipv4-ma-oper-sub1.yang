submodule Cisco-IOS-XR-ipv4-ma-oper-sub1 {

  belongs-to Cisco-IOS-XR-ipv4-ma-oper {
    prefix Cisco-IOS-XR-ipv4-ma-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-ma package operational data.

     Copyright (c) 2013-2015 by Cisco Systems, Inc.
     All rights reserved.";

  revision "2015-01-07" {
    description
      "IOS XR 5.3.1 revision.";
  }

  typedef Rpf-mode {
    type enumeration {
      enum strict {
        description "Strict RPF";
      }
      enum loose {
        description "Loose RPF";
      }
    }
    description "Interface line states";
  }
  typedef Str {
    type string;
    description "Str";
  }
  typedef Ipv4-ma-oper-line-state {
    type enumeration {
      enum unknown {
        description "Interface state is unknown";
      }
      enum shutdown {
        description "Interface has been shutdown";
      }
      enum down {
        description "Interface state is down";
      }
      enum up {
        description "Interface state is up";
      }
    }
    description "Interface line states";
  }

  grouping IF-SUMMARY {
    description "Count of assigned/unnumbered interfaces";
    leaf ip-assigned {
      xr:xr-xml-map "ipv4_ma_oper_interface:IPAssigned";
      type uint32;
      description "Number of interfaces with explicit addresses";
    }
    leaf ip-unnumbered {
      xr:xr-xml-map "ipv4_ma_oper_interface:IPUnnumbered";
      type uint32;
      description
        "Number of unnumbered interfaces with explicit
        addresses";
    }
  }

  grouping IPV4-IF-SUMMARY {
    description "Summary info of IP interfaces";

    container if-up-up {
      description "Number of interfaces (up,up)";
      uses IF-SUMMARY;
    }

    container if-up-down {
      description "Number of interfaces (up,down)";
      uses IF-SUMMARY;
    }

    container if-down-down {
      description "Number of interfaces (down,down)";
      uses IF-SUMMARY;
    }

    container if-shutdown-down {
      description "Number of interfaces (shutdown,down)";
      uses IF-SUMMARY;
    }
    leaf if-up-down-basecaps-up {
      xr:xr-xml-map "ipv4_ma_oper_interface:IFUpDownBasecapsUp";
      type uint32;
      description "Number of interfaces (up,down) with basecaps up";
    }
  }

  grouping IPV4-IF-BRIEF {
    description "Brief Summary of IP Interface";
    leaf primary-address {
      xr:xr-xml-map "ipv4_ma_oper_interface:PrimaryAddress";
      type inet:ipv4-address;
      description "Primary address";
    }
    leaf vrf-id {
      xr:xr-xml-map "ipv4_ma_oper_interface:VRF_ID";
      type uint32;
      description "VRF ID of the interface";
    }
    leaf line-state {
      xr:xr-xml-map "ipv4_ma_oper_interface:LineState";
      type Ipv4-ma-oper-line-state;
      description "Line state of the interface";
    }
  }

  grouping TIMEVAL-ENTRY {
    description "Creation or Update Time";
  }

  grouping BGP-PA-DIR {
    description "BGP PA config for ingress/egress direction";
    leaf enable {
      xr:xr-xml-map "ipv4_ma_oper_interface:Enable";
      type boolean;
      description "Enable BGP PA for ingress/egress";
    }
    leaf source {
      xr:xr-xml-map "ipv4_ma_oper_interface:Source";
      type boolean;
      description "Enable source accouting";
    }
    leaf destination {
      xr:xr-xml-map "ipv4_ma_oper_interface:Destination";
      type boolean;
      description "Enable destination accouting";
    }
  }

  grouping BGP-PA-CONFIG {
    description "BGP PA config information";

    container input {
      description "BGP PA input config";
      uses BGP-PA-DIR;
    }

    container output {
      description "BGP PA output config";
      uses BGP-PA-DIR;
    }
  }

  grouping RPF-CONFIG {
    description "RPF config information";
    leaf enable {
      xr:xr-xml-map "ipv4_ma_oper_interface:Enable";
      type boolean;
      description "Enable RPF config";
    }
    leaf allow-default-route {
      xr:xr-xml-map "ipv4_ma_oper_interface:AllowDefaultRoute";
      type boolean;
      description "Allow Default Route";
    }
    leaf allow-self-ping {
      xr:xr-xml-map "ipv4_ma_oper_interface:AllowSelfPing";
      type boolean;
      description "Allow Self Ping";
    }
    leaf mode {
      xr:xr-xml-map "ipv4_ma_oper_interface:Mode";
      type Rpf-mode;
      description "RPF Mode (loose/strict)";
    }
  }

  grouping HADDR-ARRAY {
    description "Helper Address List ";
    leaf-list address-array {
      xr:xr-xml-map "ipv4_ma_oper_interface:AddressArray";
      type inet:ipv4-address;
      description "Helper address";
    }
  }

  grouping ACL-CONFIG {
    description "ACL config information";
    leaf-list inbound {
      xr:xr-xml-map "ipv4_ma_oper_interface:inbound";
      type Str;
      max-elements "5";
      description "Inbound ACLs";
    }
    leaf-list outbound {
      xr:xr-xml-map "ipv4_ma_oper_interface:outbound";
      type Str;
      max-elements "5";
      description "Outbound ACLs";
    }
    leaf-list common {
      xr:xr-xml-map "ipv4_ma_oper_interface:common";
      type Str;
      max-elements "5";
      description "Common ACLs";
    }
  }

  grouping IP-ADDR-NODE {
    description "List of IP Addresses ";
    leaf address {
      xr:xr-xml-map "ipv4_ma_oper_interface:Address";
      type inet:ipv4-address;
      description "Address";
    }
    leaf prefix-length {
      xr:xr-xml-map "ipv4_ma_oper_interface:PrefixLength";
      type uint32;
      description "Prefix length of address";
    }
    leaf route-tag {
      xr:xr-xml-map "ipv4_ma_oper_interface:RouteTag";
      type uint32;
      description
        "Route Tag associated with this address (0 = no
        tag)";
    }
  }

  grouping MCAST-GROUP {
    description "MCast Group List ";
    leaf group-address {
      xr:xr-xml-map "ipv4_ma_oper_interface:GroupAddress";
      type inet:ipv4-address;
      description "Address of multicast group";
    }
  }

  grouping IPV4-IF-DETAIL {
    description "Detailed Info of IP Interface";

    container acl {
      description "ACLs configured on the interface";
      uses ACL-CONFIG;
    }

    container helper-address {
      description "Helper Addresses configured on the interface";
      uses HADDR-ARRAY;
    }

    container rpf {
      description "RPF config on the interface";
      uses RPF-CONFIG;
    }

    container bgp-pa {
      description "BGP PA config on the interface";
      uses BGP-PA-CONFIG;
    }

    container pub-utime {
      description "Address Publish Time";
      uses TIMEVAL-ENTRY;
    }

    container idb-utime {
      description "IDB Create Time";
      uses TIMEVAL-ENTRY;
    }

    container caps-utime {
      description "CAPS Add Time";
      uses TIMEVAL-ENTRY;
    }

    container fwd-en-utime {
      description "FWD ENABLE Time";
      uses TIMEVAL-ENTRY;
    }

    container fwd-dis-utime {
      description "FWD DISABLE Time";
      uses TIMEVAL-ENTRY;
    }
    leaf primary-address {
      xr:xr-xml-map "ipv4_ma_oper_interface:PrimaryAddress";
      type inet:ipv4-address;
      description "Primary address";
    }
    leaf vrf-id {
      xr:xr-xml-map "ipv4_ma_oper_interface:VRF_ID";
      type uint32;
      description "VRF ID of the interface";
    }
    leaf line-state {
      xr:xr-xml-map "ipv4_ma_oper_interface:LineState";
      type Ipv4-ma-oper-line-state;
      description "Line state of the interface";
    }
    leaf prefix-length {
      xr:xr-xml-map "ipv4_ma_oper_interface:PrefixLength";
      type uint32;
      description "Prefix length of primary address";
    }
    leaf route-tag {
      xr:xr-xml-map "ipv4_ma_oper_interface:RouteTag";
      type uint32;
      description
        "Route tag associated with the primary address (0
        = no tag)";
    }
    leaf mtu {
      xr:xr-xml-map "ipv4_ma_oper_interface:MTU";
      type uint32;
      description "IP MTU of the interface";
    }
    leaf unreachable {
      xr:xr-xml-map "ipv4_ma_oper_interface:Unreachable";
      type boolean;
      description "Are ICMP unreachables sent on the interface?";
    }
    leaf redirect {
      xr:xr-xml-map "ipv4_ma_oper_interface:Redirect";
      type boolean;
      description "Are ICMP redirects sent on the interface?";
    }
    leaf direct-broadcast {
      xr:xr-xml-map "ipv4_ma_oper_interface:DirectBroadcast";
      type boolean;
      description "Are direct broadcasts sent on the interface?";
    }
    leaf mask-reply {
      xr:xr-xml-map "ipv4_ma_oper_interface:MaskReply";
      type boolean;
      description "Are mask replies sent on the interface?";
    }
    leaf rg-id-exists {
      xr:xr-xml-map "ipv4_ma_oper_interface:RG_IDExists";
      type boolean;
      description "Does ICCP RG ID exist on the interface?";
    }
    leaf mlacp-active {
      xr:xr-xml-map "ipv4_ma_oper_interface:mLACPActive";
      type boolean;
      description "Is mLACP state Active (valid if RG ID exists)";
    }
    leaf unnumbered-interface-name {
      xr:xr-xml-map "ipv4_ma_oper_interface:UnnumberedInterfaceName";
      type string {
        length "0..64";
      }
      description
        "Name of referenced interface (valid if
        unnumbered)";
    }
    leaf proxy-arp-disabled {
      xr:xr-xml-map "ipv4_ma_oper_interface:ProxyARPDisabled";
      type boolean;
      description "Is Proxy ARP disabled on the interface?";
    }
    leaf flow-tag-src {
      xr:xr-xml-map "ipv4_ma_oper_interface:FLOW_TAG_SRC";
      type boolean;
      description "Is BGP Flow Tag Source is enable";
    }
    leaf flow-tag-dst {
      xr:xr-xml-map "ipv4_ma_oper_interface:FLOW_TAG_DST";
      type boolean;
      description "Is BGP Flow Tag Destination is enable";
    }

    list multicast-group {
      description "Multicast groups joined on the interface";
      uses MCAST-GROUP;
    }

    list secondary-address {
      description "Secondary addresses on the interface";
      uses IP-ADDR-NODE;
    }
  }
}
