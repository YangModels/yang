module Cisco-IOS-XR-ipv6-ma-subscriber-cfg {

  /*** NAMESPACE / PREFIX DEFINITION ***/

  namespace "http://cisco.com/ns/yang"+
    "/Cisco-IOS-XR-ipv6-ma-subscriber-cfg";


  prefix "ipv6-ma-subscriber-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ma-subscriber package configuration.

     This YANG module augments the
       Cisco-IOS-XR-subscriber-infra-tmplmgr-cfg
     module with configuration data.

     Copyright (c) 2013-2015 by Cisco Systems, Inc.
     All rights reserved.";

  revision "2015-01-07" {
    description
      "IOS XR 5.3.1 revision.";
  }

  typedef Ipv6-reachable-via {
    type enumeration {
      enum received {
        value 1;
        description
          "Source is reachable via interface on which
          packet was received";
      }
    }
    description "Ipv6 reachable via";
  }

  grouping IPV6-NETWORK {
    description
      "Common node of ip-subscriber, ppp,
      subscriber-service";

    container ipv6-network {
      xr:xr-xml-map "cfg_ipv6_ma_dyn_tmpl:IPV6Network";
      description "Interface IPv6 Network configuration data";

      container addresses {
        xr:xr-xml-map "cfg_ipv6_ma_dyn_tmpl:Addresses";
        description "Set the IPv6 address of an interface";

        container auto-configuration {
          xr:xr-xml-map "cfg_ipv6_ma_dyn_tmpl:AutoConfiguration";
          description "Auto IPv6 Interface Configuration";
          leaf enable {
            xr:xr-xml-map "cfg_ipv6_ma_dyn_tmpl:Enable";
            type empty;
            description
              "The flag to enable auto ipv6 interface
              configuration";
          }
        }
      }
      leaf mtu {
        xr:xr-xml-map "cfg_ipv6_ma_dyn_tmpl:MTU";
        type uint32 {
          range "1280..65535";
        }
        units "byte";
        description "MTU(bytes)";
      }
      leaf unreachables {
        xr:xr-xml-map "cfg_ipv6_ma_dyn_tmpl:Unreachables";
        type empty;
        description "Override Sending of ICMP Unreachable Messages";
      }
      leaf verify {
        xr:xr-xml-map "cfg_ipv6_ma_dyn_tmpl:Verify";
        type Ipv6-reachable-via;
        description "Source Reachable Interface";
      }
    }
  }

  augment "/a1:dynamic-template/a1:subscriber-services"+
    "/a1:subscriber-service" {
    description
      "This augment extends the configuration data of
      'Cisco-IOS-XR-subscriber-infra-tmplmgr-cfg'";
    uses IPV6-NETWORK;
  }

  augment "/a1:dynamic-template/a1:ppps/a1:ppp" {
    description
      "This augment extends the configuration data of
      'Cisco-IOS-XR-subscriber-infra-tmplmgr-cfg'";
    uses IPV6-NETWORK;
  }

  augment "/a1:dynamic-template/a1:ip-subscribers/a1:ip-subscriber" {
    description
      "This augment extends the configuration data of
      'Cisco-IOS-XR-subscriber-infra-tmplmgr-cfg'";
    uses IPV6-NETWORK;
  }
}
