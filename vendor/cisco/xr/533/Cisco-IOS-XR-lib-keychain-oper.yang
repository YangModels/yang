module Cisco-IOS-XR-lib-keychain-oper {

  /*** NAMESPACE / PREFIX DEFINITION ***/

  namespace "http://cisco.com/ns"+
    "/yang/Cisco-IOS-XR-lib-keychain-oper";


  prefix "lib-keychain-oper";

  /*** LINKAGE (IMPORTS / INCLUDES) ***/

  import Cisco-IOS-XR-types { prefix "xr"; }

  include Cisco-IOS-XR-lib-keychain-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-keychain package operational data.

     This module contains definitions
     for the following management objects:
       keychain: Keychain operational data

     Copyright (c) 2013-2015 by Cisco Systems, Inc.
     All rights reserved.";

  revision "2015-01-07" {
    description
      "IOS XR 5.3.1 revision.";
  }


  container keychain {
    xr:xr-xml-map "keychain_oper:Keychain";
    config false;
    description "Keychain operational data";

    container keies {
      xr:xr-xml-map "keychain_oper:KeyTable";
      description "List of configured key names";

      list key {
        xr:xr-xml-map "keychain_oper:Key";
        key "key-name";
        description "Configured key name";
        leaf key-name {
          xr:xr-xml-map "keychain_oper:KeyName";
          type xr:Cisco-ios-xr-string;
          description "Key name";
        }
        uses KEY-CHAIN;
      }
    }
  }
}
