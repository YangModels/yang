submodule Cisco-IOS-XR-icpe-sdacp-oper-sub2 {
  belongs-to Cisco-IOS-XR-icpe-sdacp-oper {
    prefix Cisco-IOS-XR-icpe-sdacp-oper;
  }

  import ietf-inet-types {
    prefix inet;
  }
  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-sdacp package operational data.
     
     Copyright (c) 2013-2017 by Cisco Systems, Inc.
     All rights reserved.";

  revision 2015-11-09 {
    description
      "IOS XR 6.0 revision.";
  }

  typedef Dpm-proto-host-state {
    type enumeration {
      enum "dpm-proto-host-state-idle" {
        description
          "Idle";
      }
      enum "dpm-proto-host-state-discovered" {
        description
          "Discovered";
      }
      enum "dpm-proto-host-state-rejecting" {
        description
          "Rejecting";
      }
    }
    description
      "Dpm proto host state";
  }

  typedef Dpm-proto-state {
    type enumeration {
      enum "dpm-proto-state-idle" {
        description
          "Idle";
      }
      enum "dpm-proto-state-probing" {
        description
          "Probing";
      }
      enum "dpm-proto-state-legacy" {
        description
          "Legacy";
      }
      enum "dpm-proto-state-configuring" {
        description
          "Configuring";
      }
      enum "dpm-proto-state-discovered" {
        description
          "Discovered";
      }
      enum "dpm-proto-state-rejecting" {
        description
          "Rejecting";
      }
      enum "dpm-proto-state-seen" {
        description
          "Seen";
      }
    }
    description
      "Dpm proto state";
  }

  typedef Xr-yang-string {
    type string;
    description
      "Xr yang string";
  }

  grouping ICPE-YANG-CAPABILITIES-TLV-TYPE {
    description
      "ICPE YANG CAPABILITIES TLV TYPE";
    leaf type {
      type uint32;
      description
        "Type";
    }
    leaf debug {
      type Xr-yang-string;
      description
        "Debug";
    }
    leaf-list value {
      type uint8;
      description
        "Value";
    }
  }

  grouping ICPE-YANG-CAPABILITIES-TYPE {
    description
      "ICPE YANG CAPABILITIES TYPE";
    list tl-vs {
      description
        "Capability TLVs table";
      uses ICPE-YANG-CAPABILITIES-TLV-TYPE;
    }
  }

  grouping DPM-OPER-HOST-TYPE {
    description
      "DPM OPER HOST TYPE";
    leaf host-chassis-mac {
      type yang:mac-address;
      description
        "Host chassis MAC";
    }
    leaf host-interface-mac {
      type yang:mac-address;
      description
        "Host interface MAC";
    }
    leaf discovery-protocol-state {
      type Dpm-proto-host-state;
      description
        "Discovery protocol state";
    }
    leaf route-length {
      type uint32;
      description
        "Route length";
    }
    leaf current-timeout {
      type uint32;
      description
        "Current timeout";
    }
    leaf host-ack-packets-received {
      type uint64;
      description
        "Host ack packets received";
    }
    leaf host-ack-packets-sent {
      type uint64;
      description
        "Host ack packets sent";
    }
    leaf secs-since-pkts-cleaned {
      type uint64;
      units "second";
      description
        "Secs since pkts cleaned";
    }
  }

  grouping DPM-OPER-SAT-TYPE {
    description
      "DPM OPER SAT TYPE";
    leaf satellite-id {
      type uint16;
      description
        "Satellite ID";
    }
    leaf satellite-interface-id {
      type uint32;
      description
        "Satellite interface ID";
    }
    leaf satellite-interface-mac {
      type yang:mac-address;
      description
        "Satellite interface MAC";
    }
    leaf satellite-ip-address {
      type inet:ipv4-address;
      description
        "Satellite IP address";
    }
    leaf host-ip-address {
      type inet:ipv4-address;
      description
        "Host IP address";
    }
    leaf satellite-chassis-type {
      type Xr-yang-string;
      description
        "Satellite chassis type";
    }
    leaf satellite-chassis-vendor {
      type Xr-yang-string;
      description
        "Satellite chassis vendor";
    }
    leaf satellite-chassis-mac {
      type yang:mac-address;
      description
        "Satellite chassis MAC";
    }
    leaf satellite-serial-id {
      type Xr-yang-string;
      description
        "Satellite serial id";
    }
    leaf satellite-module-type {
      type Xr-yang-string;
      description
        "Satellite module type";
    }
    leaf satellite-module-vendor {
      type Xr-yang-string;
      description
        "Satellite module vendor";
    }
    leaf satellite-module-mac {
      type yang:mac-address;
      description
        "Satellite module MAC";
    }
    leaf conflict-reason {
      type uint32;
      description
        "Conflict reason";
    }
    leaf received-sys-mac {
      type yang:mac-address;
      description
        "Received sys MAC";
    }
    leaf host-chassis-type {
      type Xr-yang-string;
      description
        "Host chassis type";
    }
    leaf host-chassis-vendor {
      type Xr-yang-string;
      description
        "Host chassis vendor";
    }
    leaf host-chassis-mac {
      type yang:mac-address;
      description
        "Host chassis MAC";
    }
    leaf discovery-protocol-state {
      type Dpm-proto-state;
      description
        "Discovery protocol state";
    }
    leaf last-imdr-state {
      type uint32;
      description
        "Last IMDR state";
    }
    leaf current-timeout {
      type uint32;
      description
        "Current timeout";
    }
    leaf is-queued-for-efd {
      type boolean;
      description
        "Is queued for EFD";
    }
    leaf is-queued-for-oc {
      type boolean;
      description
        "Is queued for OC";
    }
    leaf ifmgr-state {
      type boolean;
      description
        "Ifmgr state";
    }
    leaf legacy {
      type boolean;
      description
        "Legacy";
    }
    leaf deleting {
      type boolean;
      description
        "Deleting";
    }
    leaf ident-packets-received {
      type uint64;
      description
        "Ident packets received";
    }
    leaf ready-packets-received {
      type uint64;
      description
        "Ready packets received";
    }
    leaf los-packets-received {
      type uint64;
      description
        "Los packets received";
    }
    leaf invalid-packets-received {
      type uint64;
      description
        "Invalid packets received";
    }
    leaf configuration-packets-sent {
      type uint64;
      description
        "Configuration packets sent";
    }
    leaf ack-packets-sent {
      type uint64;
      description
        "Ack packets sent";
    }
    leaf reject-packets-sent {
      type uint64;
      description
        "Reject packets sent";
    }
    leaf secs-since-pkts-cleaned {
      type uint64;
      units "second";
      description
        "Secs since pkts cleaned";
    }
  }

  grouping DPM-OPER-IF {
    description
      "ICPE DPM operational information";
    leaf discovery-interface-xr {
      type Xr-yang-string;
      description
        "Discovery interface";
    }
    leaf discovery-interface-handle {
      type xr:Interface-name;
      description
        "Discovery interface handle";
    }
    leaf discovery-interface-status {
      type Dpm-proto-state;
      description
        "Discovery interface status";
    }
    leaf ident-packets-received {
      type uint64;
      description
        "Ident packets received";
    }
    leaf ready-packets-received {
      type uint64;
      description
        "Ready packets received";
    }
    leaf los-packets-received {
      type uint64;
      description
        "Los packets received";
    }
    leaf invalid-packets-received {
      type uint64;
      description
        "Invalid packets received";
    }
    leaf configuration-packets-sent {
      type uint64;
      description
        "Configuration packets sent";
    }
    leaf ack-packets-sent {
      type uint64;
      description
        "Ack packets sent";
    }
    leaf reject-packets-sent {
      type uint64;
      description
        "Reject packets sent";
    }
    leaf probe-packets-sent {
      type uint64;
      description
        "Probe packets sent";
    }
    leaf host-ack-packets-received {
      type uint64;
      description
        "Host ack packets received";
    }
    leaf host-ack-packets-sent {
      type uint64;
      description
        "Host ack packets sent";
    }
    leaf secs-since-pkts-cleaned {
      type uint64;
      units "second";
      description
        "Secs since pkts cleaned";
    }
    list satellite {
      description
        "ICPE DPM satellite operational information table";
      uses DPM-OPER-SAT-TYPE;
    }
    list remote-host {
      description
        "ICPE DPM remote host operational information
         table";
      uses DPM-OPER-HOST-TYPE;
    }
  }
}
