module Cisco-IOS-XR-asr9k-lc-ethctrl-oper {
  namespace "http://cisco.com/ns/yang/Cisco-IOS-XR-asr9k-lc-ethctrl-oper";
  prefix asr9k-lc-ethctrl-oper;

  import Cisco-IOS-XR-types {
    prefix xr;
  }
  include Cisco-IOS-XR-asr9k-lc-ethctrl-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lc-ethctrl package operational data.
     
     This module contains definitions
     for the following management objects:
       mlan: Management LAN Operational data space
     
     Copyright (c) 2013-2017 by Cisco Systems, Inc.
     All rights reserved.";

  revision 2015-11-09 {
    description
      "IOS XR 6.0 revision.";
  }

  container mlan {
    config false;
    description
      "Management LAN Operational data space";
    container nodes {
      description
        "Table of nodes";
      list node {
        key "node";
        description
          "Number";
        container port-status-numbers {
          description
            "Table of port status";
          list port-status-number {
            key "number";
            description
              "Number";
            container port-status {
              description
                "mlan port status info";
              uses MLAN-PORT-STATUS;
            }
            leaf number {
              type int32;
              description
                "port number";
            }
          }
        }
        container switch-status-table {
          description
            "Table of switch status";
          container switch-status {
            description
              "mlan switch status info";
            uses MLAN-SWITCH-STATUS-DATA;
          }
        }
        container port-counters-numbers {
          description
            "Table of port counters";
          list port-counters-number {
            key "number";
            description
              "Number";
            container port-counters {
              description
                "mlan port counters info";
              uses MLAN-PORT-COUNTERS;
            }
            leaf number {
              type int32;
              description
                "port number";
            }
          }
        }
        container atu-entry-numbers {
          description
            "Table of switch ATU";
          list atu-entry-number {
            key "entry";
            description
              "Entry number";
            container switch-counters {
              description
                "mlan switch counters info";
              uses MLAN-SWITCH-ATU-DATA;
            }
            leaf entry {
              type int32;
              description
                "entry number";
            }
          }
        }
        leaf node {
          type xr:Node-id;
          description
            "node number";
        }
      }
    }
  }
}
