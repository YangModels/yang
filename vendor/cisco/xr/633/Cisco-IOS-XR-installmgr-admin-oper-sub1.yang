submodule Cisco-IOS-XR-installmgr-admin-oper-sub1 {
  belongs-to Cisco-IOS-XR-installmgr-admin-oper {
    prefix Cisco-IOS-XR-installmgr-admin-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR installmgr-admin package operational data.
     
     Copyright (c) 2013-2017 by Cisco Systems, Inc.
     All rights reserved.";

  revision 2015-11-09 {
    description
      "IOS XR 6.0 revision.";
  }

  typedef Instmgr-bag-log-entry-user-msg-category {
    type enumeration {
      enum "user-error" {
        value 1;
        description
          "User error";
      }
      enum "non-specific" {
        value 2;
        description
          "Non-specific message";
      }
      enum "warning" {
        value 3;
        description
          "Warning message";
      }
      enum "information" {
        value 4;
        description
          "Information message";
      }
      enum "user-prompt" {
        value 5;
        description
          "User prompt";
      }
      enum "log" {
        value 6;
        description
          "Log message";
      }
      enum "system-error" {
        value 7;
        description
          "System error";
      }
      enum "user-response" {
        value 8;
        description
          "User response";
      }
    }
    description
      "Category type";
  }

  grouping INSTMGR-BAG-LOG-ENTRY-USER-MSG-SCOPE-TYPE {
    description
      "INSTMGR BAG LOG ENTRY USER MSG SCOPE TYPE";
    leaf admin-read {
      type boolean;
      description
        "Does the admin want to read this?";
    }
    leaf affected-sd-rs {
      type uint32;
      description
        "Which SDRs are affected by the message";
    }
  }

  grouping INSTMGR-BAG-LOG-ENTRY-V3 {
    description
      "INSTMGR BAG LOG ENTRY V3";
    container scope {
      description
        "Scope of the message";
      uses INSTMGR-BAG-LOG-ENTRY-USER-MSG-SCOPE-TYPE;
    }
    leaf category {
      type Instmgr-bag-log-entry-user-msg-category;
      description
        "Category of the message";
    }
    leaf message {
      type string;
      description
        "Message";
    }
  }

  grouping MSG-CONTENTS {
    description
      "MSG CONTENTS";
    container v3 {
      when "../version = '3'" {
        description
          "../Version = '3'";
      }
      description
        "v3";
      uses INSTMGR-BAG-LOG-ENTRY-V3;
    }
    leaf version {
      type uint32;
      description
        "Version";
    }
  }

  grouping INSTMGR-BAG-LOG-ENTRY-USER-MSG-TYPE-3 {
    description
      "A user message";
    container log-contents {
      description
        "Log contents";
      uses MSG-CONTENTS;
    }
  }

  grouping INSTALL-LOG-ENTRY-4 {
    description
      "Install manager history log entry";
    list header {
      description
        "Header information";
      uses INSTMGR-BAG-LOG-ENTRY-USER-MSG-TYPE-3;
    }
    list summary {
      description
        "Summary information";
      uses INSTMGR-BAG-LOG-ENTRY-USER-MSG-TYPE-3;
    }
    list message {
      description
        "Status Information Logs";
      uses INSTMGR-BAG-LOG-ENTRY-USER-MSG-TYPE-3;
    }
    list change {
      description
        "Install changes";
      uses INSTMGR-BAG-LOG-ENTRY-USER-MSG-TYPE-3;
    }
    list detail {
      description
        "Install details";
      uses INSTMGR-BAG-LOG-ENTRY-USER-MSG-TYPE-3;
    }
    list communication {
      description
        "Install communications";
      uses INSTMGR-BAG-LOG-ENTRY-USER-MSG-TYPE-3;
    }
  }
}
