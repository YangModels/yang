module valtest {
  namespace "http://www.cisco.com/panini/calvados/valtest";
  prefix valtest;

  organization
    "Cisco Systems Inc.";
  contact
    "conger@cisco.com";
  description
    "This module contains definitions
     for the Calvados model objects.
     
     This module holds a sample validation.
     
     Copyright (c) 2012-2018 by Cisco Systems, Inc.
     All rights reserved.";

  revision 2012-08-20 {
    description
      "Initial revision";
  }

  container config {
    config true;
    container valtest {
      leaf a_number {
        type int64;
        default "42";
      }
      leaf b_number {
        type int64;
        default "7";
      }
    }
  }
}
