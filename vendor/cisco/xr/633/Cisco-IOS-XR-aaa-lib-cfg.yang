module Cisco-IOS-XR-aaa-lib-cfg {
  namespace "http://cisco.com/ns/yang/Cisco-IOS-XR-aaa-lib-cfg";
  prefix aaa-lib-cfg;

  import Cisco-IOS-XR-types {
    prefix xr;
  }
  import Cisco-IOS-XR-aaa-lib-datatypes {
    prefix dt1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-lib package configuration.
     
     This module contains definitions
     for the following management objects:
       aaa: Authentication, Authorization and Accounting
     
     Copyright (c) 2013-2017 by Cisco Systems, Inc.
     All rights reserved.";

  revision 2017-11-14 {
    description
      "Modified Accounting method to support local accounting as syslog";
  }
  revision 2017-05-01 {
    description
      "Fixing backward compatibility error in module.";
  }
  revision 2015-11-09 {
    description
      "IOS XR 6.0 revision.";
  }

  container aaa {
    description
      "Authentication, Authorization and Accounting";
    container accountings {
      description
        "AAA accounting";
      list accounting {
        key "type listname";
        description
          "Configurations related to accounting";
        leaf type {
          type xr:Cisco-ios-xr-string;
          description
            "exec:Account exec sessions, commands: Account
             CLI commands";
        }
        leaf listname {
          type xr:Cisco-ios-xr-string;
          description
            "Named accounting list";
        }
        leaf rp-failover {
          type dt1:Aaa-accounting-rp-failover;
          description
            "rpfailover";
        }
        leaf broadcast {
          type dt1:Aaa-accounting-broadcast;
          description
            "Broadcast";
        }
        leaf type-xr {
          type dt1:Aaa-accounting;
          description
            "Stop only/Start Stop";
        }
        leaf method1 {
          type dt1:Aaa-method-accounting;
          description
            "Method Type";
        }
        leaf method2 {
          type dt1:Aaa-method-accounting;
          description
            "Method Type";
        }
        leaf method3 {
          type dt1:Aaa-method-accounting;
          description
            "Method Type";
        }
        leaf method4 {
          type dt1:Aaa-method-accounting;
          description
            "Method Type";
        }
        leaf server-group-name1 {
          type string;
          description
            "Server group name";
        }
        leaf server-group-name2 {
          type string;
          description
            "Server group name";
        }
        leaf server-group-name3 {
          type string;
          description
            "Server group name";
        }
        leaf server-group-name4 {
          type string;
          description
            "Server group name";
        }
      }
    }
    container authorizations {
      description
        "AAA authorization";
      list authorization {
        key "type listname";
        description
          "Configurations related to authorization";
        leaf type {
          type xr:Cisco-ios-xr-string;
          description
            "network: Authorize IKE requests, commands:
             Authorize CLI commands";
        }
        leaf listname {
          type xr:Cisco-ios-xr-string;
          description
            "List name for AAA authorization";
        }
        leaf method1 {
          type dt1:Aaa-method;
          description
            "Method Type";
        }
        leaf method2 {
          type dt1:Aaa-method;
          description
            "Method Type";
        }
        leaf method3 {
          type dt1:Aaa-method;
          description
            "Method Type";
        }
        leaf method4 {
          type dt1:Aaa-method;
          description
            "Method Type";
        }
        leaf server-group-name1 {
          type string;
          description
            "Server group name";
        }
        leaf server-group-name2 {
          type string;
          description
            "Server group name";
        }
        leaf server-group-name3 {
          type string;
          description
            "Server group name";
        }
        leaf server-group-name4 {
          type string;
          description
            "Server group name";
        }
      }
    }
    container accounting-update {
      presence "Indicates a accounting-update node is configured.";
      description
        "Configuration related to 'update' accounting";
      leaf type {
        type dt1:Aaa-accounting-update;
        mandatory true;
        description
          "newinfo/periodic";
      }
      leaf periodic-interval {
        type uint32 {
          range "0..35791394";
        }
        units "minute";
        description
          "Periodic update interval in minutes";
      }
    }
    container banner {
      description
        "AAA banner";
      leaf login {
        type string;
        description
          "AAA login banner";
      }
    }
    container authentications {
      description
        "AAA authentication";
      list authentication {
        key "type listname";
        description
          "Configurations related to authentication";
        leaf type {
          type xr:Cisco-ios-xr-string;
          description
            "login: Authenticate login sessions, ppp:
             Authenticate ppp sessions";
        }
        leaf listname {
          type xr:Cisco-ios-xr-string;
          description
            "List name for AAA authentication";
        }
        leaf method1 {
          type dt1:Aaa-method;
          description
            "Method Type";
        }
        leaf method2 {
          type dt1:Aaa-method;
          description
            "Method Type";
        }
        leaf method3 {
          type dt1:Aaa-method;
          description
            "Method Type";
        }
        leaf method4 {
          type dt1:Aaa-method;
          description
            "Method Type";
        }
        leaf server-group-name1 {
          type string;
          description
            "Server group name";
        }
        leaf server-group-name2 {
          type string;
          description
            "Server group name";
        }
        leaf server-group-name3 {
          type string;
          description
            "Server group name";
        }
        leaf server-group-name4 {
          type string;
          description
            "Server group name";
        }
      }
    }
  }
}
