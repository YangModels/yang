module Cisco-IOS-XR-infra-xtc-cfg {
  namespace "http://cisco.com/ns/yang/Cisco-IOS-XR-infra-xtc-cfg";
  prefix infra-xtc-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-xtc package configuration.
     
     This module contains definitions
     for the following management objects:
       pce: PCE configuration data
     
     Copyright (c) 2013-2017 by Cisco Systems, Inc.
     All rights reserved.";

  revision 2016-05-31 {
    description
      "Revision description string.";
  }
  revision 2015-11-09 {
    description
      "IOS XR 6.0 revision.";
  }

  typedef Pce-disjoint-path {
    type enumeration {
      enum "link" {
        value 1;
        description
          "Link";
      }
      enum "node" {
        value 2;
        description
          "Node";
      }
      enum "srlg" {
        value 3;
        description
          "SRLG";
      }
      enum "srlg-node" {
        value 4;
        description
          "SRLG Node";
      }
    }
    description
      "Pce disjoint path";
  }

  typedef Pcerest-authentication {
    type enumeration {
      enum "basic" {
        value 1;
        description
          "Basic HTTP auth";
      }
      enum "digest" {
        value 2;
        description
          "MD5-Digest HTTP auth";
      }
    }
    description
      "Pcerest authentication";
  }

  typedef Pce-explicit-path-hop {
    type enumeration {
      enum "address" {
        value 1;
        description
          "Address";
      }
      enum "sid-node" {
        value 2;
        description
          "SID Node";
      }
      enum "sid-adjancency" {
        value 3;
        description
          "SID Adjacency";
      }
      enum "binding-sid" {
        value 4;
        description
          "Binding SID";
      }
    }
    description
      "Pce explicit path hop";
  }

  grouping ENABLE {
    description
      "Common node of pce, lsp-name, disjoint-path,
       group, rsvp-te, explicit-path, pcc-address, rest,
       rest-user, netconf";
    leaf enable {
      type empty;
      description
        "True only";
    }
  }

  container pce {
    description
      "PCE configuration data";
    container pcc-addresses {
      description
        "Path computation client configuration";
      list pcc-address {
        key "address";
        description
          "Path computation client address";
        container lsp-names {
          description
            "MPLS label switched path";
          list lsp-name {
            key "name";
            description
              "MPLS label switched path";
            container rsvp-te {
              description
                "RSVP-TE configuration";
              container affinity {
                description
                  "LSP Affinity";
                leaf include-any {
                  type xr:Hex-integer;
                  description
                    "Include-any affinity value";
                }
                leaf include-all {
                  type xr:Hex-integer;
                  description
                    "Include-all affinity value";
                }
                leaf exclude-any {
                  type xr:Hex-integer;
                  description
                    "Exclude-any affinity value";
                }
              }
              container priority {
                presence "Indicates a priority node is configured.";
                description
                  "Tunnel Setup and Hold Priorities";
                leaf setup-priority {
                  type uint32 {
                    range "0..7";
                  }
                  mandatory true;
                  description
                    "Setup Priority";
                }
                leaf hold-priority {
                  type uint32 {
                    range "0..7";
                  }
                  mandatory true;
                  description
                    "Hold Priority";
                }
              }
              leaf fast-protect {
                type empty;
                description
                  "Enable fast protection";
              }
              leaf bandwidth {
                type int32;
                units "kbit/s";
                description
                  "Bandwidth configuration";
              }
              uses ENABLE;
            }
            leaf undelegate {
              type empty;
              description
                "Undelegate LSP";
            }
            leaf explicit-path-name {
              type string;
              description
                "Explicit-path name";
            }
            leaf name {
              type xr:Cisco-ios-xr-string;
              description
                "LSP name";
            }
            uses ENABLE;
          }
        }
        leaf address {
          type inet:ipv4-address-no-zone;
          description
            "IPv4 address";
        }
        uses ENABLE;
      }
    }
    container logging {
      description
        "PCE logging configuration";
      leaf no-path {
        type empty;
        description
          "Logging NO-PATH configuration";
      }
      leaf pcerr {
        type empty;
        description
          "Logging of received PCErr messages";
      }
      leaf fallback {
        type empty;
        description
          "Logging fallback configuration";
      }
    }
    container backoff {
      description
        "PCE backoff configuration";
      leaf ratio {
        type uint32 {
          range "0..255";
        }
        default "2";
        description
          "Backoff common ratio configuration";
      }
      leaf threshold {
        type uint32 {
          range "0..3600";
        }
        default "0";
        description
          "Backoff threshold configuration";
      }
      leaf difference {
        type uint32 {
          range "0..255";
        }
        default "2";
        description
          "Backoff common difference configuration";
      }
    }
    container rest {
      description
        "REST configuration";
      container rest-users {
        description
          "REST authorized users configuration";
        list rest-user {
          key "name";
          description
            "REST authorized user";
          leaf rest-user-password {
            type xr:Proprietary-password;
            description
              "REST user password configuration";
          }
          leaf name {
            type xr:Cisco-ios-xr-string;
            description
              "User name";
          }
          uses ENABLE;
        }
      }
      leaf rest-authentication {
        type Pcerest-authentication;
        description
          "REST authentication type";
      }
      uses ENABLE;
    }
    container state-syncs {
      description
        "Standby PCE configuration";
      list state-sync {
        key "address";
        description
          "Standby PCE ipv4 address";
        leaf address {
          type inet:ipv4-address-no-zone;
          description
            "IPv4 address";
        }
      }
    }
    container segment-routing {
      description
        "PCE segment-routing configuration";
      leaf te-latency {
        type empty;
        description
          "Use te-latency algorithm configuration";
      }
      leaf strict-sid-only {
        type empty;
        description
          "Use strict-sid-only configuration";
      }
    }
    container timers {
      description
        "PCE Timers configuration";
      leaf reoptimization-timer {
        type uint32 {
          range "10..3600";
        }
        units "second";
        default "60";
        description
          "Topology reoptimization timer configuration";
      }
      leaf keepalive {
        type uint32 {
          range "0..255";
        }
        units "second";
        default "30";
        description
          "Keepalive interval in seconds, zero to disable";
      }
      leaf minimum-peer-keepalive {
        type uint32 {
          range "0..255";
        }
        units "second";
        default "20";
        description
          "Minimum acceptable peer proposed keepalive
           interval";
      }
    }
    container netconf {
      description
        "NETCONF configuration";
      container netconf-ssh {
        description
          "NETCONF SSH configuration";
        leaf netconf-ssh-password {
          type xr:Proprietary-password;
          description
            "Password to use for NETCONF SSH connections";
        }
        leaf netconf-ssh-user {
          type string;
          description
            "User name to use for NETCONF SSH connections";
        }
      }
      uses ENABLE;
    }
    container disjoint-path {
      description
        "Disjoint path configuration";
      container groups {
        description
          "Association configuration";
        list group {
          key "group-id dp-type sub-id";
          description
            "Association Group Configuration";
          container group-lsp-records {
            description
              "lsp pcc records container with in group";
            list group-lsp-record {
              key "lsp-id";
              description
                "LSP first/second PCC record tuple
                 containingIpAddr, LspName, DisjPath";
              leaf lsp-id {
                type uint32 {
                  range "1..2";
                }
                description
                  "Lsp id";
              }
              leaf ip-addr {
                type inet:ipv4-address-no-zone;
                description
                  "IP address of PCC";
              }
              leaf lsp-name {
                type string;
                description
                  "Identifying name for LSP";
              }
              leaf disj-path {
                type int32;
                description
                  "Set LSP to follow shortest-path";
              }
            }
          }
          leaf strict {
            type empty;
            description
              "Disable Fallback";
          }
          leaf group-id {
            type uint32 {
              range "1..65535";
            }
            description
              "Group ID";
          }
          leaf dp-type {
            type Pce-disjoint-path;
            description
              "Disjointness type";
          }
          leaf sub-id {
            type uint32 {
              range "0..65535";
            }
            description
              "Sub group ID, 0 to unset";
          }
          uses ENABLE;
        }
      }
      uses ENABLE;
    }
    container explicit-paths {
      description
        "Explicit paths";
      list explicit-path {
        key "name";
        description
          "Explicit-path configuration";
        container path-hops {
          description
            "Path Hops";
          list path-hop {
            key "index";
            description
              "Explicit path hop configuration";
            leaf index {
              type uint32 {
                range "1..65535";
              }
              description
                "Hop Index";
            }
            leaf hop-type {
              type Pce-explicit-path-hop;
              description
                "Path hop type";
            }
            leaf address {
              when "../hop-type = 'address' or ../hop-type = 'sid-node' or ../hop-type = 'sid-adjancency'" {
                description
                  "../HopType = Address or ../HopType =
                   SIDNode or ../HopType = SIDAdjancency";
              }
              type inet:ipv4-address-no-zone;
              default "0.0.0.0";
              description
                "IPv4 Address";
            }
            leaf remote-address {
              when "../hop-type = 'sid-adjancency'" {
                description
                  "../HopType = SIDAdjancency";
              }
              type inet:ipv4-address-no-zone;
              default "0.0.0.0";
              description
                "Remote IPv4 address";
            }
            leaf mpls-label {
              when "../hop-type = 'sid-node' or ../hop-type = 'sid-adjancency' or ../hop-type = 'binding-sid'" {
                description
                  "../HopType = SIDNode or ../HopType =
                   SIDAdjancency or ../HopType = BindingSID";
              }
              type uint32 {
                range "0..1048575";
              }
              default "0";
              description
                "MPLS Label";
            }
          }
        }
        leaf name {
          type xr:Cisco-ios-xr-string;
          description
            "Explicit-path name";
        }
        uses ENABLE;
      }
    }
    leaf server-address {
      type inet:ipv4-address-no-zone;
      description
        "IPv4 address of PCE server";
    }
    leaf password {
      type xr:Proprietary-password;
      description
        "MD5 password";
    }
    uses ENABLE;
  }
}
