submodule Cisco-IOS-XR-asr9k-lc-ethctrl-oper-sub1 {
  belongs-to Cisco-IOS-XR-asr9k-lc-ethctrl-oper {
    prefix Cisco-IOS-XR-asr9k-lc-ethctrl-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-lc-ethctrl package operational data.
     
     Copyright (c) 2013-2017 by Cisco Systems, Inc.
     All rights reserved.";

  revision 2015-11-09 {
    description
      "IOS XR 6.0 revision.";
  }

  grouping MLAN-ATU {
    description
      "MLAN ATU";
    leaf db-num {
      type uint16;
      description
        "dbNum";
    }
    leaf priority {
      type uint8;
      description
        "priority";
    }
    leaf trunk {
      type boolean;
      description
        "trunk";
    }
    leaf dpv {
      type uint8;
      description
        "dpv";
    }
    leaf es {
      type uint8;
      description
        "es";
    }
    leaf-list macaddr {
      type uint16;
      max-elements "3";
      description
        "macaddr";
    }
  }

  grouping MLAN-SWITCH-ATU-DATA {
    description
      "";
    container atu {
      description
        "Switch ATU Data";
      uses MLAN-ATU;
    }
    leaf entry-num {
      type uint32;
      description
        "Index of ATU Entry";
    }
  }

  grouping MLAN-PORT-COUNTER {
    description
      "MLAN PORT COUNTER";
    leaf in-good-octets-hi {
      type uint32;
      description
        "inGoodOctets hi";
    }
    leaf in-good-octets {
      type uint32;
      description
        "inGoodOctets";
    }
    leaf in-bad-octets {
      type uint32;
      description
        "inBadOctets";
    }
    leaf in-unicast-pkt {
      type uint32;
      description
        "inUnicastPkt";
    }
    leaf in-bcast-pkt {
      type uint32;
      description
        "inBcastPkt";
    }
    leaf in-mcast-pkt {
      type uint32;
      description
        "inMcastPkt";
    }
    leaf in-pause-pkt {
      type uint32;
      description
        "inPausePkt";
    }
    leaf in-undersize-pkt {
      type uint32;
      description
        "inUndersizePkt";
    }
    leaf in-fragments {
      type uint32;
      description
        "inFragments";
    }
    leaf in-oversize {
      type uint32;
      description
        "inOversize";
    }
    leaf in-jabber {
      type uint32;
      description
        "inJabber";
    }
    leaf in-rx-err {
      type uint32;
      description
        "inRxErr";
    }
    leaf in-fcs-err {
      type uint32;
      description
        "inFcsErr";
    }
    leaf out-octets-hi {
      type uint32;
      description
        "outOctets hi";
    }
    leaf out-octets {
      type uint32;
      description
        "outOctets";
    }
    leaf out-unicast-pkt {
      type uint32;
      description
        "outUnicastPkt";
    }
    leaf out-bcast-pkt {
      type uint32;
      description
        "outBcastPkt";
    }
    leaf out-mcast-pkt {
      type uint32;
      description
        "outMcastPkt";
    }
    leaf out-pause-pkt {
      type uint32;
      description
        "outPausePkt";
    }
    leaf excessive {
      type uint32;
      description
        "excessive";
    }
    leaf collisions {
      type uint32;
      description
        "collisions";
    }
    leaf deferred {
      type uint32;
      description
        "deferred";
    }
    leaf single {
      type uint32;
      description
        "single";
    }
    leaf multiple {
      type uint32;
      description
        "multiple";
    }
    leaf out-fcs-err {
      type uint32;
      description
        "outFcsErr";
    }
    leaf late {
      type uint32;
      description
        "late";
    }
    leaf rx-tx-64-octets {
      type uint32;
      description
        "rx tx 64 Octets";
    }
    leaf rx-tx-65-127-octets {
      type uint32;
      description
        "rx tx 65 127 Octets";
    }
    leaf rx-tx-128-255-octets {
      type uint32;
      description
        "rx tx 128 255 Octets";
    }
    leaf rx-tx-256-511-octets {
      type uint32;
      description
        "rx tx 256 511 Octets";
    }
    leaf rx-tx-512-1023-octets {
      type uint32;
      description
        "rx tx 512 1023 Octets";
    }
    leaf rx-tx-1024-max-octets {
      type uint32;
      description
        "rx tx 1024 Max Octets";
    }
    leaf in-discards {
      type uint32;
      description
        "inDiscards";
    }
    leaf in-filtered {
      type uint32;
      description
        "inFiltered";
    }
    leaf out-filtered {
      type uint32;
      description
        "outFiltered";
    }
  }

  grouping MLAN-PORT-COUNTERS {
    description
      "";
    container mlan-stats {
      description
        "Switch Port Statistics";
      uses MLAN-PORT-COUNTER;
    }
    leaf port-num {
      type uint32;
      description
        "Port Number";
    }
  }

  grouping MLAN-SWITCH-STATUS {
    description
      "MLAN SWITCH STATUS";
    leaf ppu {
      type uint32;
      description
        "ppu";
    }
    leaf mtu {
      type uint32;
      description
        "mtu";
    }
    leaf mac {
      type string {
        length "0..6";
      }
      description
        "mac";
    }
    leaf cpu-port {
      type uint16;
      description
        "cpu port";
    }
    leaf cpu-mac {
      type uint16;
      description
        "cpu mac";
    }
    leaf initialized {
      type uint16;
      description
        "initialized";
    }
    leaf restarted {
      type uint16;
      description
        "restarted";
    }
  }

  grouping MLAN-SWITCH-STATUS-DATA {
    description
      "";
    container sw-reg-1 {
      description
        "Switch Global Registers";
      uses MLAN-SWITCH-REG-BANK;
    }
    container sw-reg-2 {
      description
        "Switch Global Registers";
      uses MLAN-SWITCH-REG-BANK;
    }
    container sw-status {
      description
        "Switch Status Data";
      uses MLAN-SWITCH-STATUS;
    }
    leaf rate-limit {
      type int32;
      description
        "CPU Interface Rate Limit";
    }
  }

  grouping MLAN-SWITCH-REG-BANK {
    description
      "MLAN SWITCH REG BANK";
    leaf-list reg {
      type uint16;
      max-elements "32";
      description
        "reg";
    }
  }

  grouping MLAN-PORT-CONFIG {
    description
      "MLAN PORT CONFIG";
    leaf speed {
      type uint32;
      description
        "speed";
    }
    leaf duplex {
      type uint32;
      description
        "duplex";
    }
    leaf pause {
      type uint16;
      description
        "pauseEn";
    }
    leaf my-pause {
      type uint16;
      description
        "myPause";
    }
    leaf loopback {
      type uint32;
      description
        "loopback";
    }
  }

  grouping MLAN-PORT-STATUS {
    description
      "";
    container config {
      description
        "Configuration Data";
      uses MLAN-PORT-CONFIG;
    }
    container phy {
      description
        "PHY Registers";
      uses MLAN-SWITCH-REG-BANK;
    }
    container serdes {
      description
        "SERDES Registers";
      uses MLAN-SWITCH-REG-BANK;
    }
    container mac {
      description
        "MAC Registers";
      uses MLAN-SWITCH-REG-BANK;
    }
    leaf port-num {
      type uint32;
      description
        "Port Number";
    }
    leaf phy-valid {
      type uint32;
      description
        "PHY data valid";
    }
    leaf serdes-valid {
      type uint32;
      description
        "SERDES data valid";
    }
    leaf mac-valid {
      type uint32;
      description
        "MAC data valid";
    }
  }
}
