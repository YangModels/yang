module Cisco-IOS-XR-sysadmin-obfl-clear {
  namespace "http://cisco.com/ns/yang/Cisco-IOS-XR-sysadmin-obfl-clear";
  prefix obflclear;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module is for clearing OBFL data.
     
     Copyright (c) 2012-2018 by Cisco Systems, Inc.
     All rights reserved.";

  revision 2017-07-31 {
    description
      "Changed namespace to follow Cisco guidelines on naming conventions";
  }

  grouping obflclear-grp {
    container logging {
      config false;
      container onboard {
        config false;
        list location {
          key "location";
          config false;
          leaf location {
            type string;
          }
          tailf:action "clear" {
            input {
              leaf all {
                type empty;
                mandatory true;
              }
            }
          }
        }
      }
    }
  }
}
