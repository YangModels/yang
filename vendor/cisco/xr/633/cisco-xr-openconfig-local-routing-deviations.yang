module cisco-xr-openconfig-local-routing-deviations {
  namespace "http://cisco.com/ns/yang/cisco-xr-openconfig-local-routing-deviations";
  prefix oc-loc-rtdevs;

  import openconfig-local-routing {
    prefix oc-loc-rt;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for
     
     openconfig-local-routing.yang@2016-05-11
     
     on Cisco IOS-XR devices.
     
     Copyright (c) 2016-2017 by Cisco Systems, Inc.
     All rights reserved.";

  revision 2017-02-04 {
    description
      "Initial revision applicable to IOS-XR 6.2.1";
  }

  deviation "/oc-loc-rt:local-routes/oc-loc-rt:static-routes/oc-loc-rt:static/oc-loc-rt:next-hops/oc-loc-rt:next-hop/oc-loc-rt:config/oc-loc-rt:recurse" {
    deviate not-supported;
  }
  deviation "/oc-loc-rt:local-routes/oc-loc-rt:static-routes/oc-loc-rt:static/oc-loc-rt:next-hops/oc-loc-rt:next-hop/oc-loc-rt:state/oc-loc-rt:recurse" {
    deviate not-supported;
  }
  deviation "/oc-loc-rt:local-routes/oc-loc-rt:local-aggregates/oc-loc-rt:aggregate" {
    deviate not-supported;
  }
}
