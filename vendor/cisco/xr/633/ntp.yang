module ntp {
  namespace "http://cisco.com/calvados/ntp";
  prefix ntp;

  import tailf-common {
    prefix tailf;
  }
  import ietf-yang-types {
    prefix yang;
  }
  import Cisco-IOS-XR-sysadmin-show-trace {
    prefix show_trace;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG definitions
     for Cisco IOS-XR syadmin NTP configuration.
     
     This module contains definitions
     for the following management objects:
     NTP configuration data
     
     Copyright (c) 2013-2016 by Cisco Systems, Inc.
     All rights reserved.
     
     Copyright (c) 2012-2018 by Cisco Systems, Inc.
     All rights reserved.";

  revision 2016-07-04 {
    description
      "Remove refine stmt";
  }

  grouping ntp_target {
    leaf name {
      type string;
    }
    leaf version {
      type int32 {
        range "1 .. 4";
      }
    }
    leaf key-id {
      type int32 {
        range "1 .. 65534";
      }
    }
    leaf prefer {
      type empty;
    }
  }

  container ntp {
    list peer {
      key "name";
      uses ntp_target;
    }
    list server {
      key "name";
      uses ntp_target;
    }
    leaf-list trusted-key {
      type int32 {
        range "1 .. 65534";
      }
    }
    leaf authenticate {
      type empty;
    }
    list authentication-key {
      key "key-number";
      leaf key-number {
        type int32 {
          range "1 .. 65534";
        }
      }
      leaf md5-keyword {
        type enumeration {
          enum "md5";
        }
        mandatory true;
      }
      leaf encryption {
        type enumeration {
          enum "clear";
          enum "encrypted";
        }
        mandatory false;
      }
      leaf keyname {
        type string {
          length "min .. 32";
        }
        mandatory true;
      }
    }
    container trace {
      config false;
      container ntp_helper {
        uses show_trace:traceable;
      }
    }
  }
  container clock-action {
    config false;
    container clock {
      container Action {
        tailf:action "update-calendar" {
          output {
            leaf status {
              type string;
              mandatory false;
            }
          }
        }
        tailf:action "read-calendar" {
          output {
            leaf status {
              type string;
              mandatory false;
            }
          }
        }
        tailf:action "set" {
          input {
            leaf time {
              type yang:date-and-time;
              mandatory true;
            }
          }
          output {
            leaf status {
              type string;
              mandatory false;
            }
          }
        }
      }
    }
  }
}
