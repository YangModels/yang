module client-requests {
  namespace "http://cisco.com/calvados/issu/test/it/client/client-requests";
  prefix it-client;

  import tailf-common {
    prefix tailf;
  }

  description
    "IT client request handling";

  typedef announcement-type {
    type enumeration {
      enum "calv-operation-start" {
        description
          "Announcements at the start of the Calvados upgrade";
      }
      enum "calv-phase-start" {
        description
          "Announcements at the start of each phase of node upgrades";
      }
    }
    description
      "Enumeration of possible announcement types";
  }

  grouping request-output {
    leaf result {
      type boolean;
      description
        "An indication of whether the request completed successfully";
    }
  }

  container requests {
    tailf:action "set-response" {
      tailf:actionpoint "set-response";
      description
        "Request to set response details";
      input {
        leaf announcement {
          type announcement-type;
          description
            "Type of announcement to act upon";
        }
        leaf success-response {
          type boolean;
          description
            "True if the response should succeed. False otherwise";
        }
        leaf error-details {
          type string;
          description
            "Error string to be returned, if response is failure";
        }
      }
      output {
        uses request-output;
      }
    }
    tailf:action "hold-response" {
      tailf:actionpoint "hold-response";
      description
        "Request to hold a response type";
      input {
        leaf announcement {
          type announcement-type;
          description
            "Type of announcement to act upon";
        }
      }
      output {
        uses request-output;
      }
    }
    tailf:action "unhold-response" {
      tailf:actionpoint "unhold-response";
      description
        "Request to unhold a response type";
      input {
        leaf announcement {
          type announcement-type;
          description
            "Type of announcement to act upon";
        }
      }
      output {
        uses request-output;
      }
    }
    tailf:action "send-abort" {
      tailf:actionpoint "send-abort";
      description
        "Request to send an abort message";
      input {
        leaf error-details {
          type string;
          description
            "Error string to return as part of abort message";
        }
      }
      output {
        uses request-output;
      }
    }
  }
}
