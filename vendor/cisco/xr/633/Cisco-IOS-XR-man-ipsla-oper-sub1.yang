submodule Cisco-IOS-XR-man-ipsla-oper-sub1 {
  belongs-to Cisco-IOS-XR-man-ipsla-oper {
    prefix Cisco-IOS-XR-man-ipsla-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR man-ipsla package operational data.
     
     Copyright (c) 2013-2017 by Cisco Systems, Inc.
     All rights reserved.";

  revision 2015-11-09 {
    description
      "IOS XR 6.0 revision.";
  }

  typedef Sla-op-types {
    type enumeration {
      enum "oper-icmp-echo" {
        value 1;
        description
          "ICMP Echo";
      }
      enum "oper-icmp-path-jitter" {
        value 2;
        description
          "ICMP PathJitter";
      }
      enum "oper-icmp-path-echo" {
        value 4;
        description
          "ICMP Path Echo";
      }
      enum "oper-udp-jitter" {
        value 8;
        description
          "UDP Jitter";
      }
      enum "oper-udp-echo" {
        value 16;
        description
          "UDP Echo";
      }
      enum "oper-mpls-lsp-ping" {
        value 32;
        description
          "MPLS LSP Ping";
      }
      enum "oper-mpls-lsp-trace" {
        value 64;
        description
          "MPLS LSP Trace";
      }
      enum "oper-mpls-lsp-group" {
        value 128;
        description
          "MPLS LSP Group";
      }
    }
    description
      "IPSLA Operation Types";
  }

  grouping IPSLA-APPLICATION-BAG {
    description
      "IPSLA application information";
    leaf version {
      type string;
      description
        "Version of the IPSLA in Version.Release
         .Patch-level format";
    }
    leaf max-entries {
      type uint32;
      description
        "Maximum number of entries";
    }
    leaf entries-configured {
      type uint32;
      description
        "Number of entries configured";
    }
    leaf active-entries {
      type uint32;
      description
        "Number of active entries";
    }
    leaf pending-entries {
      type uint32;
      description
        "Number of pending entries";
    }
    leaf inactive-entries {
      type uint32;
      description
        "Number of inactive entries";
    }
    leaf configurable-probes {
      type uint32;
      description
        "Number of configurable probes";
    }
    leaf min-memory {
      type uint32;
      description
        "IPSLA low memory watermark in KB";
    }
    leaf hw-timestamp-disabled {
      type boolean;
      description
        "IPSLA HW timestamp Disabled flag";
    }
    leaf-list operation-type {
      type Sla-op-types;
      max-elements "8";
      description
        "Operation types available in this IPSLA version";
    }
  }
}
