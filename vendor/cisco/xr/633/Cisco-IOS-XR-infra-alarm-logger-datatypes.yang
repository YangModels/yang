module Cisco-IOS-XR-infra-alarm-logger-datatypes {
  namespace "http://cisco.com/ns/yang/Cisco-IOS-XR-infra-alarm-logger-datatypes";
  prefix infra-alarm-logger-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2017 by Cisco Systems, Inc.
     All rights reserved.";

  revision 2015-01-07 {
    description
      "IOS XR 5.3.1 revision.";
  }

  typedef Alarm-logger-severity-level {
    type enumeration {
      enum "emergency" {
        value 0;
        description
          "Emergency";
      }
      enum "alert" {
        value 1;
        description
          "Alert";
      }
      enum "critical" {
        value 2;
        description
          "Critical";
      }
      enum "error" {
        value 3;
        description
          "Error";
      }
      enum "warning" {
        value 4;
        description
          "Warning";
      }
      enum "notice" {
        value 5;
        description
          "Notice";
      }
      enum "informational" {
        value 6;
        description
          "Informational";
      }
    }
    description
      "Alarm logger severity level";
  }
}
