module tailf-confd-monitoring {
  namespace "http://tail-f.com/yang/confd-monitoring";
  prefix tfcm;

  import tailf-common-monitoring {
    prefix tfcg;
    revision-date 2012-03-08;
  }

  organization
    "Tail-f Systems";
  description
    "This module defines status objects for monitoring of ConfD.";

  revision 2012-03-08 {
    description
      "Released as part of ConfD-3.9.
       
       Imported latest tailf-common-monitoring module.";
  }
  revision 2011-12-08 {
    description
      "Released as part of ConfD-3.8.
       
       Imported latest tailf-common-monitoring module.";
  }
  revision 2011-09-22 {
    description
      "Released as part of ConfD-3.7.";
  }

  container confd-state {
    config false;
    uses tfcg:common-monitoring-objects;
  }
}
