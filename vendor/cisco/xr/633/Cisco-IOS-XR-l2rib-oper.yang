module Cisco-IOS-XR-l2rib-oper {
  namespace "http://cisco.com/ns/yang/Cisco-IOS-XR-l2rib-oper";
  prefix l2rib-oper;

  import ietf-inet-types {
    prefix inet;
  }
  import ietf-yang-types {
    prefix yang;
  }
  include Cisco-IOS-XR-l2rib-oper-sub1 {
    revision-date 2017-08-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2rib package operational data.
     
     This module contains definitions
     for the following management objects:
       l2rib: L2RIB operational information
     
     Copyright (c) 2013-2017 by Cisco Systems, Inc.
     All rights reserved.";

  revision 2017-08-16 {
    description
      "Descriptions switch int32 to uint32.";
  }
  revision 2015-11-09 {
    description
      "IOS XR 6.0 revision.";
  }

  container l2rib {
    config false;
    description
      "L2RIB operational information ";
    container producers-details {
      description
        "L2RIB detailed producer table";
      list producers-detail {
        description
          "L2RIB producers detail information";
        leaf object-id {
          type uint32;
          description
            "Object ID";
        }
        leaf product-id {
          type uint32;
          description
            "Product ID";
        }
        uses L2RIB-PROD-DETAIL;
      }
    }
    container summary {
      description
        "L2RIB EVPN Summary";
      uses L2RIB-SUMMARY;
    }
    container producers {
      description
        "L2RIB producer table";
      list producer {
        description
          "L2RIB producers";
        leaf object-id {
          type uint32;
          description
            "Object ID";
        }
        leaf product-id {
          type uint32;
          description
            "Product ID";
        }
        uses L2RIB-PROD;
      }
    }
    container clients {
      description
        "L2RIB client table";
      list client {
        key "client-id";
        description
          "L2RIB clients";
        leaf client-id {
          type uint32;
          description
            "Client ID";
        }
        uses L2RIB-CLIENT;
      }
    }
    container evis-xr {
      description
        "L2RIB EVPN EVI Detail Table";
      list evi {
        key "evi";
        description
          "L2RIB EVPN EVI Entry";
        leaf evi {
          type uint32;
          description
            "EVI ID";
        }
        uses L2RIB-TOPOLOGY-DETAIL;
      }
    }
    container clients-details {
      description
        "L2RIB detailed client table";
      list clients-detail {
        key "client-id";
        description
          "L2RIB clients detail information";
        leaf client-id {
          type uint32;
          description
            "Client ID";
        }
        uses L2RIB-CLIENT-DETAIL;
      }
    }
    container evi-child-tables {
      description
        "Container for all EVI Child Tables";
      container macip-details {
        description
          "L2RIB EVPN EVI MAC IP Detail table";
        list macip-detail {
          description
            "L2RIB EVPN MAC IP Detail table";
          leaf evi {
            type uint32;
            description
              "EVPN ID";
          }
          leaf tag-id {
            type uint32;
            description
              "Tag ID";
          }
          leaf mac-addr {
            type yang:mac-address;
            description
              "MAC IP Address";
          }
          leaf ip-addr {
            type inet:ip-address-no-zone;
            description
              "IP Address";
          }
          leaf admin-dist {
            type uint32;
            description
              "Admin distance";
          }
          leaf prod-id {
            type uint32;
            description
              "Producer ID";
          }
          uses L2RIB-MAC-IP-ROUTE-DETAIL;
        }
      }
      container mac-ips {
        description
          "L2RIB EVPN EVI MAC IP table";
        list mac-ip {
          description
            "L2RIB EVPN MAC IP table";
          leaf evi {
            type uint32;
            description
              "EVPN ID";
          }
          leaf tag-id {
            type uint32;
            description
              "Tag ID";
          }
          leaf mac-addr {
            type yang:mac-address;
            description
              "MAC-IP Address";
          }
          leaf ip-addr {
            type inet:ip-address-no-zone;
            description
              "IP Address";
          }
          leaf admin-dist {
            type uint32;
            description
              "Admin distance";
          }
          leaf prod-id {
            type uint32;
            description
              "Producer ID";
          }
          uses L2RIB-MAC-IP-ROUTE;
        }
      }
      container macs {
        description
          "L2RIB EVPN EVI MAC table";
        list mac {
          description
            "L2RIB EVPN MAC table";
          leaf evi {
            type uint32;
            description
              "EVPN ID";
          }
          leaf tag-id {
            type uint32;
            description
              "Tag ID";
          }
          leaf mac-addr {
            type yang:mac-address;
            description
              "MAC Address";
          }
          leaf admin-dist {
            type uint32;
            description
              "Admin distance";
          }
          leaf prod-id {
            type uint32;
            description
              "Producer ID";
          }
          uses L2RIB-MAC-ROUTE;
        }
      }
      container imets {
        description
          "L2RIB EVPN EVI IMET table";
        list imet {
          description
            "L2RIB EVPN IMET table";
          leaf evi {
            type uint32;
            description
              "EVPN ID";
          }
          leaf tag-id {
            type uint32;
            description
              "Tag ID";
          }
          leaf ip-addr {
            type inet:ip-address-no-zone;
            description
              "Originating Router IP Address";
          }
          leaf admin-dist {
            type uint32;
            description
              "Admin distance";
          }
          leaf prod-id {
            type uint32;
            description
              "Producer ID";
          }
          uses L2RIB-IMET-ROUTE;
        }
      }
      container mac-details {
        description
          "L2RIB EVPN EVI MAC Detail table";
        list mac-detail {
          description
            "L2RIB EVPN MAC Detail table";
          leaf evi {
            type uint32;
            description
              "EVPN ID";
          }
          leaf tag-id {
            type uint32;
            description
              "Tag ID";
          }
          leaf mac-addr {
            type yang:mac-address;
            description
              "MAC Address";
          }
          leaf admin-dist {
            type uint32;
            description
              "Admin distance";
          }
          leaf prod-id {
            type uint32;
            description
              "Producer ID";
          }
          uses L2RIB-MAC-ROUTE-DETAIL;
        }
      }
      container imet-details {
        description
          "L2RIB EVPN EVI IMET Detail table";
        list imet-detail {
          description
            "L2RIB EVPN IMET Detail table";
          leaf evi {
            type uint32;
            description
              "EVPN ID";
          }
          leaf tag-id {
            type uint32;
            description
              "Tag ID";
          }
          leaf ip-addr {
            type inet:ip-address-no-zone;
            description
              "Originating Router IP Address";
          }
          leaf admin-dist {
            type uint32;
            description
              "Admin distance";
          }
          leaf prod-id {
            type uint32;
            description
              "Producer ID";
          }
          uses L2RIB-IMET-ROUTE-DETAIL;
        }
      }
    }
    container evis {
      description
        "L2RIB EVPN EVI Table";
      list evi {
        key "evi";
        description
          "L2RIB EVPN EVI Entry";
        leaf evi {
          type uint32;
          description
            "EVI ID";
        }
        uses L2RIB-TOPOLOGY;
      }
    }
  }
}
