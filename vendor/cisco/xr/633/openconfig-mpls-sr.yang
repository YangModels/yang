module openconfig-mpls-sr {
  yang-version 1;
  namespace "http://openconfig.net/yang/sr";
  prefix sr;

  import ietf-inet-types {
    prefix inet;
  }
  import openconfig-mpls-types {
    prefix mplst;
  }
  import openconfig-extensions {
    prefix oc-ext;
  }
  import cisco-xr-openconfig-interfaces-types {
    prefix ocif;
  }

  organization
    "OpenConfig working group";
  contact
    "OpenConfig working group
     netopenconfig@googlegroups.com";
  description
    "Configuration for MPLS with segment routing-based LSPs,
     including global parameters, and LSP-specific configuration for
     both constrained-path and IGP-congruent LSPs";

  revision 2015-11-05 {
    description
      "Initial public release of MPLS models";
    reference "0.2.1";
  }
  revision 2015-10-14 {
    description
      "Work in progress";
    reference "0.2.0";
  }

  grouping srgb_config {
    description
      "List of global blocks to be advertised.";
    leaf lower-bound {
      type uint32;
      description
        "Lower value in the block.";
    }
    leaf upper-bound {
      type uint32;
      description
        "Upper value in the block.";
    }
  }

  grouping srgb_state {
    description
      "State parameters relating to the SRGB";
    leaf size {
      type uint32;
      description
        "Number of indexes in the SRGB block";
    }
    leaf free {
      type uint32;
      description
        "Number of SRGB indexes that have not yet been allocated";
    }
    leaf used {
      type uint32;
      description
        "Number of SRGB indexes that are currently allocated";
    }
  }

  grouping adjacency-sid_config {
    description
      "Configuration related to an Adjacency Segment Identifier
       (SID)";
    leaf-list advertise {
      type enumeration {
        enum "PROTECTED" {
          description
            "Advertise an Adjacency-SID for this interface, which is
             eligible to be protected using a local protection
             mechanism on the local LSR. The local protection
             mechanism selected is dependent upon the configuration
             of RSVP-TE FRR or LFA elsewhere on the system";
        }
        enum "UNPROTECTED" {
          description
            "Advertise an Adajcency-SID for this interface, which is
             explicitly excluded from being protected by any local
             protection mechanism";
        }
      }
      description
        "Specifies the type of adjacency SID which should be
         advertised for the specified entity.";
    }
    leaf-list groups {
      type uint32;
      description
        "Specifies the groups to which this interface belongs.
         Setting a value in this list results in an additional AdjSID
         being advertised, with the S-bit set to 1. The AdjSID is
         assumed to be protected";
    }
  }

  grouping interface_config {
    description
      "Configuration parameters relating to a Segment Routing
       enabled interface";
    leaf interface {
      type ocif:interface-ref;
      description
        "Reference to the interface for which segment routing
         configuration is to be applied.";
    }
  }

  grouping sr-global {
    description
      "Global segment routing signaling configuration";
    container segment-routing {
      description
        "SR global signaling config";
      list srgb {
        key "lower-bound upper-bound";
        description
          "List of Segment Routing Global Block (SRGB) entries. These
           label blocks are reserved to be allocated as domain-wide
           entries.";
        uses srgb_config;
        container config {
          description
            "Configuration parameters relating to the Segment Routing
             Global Block (SRGB)";
          uses srgb_config;
        }
        container state {
          config false;
          description
            "State parameters relating to the Segment Routing Global
             Block (SRGB)";
          uses srgb_config;
          uses srgb_state;
        }
      }
      list interfaces {
        key "interface";
        description
          "List of interfaces with associated segment routing
           configuration";
        uses interface_config;
        container config {
          description
            "Interface configuration parameters for Segment Routing
             relating to the specified interface";
          uses interface_config;
        }
        container state {
          config false;
          description
            "State parameters for Segment Routing features relating
             to the specified interface";
          uses interface_config;
        }
        container adjacency-sid {
          description
            "Configuration for Adjacency SIDs that are related to
             the specified interface";
          container config {
            description
              "Configuration parameters for the Adjacency-SIDs
               that are related to this interface";
            uses adjacency-sid_config;
          }
          container state {
            config false;
            description
              "State parameters for the Adjacency-SIDs that are
               related to this interface";
            uses adjacency-sid_config;
          }
        }
      }
    }
  }

  grouping sr-path-attributes_config {
    description
      "Configuration parameters relating to SR-TE LSPs";
    leaf sid-selection-mode {
      type enumeration {
        enum "ADJ-SID-ONLY" {
          description
            "The SR-TE tunnel should only use adjacency SIDs
             to build the SID stack to be pushed for the LSP";
        }
        enum "MIXED-MODE" {
          description
            "The SR-TE tunnel can use a mix of adjacency
             and prefix SIDs to build the SID stack to be pushed
             to the LSP";
        }
      }
      default "MIXED-MODE";
      description
        "The restrictions placed on the SIDs to be selected by the
         calculation method for the SR-TE LSP";
    }
    leaf sid-protection-required {
      type boolean;
      default "false";
      description
        "When this value is set to true, only SIDs that are
         protected are to be selected by the calculating method
         for the SR-TE LSP.";
    }
  }

  grouping sr_fec-address_config {
    description
      "Configuration parameters relating to a FEC that is to be
       advertised by Segment Routing";
    leaf fec-address {
      type inet:ip-prefix;
      description
        "FEC that is to be advertised as part of the Prefix-SID";
    }
  }

  grouping sr_fec-prefix-sid_config {
    description
      "Configuration parameters relating to the nature of the
       Prefix-SID that is to be advertised for a particular FEC";
    leaf type {
      type enumeration {
        enum "INDEX" {
          description
            "Set when the value of the prefix SID should be specified
             as an off-set from the SRGB's zero-value. When multiple
             SRGBs are specified, the zero-value is the minimum
             of their lower bounds";
        }
        enum "ABSOLUTE" {
          description
            "Set when the value of a prefix SID is specified as the
             absolute value within an SRGB. It is an error to specify
             an absolute value outside of a specified SRGB";
        }
      }
      default "INDEX";
      description
        "Specifies how the value of the Prefix-SID should be
         interpreted - whether as an offset to the SRGB, or as an
         absolute value";
    }
    leaf node-flag {
      type boolean;
      description
        "Specifies that the Prefix-SID is to be treated as a Node-SID
         by setting the N-flag in the advertised Prefix-SID TLV in the
         IGP";
    }
    leaf last-hop-behavior {
      type enumeration {
        enum "EXPLICIT-NULL" {
          description
            "Specifies that the explicit null label is to be used
             when the penultimate hop forwards a labelled packet to
             this Prefix-SID";
        }
        enum "UNCHANGED" {
          description
            "Specicies that the Prefix-SID's label value is to be
             left in place when the penultimate hop forwards to this
             Prefix-SID";
        }
        enum "PHP" {
          description
            "Specicies that the penultimate hop should pop the
             Prefix-SID label before forwarding to the eLER";
        }
      }
      description
        "Configuration relating to the LFIB actions for the
         Prefix-SID to be used by the penultimate-hop";
    }
  }

  grouping igp-tunnel-sr {
    description
      "defintiions for SR-signaled, IGP-based LSP tunnel
       types";
    container tunnel {
      description
        "contains configuration stanzas for different LSP
         tunnel types (P2P, P2MP, etc.)";
      leaf tunnel-type {
        type mplst:tunnel-type;
        description
          "specifies the type of LSP, e.g., P2P or P2MP";
      }
      container p2p-lsp {
        when "tunnel-type = 'P2P'" {
          description
            "container active when LSP tunnel type is
             point to point";
        }
        description
          "properties of point-to-point tunnels";
        list fec {
          key "fec-address";
          description
            "List of FECs that are to be originated as SR LSPs";
          uses sr_fec-address_config;
          container config {
            description
              "Configuration parameters relating to the FEC to be
               advertised by SR";
            uses sr_fec-address_config;
          }
          container state {
            config false;
            description
              "Operational state relating to a FEC advertised by SR";
            uses sr_fec-address_config;
          }
          container prefix-sid {
            description
              "Parameters relating to the Prefix-SID
               used for the originated FEC";
            container config {
              description
                "Configuration parameters relating to the Prefix-SID
                 used for the originated FEC";
              uses sr_fec-prefix-sid_config;
            }
            container state {
              config false;
              description
                "Operational state parameters relating to the
                 Prefix-SID used for the originated FEC";
              uses sr_fec-prefix-sid_config;
            }
          }
        }
      }
    }
  }

  grouping igp-lsp-sr-setup {
    description
      "grouping for SR-IGP path setup for IGP-congruent
       LSPs";
    container segment-routing {
      presence
        "Presence of this container sets the LSP to use
         SR signaling";
      description
        "segment routing signaling extensions for
         IGP-confgruent LSPs";
      uses igp-tunnel-sr;
    }
  }
  oc-ext:openconfig-version "0.2.1";
}
