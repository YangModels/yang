submodule Cisco-IOS-XR-ipv4-bgp-oc-oper-sub1 {
  belongs-to Cisco-IOS-XR-ipv4-bgp-oc-oper {
    prefix Cisco-IOS-XR-ipv4-bgp-oc-oper;
  }

  import ietf-inet-types {
    prefix inet;
  }
  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-bgp-oc package operational data.
     
     Copyright (c) 2013-2017 by Cisco Systems, Inc.
     All rights reserved.";

  revision 2017-05-01 {
    description
      "Fixing backward compatibility error in module.";
  }
  revision 2015-11-09 {
    description
      "IOS XR 6.0 revision.";
  }

  typedef Bgp-oc-invalid-route-reason {
    type enumeration {
      enum "valid-route" {
        value 1;
        description
          "Valid route";
      }
      enum "invalid-clsuter-loop" {
        value 2;
        description
          "ClusterLoop";
      }
      enum "invalid-as-path-loop" {
        value 3;
        description
          "AsPathLoop";
      }
      enum "invalid-origin-at-or-id" {
        value 4;
        description
          "OriginatorID";
      }
      enum "invalid-as-confed-loop" {
        value 5;
        description
          "ASConfedLoop";
      }
    }
    description
      "Invalid route reason";
  }

  typedef Bgp-oc-origin-attr {
    type enumeration {
      enum "igp" {
        value 0;
        description
          "IGP";
      }
      enum "egp" {
        value 1;
        description
          "EGP";
      }
      enum "incomplete" {
        value 2;
        description
          "Incomplete";
      }
    }
    description
      "Origin Type";
  }

  typedef Ipv6-address {
    type inet:ipv6-address;
    description
      "IPV6 Address type";
  }

  typedef Bgp-oc-afi {
    type enumeration {
      enum "ipv4" {
        value 0;
        description
          "IPv4 unicast";
      }
      enum "ipv6" {
        value 5;
        description
          "IPv6 unicast";
      }
    }
    description
      "BGP Address family";
  }

  grouping BGP-OC-RIB-COMMON-BAG {
    description
      "OpenConfig BGP_RIB common attributes";
    leaf num-routes {
      type uint64;
      description
        "NumRoutes";
    }
  }

  grouping BGP-OC-DATE-AND-TIME {
    description
      "BGP OC DATE AND TIME";
    leaf time-value {
      type string;
      description
        "TimeValue";
    }
  }

  grouping BGP-OC-UNKNOWN-ATTR-TYPE {
    description
      "BGP OC UNKNOWN ATTR TYPE";
    leaf attribute-type {
      type uint16;
      description
        "AttributeType";
    }
    leaf attribute-length {
      type uint16;
      description
        "AttributeLength";
    }
    leaf attribute-value {
      type yang:hex-string;
      description
        "Atributevalue";
    }
  }

  grouping BGP-OC-EXT-ATTR {
    description
      "BGP OC EXT ATTR";
    leaf originator-id {
      type inet:ipv4-address;
      description
        "OriginatorID";
    }
    leaf aigp {
      type uint64;
      description
        "AIGP";
    }
    leaf path-id {
      type uint32;
      description
        "PathId";
    }
    leaf-list cluster {
      type inet:ipv4-address;
      description
        "ClusterList";
    }
    list ext-community {
      description
        "ExtendedCommunityArray";
      uses BGP-OC-STRING-TYPE;
    }
    list unknown-attributes {
      description
        "UnknownAttributes";
      uses BGP-OC-UNKNOWN-ATTR-TYPE;
    }
  }

  grouping BGP-OC-STRING-TYPE {
    description
      "Names of bgp oc objects";
    leaf objects {
      type string;
      description
        "BGP OC objects";
    }
  }

  grouping BGP-OC-AGGREGATOR-TYPE {
    description
      "BGP OC AGGREGATOR TYPE";
    leaf as {
      type uint32;
      description
        "AS number";
    }
    leaf as4 {
      type uint32;
      description
        "AS4 number";
    }
    leaf address {
      type inet:ipv4-address;
      description
        "IPv4 address";
    }
  }

  grouping BGP-OC-ROUTE-ATTR {
    description
      "BGP OC ROUTE ATTR";
    container next-hop {
      description
        "NextHopAddress";
      uses BGP-OC-ADDRTYPE;
    }
    container aggregrator-attributes {
      description
        "AggregatorList";
      uses BGP-OC-AGGREGATOR-TYPE;
    }
    leaf origin-type {
      type Bgp-oc-origin-attr;
      description
        "Origin Attribute Type";
    }
    leaf as-path {
      type string;
      description
        "AS Path";
    }
    leaf as4-path {
      type string;
      description
        "AS4 Path";
    }
    leaf med {
      type uint32;
      description
        "Med";
    }
    leaf local-pref {
      type uint32;
      description
        "LocalPref";
    }
    leaf atomic-aggr {
      type boolean;
      description
        "AtomicAggr";
    }
    list community {
      description
        "CommunityArray";
      uses BGP-OC-STRING-TYPE;
    }
  }

  grouping BGP-OC-ADDRTYPE {
    description
      "BGP OC ADDRTYPE";
    leaf afi {
      type Bgp-oc-afi;
      description
        "AFI";
    }
    leaf ipv4-address {
      when "../afi = 'ipv4'" {
        description
          "../AFI = 'IPv4'";
      }
      type inet:ipv4-address;
      description
        "IPv4 Addr";
    }
    leaf ipv6-address {
      when "../afi = 'ipv6'" {
        description
          "../AFI = 'IPv6'";
      }
      type Ipv6-address;
      description
        "IPv6 Addr";
    }
  }

  grouping BGP-OC-PREFIXTYPE {
    description
      "BGP OC PREFIXTYPE";
    container prefix {
      description
        "Prefix";
      uses BGP-OC-ADDRTYPE;
    }
    leaf prefix-length {
      type uint8;
      description
        "Prefix length";
    }
  }

  grouping BGP-OC-ROUTE-BAG {
    description
      "OpenConfig BGP_RIB Route";
    container prefix-name {
      description
        "Prefix";
      uses BGP-OC-PREFIXTYPE;
    }
    container route-attr-list {
      description
        "RouteAttributesList";
      uses BGP-OC-ROUTE-ATTR;
    }
    container ext-attributes-list {
      description
        "ExtAttributesList";
      uses BGP-OC-EXT-ATTR;
    }
    container last-modified-date {
      description
        "LastModifiedDate";
      uses BGP-OC-DATE-AND-TIME;
    }
    container last-update-recieved {
      description
        "LastUpdateRecieved";
      uses BGP-OC-DATE-AND-TIME;
    }
    leaf valid-route {
      type boolean;
      description
        "ValidRoute";
    }
    leaf invalid-reason {
      type Bgp-oc-invalid-route-reason;
      description
        "IndentityRef";
    }
    leaf best-path {
      type boolean;
      description
        "BestPath";
    }
  }
}
