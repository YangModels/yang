module Cisco-IOS-XR-sysadmin-tacacs-test-tacacs {
  namespace "http://www.cisco.com/ns/yang/Cisco-IOS-XR-sysadmin-tacacs-test-tacacs";
  prefix test_tacacs;

  import Cisco-IOS-XR-sysadmin-tacacs-tacacs-server {
    prefix tacacs-server;
  }

  organization
    "Cisco Systems Inc.";
  contact
    "aaa-ng-tacacs-dev@cisco.com";
  description
    "This module contains definitions
     for the Calvados model objects.
     
     This clie part is for test commands for tacacs
     
     Copyright (c) 2012-2018 by Cisco Systems, Inc.
     All rights reserved.";

  revision 2017-05-10 {
    description
      "Namespace changed from test_tacacs to Cisco-IOS-XR-sysadmin-tacacs-test-tacacs";
  }

  augment "/tacacs-server:tacacs-server" {
    container test-authentication {
      presence "";
      config false;
      leaf authentication {
        type string;
        mandatory false;
        description
          "Authentication";
      }
    }
    container test-authorization {
      presence "";
      config false;
      leaf authorization {
        type string;
        mandatory false;
        description
          "Authorization";
      }
    }
    container test-accounting {
      presence "";
      config false;
      leaf accounting {
        type string;
        mandatory false;
        description
          "Accounting";
      }
    }
  }
}
