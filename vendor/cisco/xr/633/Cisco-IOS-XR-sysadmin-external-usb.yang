module Cisco-IOS-XR-sysadmin-external-usb {
  namespace "http://www.cisco.com/ns/yang/Cisco-IOS-XR-sysadmin-external-usb";
  prefix extusbconf;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module defines the top level container for
     all 'external-usb' commands for Sysadmin.
     
     Copyright(c) 2017 by Cisco Systems, Inc.
     All rights reserved.
     
     Copyright (c) 2012-2018 by Cisco Systems, Inc.
     All rights reserved.";

  revision 2017-04-10 {
    description
      "Initial revision. Added config to disable";
  }

  container external-usb {
    container config {
      config true;
      leaf disable {
        type empty;
      }
    }
  }
}
