module confd_dyncfg {
  namespace "http://tail-f.com/ns/confd_dyncfg/1.0";
  prefix confd_dyncfg;

  import ietf-yang-types {
    prefix yang;
  }
  import ietf-inet-types {
    prefix inet;
  }
  import tailf-common {
    prefix tailf;
  }
  import tailf-xsd-types {
    prefix xs;
  }

  organization
    "Tail-f Systems";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module defines the Tail-f ConfD configuration parameters
     that can be modified in runtime.
     
     Copyright (c) 2012-2018 by Cisco Systems, Inc.
     All rights reserved.";

  revision 2013-01-10 {
    description
      "Released as part of ConfD-3.9.5.1.";
  }

  typedef candidateImplementationType {
    type enumeration {
      enum "confd" {
        value 664387550;
      }
      enum "external" {
        value 1055777754;
      }
    }
  }

  typedef whoHistoryDateTimeFormatType {
    type enumeration {
      enum "long" {
        value 105537656;
      }
      enum "short" {
        value 2029155337;
      }
    }
  }

  typedef multiPatternOperationType {
    type enumeration {
      enum "any" {
        value 383440309;
      }
      enum "all" {
        value 2031982792;
      }
    }
  }

  typedef confirmUncommitedOnExitType {
    type enumeration {
      enum "prompt" {
        value 1796253006;
      }
      enum "discard" {
        value 664427145;
      }
      enum "commit" {
        value 128787545;
      }
    }
  }

  typedef tableBehaviorType {
    type enumeration {
      enum "dynamic" {
        value 1339207079;
      }
      enum "suppress" {
        value 1746378947;
      }
      enum "enforce" {
        value 868039165;
      }
    }
  }

  typedef rollNumbering {
    type enumeration {
      enum "fixed" {
        value 1180146474;
      }
      enum "rolling" {
        value 492733776;
      }
    }
  }

  typedef pipeHelpModeType {
    type enumeration {
      enum "always" {
        value 1980885055;
      }
      enum "auto" {
        value 1146214388;
      }
      enum "never" {
        value 1258673503;
      }
    }
  }

  typedef candidateStorageType {
    type enumeration {
      enum "disk" {
        value 334675513;
      }
      enum "ram" {
        value 781613798;
      }
      enum "auto" {
        value 1146214388;
      }
    }
  }

  typedef editWrapModeType {
    type enumeration {
      enum "wrap" {
        value 1386835265;
      }
      enum "newline" {
        value 100405574;
      }
      enum "vt100" {
        value 321017956;
      }
    }
  }

  typedef cliTimezoneType {
    type enumeration {
      enum "utc" {
        value 1427039597;
      }
      enum "local" {
        value 2129802687;
      }
    }
  }

  typedef configurationReplicationType {
    type enumeration {
      enum "async" {
        value 1368962940;
      }
      enum "sync" {
        value 2047869128;
      }
    }
  }

  typedef operationalPersistentType {
    type enumeration {
      enum "confspec" {
        value 2093298699;
      }
      enum "always" {
        value 1980885055;
      }
      enum "never" {
        value 1258673503;
      }
    }
  }

  typedef operationalReplicationType {
    type enumeration {
      enum "never" {
        value 1258673503;
      }
      enum "always" {
        value 1980885055;
      }
      enum "persistent" {
        value 1783422916;
      }
    }
  }

  typedef operationalReplicationModeType {
    type enumeration {
      enum "async" {
        value 1368962940;
      }
      enum "sync" {
        value 2047869128;
      }
    }
  }

  typedef snmpVersionType {
    type enumeration {
      enum "v1" {
        value 1223356638;
      }
      enum "v2c" {
        value 406691283;
      }
    }
  }

  typedef dscpType {
    type uint8 {
      range "0 .. 63";
    }
  }

  typedef limitType {
    type union {
      type uint32;
      type unboundedType;
    }
  }

  typedef unboundedType {
    type enumeration {
      enum "unbounded" {
        value 1813338730;
      }
    }
  }

  typedef infinityType {
    type enumeration {
      enum "infinity" {
        value 1378257424;
      }
    }
  }

  typedef timeoutType {
    type union {
      type xs:duration;
      type infinityType;
    }
  }

  typedef rpcErrorType {
    type enumeration {
      enum "close" {
        value 1912083739;
      }
      enum "inline" {
        value 1987224790;
      }
    }
  }

  typedef dbAccessType {
    type enumeration {
      enum "read-only" {
        value 1971071769;
      }
      enum "read-write" {
        value 1464236954;
      }
      enum "writable-through-candidate" {
        value 532826246;
      }
    }
  }

  typedef defaultHandlingModeType {
    type enumeration {
      enum "explicit" {
        value 920928367;
      }
      enum "trim" {
        value 250701330;
      }
      enum "report-all" {
        value 1824535838;
      }
    }
  }

  typedef syslogVersionType {
    type enumeration {
      enum "bsd" {
        value 1701318;
      }
      enum "1" {
        value 1535449617;
      }
    }
  }

  typedef cliAuditLogType {
    type enumeration {
      enum "all" {
        value 2031982792;
      }
      enum "none" {
        value 432063804;
      }
      enum "denied" {
        value 1293974345;
      }
      enum "allowed" {
        value 1631106802;
      }
    }
  }

  typedef cliActionMapType {
    type enumeration {
      enum "both" {
        value 1577301616;
      }
      enum "config" {
        value 2105663071;
      }
      enum "oper" {
        value 1313484953;
      }
    }
  }

  typedef cliModeNameStyleType {
    type enumeration {
      enum "short" {
        value 2029155337;
      }
      enum "two" {
        value 87009233;
      }
      enum "full" {
        value 476261018;
      }
    }
  }

  typedef quoteStyleType {
    type enumeration {
      enum "quote" {
        value 883581901;
      }
      enum "backslash" {
        value 1857839842;
      }
    }
  }

  typedef modeInfoInAAAType {
    type enumeration {
      enum "true" {
        value 1808796341;
      }
      enum "false" {
        value 1249155036;
      }
      enum "path" {
        value 1002915403;
      }
    }
  }

  typedef enableDisplayLevelType {
    type enumeration {
      enum "true" {
        value 1808796341;
      }
      enum "false" {
        value 1249155036;
      }
      enum "pipe" {
        value 612053909;
      }
    }
  }

  typedef cliStyle {
    type enumeration {
      enum "j" {
        value 641834109;
      }
      enum "c" {
        value 589337185;
      }
      enum "i" {
        value 1541010383;
      }
    }
  }

  typedef rollbackType {
    type enumeration {
      enum "full" {
        value 476261018;
      }
      enum "delta" {
        value 1928409309;
      }
    }
  }

  typedef syslogFacilityType {
    type union {
      type bsdFacilityType;
      type intFacilityType;
    }
  }

  typedef bsdFacilityType {
    type enumeration {
      enum "daemon" {
        value 137874048;
      }
      enum "authpriv" {
        value 2143429981;
      }
      enum "local0" {
        value 1223389442;
      }
      enum "local1" {
        value 659974174;
      }
      enum "local2" {
        value 388815177;
      }
      enum "local3" {
        value 133202671;
      }
      enum "local4" {
        value 1369253367;
      }
      enum "local5" {
        value 37794477;
      }
      enum "local6" {
        value 918612352;
      }
      enum "local7" {
        value 1098748970;
      }
    }
  }

  typedef intFacilityType {
    type uint32 {
      range "min .. 2147483647";
    }
  }

  typedef cliMax {
    type uint32 {
      range "5 .. 2147483647";
    }
  }

  typedef rollMax {
    type uint32 {
      range "0 .. 2147483647";
    }
  }

  typedef hex8ValueType {
    type xs:hexBinary;
  }

  typedef charType {
    type string {
      length "1";
    }
  }

  typedef falseType {
    type enumeration {
      enum "false" {
        value 1249155036;
      }
    }
  }

  typedef aliasQuoteType {
    type union {
      type falseType;
      type charType;
    }
  }

  typedef hex16ValueType {
    type xs:hexBinary;
  }

  typedef verifyType {
    type uint32 {
      range "1 .. 3";
    }
  }

  typedef pendingChangesActionType {
    type enumeration {
      enum "continue" {
        value 1852005625;
      }
      enum "fail" {
        value 1504483183;
      }
    }
  }

  typedef developerLogLevelType {
    type enumeration {
      enum "error" {
        value 126243105;
      }
      enum "info" {
        value 2062105651;
      }
      enum "trace" {
        value 1896625767;
      }
    }
  }

  typedef netconfTraceFormatType {
    type enumeration {
      enum "pretty" {
        value 560733322;
      }
      enum "raw" {
        value 764753385;
      }
    }
  }

  typedef subagentNameType {
    type xs:token {
      length "min .. 31";
    }
  }

  typedef SNMPAgentNameType {
    type xs:token {
      length "min .. 31";
    }
  }

  typedef runtimeReconfigurationType {
    type enumeration {
      enum "config-file" {
        value 2073952695;
      }
      enum "namespace" {
        value 1847615892;
      }
    }
  }

  typedef idType {
    type union {
      type uint64 {
        range "1 .. max";
      }
      type fixedIdType;
    }
  }

  typedef fixedIdType {
    type enumeration {
      enum "confd" {
        value 664387550;
      }
      enum "user" {
        value 1529217067;
      }
      enum "root" {
        value 1945751049;
      }
    }
  }

  grouping logType {
    leaf enabled {
      type boolean;
      default "true";
    }
    container file {
      presence "";
      leaf enabled {
        type boolean;
        default "false";
      }
      leaf name {
        type string;
        mandatory true;
      }
    }
    container syslog {
      presence "";
      leaf enabled {
        type boolean;
        default "false";
      }
      leaf facility {
        type syslogFacilityType;
      }
    }
  }

  container confdConfig {
    container subagents {
      presence "";
      list subagent {
        key "name";
        leaf name {
          type subagentNameType;
        }
        leaf enabled {
          type boolean;
          default "true";
        }
        container tcp {
          presence "";
          leaf ip {
            type inet:ip-address;
            mandatory true;
          }
          leaf port {
            type inet:port-number;
            default "2023";
          }
          container confdAuth {
            leaf user {
              type string;
              mandatory true;
            }
            leaf group {
              type string;
              mandatory true;
            }
          }
        }
        container ssh {
          presence "";
          leaf ip {
            type inet:ip-address;
            mandatory true;
          }
          leaf port {
            type inet:port-number;
            default "2022";
          }
          leaf user {
            type string;
            mandatory true;
          }
          leaf password {
            type string;
            mandatory true;
          }
        }
        container mount {
          leaf path {
            type string;
            mandatory true;
          }
          leaf-list node {
            type xs:QName;
          }
        }
        leaf disableSubtreeOptimization {
          type boolean;
          default "false";
        }
      }
    }
    container notifications {
      presence "";
      container eventStreams {
        list stream {
          key "name";
          leaf name {
            type xs:token;
          }
          leaf description {
            type string;
            mandatory true;
          }
          leaf replaySupport {
            type boolean;
            mandatory true;
          }
          container builtinReplayStore {
            presence "";
            leaf enabled {
              type boolean;
              default "false";
            }
            leaf dir {
              type string;
              mandatory true;
            }
            leaf maxSize {
              type tailf:size;
              mandatory true;
            }
            leaf maxFiles {
              type int64;
              mandatory true;
            }
          }
        }
      }
    }
    container opcache {
      presence "";
      leaf enabled {
        type boolean;
        default "false";
      }
      leaf timeout {
        type uint64 {
          range "0 .. max";
        }
        mandatory true;
      }
    }
    container snmpgw {
      presence "";
      leaf enabled {
        type boolean;
        default "false";
      }
      leaf trapPort {
        type inet:port-number;
      }
      list agent {
        key "name";
        leaf name {
          type SNMPAgentNameType;
        }
        leaf subscriptionId {
          type xs:token;
          mandatory true;
        }
        leaf enabled {
          type boolean;
          default "true";
        }
        leaf community {
          type string;
          default "private";
        }
        leaf community_bin {
          type xs:hexBinary;
        }
        leaf version {
          type snmpVersionType;
          default "v2c";
        }
        leaf timeout {
          type xs:duration;
          default "PT5S";
        }
        leaf ip {
          type inet:ip-address;
          mandatory true;
        }
        leaf port {
          type inet:port-number;
          default "161";
        }
        leaf-list module {
          type string;
          max-elements "unbounded";
        }
      }
    }
    list hideGroup {
      key "name";
      leaf name {
        type string;
      }
      leaf password {
        type tailf:md5-digest-string;
        default "";
      }
      leaf callback {
        type string;
      }
    }
    container encryptedStrings {
      presence "";
      container DES3CBC {
        presence "";
        leaf key1 {
          type hex8ValueType;
          mandatory true;
        }
        leaf key2 {
          type hex8ValueType;
          mandatory true;
        }
        leaf key3 {
          type hex8ValueType;
          mandatory true;
        }
        leaf initVector {
          type hex8ValueType;
          mandatory true;
        }
      }
      container AESCFB128 {
        presence "";
        leaf key {
          type hex16ValueType;
          mandatory true;
        }
        leaf initVector {
          type hex16ValueType;
          mandatory true;
        }
      }
    }
    container logs {
      presence "";
      container syslogConfig {
        presence "";
        leaf version {
          type syslogVersionType;
          default "bsd";
        }
        leaf facility {
          type syslogFacilityType;
          default "daemon";
        }
        container udp {
          presence "";
          leaf enabled {
            type boolean;
            default "false";
          }
          leaf host {
            type inet:host;
            mandatory true;
          }
          leaf port {
            type inet:port-number;
            default "514";
          }
        }
        container syslogServers {
          presence "";
          list server {
            key "host";
            leaf host {
              type inet:host;
            }
            leaf port {
              type inet:port-number;
              default "514";
            }
            leaf version {
              type syslogVersionType;
              default "bsd";
            }
            leaf facility {
              type syslogFacilityType;
              default "daemon";
            }
            leaf enabled {
              type boolean;
              default "true";
            }
          }
        }
      }
      container confdLog {
        presence "";
        uses logType;
      }
      container developerLog {
        presence "";
        uses logType;
      }
      leaf developerLogLevel {
        type developerLogLevelType;
        default "info";
      }
      container auditLog {
        presence "";
        uses logType;
      }
      leaf auditLogCommit {
        type boolean;
        default "false";
      }
      container netconfLog {
        presence "";
        uses logType;
      }
      container snmpLog {
        presence "";
        uses logType;
      }
      container webuiBrowserLog {
        presence "";
        leaf enabled {
          type boolean;
          default "false";
        }
        leaf filename {
          type string;
          mandatory true;
        }
      }
      container webuiAccessLog {
        presence "";
        leaf enabled {
          type boolean;
          default "false";
        }
        leaf dir {
          type string;
          mandatory true;
        }
      }
      container netconfTraceLog {
        presence "";
        leaf enabled {
          type boolean;
          default "false";
        }
        leaf filename {
          type string;
          mandatory true;
        }
        leaf format {
          type netconfTraceFormatType;
          default "pretty";
        }
      }
      container xpathTraceLog {
        presence "";
        leaf enabled {
          type boolean;
          default "false";
        }
        leaf filename {
          type string;
          mandatory true;
        }
      }
      container errorLog {
        presence "";
        leaf enabled {
          type boolean;
          default "false";
        }
        leaf filename {
          type string;
          mandatory true;
        }
        leaf maxSize {
          type tailf:size;
          default "S1M";
        }
        container debug {
          presence "";
          leaf enabled {
            type boolean;
            default "false";
          }
          leaf level {
            type uint16;
            default "2";
          }
          leaf-list tag {
            type xs:token;
            max-elements "unbounded";
          }
        }
      }
    }
    container sessionLimits {
      presence "";
      leaf maxSessions {
        type limitType;
        default "unbounded";
      }
      list sessionLimit {
        key "context";
        leaf context {
          type xs:token;
        }
        leaf maxSessions {
          type limitType;
          mandatory true;
        }
      }
      leaf maxConfigSessions {
        type limitType;
        default "unbounded";
      }
      list configSessionLimit {
        key "context";
        leaf context {
          type xs:token;
        }
        leaf maxSessions {
          type limitType;
          mandatory true;
        }
      }
    }
    container aaa {
      presence "";
      leaf sshLoginGraceTime {
        type xs:duration;
        default "PT10M";
      }
      leaf defaultGroup {
        type string;
      }
      leaf authOrder {
        type string;
      }
      container pam {
        presence "";
        leaf enabled {
          type boolean;
          default "false";
        }
        leaf service {
          type string;
          default "common-auth";
        }
      }
      container externalAuthentication {
        presence "";
        leaf enabled {
          type boolean;
          default "false";
        }
        leaf executable {
          type string;
        }
        leaf useBase64 {
          type boolean;
          default "false";
        }
        leaf includeExtra {
          type boolean;
          default "false";
        }
      }
      container localAuthentication {
        presence "";
        leaf enabled {
          type boolean;
          default "true";
        }
      }
      container authenticationCallback {
        presence "";
        leaf enabled {
          type boolean;
          default "false";
        }
      }
      container authorization {
        presence "";
        leaf enabled {
          type boolean;
          default "true";
        }
        container callback {
          presence "";
          leaf enabled {
            type boolean;
            default "false";
          }
        }
      }
    }
    container ssh {
      presence "";
      leaf idleConnectionTimeout {
        type xs:duration;
        default "PT10M";
      }
    }
    container cli {
      presence "";
      leaf enabled {
        type boolean;
        default "true";
      }
      leaf modeNameStyle {
        type cliModeNameStyleType;
        default "short";
      }
      leaf allowOverwriteOnCopy {
        type boolean;
        default "false";
      }
      leaf inheritPaginate {
        type boolean;
        default "false";
      }
      leaf safeScriptExecution {
        type boolean;
        default "true";
      }
      leaf exitConfigModeOnCtrlC {
        type boolean;
        default "true";
      }
      leaf execNavigationCmds {
        type boolean;
        default "false";
      }
      leaf allowOldStyleModeCmds {
        type boolean;
        default "false";
      }
      leaf mixedMode {
        type boolean;
        default "false";
      }
      leaf topLevelCmdsInSubMode {
        type boolean;
        default "false";
      }
      leaf completionShowOldVal {
        type boolean;
        default "true";
      }
      leaf reportInvalidCompletionInput {
        type boolean;
        default "false";
      }
      leaf useShortEnabled {
        type boolean;
        default "true";
      }
      leaf smartRenameFiltering {
        type boolean;
        default "true";
      }
      leaf allowParenQuotes {
        type boolean;
        default "false";
      }
      leaf singleElemPattern {
        type boolean;
        default "true";
      }
      leaf multiPatternOperation {
        type multiPatternOperationType;
        default "any";
      }
      leaf sortSubmodeCmds {
        type boolean;
        default "true";
      }
      leaf sortLocalCmds {
        type boolean;
        default "true";
      }
      leaf displayEmptyConfigContainers {
        type boolean;
        default "true";
      }
      leaf whoShowMode {
        type boolean;
        default "true";
      }
      leaf whoHistoryDateTimeFormat {
        type whoHistoryDateTimeFormatType;
        default "short";
      }
      leaf editWrapMode {
        type editWrapModeType;
        default "wrap";
      }
      leaf supportQuotedEOL {
        type boolean;
        default "true";
      }
      leaf allowWildcard {
        type boolean;
        default "true";
      }
      leaf allowAllAsWildcard {
        type boolean;
        default "false";
      }
      leaf allowRangeExpression {
        type boolean;
        default "true";
      }
      leaf addExtraTableSpacing {
        type boolean;
        default "false";
      }
      leaf suppressRangeKeyword {
        type boolean;
        default "false";
      }
      leaf tableLabel {
        type boolean;
        default "false";
      }
      leaf tableLookAhead {
        type uint64 {
          range "1 .. max";
        }
        default "50";
      }
      leaf showTableLabelsIfMultiple {
        type boolean;
        default "false";
      }
      leaf defaultTableBehavior {
        type tableBehaviorType;
        default "dynamic";
      }
      leaf allowTableOverflow {
        type boolean;
        default "false";
      }
      leaf tableOverflowTruncate {
        type boolean;
        default "false";
      }
      leaf allowTableCellWrap {
        type boolean;
        default "true";
      }
      leaf showAllNs {
        type boolean;
        default "false";
      }
      leaf leafPrompting {
        type boolean;
        default "true";
      }
      leaf auditLogMode {
        type cliAuditLogType;
        default "all";
      }
      leaf transactions {
        type boolean;
        default "true";
      }
      leaf transactionCtrlCmds {
        type boolean;
        default "false";
      }
      leaf style {
        type cliStyle;
        default "j";
      }
      leaf completionShowMax {
        type cliMax;
        default "100";
      }
      leaf rollbackMax {
        type rollMax;
        default "1000";
      }
      leaf rollbackNumbering {
        type rollNumbering;
        default "rolling";
      }
      leaf rollbackNumberingInitial {
        type int64;
        default "10000";
      }
      leaf showDefaults {
        type boolean;
        default "false";
      }
      leaf reallocateOperTrans {
        type boolean;
        default "false";
      }
      leaf quickSshTeardown {
        type boolean;
        default "false";
      }
      leaf cAlignLeafValues {
        type boolean;
        default "true";
      }
      leaf defaultPrefix {
        type string;
        default "";
      }
      leaf jWarningPrefix {
        type string;
        default "Warning: ";
      }
      leaf jAbortedPrefix {
        type string;
        default "Aborted: ";
      }
      leaf jErrorPrefix {
        type string;
        default "Error: ";
      }
      leaf cWarningPrefix {
        type string;
        default "Warning: ";
      }
      leaf cAbortedPrefix {
        type string;
        default "Aborted: ";
      }
      leaf cErrorPrefix {
        type string;
        default "Error: ";
      }
      leaf invalidDataString {
        type string;
        default "--ERROR--";
      }
      leaf showKeyName {
        type boolean;
        default "true";
      }
      leaf commitRetryTimeout {
        type timeoutType;
        default "PT0S";
      }
      leaf timezone {
        type cliTimezoneType;
        default "local";
      }
      leaf utcOffset {
        type int64;
        default "0";
      }
      leaf oldDetailsArg {
        type boolean;
        default "false";
      }
      leaf withDefaults {
        type boolean;
        default "false";
      }
      leaf trimDefaultShow {
        type boolean;
        default "false";
      }
      leaf trimDefaultSave {
        type boolean;
        default "false";
      }
      leaf banner {
        type string;
        default "";
      }
      leaf bannerFile {
        type string;
        default "";
      }
      leaf prompt1 {
        type string;
        default "\\u@\\h\\M> ";
      }
      leaf prompt2 {
        type string;
        default "\\u@\\h\\M% ";
      }
      leaf cPrompt1 {
        type string;
        default "\\h\\M# ";
      }
      leaf cPrompt2 {
        type string;
        default "\\h(\\m)# ";
      }
      leaf cStylePromptInJStyle {
        type boolean;
        default "false";
      }
      leaf promptHostnameDelimiter {
        type string;
        default ".";
      }
      leaf asyncPromptRefresh {
        type boolean;
        default "true";
      }
      leaf showLogDirectory {
        type string;
        default "/var/log";
      }
      leaf idleTimeout {
        type xs:duration;
        default "PT30M";
      }
      leaf disableIdleTimeoutOnCmd {
        type boolean;
        default "true";
      }
      leaf commandTimeout {
        type timeoutType;
        default "infinity";
      }
      container spaceCompletion {
        presence "";
        leaf enabled {
          type boolean;
          default "true";
        }
      }
      container timestamp {
        presence "";
        leaf enabled {
          type boolean;
          default "false";
        }
      }
      container autoWizard {
        presence "";
        leaf enabled {
          type boolean;
          default "true";
        }
      }
      container ssh {
        presence "";
        leaf enabled {
          type boolean;
          default "true";
        }
        leaf ip {
          type inet:ip-address;
          default "0.0.0.0";
        }
        leaf port {
          type inet:port-number;
          default "2024";
        }
        leaf-list extraIpPorts {
          type xs:token;
        }
        leaf dscp {
          type dscpType;
        }
        leaf banner {
          type string;
          default "";
        }
        leaf bannerFile {
          type string;
          default "";
        }
      }
      leaf commitMessage {
        type boolean;
        default "true";
      }
      leaf commitMessageFormat {
        type string;
        default "\\nSystem message at $(time)...\\nCommit performed by $(user) via $(proto) using $(ctx).\\n";
      }
      container suppressCommitMessages {
        presence "";
        leaf-list context {
          type string;
          max-elements "unbounded";
        }
      }
      leaf jShowCR {
        type boolean;
        default "false";
      }
      leaf showPipe {
        type boolean;
        default "true";
      }
      leaf showPipeConfig {
        type boolean;
        default "false";
      }
      leaf disablePipe {
        type boolean;
        default "false";
      }
      leaf disablePipeConfig {
        type boolean;
        default "false";
      }
      leaf pipeHelpMode {
        type pipeHelpModeType;
        default "auto";
      }
      leaf jAllowDeleteAll {
        type boolean;
        default "true";
      }
      leaf cSilentNo {
        type boolean;
        default "true";
      }
      leaf noFollowIncompleteCommand {
        type boolean;
        default "false";
      }
      leaf cRestrictiveNo {
        type boolean;
        default "false";
      }
      leaf prioritizeSubmodeCmds {
        type boolean;
        default "true";
      }
      leaf cExtendedCmdSearch {
        type boolean;
        default "true";
      }
      leaf enterSubmodeOnLeaf {
        type boolean;
        default "true";
      }
      leaf jExtendedShow {
        type boolean;
        default "true";
      }
      leaf jShowUnset {
        type boolean;
        default "false";
      }
      leaf jShowUnsetText {
        type string;
        default "UNSET";
      }
      leaf jStatusFormat {
        type string;
        default "[$(status)][$(time)]\\n";
      }
      leaf cModeExitFormat {
        type string;
        default "!";
      }
      leaf forcedExitFormat {
        type string;
        default "\\nYou are forced out of configure mode by $(sender).\\n";
      }
      leaf showSubsystemMessages {
        type boolean;
        default "true";
      }
      leaf ignoreSubsystemFailures {
        type boolean;
        default "false";
      }
      leaf showEmptyContainers {
        type boolean;
        default "false";
      }
      leaf showTags {
        type boolean;
        default "true";
      }
      leaf showAnnotations {
        type boolean;
        default "true";
      }
      leaf jShowTableRecursive {
        type boolean;
        default "false";
      }
      leaf cPrivate {
        type boolean;
        default "false";
      }
      leaf cTab {
        type boolean;
        default "false";
      }
      leaf cTabInfo {
        type boolean;
        default "false";
      }
      leaf tabExtend {
        type boolean;
        default "false";
      }
      leaf cHelp {
        type boolean;
        default "true";
      }
      leaf restrictedFileAccess {
        type boolean;
        default "false";
      }
      leaf hideDotFiles {
        type boolean;
        default "false";
      }
      leaf restrictedFileRegexp {
        type string;
        default "";
      }
      leaf historyRemoveDuplicates {
        type boolean;
        default "false";
      }
      leaf historyMaxSize {
        type int64;
        default "1000";
      }
      leaf messageMaxSize {
        type int64;
        default "10000";
      }
      leaf mapActions {
        type cliActionMapType;
        default "both";
      }
      leaf compactTable {
        type boolean;
        default "true";
      }
      leaf compactShow {
        type boolean;
        default "false";
      }
      leaf compactStatsShow {
        type boolean;
        default "false";
      }
      leaf prettifyStatsName {
        type boolean;
        default "false";
      }
      leaf showCommitProgress {
        type boolean;
        default "false";
      }
      leaf commitActivityClock {
        type boolean;
        default "false";
      }
      leaf confirmUncommitedOnExit {
        type confirmUncommitedOnExitType;
        default "prompt";
      }
      leaf reconfirmHidden {
        type boolean;
        default "false";
      }
      leaf dequoteHidden {
        type boolean;
        default "false";
      }
      leaf enumKeyInfo {
        type boolean;
        default "false";
      }
      leaf columnStats {
        type boolean;
        default "false";
      }
      leaf allowAbbrevCmds {
        type boolean;
        default "true";
      }
      leaf allowAbbrevCmdsOnLoad {
        type boolean;
        default "true";
      }
      leaf allowAbbrevKeys {
        type boolean;
        default "true";
      }
      leaf allowAbbrevParamNames {
        type boolean;
        default "false";
      }
      leaf allowAbbrevEnums {
        type boolean;
        default "true";
      }
      leaf allowCaseInsensitiveEnums {
        type boolean;
        default "true";
      }
      leaf strictRefsOnLoad {
        type boolean;
        default "false";
      }
      leaf stopLoadOnError {
        type boolean;
        default "true";
      }
      leaf autocommitLoad {
        type boolean;
        default "false";
      }
      leaf enableLoadMerge {
        type boolean;
        default "true";
      }
      leaf loadActivityClock {
        type boolean;
        default "false";
      }
      leaf instanceDescription {
        type boolean;
        default "true";
      }
      leaf addErrorPrefixSuffix {
        type boolean;
        default "true";
      }
      leaf compListCompact {
        type boolean;
        default "false";
      }
      leaf completionListLine {
        type boolean;
        default "false";
      }
      leaf infoOnMatch {
        type boolean;
        default "true";
      }
      leaf externalActionErrorMsg {
        type string;
      }
      leaf enableDisplayLevel {
        type enableDisplayLevelType;
        default "pipe";
      }
      leaf defaultDisplayLevel {
        type int64;
        default "99999999";
      }
      leaf enableDisplayGroups {
        type boolean;
        default "true";
      }
      leaf unifiedHistory {
        type boolean;
        default "false";
      }
      leaf modeInfoInAAA {
        type modeInfoInAAAType;
        default "false";
      }
      leaf cmdAAAForAutowizard {
        type boolean;
        default "false";
      }
      leaf quoteStyle {
        type quoteStyleType;
        default "backslash";
      }
      leaf laxBarQuoting {
        type boolean;
        default "false";
      }
      leaf expandAliasEscape {
        type aliasQuoteType;
        default "false";
      }
      leaf docWrap {
        type boolean;
        default "true";
      }
      leaf infoOnTab {
        type boolean;
        default "true";
      }
      leaf infoOnSpace {
        type boolean;
        default "true";
      }
      leaf newLogout {
        type boolean;
        default "true";
      }
      leaf newInsert {
        type boolean;
        default "true";
      }
      leaf messageFormat {
        type string;
        default "\\nMessage from $(sender) at $(time)...\\n$(message)\\nEOF\\n";
      }
      leaf messageWordWrap {
        type boolean;
        default "false";
      }
      leaf messageQueueSize {
        type int64;
        default "10";
      }
      leaf promptEnumLimit {
        type uint64 {
          range "0 .. max";
        }
        default "4";
      }
      leaf caseInsensitive {
        type boolean;
        default "false";
      }
      leaf caseInsensitiveKeys {
        type boolean;
        default "false";
      }
      leaf ignoreLeadingWhitespace {
        type boolean;
        default "false";
      }
      leaf indentTemplates {
        type boolean;
        default "false";
      }
      leaf wrapInfo {
        type boolean;
        default "true";
      }
      leaf wrapPrompt {
        type boolean;
        default "false";
      }
      leaf sortShowElems {
        type boolean;
        default "true";
      }
      leaf showMatchBeforePossible {
        type boolean;
        default "false";
      }
      leaf possibleCompletionsFormat {
        type string;
        default "Possible completions:";
      }
      leaf matchCompletionsFormat {
        type string;
        default "Possible match completions:";
      }
      leaf noMatchCompletionsFormat {
        type string;
        default "";
      }
      leaf showDescription {
        type boolean;
        default "true";
      }
      leaf explicitSetCreate {
        type boolean;
        default "false";
      }
      list templateFilter {
        key "name";
        leaf name {
          type string;
        }
        leaf callback {
          type string;
        }
      }
    }
    container webui {
      presence "";
      leaf enabled {
        type boolean;
        default "false";
      }
      leaf serverName {
        type xs:token;
        default "localhost";
      }
      leaf matchHostName {
        type boolean;
        default "false";
      }
      leaf cacheRefreshSecs {
        type uint64 {
          range "0 .. max";
        }
        default "0";
      }
      leaf maxRefEntries {
        type uint64 {
          range "0 .. max";
        }
        default "100";
      }
      leaf docroot {
        type string;
        mandatory true;
      }
      container disableAuth {
        presence "";
        leaf-list dir {
          type string;
          max-elements "unbounded";
        }
      }
      leaf allowSymlinks {
        type boolean;
        default "true";
      }
      container transport {
        presence "";
        container tcp {
          presence "";
          leaf enabled {
            type boolean;
            default "true";
          }
          leaf disableNonAuthRedirect {
            type boolean;
            default "false";
          }
          leaf redirect {
            type string;
          }
          leaf ip {
            type inet:ip-address;
            default "0.0.0.0";
          }
          leaf port {
            type inet:port-number;
            default "8008";
          }
          leaf-list extraIpPorts {
            type xs:token;
          }
          leaf dscp {
            type dscpType;
          }
        }
        container ssl {
          presence "";
          leaf enabled {
            type boolean;
            default "false";
          }
          leaf disableNonAuthRedirect {
            type boolean;
            default "false";
          }
          leaf redirect {
            type string;
          }
          leaf ip {
            type inet:ip-address;
            default "0.0.0.0";
          }
          leaf port {
            type inet:port-number;
            default "8888";
          }
          leaf-list extraIpPorts {
            type xs:token;
          }
          leaf dscp {
            type dscpType;
          }
          leaf keyFile {
            type string;
            mandatory true;
          }
          leaf certFile {
            type string;
            mandatory true;
          }
          leaf caCertFile {
            type string;
          }
          leaf verify {
            type verifyType;
            default "1";
          }
          leaf depth {
            type uint64 {
              range "0 .. max";
            }
            default "1";
          }
          leaf ciphers {
            type string;
            default "DEFAULT";
          }
        }
      }
      container cgi {
        presence "";
        leaf enabled {
          type boolean;
          default "false";
        }
        leaf dir {
          type string;
          default "cgi-bin";
        }
        leaf requestFilter {
          type string;
        }
        leaf maxRequestLength {
          type uint16;
        }
        container php {
          presence "";
          leaf enabled {
            type boolean;
            default "false";
          }
        }
      }
      leaf idleTimeout {
        type xs:duration;
        default "PT30M";
      }
    }
    container rest {
      presence "";
      leaf enabled {
        type boolean;
        default "false";
      }
    }
    container proxyForwarding {
      presence "";
      leaf autoLogin {
        type boolean;
        default "false";
      }
      list proxy {
        key "target";
        leaf target {
          type xs:token;
        }
        leaf address {
          type inet:host;
          mandatory true;
        }
        container netconf {
          presence "";
          container ssh {
            leaf port {
              type inet:port-number;
              default "2022";
            }
          }
          container tcp {
            leaf port {
              type inet:port-number;
              default "2023";
            }
          }
        }
        container cli {
          presence "";
          container ssh {
            leaf port {
              type inet:port-number;
              default "22";
            }
          }
        }
      }
    }
    container snmpAgent {
      presence "";
      leaf enabled {
        type boolean;
        default "false";
      }
      leaf ip {
        type inet:ip-address;
        default "0.0.0.0";
      }
      leaf port {
        type inet:port-number;
        default "161";
      }
      leaf-list extraIpPorts {
        type xs:token;
      }
      leaf dscp {
        type dscpType;
      }
      container mibs {
        presence "";
        leaf-list file {
          type string;
          max-elements "unbounded";
        }
        leaf fromLoadPath {
          type boolean;
          default "false";
        }
      }
      leaf temporaryStorageTime {
        type uint32;
        default "300";
      }
      container snmpVersions {
        presence "";
        leaf v1 {
          type boolean;
          default "true";
        }
        leaf v2c {
          type boolean;
          default "true";
        }
        leaf v3 {
          type boolean;
          default "true";
        }
      }
      container snmpEngine {
        presence "";
        leaf snmpEngineID {
          type tailf:hex-list;
          mandatory true;
        }
        leaf snmpEngineMaxMessageSize {
          type uint64 {
            range "0 .. max";
          }
          default "50000";
        }
      }
      leaf authenticationFailureNotifyName {
        type string;
        default "";
      }
      container candidate {
        presence "";
        leaf maxLockWait {
          type xs:duration;
          default "PT0S";
        }
        leaf pendingChangesAction {
          type pendingChangesActionType;
          default "continue";
        }
      }
      container system {
        presence "";
        leaf sysDescr {
          type string;
        }
        leaf sysObjectID {
          type yang:object-identifier;
        }
        leaf sysServices {
          type uint64 {
            range "0 .. max";
          }
          default "72";
        }
        container sysORTable {
          presence "";
          list sysOREntry {
            key "sysORIndex";
            leaf sysORIndex {
              type uint64 {
                range "0 .. max";
              }
            }
            leaf sysORID {
              type yang:object-identifier;
              mandatory true;
            }
            leaf sysORDescr {
              type string;
              mandatory true;
            }
          }
        }
      }
    }
    container netconf {
      presence "";
      leaf enabled {
        type boolean;
        default "true";
      }
      container transport {
        presence "";
        container ssh {
          presence "";
          leaf enabled {
            type boolean;
            default "true";
          }
          leaf ip {
            type inet:ip-address;
            default "0.0.0.0";
          }
          leaf port {
            type inet:port-number;
            default "2022";
          }
          leaf-list extraIpPorts {
            type xs:token;
          }
          leaf dscp {
            type dscpType;
          }
        }
        container tcp {
          presence "";
          leaf enabled {
            type boolean;
            default "false";
          }
          leaf ip {
            type inet:ip-address;
            default "0.0.0.0";
          }
          leaf port {
            type inet:port-number;
            default "2023";
          }
          leaf-list extraIpPorts {
            type xs:token;
          }
          leaf dscp {
            type dscpType;
          }
        }
      }
      leaf extendedSessions {
        type boolean;
        default "false";
      }
      leaf sendDefaults {
        type boolean;
        default "false";
      }
      leaf idleTimeout {
        type xs:duration;
        default "PT0S";
      }
      leaf rpcErrors {
        type rpcErrorType;
        default "close";
      }
      leaf maxBatchProcesses {
        type limitType;
        default "unbounded";
      }
    }
  }
}
