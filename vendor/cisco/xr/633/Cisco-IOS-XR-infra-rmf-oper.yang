module Cisco-IOS-XR-infra-rmf-oper {
  namespace "http://cisco.com/ns/yang/Cisco-IOS-XR-infra-rmf-oper";
  prefix infra-rmf-oper;

  import Cisco-IOS-XR-types {
    prefix xr;
  }
  include Cisco-IOS-XR-infra-rmf-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-rmf package operational data.
     
     This module contains definitions
     for the following management objects:
       redundancy: Redundancy show information
     
     Copyright (c) 2013-2017 by Cisco Systems, Inc.
     All rights reserved.";

  revision 2015-11-09 {
    description
      "IOS XR 6.0 revision.";
  }

  container redundancy {
    config false;
    description
      "Redundancy show information";
    container nodes {
      description
        "Location show information";
      list node {
        key "node-id";
        description
          "Redundancy Node Information";
        leaf node-id {
          type xr:Node-id;
          description
            "Node Location";
        }
        uses RED-NODE-INFO;
      }
    }
    container summary {
      description
        "Redundancy Summary of Nodes";
      uses RED-SUMMARY;
    }
  }
}
