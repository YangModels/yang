module Cisco-IOS-XR-sysadmin-entity-state-tc-mib {
  namespace "http://www.cisco.com/ns/yang/Cisco-IOS-XR-sysadmin-entity-state-tc-mib";
  prefix ENTITY_STATE_TC_MIB;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2015-2017 by Cisco Systems, Inc.
     All rights reserved.";

  revision 2017-04-12 {
    description
      "Changed namespace and module name";
  }
  revision 2005-11-22 {
    description
      "";
  }

  typedef EntityAdminState {
    type enumeration {
      enum "unknown" {
        value 1;
      }
      enum "locked" {
        value 2;
      }
      enum "shuttingDown" {
        value 3;
      }
      enum "unlocked" {
        value 4;
      }
    }
  }

  typedef EntityOperState {
    type enumeration {
      enum "unknown" {
        value 1;
      }
      enum "disabled" {
        value 2;
      }
      enum "enabled" {
        value 3;
      }
      enum "testing" {
        value 4;
      }
    }
  }

  typedef EntityUsageState {
    type enumeration {
      enum "unknown" {
        value 1;
      }
      enum "idle" {
        value 2;
      }
      enum "active" {
        value 3;
      }
      enum "busy" {
        value 4;
      }
    }
  }

  typedef EntityAlarmStatus {
    type bits {
      bit unknown {
        position 0;
      }
      bit underRepair {
        position 1;
      }
      bit critical {
        position 2;
      }
      bit major {
        position 3;
      }
      bit minor {
        position 4;
      }
      bit warning {
        position 5;
      }
      bit indeterminate {
        position 6;
      }
    }
  }

  typedef EntityStandbyStatus {
    type enumeration {
      enum "unknown" {
        value 1;
      }
      enum "hotStandby" {
        value 2;
      }
      enum "coldStandby" {
        value 3;
      }
      enum "providingService" {
        value 4;
      }
    }
  }
  tailf:id "http://tail-f.com/ns/mibs/ENTITY-STATE-TC-MIB/200511220000Z";
  tailf:snmp-mib-module-name "ENTITY-STATE-TC-MIB";
}
