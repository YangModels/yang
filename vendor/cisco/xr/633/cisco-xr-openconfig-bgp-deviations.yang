module cisco-xr-openconfig-bgp-deviations {
  namespace "http://cisco.com/ns/yang/cisco-xr-openconfig-bgp-deviations";
  prefix cisco-xr-oc-bgp-devs;

  import openconfig-bgp {
    prefix bgp;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations of Open Config BGP YANG
     set for Cisco IOS-XR.
     
     Copyright (c) 2015-2017 by Cisco Systems, Inc.
     All rights reserved.";

  revision 2017-02-02 {
    description
      "Updated revision applicable to IOS-XR 6.2.2";
  }

  deviation "/bgp:bgp/bgp:global/bgp:confederation/bgp:config/bgp:enabled" {
    deviate not-supported;
  }
  deviation "/bgp:bgp/bgp:global/bgp:graceful-restart/bgp:config/bgp:helper-only" {
    deviate not-supported;
  }
  deviation "/bgp:bgp/bgp:global/bgp:graceful-restart/bgp:state/bgp:helper-only" {
    deviate not-supported;
  }
  deviation "/bgp:bgp/bgp:global/bgp:use-multiple-paths/bgp:config" {
    deviate not-supported;
  }
  deviation "/bgp:bgp/bgp:global/bgp:use-multiple-paths/bgp:ebgp/bgp:config/bgp:allow-multiple-as" {
    deviate not-supported;
  }
  deviation "/bgp:bgp/bgp:global/bgp:use-multiple-paths/bgp:ebgp/bgp:state/bgp:allow-multiple-as" {
    deviate not-supported;
  }
  deviation "/bgp:bgp/bgp:global/bgp:route-selection-options/bgp:config/bgp:external-compare-router-id" {
    deviate replace {
      default "false";
    }
  }
  deviation "/bgp:bgp/bgp:global/bgp:route-selection-options/bgp:config/bgp:advertise-inactive-routes" {
    deviate not-supported;
  }
  deviation "/bgp:bgp/bgp:global/bgp:route-selection-options/bgp:config/bgp:enable-aigp" {
    deviate replace {
      default "true";
    }
  }
  deviation "/bgp:bgp/bgp:global/bgp:route-selection-options/bgp:config/bgp:ignore-next-hop-igp-metric" {
    deviate not-supported;
  }
  deviation "/bgp:bgp/bgp:global/bgp:route-selection-options/bgp:state/bgp:external-compare-router-id" {
    deviate replace {
      default "false";
    }
  }
  deviation "/bgp:bgp/bgp:global/bgp:route-selection-options/bgp:state/bgp:advertise-inactive-routes" {
    deviate not-supported;
  }
  deviation "/bgp:bgp/bgp:global/bgp:route-selection-options/bgp:state/bgp:enable-aigp" {
    deviate replace {
      default "true";
    }
  }
  deviation "/bgp:bgp/bgp:global/bgp:route-selection-options/bgp:state/bgp:ignore-next-hop-igp-metric" {
    deviate not-supported;
  }
  deviation "/bgp:bgp/bgp:global/bgp:afi-safis/bgp:afi-safi/bgp:graceful-restart" {
    deviate not-supported;
  }
  deviation "/bgp:bgp/bgp:global/bgp:afi-safis/bgp:afi-safi/bgp:apply-policy" {
    deviate not-supported;
  }
  deviation "/bgp:bgp/bgp:global/bgp:afi-safis/bgp:afi-safi/bgp:ipv4-unicast" {
    deviate not-supported;
  }
  deviation "/bgp:bgp/bgp:global/bgp:afi-safis/bgp:afi-safi/bgp:ipv6-unicast" {
    deviate not-supported;
  }
  deviation "/bgp:bgp/bgp:global/bgp:afi-safis/bgp:afi-safi/bgp:ipv4-labeled-unicast" {
    deviate not-supported;
  }
  deviation "/bgp:bgp/bgp:global/bgp:afi-safis/bgp:afi-safi/bgp:ipv6-labeled-unicast" {
    deviate not-supported;
  }
  deviation "/bgp:bgp/bgp:global/bgp:afi-safis/bgp:afi-safi/bgp:l3vpn-ipv4-unicast" {
    deviate not-supported;
  }
  deviation "/bgp:bgp/bgp:global/bgp:afi-safis/bgp:afi-safi/bgp:l3vpn-ipv6-unicast" {
    deviate not-supported;
  }
  deviation "/bgp:bgp/bgp:global/bgp:afi-safis/bgp:afi-safi/bgp:l3vpn-ipv4-multicast" {
    deviate not-supported;
  }
  deviation "/bgp:bgp/bgp:global/bgp:afi-safis/bgp:afi-safi/bgp:l3vpn-ipv6-multicast" {
    deviate not-supported;
  }
  deviation "/bgp:bgp/bgp:global/bgp:afi-safis/bgp:afi-safi/bgp:l2vpn-vpls" {
    deviate not-supported;
  }
  deviation "/bgp:bgp/bgp:global/bgp:afi-safis/bgp:afi-safi/bgp:l2vpn-evpn" {
    deviate not-supported;
  }
  deviation "/bgp:bgp/bgp:global/bgp:afi-safis/bgp:afi-safi/bgp:route-selection-options" {
    deviate not-supported;
  }
  deviation "/bgp:bgp/bgp:global/bgp:afi-safis/bgp:afi-safi/bgp:use-multiple-paths/bgp:config" {
    deviate not-supported;
  }
  deviation "/bgp:bgp/bgp:global/bgp:afi-safis/bgp:afi-safi/bgp:use-multiple-paths/bgp:ebgp/bgp:config/bgp:allow-multiple-as" {
    deviate not-supported;
  }
  deviation "/bgp:bgp/bgp:global/bgp:afi-safis/bgp:afi-safi/bgp:use-multiple-paths/bgp:ebgp/bgp:state/bgp:allow-multiple-as" {
    deviate not-supported;
  }
  deviation "/bgp:bgp/bgp:global/bgp:apply-policy" {
    deviate not-supported;
  }
  deviation "/bgp:bgp/bgp:neighbors/bgp:neighbor/bgp:config/bgp:enabled" {
    deviate not-supported;
  }
  deviation "/bgp:bgp/bgp:neighbors/bgp:neighbor/bgp:config/bgp:peer-type" {
    deviate not-supported;
  }
  deviation "/bgp:bgp/bgp:neighbors/bgp:neighbor/bgp:config/bgp:route-flap-damping" {
    deviate not-supported;
  }
  deviation "/bgp:bgp/bgp:neighbors/bgp:neighbor/bgp:state/bgp:enabled" {
    deviate not-supported;
  }
  deviation "/bgp:bgp/bgp:neighbors/bgp:neighbor/bgp:state/bgp:peer-type" {
    deviate not-supported;
  }
  deviation "/bgp:bgp/bgp:neighbors/bgp:neighbor/bgp:state/bgp:route-flap-damping" {
    deviate not-supported;
  }
  deviation "/bgp:bgp/bgp:neighbors/bgp:neighbor/bgp:state/bgp:last-established" {
    deviate not-supported;
  }
  deviation "/bgp:bgp/bgp:neighbors/bgp:neighbor/bgp:state/bgp:established-transitions" {
    deviate not-supported;
  }
  deviation "/bgp:bgp/bgp:neighbors/bgp:neighbor/bgp:timers/bgp:config/bgp:connect-retry" {
    deviate not-supported;
  }
  deviation "/bgp:bgp/bgp:neighbors/bgp:neighbor/bgp:timers/bgp:state/bgp:connect-retry" {
    deviate not-supported;
  }
  deviation "/bgp:bgp/bgp:neighbors/bgp:neighbor/bgp:transport/bgp:config/bgp:mtu-discovery" {
    deviate not-supported;
  }
  deviation "/bgp:bgp/bgp:neighbors/bgp:neighbor/bgp:transport/bgp:state/bgp:mtu-discovery" {
    deviate not-supported;
  }
  deviation "/bgp:bgp/bgp:neighbors/bgp:neighbor/bgp:error-handling" {
    deviate not-supported;
  }
  deviation "/bgp:bgp/bgp:neighbors/bgp:neighbor/bgp:logging-options" {
    deviate not-supported;
  }
  deviation "/bgp:bgp/bgp:neighbors/bgp:neighbor/bgp:as-path-options" {
    deviate not-supported;
  }
  deviation "/bgp:bgp/bgp:neighbors/bgp:neighbor/bgp:add-paths" {
    deviate not-supported;
  }
  deviation "/bgp:bgp/bgp:neighbors/bgp:neighbor/bgp:afi-safis/bgp:afi-safi/bgp:state/bgp:prefixes/bgp:installed" {
    deviate not-supported;
  }
  deviation "/bgp:bgp/bgp:neighbors/bgp:neighbor/bgp:afi-safis/bgp:afi-safi/bgp:graceful-restart" {
    deviate not-supported;
  }
  deviation "/bgp:bgp/bgp:neighbors/bgp:neighbor/bgp:afi-safis/bgp:afi-safi/bgp:apply-policy" {
    deviate not-supported;
  }
  deviation "/bgp:bgp/bgp:neighbors/bgp:neighbor/bgp:afi-safis/bgp:afi-safi/bgp:ipv4-unicast/bgp:prefix-limit/bgp:config/bgp:max-prefixes" {
    deviate add {
      must "shutdown-threshold-pct";
    }
  }
  deviation "/bgp:bgp/bgp:neighbors/bgp:neighbor/bgp:afi-safis/bgp:afi-safi/bgp:ipv4-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:ipv4-unicast/bgp:prefix-limit/bgp:config/bgp:restart-timer" {
    deviate not-supported;
  }
  deviation "/bgp:bgp/bgp:neighbors/bgp:neighbor/bgp:afi-safis/bgp:afi-safi/bgp:ipv4-unicast/bgp:prefix-limit/bgp:state/bgp:max-prefixes" {
    deviate add {
      must "shutdown-threshold-pct";
    }
  }
  deviation "/bgp:bgp/bgp:neighbors/bgp:neighbor/bgp:afi-safis/bgp:afi-safi/bgp:ipv4-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:ipv4-unicast/bgp:prefix-limit/bgp:state/bgp:restart-timer" {
    deviate not-supported;
  }
  deviation "/bgp:bgp/bgp:neighbors/bgp:neighbor/bgp:afi-safis/bgp:afi-safi/bgp:ipv6-unicast/bgp:prefix-limit/bgp:config/bgp:max-prefixes" {
    deviate add {
      must "shutdown-threshold-pct";
    }
  }
  deviation "/bgp:bgp/bgp:neighbors/bgp:neighbor/bgp:afi-safis/bgp:afi-safi/bgp:ipv6-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:ipv6-unicast/bgp:prefix-limit/bgp:config/bgp:restart-timer" {
    deviate not-supported;
  }
  deviation "/bgp:bgp/bgp:neighbors/bgp:neighbor/bgp:afi-safis/bgp:afi-safi/bgp:ipv6-unicast/bgp:prefix-limit/bgp:state/bgp:max-prefixes" {
    deviate add {
      must "shutdown-threshold-pct";
    }
  }
  deviation "/bgp:bgp/bgp:neighbors/bgp:neighbor/bgp:afi-safis/bgp:afi-safi/bgp:ipv6-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:ipv6-unicast/bgp:prefix-limit/bgp:state/bgp:restart-timer" {
    deviate not-supported;
  }
  deviation "/bgp:bgp/bgp:neighbors/bgp:neighbor/bgp:afi-safis/bgp:afi-safi/bgp:ipv4-labeled-unicast/bgp:prefix-limit/bgp:config/bgp:max-prefixes" {
    deviate add {
      must "shutdown-threshold-pct";
    }
  }
  deviation "/bgp:bgp/bgp:neighbors/bgp:neighbor/bgp:afi-safis/bgp:afi-safi/bgp:ipv4-labeled-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:ipv4-labeled-unicast/bgp:prefix-limit/bgp:config/bgp:restart-timer" {
    deviate not-supported;
  }
  deviation "/bgp:bgp/bgp:neighbors/bgp:neighbor/bgp:afi-safis/bgp:afi-safi/bgp:ipv4-labeled-unicast/bgp:prefix-limit/bgp:state/bgp:max-prefixes" {
    deviate add {
      must "shutdown-threshold-pct";
    }
  }
  deviation "/bgp:bgp/bgp:neighbors/bgp:neighbor/bgp:afi-safis/bgp:afi-safi/bgp:ipv4-labeled-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:ipv4-labeled-unicast/bgp:prefix-limit/bgp:state/bgp:restart-timer" {
    deviate not-supported;
  }
  deviation "/bgp:bgp/bgp:neighbors/bgp:neighbor/bgp:afi-safis/bgp:afi-safi/bgp:ipv6-labeled-unicast/bgp:prefix-limit/bgp:config/bgp:max-prefixes" {
    deviate add {
      must "shutdown-threshold-pct";
    }
  }
  deviation "/bgp:bgp/bgp:neighbors/bgp:neighbor/bgp:afi-safis/bgp:afi-safi/bgp:ipv6-labeled-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:ipv6-labeled-unicast/bgp:prefix-limit/bgp:config/bgp:restart-timer" {
    deviate not-supported;
  }
  deviation "/bgp:bgp/bgp:neighbors/bgp:neighbor/bgp:afi-safis/bgp:afi-safi/bgp:ipv6-labeled-unicast/bgp:prefix-limit/bgp:state/bgp:max-prefixes" {
    deviate add {
      must "shutdown-threshold-pct";
    }
  }
  deviation "/bgp:bgp/bgp:neighbors/bgp:neighbor/bgp:afi-safis/bgp:afi-safi/bgp:ipv6-labeled-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:ipv6-labeled-unicast/bgp:prefix-limit/bgp:state/bgp:restart-timer" {
    deviate not-supported;
  }
  deviation "/bgp:bgp/bgp:neighbors/bgp:neighbor/bgp:afi-safis/bgp:afi-safi/bgp:l3vpn-ipv4-unicast/bgp:prefix-limit/bgp:config/bgp:max-prefixes" {
    deviate add {
      must "shutdown-threshold-pct";
    }
  }
  deviation "/bgp:bgp/bgp:neighbors/bgp:neighbor/bgp:afi-safis/bgp:afi-safi/bgp:l3vpn-ipv4-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:l3vpn-ipv4-unicast/bgp:prefix-limit/bgp:config/bgp:restart-timer" {
    deviate not-supported;
  }
  deviation "/bgp:bgp/bgp:neighbors/bgp:neighbor/bgp:afi-safis/bgp:afi-safi/bgp:l3vpn-ipv4-unicast/bgp:prefix-limit/bgp:state/bgp:max-prefixes" {
    deviate add {
      must "shutdown-threshold-pct";
    }
  }
  deviation "/bgp:bgp/bgp:neighbors/bgp:neighbor/bgp:afi-safis/bgp:afi-safi/bgp:l3vpn-ipv4-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:l3vpn-ipv4-unicast/bgp:prefix-limit/bgp:state/bgp:restart-timer" {
    deviate not-supported;
  }
  deviation "/bgp:bgp/bgp:neighbors/bgp:neighbor/bgp:afi-safis/bgp:afi-safi/bgp:l3vpn-ipv6-unicast/bgp:prefix-limit/bgp:config/bgp:max-prefixes" {
    deviate add {
      must "shutdown-threshold-pct";
    }
  }
  deviation "/bgp:bgp/bgp:neighbors/bgp:neighbor/bgp:afi-safis/bgp:afi-safi/bgp:l3vpn-ipv6-unicast/bgp:prefix-limit/bgp:config/bgp:shutdown-threshold-pct" {
    deviate add {
      must "max-prefixes";
      default "75";
    }
  }
  deviation "/bgp:bgp/bgp:neighbors/bgp:neighbor/bgp:afi-safis/bgp:afi-safi/bgp:l3vpn-ipv6-unicast/bgp:prefix-limit/bgp:config/bgp:restart-timer" {
    deviate not-supported;
  }
  deviation "/bgp:bgp/bgp:neighbors/bgp:neighbor/bgp:afi-safis/bgp:afi-safi/bgp:l3vpn-ipv6-unicast/bgp:prefix-limit/bgp:state/bgp:max-prefixes" {
    deviate add {
      must "shutdown-threshold-pct";
    }
  }
  deviation "/bgp:bgp/bgp:neighbors/bgp:neighbor/bgp:afi-safis/bgp:afi-safi/bgp:l3vpn-ipv6-unicast/bgp:prefix-limit/bgp:state/bgp:shutdown-threshold-pct" {
    deviate add {
      must "max-prefixes";
      default "75";
    }
  }
  deviation "/bgp:bgp/bgp:neighbors/bgp:neighbor/bgp:afi-safis/bgp:afi-safi/bgp:l3vpn-ipv6-unicast/bgp:prefix-limit/bgp:state/bgp:restart-timer" {
    deviate not-supported;
  }
  deviation "/bgp:bgp/bgp:neighbors/bgp:neighbor/bgp:afi-safis/bgp:afi-safi/bgp:l3vpn-ipv4-multicast/bgp:prefix-limit/bgp:config/bgp:max-prefixes" {
    deviate add {
      must "shutdown-threshold-pct";
    }
  }
  deviation "/bgp:bgp/bgp:neighbors/bgp:neighbor/bgp:afi-safis/bgp:afi-safi/bgp:l3vpn-ipv4-multicast/bgp:prefix-limit/bgp:config/bgp:shutdown-threshold-pct" {
    deviate add {
      must "max-prefixes";
      default "75";
    }
  }
  deviation "/bgp:bgp/bgp:neighbors/bgp:neighbor/bgp:afi-safis/bgp:afi-safi/bgp:l3vpn-ipv4-multicast/bgp:prefix-limit/bgp:config/bgp:restart-timer" {
    deviate not-supported;
  }
  deviation "/bgp:bgp/bgp:neighbors/bgp:neighbor/bgp:afi-safis/bgp:afi-safi/bgp:l3vpn-ipv4-multicast/bgp:prefix-limit/bgp:state/bgp:max-prefixes" {
    deviate add {
      must "shutdown-threshold-pct";
    }
  }
  deviation "/bgp:bgp/bgp:neighbors/bgp:neighbor/bgp:afi-safis/bgp:afi-safi/bgp:l3vpn-ipv4-multicast/bgp:prefix-limit/bgp:state/bgp:shutdown-threshold-pct" {
    deviate add {
      must "max-prefixes";
      default "75";
    }
  }
  deviation "/bgp:bgp/bgp:neighbors/bgp:neighbor/bgp:afi-safis/bgp:afi-safi/bgp:l3vpn-ipv4-multicast/bgp:prefix-limit/bgp:state/bgp:restart-timer" {
    deviate not-supported;
  }
  deviation "/bgp:bgp/bgp:neighbors/bgp:neighbor/bgp:afi-safis/bgp:afi-safi/bgp:l3vpn-ipv6-multicast/bgp:prefix-limit/bgp:config/bgp:max-prefixes" {
    deviate add {
      must "shutdown-threshold-pct";
    }
  }
  deviation "/bgp:bgp/bgp:neighbors/bgp:neighbor/bgp:afi-safis/bgp:afi-safi/bgp:l3vpn-ipv6-multicast/bgp:prefix-limit/bgp:config/bgp:shutdown-threshold-pct" {
    deviate add {
      must "max-prefixes";
      default "75";
    }
  }
  deviation "/bgp:bgp/bgp:neighbors/bgp:neighbor/bgp:afi-safis/bgp:afi-safi/bgp:l3vpn-ipv6-multicast/bgp:prefix-limit/bgp:config/bgp:restart-timer" {
    deviate not-supported;
  }
  deviation "/bgp:bgp/bgp:neighbors/bgp:neighbor/bgp:afi-safis/bgp:afi-safi/bgp:l3vpn-ipv6-multicast/bgp:prefix-limit/bgp:state/bgp:max-prefixes" {
    deviate add {
      must "shutdown-threshold-pct";
    }
  }
  deviation "/bgp:bgp/bgp:neighbors/bgp:neighbor/bgp:afi-safis/bgp:afi-safi/bgp:l3vpn-ipv6-multicast/bgp:prefix-limit/bgp:state/bgp:shutdown-threshold-pct" {
    deviate add {
      must "max-prefixes";
      default "75";
    }
  }
  deviation "/bgp:bgp/bgp:neighbors/bgp:neighbor/bgp:afi-safis/bgp:afi-safi/bgp:l3vpn-ipv6-multicast/bgp:prefix-limit/bgp:state/bgp:restart-timer" {
    deviate not-supported;
  }
  deviation "/bgp:bgp/bgp:neighbors/bgp:neighbor/bgp:afi-safis/bgp:afi-safi/bgp:l2vpn-vpls/bgp:prefix-limit/bgp:config/bgp:max-prefixes" {
    deviate add {
      must "shutdown-threshold-pct";
    }
  }
  deviation "/bgp:bgp/bgp:neighbors/bgp:neighbor/bgp:afi-safis/bgp:afi-safi/bgp:l2vpn-vpls/bgp:prefix-limit/bgp:config/bgp:shutdown-threshold-pct" {
    deviate add {
      must "max-prefixes";
      default "75";
    }
  }
  deviation "/bgp:bgp/bgp:neighbors/bgp:neighbor/bgp:afi-safis/bgp:afi-safi/bgp:l2vpn-vpls/bgp:prefix-limit/bgp:config/bgp:restart-timer" {
    deviate not-supported;
  }
  deviation "/bgp:bgp/bgp:neighbors/bgp:neighbor/bgp:afi-safis/bgp:afi-safi/bgp:l2vpn-vpls/bgp:prefix-limit/bgp:state/bgp:max-prefixes" {
    deviate add {
      must "shutdown-threshold-pct";
    }
  }
  deviation "/bgp:bgp/bgp:neighbors/bgp:neighbor/bgp:afi-safis/bgp:afi-safi/bgp:l2vpn-vpls/bgp:prefix-limit/bgp:state/bgp:shutdown-threshold-pct" {
    deviate add {
      must "max-prefixes";
      default "75";
    }
  }
  deviation "/bgp:bgp/bgp:neighbors/bgp:neighbor/bgp:afi-safis/bgp:afi-safi/bgp:l2vpn-vpls/bgp:prefix-limit/bgp:state/bgp:restart-timer" {
    deviate not-supported;
  }
  deviation "/bgp:bgp/bgp:neighbors/bgp:neighbor/bgp:afi-safis/bgp:afi-safi/bgp:l2vpn-evpn/bgp:prefix-limit/bgp:config/bgp:max-prefixes" {
    deviate add {
      must "shutdown-threshold-pct";
    }
  }
  deviation "/bgp:bgp/bgp:neighbors/bgp:neighbor/bgp:afi-safis/bgp:afi-safi/bgp:l2vpn-evpn/bgp:prefix-limit/bgp:config/bgp:shutdown-threshold-pct" {
    deviate add {
      must "max-prefixes";
      default "75";
    }
  }
  deviation "/bgp:bgp/bgp:neighbors/bgp:neighbor/bgp:afi-safis/bgp:afi-safi/bgp:l2vpn-evpn/bgp:prefix-limit/bgp:config/bgp:restart-timer" {
    deviate not-supported;
  }
  deviation "/bgp:bgp/bgp:neighbors/bgp:neighbor/bgp:afi-safis/bgp:afi-safi/bgp:l2vpn-evpn/bgp:prefix-limit/bgp:state/bgp:max-prefixes" {
    deviate add {
      must "shutdown-threshold-pct";
    }
  }
  deviation "/bgp:bgp/bgp:neighbors/bgp:neighbor/bgp:afi-safis/bgp:afi-safi/bgp:l2vpn-evpn/bgp:prefix-limit/bgp:state/bgp:shutdown-threshold-pct" {
    deviate add {
      must "max-prefixes";
      default "75";
    }
  }
  deviation "/bgp:bgp/bgp:neighbors/bgp:neighbor/bgp:afi-safis/bgp:afi-safi/bgp:l2vpn-evpn/bgp:prefix-limit/bgp:state/bgp:restart-timer" {
    deviate not-supported;
  }
  deviation "/bgp:bgp/bgp:neighbors/bgp:neighbor/bgp:afi-safis/bgp:afi-safi/bgp:use-multiple-paths/bgp:ebgp" {
    deviate not-supported;
  }
  deviation "/bgp:bgp/bgp:neighbors/bgp:neighbor/bgp:graceful-restart/bgp:config/bgp:helper-only" {
    deviate not-supported;
  }
  deviation "/bgp:bgp/bgp:neighbors/bgp:neighbor/bgp:graceful-restart/bgp:state/bgp:helper-only" {
    deviate not-supported;
  }
  deviation "/bgp:bgp/bgp:neighbors/bgp:neighbor/bgp:graceful-restart/bgp:state/bgp:peer-restarting" {
    deviate not-supported;
  }
  deviation "/bgp:bgp/bgp:neighbors/bgp:neighbor/bgp:graceful-restart/bgp:state/bgp:local-restarting" {
    deviate not-supported;
  }
  deviation "/bgp:bgp/bgp:neighbors/bgp:neighbor/bgp:graceful-restart/bgp:state/bgp:mode" {
    deviate not-supported;
  }
  deviation "/bgp:bgp/bgp:neighbors/bgp:neighbor/bgp:apply-policy" {
    deviate not-supported;
  }
  deviation "/bgp:bgp/bgp:neighbors/bgp:neighbor/bgp:use-multiple-paths" {
    deviate not-supported;
  }
  deviation "/bgp:bgp/bgp:peer-groups/bgp:peer-group/bgp:config/bgp:peer-type" {
    deviate not-supported;
  }
  deviation "/bgp:bgp/bgp:peer-groups/bgp:peer-group/bgp:config/bgp:route-flap-damping" {
    deviate not-supported;
  }
  deviation "/bgp:bgp/bgp:peer-groups/bgp:peer-group/bgp:state/bgp:peer-type" {
    deviate not-supported;
  }
  deviation "/bgp:bgp/bgp:peer-groups/bgp:peer-group/bgp:state/bgp:route-flap-damping" {
    deviate not-supported;
  }
  deviation "/bgp:bgp/bgp:peer-groups/bgp:peer-group/bgp:state/bgp:total-paths" {
    deviate not-supported;
  }
  deviation "/bgp:bgp/bgp:peer-groups/bgp:peer-group/bgp:state/bgp:total-prefixes" {
    deviate not-supported;
  }
  deviation "/bgp:bgp/bgp:peer-groups/bgp:peer-group/bgp:timers/bgp:config/bgp:connect-retry" {
    deviate not-supported;
  }
  deviation "/bgp:bgp/bgp:peer-groups/bgp:peer-group/bgp:timers/bgp:state/bgp:connect-retry" {
    deviate not-supported;
  }
  deviation "/bgp:bgp/bgp:peer-groups/bgp:peer-group/bgp:transport/bgp:config/bgp:mtu-discovery" {
    deviate not-supported;
  }
  deviation "/bgp:bgp/bgp:peer-groups/bgp:peer-group/bgp:transport/bgp:state/bgp:mtu-discovery" {
    deviate not-supported;
  }
  deviation "/bgp:bgp/bgp:peer-groups/bgp:peer-group/bgp:error-handling" {
    deviate not-supported;
  }
  deviation "/bgp:bgp/bgp:peer-groups/bgp:peer-group/bgp:logging-options" {
    deviate not-supported;
  }
  deviation "/bgp:bgp/bgp:peer-groups/bgp:peer-group/bgp:as-path-options" {
    deviate not-supported;
  }
  deviation "/bgp:bgp/bgp:peer-groups/bgp:peer-group/bgp:add-paths" {
    deviate not-supported;
  }
  deviation "/bgp:bgp/bgp:peer-groups/bgp:peer-group/bgp:afi-safis/bgp:afi-safi/bgp:graceful-restart" {
    deviate not-supported;
  }
  deviation "/bgp:bgp/bgp:peer-groups/bgp:peer-group/bgp:afi-safis/bgp:afi-safi/bgp:apply-policy/bgp:config/bgp:default-import-policy" {
    deviate not-supported;
  }
  deviation "/bgp:bgp/bgp:peer-groups/bgp:peer-group/bgp:afi-safis/bgp:afi-safi/bgp:apply-policy/bgp:config/bgp:default-export-policy" {
    deviate not-supported;
  }
  deviation "/bgp:bgp/bgp:peer-groups/bgp:peer-group/bgp:afi-safis/bgp:afi-safi/bgp:apply-policy/bgp:state/bgp:default-import-policy" {
    deviate not-supported;
  }
  deviation "/bgp:bgp/bgp:peer-groups/bgp:peer-group/bgp:afi-safis/bgp:afi-safi/bgp:apply-policy/bgp:state/bgp:default-export-policy" {
    deviate not-supported;
  }
  deviation "/bgp:bgp/bgp:peer-groups/bgp:peer-group/bgp:afi-safis/bgp:afi-safi/bgp:ipv4-unicast/bgp:prefix-limit/bgp:config/bgp:max-prefixes" {
    deviate add {
      must "shutdown-threshold-pct";
    }
  }
  deviation "/bgp:bgp/bgp:peer-groups/bgp:peer-group/bgp:afi-safis/bgp:afi-safi/bgp:ipv4-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:ipv4-unicast/bgp:prefix-limit/bgp:config/bgp:restart-timer" {
    deviate not-supported;
  }
  deviation "/bgp:bgp/bgp:peer-groups/bgp:peer-group/bgp:afi-safis/bgp:afi-safi/bgp:ipv4-unicast/bgp:prefix-limit/bgp:state/bgp:max-prefixes" {
    deviate add {
      must "shutdown-threshold-pct";
    }
  }
  deviation "/bgp:bgp/bgp:peer-groups/bgp:peer-group/bgp:afi-safis/bgp:afi-safi/bgp:ipv4-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:ipv4-unicast/bgp:prefix-limit/bgp:state/bgp:restart-timer" {
    deviate not-supported;
  }
  deviation "/bgp:bgp/bgp:peer-groups/bgp:peer-group/bgp:afi-safis/bgp:afi-safi/bgp:ipv6-unicast/bgp:prefix-limit/bgp:config/bgp:max-prefixes" {
    deviate add {
      must "shutdown-threshold-pct";
    }
  }
  deviation "/bgp:bgp/bgp:peer-groups/bgp:peer-group/bgp:afi-safis/bgp:afi-safi/bgp:ipv6-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:ipv6-unicast/bgp:prefix-limit/bgp:config/bgp:restart-timer" {
    deviate not-supported;
  }
  deviation "/bgp:bgp/bgp:peer-groups/bgp:peer-group/bgp:afi-safis/bgp:afi-safi/bgp:ipv6-unicast/bgp:prefix-limit/bgp:state/bgp:max-prefixes" {
    deviate add {
      must "shutdown-threshold-pct";
    }
  }
  deviation "/bgp:bgp/bgp:peer-groups/bgp:peer-group/bgp:afi-safis/bgp:afi-safi/bgp:ipv6-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:ipv6-unicast/bgp:prefix-limit/bgp:state/bgp:restart-timer" {
    deviate not-supported;
  }
  deviation "/bgp:bgp/bgp:peer-groups/bgp:peer-group/bgp:afi-safis/bgp:afi-safi/bgp:ipv4-labeled-unicast/bgp:prefix-limit/bgp:config/bgp:max-prefixes" {
    deviate add {
      must "shutdown-threshold-pct";
    }
  }
  deviation "/bgp:bgp/bgp:peer-groups/bgp:peer-group/bgp:afi-safis/bgp:afi-safi/bgp:ipv4-labeled-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:ipv4-labeled-unicast/bgp:prefix-limit/bgp:config/bgp:restart-timer" {
    deviate not-supported;
  }
  deviation "/bgp:bgp/bgp:peer-groups/bgp:peer-group/bgp:afi-safis/bgp:afi-safi/bgp:ipv4-labeled-unicast/bgp:prefix-limit/bgp:state/bgp:max-prefixes" {
    deviate add {
      must "shutdown-threshold-pct";
    }
  }
  deviation "/bgp:bgp/bgp:peer-groups/bgp:peer-group/bgp:afi-safis/bgp:afi-safi/bgp:ipv4-labeled-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:ipv4-labeled-unicast/bgp:prefix-limit/bgp:state/bgp:restart-timer" {
    deviate not-supported;
  }
  deviation "/bgp:bgp/bgp:peer-groups/bgp:peer-group/bgp:afi-safis/bgp:afi-safi/bgp:ipv6-labeled-unicast/bgp:prefix-limit/bgp:config/bgp:max-prefixes" {
    deviate add {
      must "shutdown-threshold-pct";
    }
  }
  deviation "/bgp:bgp/bgp:peer-groups/bgp:peer-group/bgp:afi-safis/bgp:afi-safi/bgp:ipv6-labeled-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:ipv6-labeled-unicast/bgp:prefix-limit/bgp:config/bgp:restart-timer" {
    deviate not-supported;
  }
  deviation "/bgp:bgp/bgp:peer-groups/bgp:peer-group/bgp:afi-safis/bgp:afi-safi/bgp:ipv6-labeled-unicast/bgp:prefix-limit/bgp:state/bgp:max-prefixes" {
    deviate add {
      must "shutdown-threshold-pct";
    }
  }
  deviation "/bgp:bgp/bgp:peer-groups/bgp:peer-group/bgp:afi-safis/bgp:afi-safi/bgp:ipv6-labeled-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:ipv6-labeled-unicast/bgp:prefix-limit/bgp:state/bgp:restart-timer" {
    deviate not-supported;
  }
  deviation "/bgp:bgp/bgp:peer-groups/bgp:peer-group/bgp:afi-safis/bgp:afi-safi/bgp:l3vpn-ipv4-unicast/bgp:prefix-limit/bgp:config/bgp:max-prefixes" {
    deviate add {
      must "shutdown-threshold-pct";
    }
  }
  deviation "/bgp:bgp/bgp:peer-groups/bgp:peer-group/bgp:afi-safis/bgp:afi-safi/bgp:l3vpn-ipv4-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:l3vpn-ipv4-unicast/bgp:prefix-limit/bgp:config/bgp:restart-timer" {
    deviate not-supported;
  }
  deviation "/bgp:bgp/bgp:peer-groups/bgp:peer-group/bgp:afi-safis/bgp:afi-safi/bgp:l3vpn-ipv4-unicast/bgp:prefix-limit/bgp:state/bgp:max-prefixes" {
    deviate add {
      must "shutdown-threshold-pct";
    }
  }
  deviation "/bgp:bgp/bgp:peer-groups/bgp:peer-group/bgp:afi-safis/bgp:afi-safi/bgp:l3vpn-ipv4-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:l3vpn-ipv4-unicast/bgp:prefix-limit/bgp:state/bgp:restart-timer" {
    deviate not-supported;
  }
  deviation "/bgp:bgp/bgp:peer-groups/bgp:peer-group/bgp:afi-safis/bgp:afi-safi/bgp:l3vpn-ipv6-unicast/bgp:prefix-limit/bgp:config/bgp:max-prefixes" {
    deviate add {
      must "shutdown-threshold-pct";
    }
  }
  deviation "/bgp:bgp/bgp:peer-groups/bgp:peer-group/bgp:afi-safis/bgp:afi-safi/bgp:l3vpn-ipv6-unicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:l3vpn-ipv6-unicast/bgp:prefix-limit/bgp:config/bgp:restart-timer" {
    deviate not-supported;
  }
  deviation "/bgp:bgp/bgp:peer-groups/bgp:peer-group/bgp:afi-safis/bgp:afi-safi/bgp:l3vpn-ipv6-unicast/bgp:prefix-limit/bgp:state/bgp:max-prefixes" {
    deviate add {
      must "shutdown-threshold-pct";
    }
  }
  deviation "/bgp:bgp/bgp:peer-groups/bgp:peer-group/bgp:afi-safis/bgp:afi-safi/bgp:l3vpn-ipv6-unicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:l3vpn-ipv6-unicast/bgp:prefix-limit/bgp:state/bgp:restart-timer" {
    deviate not-supported;
  }
  deviation "/bgp:bgp/bgp:peer-groups/bgp:peer-group/bgp:afi-safis/bgp:afi-safi/bgp:l3vpn-ipv4-multicast/bgp:prefix-limit/bgp:config/bgp:max-prefixes" {
    deviate add {
      must "shutdown-threshold-pct";
    }
  }
  deviation "/bgp:bgp/bgp:peer-groups/bgp:peer-group/bgp:afi-safis/bgp:afi-safi/bgp:l3vpn-ipv4-multicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:l3vpn-ipv4-multicast/bgp:prefix-limit/bgp:config/bgp:restart-timer" {
    deviate not-supported;
  }
  deviation "/bgp:bgp/bgp:peer-groups/bgp:peer-group/bgp:afi-safis/bgp:afi-safi/bgp:l3vpn-ipv4-multicast/bgp:prefix-limit/bgp:state/bgp:max-prefixes" {
    deviate add {
      must "shutdown-threshold-pct";
    }
  }
  deviation "/bgp:bgp/bgp:peer-groups/bgp:peer-group/bgp:afi-safis/bgp:afi-safi/bgp:l3vpn-ipv4-multicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:l3vpn-ipv4-multicast/bgp:prefix-limit/bgp:state/bgp:restart-timer" {
    deviate not-supported;
  }
  deviation "/bgp:bgp/bgp:peer-groups/bgp:peer-group/bgp:afi-safis/bgp:afi-safi/bgp:l3vpn-ipv6-multicast/bgp:prefix-limit/bgp:config/bgp:max-prefixes" {
    deviate add {
      must "shutdown-threshold-pct";
    }
  }
  deviation "/bgp:bgp/bgp:peer-groups/bgp:peer-group/bgp:afi-safis/bgp:afi-safi/bgp:l3vpn-ipv6-multicast/bgp:prefix-limit/bgp:config/bgp:shutdown-threshold-pct" {
    deviate add {
      must "max-prefixes";
      default "75";
    }
  }
  deviation "/bgp:bgp/bgp:peer-groups/bgp:peer-group/bgp:afi-safis/bgp:afi-safi/bgp:l3vpn-ipv6-multicast/bgp:prefix-limit/bgp:config/bgp:restart-timer" {
    deviate not-supported;
  }
  deviation "/bgp:bgp/bgp:peer-groups/bgp:peer-group/bgp:afi-safis/bgp:afi-safi/bgp:l3vpn-ipv6-multicast/bgp:prefix-limit/bgp:state/bgp:max-prefixes" {
    deviate add {
      must "shutdown-threshold-pct";
    }
  }
  deviation "/bgp:bgp/bgp:peer-groups/bgp:peer-group/bgp:afi-safis/bgp:afi-safi/bgp:l3vpn-ipv6-multicast/bgp:prefix-limit/bgp:state/bgp:shutdown-threshold-pct" {
    deviate add {
      must "max-prefixes";
      default "75";
    }
  }
  deviation "/bgp:bgp/bgp:peer-groups/bgp:peer-group/bgp:afi-safis/bgp:afi-safi/bgp:l3vpn-ipv6-multicast/bgp:prefix-limit/bgp:state/bgp:restart-timer" {
    deviate not-supported;
  }
  deviation "/bgp:bgp/bgp:peer-groups/bgp:peer-group/bgp:afi-safis/bgp:afi-safi/bgp:l2vpn-vpls/bgp:prefix-limit/bgp:config/bgp:max-prefixes" {
    deviate add {
      must "shutdown-threshold-pct";
    }
  }
  deviation "/bgp:bgp/bgp:peer-groups/bgp:peer-group/bgp:afi-safis/bgp:afi-safi/bgp:l2vpn-vpls/bgp:prefix-limit/bgp:config/bgp:shutdown-threshold-pct" {
    deviate add {
      must "max-prefixes";
      default "75";
    }
  }
  deviation "/bgp:bgp/bgp:peer-groups/bgp:peer-group/bgp:afi-safis/bgp:afi-safi/bgp:l2vpn-vpls/bgp:prefix-limit/bgp:config/bgp:restart-timer" {
    deviate not-supported;
  }
  deviation "/bgp:bgp/bgp:peer-groups/bgp:peer-group/bgp:afi-safis/bgp:afi-safi/bgp:l2vpn-vpls/bgp:prefix-limit/bgp:state/bgp:max-prefixes" {
    deviate add {
      must "shutdown-threshold-pct";
    }
  }
  deviation "/bgp:bgp/bgp:peer-groups/bgp:peer-group/bgp:afi-safis/bgp:afi-safi/bgp:l2vpn-vpls/bgp:prefix-limit/bgp:state/bgp:shutdown-threshold-pct" {
    deviate add {
      must "max-prefixes";
      default "75";
    }
  }
  deviation "/bgp:bgp/bgp:peer-groups/bgp:peer-group/bgp:afi-safis/bgp:afi-safi/bgp:l2vpn-vpls/bgp:prefix-limit/bgp:state/bgp:restart-timer" {
    deviate not-supported;
  }
  deviation "/bgp:bgp/bgp:peer-groups/bgp:peer-group/bgp:afi-safis/bgp:afi-safi/bgp:l2vpn-evpn/bgp:prefix-limit/bgp:config/bgp:max-prefixes" {
    deviate add {
      must "shutdown-threshold-pct";
    }
  }
  deviation "/bgp:bgp/bgp:peer-groups/bgp:peer-group/bgp:afi-safis/bgp:afi-safi/bgp:l2vpn-evpn/bgp:prefix-limit/bgp:config/bgp:shutdown-threshold-pct" {
    deviate add {
      must "max-prefixes";
      default "75";
    }
  }
  deviation "/bgp:bgp/bgp:peer-groups/bgp:peer-group/bgp:afi-safis/bgp:afi-safi/bgp:l2vpn-evpn/bgp:prefix-limit/bgp:config/bgp:restart-timer" {
    deviate not-supported;
  }
  deviation "/bgp:bgp/bgp:peer-groups/bgp:peer-group/bgp:afi-safis/bgp:afi-safi/bgp:l2vpn-evpn/bgp:prefix-limit/bgp:state/bgp:max-prefixes" {
    deviate add {
      must "shutdown-threshold-pct";
    }
  }
  deviation "/bgp:bgp/bgp:peer-groups/bgp:peer-group/bgp:afi-safis/bgp:afi-safi/bgp:l2vpn-evpn/bgp:prefix-limit/bgp:state/bgp:shutdown-threshold-pct" {
    deviate add {
      must "max-prefixes";
      default "75";
    }
  }
  deviation "/bgp:bgp/bgp:peer-groups/bgp:peer-group/bgp:afi-safis/bgp:afi-safi/bgp:l2vpn-evpn/bgp:prefix-limit/bgp:state/bgp:restart-timer" {
    deviate not-supported;
  }
  deviation "/bgp:bgp/bgp:peer-groups/bgp:peer-group/bgp:afi-safis/bgp:afi-safi/bgp:use-multiple-paths/bgp:ebgp" {
    deviate not-supported;
  }
  deviation "/bgp:bgp/bgp:peer-groups/bgp:peer-group/bgp:afi-safis/bgp:afi-safi/bgp:use-multiple-paths/bgp:ibgp" {
    deviate not-supported;
  }
  deviation "/bgp:bgp/bgp:peer-groups/bgp:peer-group/bgp:afi-safis/bgp:afi-safi/bgp:route-selection-options" {
    deviate not-supported;
  }
  deviation "/bgp:bgp/bgp:peer-groups/bgp:peer-group/bgp:graceful-restart/bgp:config/bgp:helper-only" {
    deviate not-supported;
  }
  deviation "/bgp:bgp/bgp:peer-groups/bgp:peer-group/bgp:graceful-restart/bgp:state/bgp:helper-only" {
    deviate not-supported;
  }
  deviation "/bgp:bgp/bgp:peer-groups/bgp:peer-group/bgp:apply-policy" {
    deviate not-supported;
  }
  deviation "/bgp:bgp/bgp:peer-groups/bgp:peer-group/bgp:use-multiple-paths" {
    deviate not-supported;
  }
  deviation "/bgp:bgp/bgp:neighbors/bgp:neighbor/bgp:config/bgp:remove-private-as" {
    deviate not-supported;
  }
  deviation "/bgp:bgp/bgp:neighbors/bgp:neighbor/bgp:config/bgp:send-community" {
    deviate not-supported;
  }
  deviation "/bgp:bgp/bgp:neighbors/bgp:neighbor/bgp:route-reflector/bgp:config/bgp:route-reflector-client" {
    deviate not-supported;
  }
  deviation "/bgp:bgp/bgp:neighbors/bgp:neighbor/bgp:route-reflector/bgp:state/bgp:route-reflector-client" {
    deviate not-supported;
  }
  deviation "/bgp:bgp/bgp:neighbors/bgp:neighbor/bgp:state/bgp:remove-private-as" {
    deviate not-supported;
  }
  deviation "/bgp:bgp/bgp:neighbors/bgp:neighbor/bgp:state/bgp:send-community" {
    deviate not-supported;
  }
  deviation "/bgp:bgp/bgp:peer-groups/bgp:peer-group/bgp:config/bgp:remove-private-as" {
    deviate not-supported;
  }
  deviation "/bgp:bgp/bgp:peer-groups/bgp:peer-group/bgp:config/bgp:send-community" {
    deviate not-supported;
  }
  deviation "/bgp:bgp/bgp:peer-groups/bgp:peer-group/bgp:route-reflector/bgp:config/bgp:route-reflector-client" {
    deviate not-supported;
  }
  deviation "/bgp:bgp/bgp:peer-groups/bgp:peer-group/bgp:route-reflector/bgp:state/bgp:route-reflector-client" {
    deviate not-supported;
  }
  deviation "/bgp:bgp/bgp:peer-groups/bgp:peer-group/bgp:state/bgp:remove-private-as" {
    deviate not-supported;
  }
  deviation "/bgp:bgp/bgp:peer-groups/bgp:peer-group/bgp:state/bgp:send-community" {
    deviate not-supported;
  }
}
