module Cisco-IOS-XR-sysadmin-fpd-infra-cli-fpd {
  namespace "http://www.cisco.com/ns/yang/Cisco-IOS-XR-sysadmin-fpd-infra-cli-fpd";
  prefix fpd;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     FPD CLI support for both oper and config
     
     Copyright (c) 2012-2018 by Cisco Systems, Inc.
     All rights reserved.";

  revision 2017-05-01 {
    description
      "Namespace change to comply with Cisco guidelines on namespace";
  }

  grouping fpd {
    container config {
      description
        "fpd config mode";
      uses global-fpd-config-group;
    }
  }

  grouping global-fpd-config-group {
    leaf auto-upgrade {
      type enumeration {
        enum "enable";
        enum "disable";
      }
      default "disable";
      config true;
    }
  }

  container fpd {
    uses fpd;
  }
}
