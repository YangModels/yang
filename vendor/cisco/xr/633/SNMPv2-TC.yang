module SNMPv2-TC {
  namespace "http://tail-f.com/ns/mibs/SNMPv2-TC/1.0";
  prefix SNMPv2_TC;

  import ietf-yang-types {
    prefix yang;
  }
  import tailf-common {
    prefix tailf;
  }
  import ietf-yang-smiv2 {
    prefix smiv2;
  }

  revision 2016-08-18 {
    description
      "Initial revision";
  }

  typedef DisplayString {
    type string {
      length "min .. 255";
    }
  }

  typedef PhysAddress {
    type tailf:hex-list {
      pattern "(((([0-9A-Fa-f]{2}):)*([0-9A-Fa-f]{2}))){0,1}";
    }
  }

  typedef MacAddress {
    type tailf:hex-list {
      pattern "(((([0-9A-Fa-f]{2}):){5,5})([0-9A-Fa-f]{2}))";
      tailf:value-length "6";
    }
  }

  typedef TruthValue {
    type enumeration {
      enum "true" {
        value 1;
      }
      enum "false" {
        value 2;
      }
    }
  }

  typedef TestAndIncr {
    type int32 {
      range "0 .. 2147483647";
    }
  }

  typedef AutonomousType {
    type yang:object-identifier;
  }

  typedef InstancePointer {
    type yang:object-identifier;
  }

  typedef VariablePointer {
    type yang:object-identifier;
  }

  typedef RowPointer {
    type yang:object-identifier;
  }

  typedef RowStatus {
    type enumeration {
      enum "active" {
        value 1;
      }
      enum "notInService" {
        value 2;
      }
      enum "notReady" {
        value 3;
      }
      enum "createAndGo" {
        value 4;
      }
      enum "createAndWait" {
        value 5;
      }
      enum "destroy" {
        value 6;
      }
    }
  }

  typedef TimeStamp {
    type uint32 {
      range "0 .. 4294967295";
    }
  }

  typedef TimeInterval {
    type int32 {
      range "0 .. 2147483647";
    }
  }

  typedef DateAndTime {
    type string;
    smiv2:display-hint "2d-1d-1d,1d:1d:1d.1d,1a1d:1d";
  }

  typedef StorageType {
    type enumeration {
      enum "other" {
        value 1;
      }
      enum "volatile" {
        value 2;
      }
      enum "nonVolatile" {
        value 3;
      }
      enum "permanent" {
        value 4;
      }
      enum "readOnly" {
        value 5;
      }
    }
  }

  typedef TDomain {
    type yang:object-identifier;
  }

  typedef TAddress {
    type tailf:octet-list {
      tailf:value-length "1 .. 255";
    }
  }
  tailf:id "";
  tailf:snmp-mib-module-name "SNMPv2-TC";
}
