module Cisco-IOS-XR-upgrade-fpd-oper {
  namespace "http://cisco.com/ns/yang/Cisco-IOS-XR-upgrade-fpd-oper";
  prefix upgrade-fpd-oper;

  import Cisco-IOS-XR-types {
    prefix xr;
  }
  include Cisco-IOS-XR-upgrade-fpd-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR upgrade-fpd package operational data.
     
     This module contains definitions
     for the following management objects:
       fpd: Field programmable device (FPD) operational data
     
     Copyright (c) 2013-2017 by Cisco Systems, Inc.
     All rights reserved.";

  revision 2015-11-09 {
    description
      "IOS XR 6.0 revision.";
  }

  typedef Fpd-sub {
    type enumeration {
      enum "fpga1" {
        value 0;
        description
          "FPGA device";
      }
      enum "rommon" {
        value 1;
        description
          "ROMMON device";
      }
      enum "rommona" {
        value 2;
        description
          "ROMMON device #A";
      }
      enum "fabldr" {
        value 3;
        description
          "Fabric loader";
      }
      enum "fpga2" {
        value 4;
        description
          "FPGA device #2";
      }
      enum "fpga3" {
        value 5;
        description
          "FPGA device #3";
      }
      enum "fpga4" {
        value 6;
        description
          "FPGA device #4";
      }
      enum "fpga5" {
        value 7;
        description
          "FPGA device #5";
      }
      enum "fpga6" {
        value 8;
        description
          "FPGA device #6";
      }
      enum "fpga7" {
        value 9;
        description
          "FPGA device #7";
      }
      enum "fpga8" {
        value 10;
        description
          "FPGA device #8";
      }
      enum "fpga9" {
        value 11;
        description
          "FPGA device #9";
      }
      enum "fpga10" {
        value 12;
        description
          "FPGA device #10";
      }
      enum "fpga11" {
        value 13;
        description
          "FPGA device #11";
      }
      enum "fpga12" {
        value 14;
        description
          "FPGA device #12";
      }
      enum "fpga13" {
        value 15;
        description
          "FPGA device #13";
      }
      enum "fpga14" {
        value 16;
        description
          "FPGA device #14";
      }
      enum "cpld1" {
        value 17;
        description
          "CPLD device #1";
      }
      enum "cpld2" {
        value 18;
        description
          "CPLD device #2";
      }
      enum "cpld3" {
        value 19;
        description
          "CPLD device #3";
      }
      enum "cpld4" {
        value 20;
        description
          "CPLD device #4";
      }
      enum "cpld5" {
        value 21;
        description
          "CPLD device #5";
      }
      enum "cpld6" {
        value 22;
        description
          "CPLD device #6";
      }
      enum "cbc" {
        value 23;
        description
          "Can bus controller";
      }
      enum "hsbi" {
        value 24;
        description
          "HSBI image";
      }
      enum "txpod" {
        value 25;
        description
          "Fabric Tx POD";
      }
      enum "rxpod" {
        value 26;
        description
          "Fabric Rx POD";
      }
      enum "ibmc" {
        value 27;
        description
          "IBMC";
      }
      enum "fsbl" {
        value 28;
        description
          "FSBL";
      }
      enum "lnx" {
        value 29;
        description
          "Linux firmware";
      }
      enum "fpga15" {
        value 30;
        description
          "FPGA device #15";
      }
      enum "fpga16" {
        value 31;
        description
          "FPGA device #16";
      }
      enum "fc-fsbl" {
        value 32;
        description
          "FC FSBL";
      }
      enum "fc-lnx" {
        value 33;
        description
          "FC linux firmware";
      }
    }
    description
      "Fpd sub";
  }

  typedef Fpd {
    type enumeration {
      enum "spa" {
        value 0;
        description
          "SPA class of fpd";
      }
      enum "lc" {
        value 1;
        description
          "Linecard class of fpd";
      }
      enum "sam" {
        value 2;
        description
          "SAM class of fpd";
      }
    }
    description
      "Fpd";
  }

  container fpd {
    config false;
    description
      "Field programmable device (FPD) operational data";
    container nodes {
      description
        "List of FPD supported nodes";
      list node {
        key "node-name";
        description
          "Information about a particular node";
        container devices {
          description
            "FPD information table";
          list device {
            description
              "FPD information for a particular fpd type";
            leaf fpd-type {
              type Fpd;
              description
                "FPD type";
            }
            leaf instance {
              type int32;
              description
                "Instance";
            }
            leaf sub-type {
              type Fpd-sub;
              description
                "FPD sub type";
            }
            uses UPGRADE-FPD-INFO;
          }
        }
        leaf node-name {
          type xr:Node-id;
          description
            "Node name";
        }
      }
    }
    container packages {
      description
        "FPD packages information";
      uses FPD-ALL-PACKAGES;
    }
  }
}
