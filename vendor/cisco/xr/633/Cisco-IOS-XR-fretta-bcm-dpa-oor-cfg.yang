module Cisco-IOS-XR-fretta-bcm-dpa-oor-cfg {
  namespace "http://cisco.com/ns/yang/Cisco-IOS-XR-fretta-bcm-dpa-oor-cfg";
  prefix fretta-bcm-dpa-oor-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-bcm-dpa-oor package configuration.
     
     This module contains definitions
     for the following management objects:
       oor-hw-config: Out-Of-Resource (OOR) configuration
     
     Copyright (c) 2013-2017 by Cisco Systems, Inc.
     All rights reserved.";

  revision 2015-11-09 {
    description
      "IOS XR 6.0 revision.";
  }

  container oor-hw-config {
    description
      "Out-Of-Resource (OOR) configuration";
    container hw {
      description
        "Hardware OOR configuration";
      container thresholds {
        description
          "Configure OOR hardware thresholds";
        list threshold {
          key "color";
          description
            "none";
          leaf color {
            type xr:Cisco-ios-xr-string;
            description
              "none";
          }
          leaf percent {
            type uint32 {
              range "0..100";
            }
            units "percentage";
            mandatory true;
            description
              "value in percent";
          }
        }
      }
      leaf dampening {
        type uint32 {
          range "0..600";
        }
        units "second";
        description
          "Configure OOR hardware dampening timeouts";
      }
    }
  }
}
