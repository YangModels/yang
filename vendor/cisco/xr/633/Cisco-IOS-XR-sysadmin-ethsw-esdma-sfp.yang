module Cisco-IOS-XR-sysadmin-ethsw-esdma-sfp {
  namespace "http://www.cisco.com/ns/yang/Cisco-IOS-XR-sysadmin-ethsw-esdma-sfp";
  prefix esdma_sfp;

  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains the YANG definitions
     for the Cisco IOS-XR SysAdmin
     'show controller switch sfp' commands.
     
     Copyright(c) 2011-2017 by Cisco Systems, Inc.
     All rights reserved.
     
     Copyright (c) 2012-2018 by Cisco Systems, Inc.
     All rights reserved.";

  revision 2017-05-01 {
    description
      "Namespace change to comply with Cisco guidelines on namespace";
  }

  grouping switch-sfp-summary-group {
    container summary {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        list sfp-port-iter {
          key "sfp-port";
          leaf sfp-port {
            type esdma_types:esdma-switch-port-type;
            description
              "Switch port";
          }
          leaf sfp-inserted {
            type esdma_types:esdma-switch-sfp-inserted-enum;
          }
          leaf sfp-controller {
            type esdma_types:esdma-switch-sfp-controller-enum;
          }
          leaf sfp-type {
            type esdma_types:esdma-switch-sfp-type-enum;
          }
          leaf connects-to {
            type string;
            description
              "Indicates what this port connects to";
          }
        }
      }
    }
  }

  grouping switch-sfp-detail-group {
    container detail {
      list location {
        key "rack card switch-id";
        leaf rack {
          type esdma_types:esdma-rack-num-enum;
        }
        leaf card {
          type esdma_types:esdma-cpu;
        }
        leaf switch-id {
          type esdma_types:esdma-switch-type-enum;
        }
        list sfp-port-iter {
          key "sfp-port";
          leaf sfp-port {
            type esdma_types:esdma-switch-port-type;
            description
              "Switch port";
          }
          leaf sfp-inserted {
            type esdma_types:esdma-switch-sfp-inserted-enum;
          }
          leaf sfp-type {
            type esdma_types:esdma-switch-sfp-type-enum;
          }
          container sfp-details {
            container sfp-port-detail {
              leaf sfp-tranceiver-type {
                type esdma_types:esdma-switch-sfp-tranceiver-type-enum;
              }
              leaf sfp-tranceiver-code {
                type esdma_types:esdma-switch-sfp-type-enum;
              }
              leaf sfp-encoding {
                type esdma_types:esdma-sfp-encoding-enum;
              }
              leaf sfp-bit-rate {
                type uint32;
              }
              leaf sfp-link-reach-9u-fiber_KM {
                when "../sfp-link-reach-9u-fiber_KM != '0'";
                type uint32;
              }
              leaf sfp-link-reach-9u-fiber_M {
                when "../sfp-link-reach-9u-fiber_M != '0'";
                type uint32;
              }
              leaf sfp-link-reach-50u-fiber_M {
                when "../sfp-link-reach-50u-fiber_M != '0'";
                type uint32;
              }
              leaf sfp-link-reach-62_5u-fiber_M {
                when "../sfp-link-reach-62_5u-fiber_M != '0'";
                type uint32;
              }
              leaf sfp-link-reach-copper_M {
                when "../sfp-link-reach-copper_M != '0'";
                type uint32;
              }
              leaf sfp-vendor-name {
                type string;
              }
              leaf sfp-vendor-oui {
                type string;
              }
              leaf sfp-vendor-part-num {
                type string;
              }
              leaf sfp-laser-wavelength {
                when "../sfp-laser-wavelength != '0'";
                type uint32;
              }
              leaf sfp-options {
                type bits {
                  bit LRO {
                    position 0;
                  }
                  bit PowerLvl2 {
                    position 1;
                  }
                  bit CooledXcvr {
                    position 2;
                  }
                  bit LOS {
                    position 9;
                  }
                  bit SignalDet {
                    position 10;
                  }
                  bit TxFault {
                    position 11;
                  }
                  bit TxDisable {
                    position 12;
                  }
                  bit RateSel {
                    position 13;
                  }
                }
              }
              leaf sfp-vendor-serial-num {
                type string;
              }
              leaf sfp-data-code {
                type string;
              }
              leaf sfp-diag-monitoring {
                type bits {
                  bit AvePwrMon {
                    position 3;
                  }
                  bit External {
                    position 4;
                  }
                  bit Internal {
                    position 5;
                  }
                  bit DigDiagMon {
                    position 6;
                  }
                }
              }
              leaf sfp-enhanced-options {
                type bits {
                  bit RateSelCtrl {
                    position 1;
                  }
                  bit ApplSelect {
                    position 2;
                  }
                  bit RateSelCtrlMon {
                    position 3;
                  }
                  bit RxLosMon {
                    position 4;
                  }
                  bit TxFaultMon {
                    position 5;
                  }
                  bit TxDisableCtrlMon {
                    position 6;
                  }
                  bit AlarmWarningFlags {
                    position 7;
                  }
                }
              }
            }
            container sfp-msa-data {
              leaf sfp-msa-0x00 {
                type string;
              }
              leaf sfp-msa-0x10 {
                type string;
              }
              leaf sfp-msa-0x20 {
                type string;
              }
              leaf sfp-msa-0x30 {
                type string;
              }
              leaf sfp-msa-0x40 {
                type string;
              }
              leaf sfp-msa-0x50 {
                type string;
              }
            }
            container sfp-diag-analog-info {
              container Thresholds {
                container Temperature {
                  leaf temp-alarm-high {
                    type string;
                  }
                  leaf temp-warning-high {
                    type string;
                  }
                  leaf temp-warning-low {
                    type string;
                  }
                  leaf temp-alarm-low {
                    type string;
                  }
                }
                container Voltage {
                  leaf volt-alarm-high {
                    type string;
                  }
                  leaf volt-warning-high {
                    type string;
                  }
                  leaf volt-warning-low {
                    type string;
                  }
                  leaf volt-alarm-low {
                    type string;
                  }
                }
                container Bias {
                  leaf bias-alarm-high {
                    type string;
                  }
                  leaf bias-warning-high {
                    type string;
                  }
                  leaf bias-warning-low {
                    type string;
                  }
                  leaf bias-alarm-low {
                    type string;
                  }
                }
                container Tx-Power {
                  leaf tx-power-alarm-high {
                    type string;
                  }
                  leaf tx-power-warning-high {
                    type string;
                  }
                  leaf tx-power-warning-low {
                    type string;
                  }
                  leaf tx-power-alarm-low {
                    type string;
                  }
                }
                container Rx-Power {
                  leaf rx-power-alarm-high {
                    type string;
                  }
                  leaf rx-power-warning-high {
                    type string;
                  }
                  leaf rx-power-warning-low {
                    type string;
                  }
                  leaf rx-power-alarm-low {
                    type string;
                  }
                }
              }
              container Real-Time-Data {
                container Current {
                  leaf cur-temperature {
                    type string;
                  }
                  leaf cur-voltage {
                    type string;
                  }
                  leaf cur-bias {
                    type string;
                  }
                  leaf cur-tx-power {
                    type string;
                  }
                  leaf cur-rx-power {
                    type string;
                  }
                  leaf optional-status-control {
                    type bits {
                      bit DataReadyBar {
                        position 0;
                      }
                      bit RxLOS {
                        position 1;
                      }
                      bit TxFault {
                        position 2;
                      }
                      bit SoftRateSel0Eq1 {
                        position 3;
                      }
                      bit RateSel0Eq1 {
                        position 4;
                      }
                      bit RateSel1Eq1 {
                        position 5;
                      }
                      bit SoftTxDisable {
                        position 6;
                      }
                      bit TxDisable {
                        position 7;
                      }
                    }
                  }
                }
              }
            }
            container sfp-diag-data1 {
              container optical-sfp-diag {
                leaf sfp-diag-0x00 {
                  type string;
                }
                leaf sfp-diag-0x10 {
                  type string;
                }
                leaf sfp-diag-0x20 {
                  type string;
                }
                leaf sfp-diag-0x30 {
                  type string;
                }
                leaf sfp-diag-0x40 {
                  type string;
                }
                leaf sfp-diag-0x50 {
                  type string;
                }
                leaf sfp-diag-0x60 {
                  type string;
                }
                leaf sfp-diag-0x70 {
                  type string;
                }
              }
            }
            container sfp-diag-user-info {
              container cisco-data {
                leaf cisco-clei-code {
                  type string;
                }
                leaf cisco-part-number {
                  type string;
                }
                leaf cisco-min-temperature {
                  type int8;
                }
                leaf cisco-max-temperature {
                  type int8;
                }
                leaf cisco-product-id {
                  type string;
                }
              }
            }
            container sfp-diag-data2 {
              container optical-sfp-diag {
                leaf sfp-diag-0x80 {
                  type string;
                }
                leaf sfp-diag-0x90 {
                  type string;
                }
                leaf sfp-diag-0xA0 {
                  type string;
                }
                leaf sfp-diag-0xB0 {
                  type string;
                }
                leaf sfp-diag-0xC0 {
                  type string;
                }
                leaf sfp-diag-0xD0 {
                  type string;
                }
                leaf sfp-diag-0xE0 {
                  type string;
                }
                leaf sfp-diag-0xF0 {
                  type string;
                }
              }
            }
          }
          container qsfp-details {
            container qsfp_page_A0_data {
              container qsfp-real-time-data {
                container qsfp-temp-volt {
                  leaf module-monitor-temperature {
                    type string;
                  }
                  leaf module-monitor-voltage {
                    type string;
                  }
                }
                container qsfp-tx-channel-bias {
                  leaf channel-monitor-Tx1-Bias {
                    type string;
                  }
                  leaf channel-monitor-Tx2-Bias {
                    type string;
                  }
                  leaf channel-monitor-Tx3-Bias {
                    type string;
                  }
                  leaf channel-monitor-Tx4-Bias {
                    type string;
                  }
                }
                container qsfp-tx-output-power {
                  leaf channel-monitor-Tx1-Power {
                    type string;
                  }
                  leaf channel-monitor-Tx2-Power {
                    type string;
                  }
                  leaf channel-monitor-Tx3-Power {
                    type string;
                  }
                  leaf channel-monitor-Tx4-Power {
                    type string;
                  }
                }
                container qsfp-rx-input-power {
                  leaf channel-monitor-Rx1-Power {
                    type string;
                  }
                  leaf channel-monitor-Rx2-Power {
                    type string;
                  }
                  leaf channel-monitor-Rx3-Power {
                    type string;
                  }
                  leaf channel-monitor-Rx4-Power {
                    type string;
                  }
                }
              }
              container qsfp-real-time-status-flags {
                container qsfp-real-time-status {
                  leaf qsfp-page-select {
                    type string;
                  }
                  leaf qsfp-status {
                    type bits {
                      bit DataNotReady {
                        position 8;
                      }
                      bit INTL {
                        position 9;
                      }
                      bit FlatMemory {
                        position 10;
                      }
                    }
                    description
                      "Status Indicator";
                  }
                }
                container qsfp-real-time-interrupt-flags {
                  leaf qsfp-int-flags-LOS-Indicator {
                    type bits {
                      bit L-Rx1-LOS {
                        position 0;
                      }
                      bit L-Rx2-LOS {
                        position 1;
                      }
                      bit L-Rx3-LOS {
                        position 2;
                      }
                      bit L-Rx4-LOS {
                        position 3;
                      }
                      bit L-Tx1-LOS {
                        position 4;
                      }
                      bit L-Tx2-LOS {
                        position 5;
                      }
                      bit L-Tx3-LOS {
                        position 6;
                      }
                      bit L-Tx4-LOS {
                        position 7;
                      }
                    }
                    description
                      "Interrupt Flag for TX/RX LOS Indicator";
                  }
                  leaf qsfp-int-flags-Fault-Indicator {
                    type bits {
                      bit L-Tx1-Fault {
                        position 0;
                      }
                      bit L-Tx2-Fault {
                        position 1;
                      }
                      bit L-Tx3-Fault {
                        position 2;
                      }
                      bit L-Tx4-Fault {
                        position 3;
                      }
                    }
                    description
                      "Interrupt Flag for TX Fault Indicator";
                  }
                  leaf qsfp-int-flags-Temperature-Indicator {
                    type bits {
                      bit Initialization-Complete-Flag {
                        position 0;
                      }
                      bit L-Temp-Low-Warning {
                        position 4;
                      }
                      bit L-Temp-High-Warning {
                        position 5;
                      }
                      bit L-Temp-Low-Alarm {
                        position 6;
                      }
                      bit L-Temp-High-Alarm {
                        position 7;
                      }
                    }
                    description
                      "Interrupt Flag for high/low alarm/warning temperature Indicator";
                  }
                  leaf qsfp-int-flags-Supply-Voltage-Indicator {
                    type bits {
                      bit L-Vcc-Low-Warning {
                        position 4;
                      }
                      bit L-Vcc-High-Warning {
                        position 5;
                      }
                      bit L-Vcc-Low-Alarm {
                        position 6;
                      }
                      bit L-Vcc-High-Alarm {
                        position 7;
                      }
                    }
                    description
                      "Interrupt Flag for high/low alarm/warning Voltage Indicator";
                  }
                  leaf qsfp-int-flags-Rx-Power-Indicator {
                    type bits {
                      bit L-Rx2-Power-Low-Warning {
                        position 0;
                      }
                      bit L-Rx2-Power-High-Warning {
                        position 1;
                      }
                      bit L-Rx2-Power-Low-Alarm {
                        position 2;
                      }
                      bit L-Rx2-Power-High-Alarm {
                        position 3;
                      }
                      bit L-Rx1-Power-Low-Warning {
                        position 4;
                      }
                      bit L-Rx1-Power-High-Warning {
                        position 5;
                      }
                      bit L-Rx1-Power-Low-Alarm {
                        position 6;
                      }
                      bit L-Rx1-Power-High-Alarm {
                        position 7;
                      }
                      bit L-Rx4-Power-Low-Warning {
                        position 8;
                      }
                      bit L-Rx4-Power-High-Warning {
                        position 9;
                      }
                      bit L-Rx4-Power-Low-Alarm {
                        position 10;
                      }
                      bit L-Rx4-Power-High-Alarm {
                        position 11;
                      }
                      bit L-Rx3-Power-Low-Warning {
                        position 12;
                      }
                      bit L-Rx3-Power-High-Warning {
                        position 13;
                      }
                      bit L-Rx3-Power-Low-Alarm {
                        position 14;
                      }
                      bit L-Rx3-Power-High-Alarm {
                        position 15;
                      }
                    }
                    description
                      "Interrupt Flag for high/low alarm/warning Rx Power in Channel 1/2/3/4 Indicator";
                  }
                  leaf qsfp-int-flags-Tx-Bias-Indicator {
                    type bits {
                      bit L-Tx2-Bias-Low-Warning {
                        position 0;
                      }
                      bit L-Tx2-Bias-High-Warning {
                        position 1;
                      }
                      bit L-Tx2-Bias-Low-Alarm {
                        position 2;
                      }
                      bit L-Tx2-Bias-High-Alarm {
                        position 3;
                      }
                      bit L-Tx1-Bias-Low-Warning {
                        position 4;
                      }
                      bit L-Tx1-Bias-High-Warning {
                        position 5;
                      }
                      bit L-Tx1-Bias-Low-Alarm {
                        position 6;
                      }
                      bit L-Tx1-Bias-High-Alarm {
                        position 7;
                      }
                      bit L-Tx4-Bias-Low-Warning {
                        position 8;
                      }
                      bit L-Tx4-Bias-High-Warning {
                        position 9;
                      }
                      bit L-Tx4-Bias-Low-Alarm {
                        position 10;
                      }
                      bit L-Tx4-Bias-High-Alarm {
                        position 11;
                      }
                      bit L-Tx3-Bias-Low-Warning {
                        position 12;
                      }
                      bit L-Tx3-Bias-High-Warning {
                        position 13;
                      }
                      bit L-Tx3-Bias-Low-Alarm {
                        position 14;
                      }
                      bit L-Tx3-Bias-High-Alarm {
                        position 15;
                      }
                    }
                    description
                      "Interrupt Flag for high/low alarm/warning Tx Bias in Channel 1/2/3/4 Indicator";
                  }
                }
              }
            }
            container qsfp_page_A0_0_data {
              leaf qsfp-identifier {
                type esdma_types:esdma-switch-sfp-tranceiver-type-enum;
              }
              leaf qsfp-transceiver {
                type esdma_types:esdma-qsfp-transceiver-enum;
              }
              leaf qsfp-extended-transceiver {
                type string;
              }
              leaf qsfp-encoding {
                type esdma_types:esdma-sfp-encoding-enum;
              }
              leaf qsfp-bit-rate {
                type uint32;
              }
              leaf qsfp-link-length-standard-SM-fiber_KM {
                when "../qsfp-link-length-standard-SM-fiber_KM != '0'";
                type uint32;
              }
              leaf qsfp-link-length-OM3-50u-fiber_M {
                when "../qsfp-link-length-OM3-50u-fiber_M != '0'";
                type uint32;
              }
              leaf qsfp-link-length-OM2-50u-fiber_M {
                when "../qsfp-link-length-OM2-50u-fiber_M != '0'";
                type uint32;
              }
              leaf qsfp-link-length-OM1-62_5u-fiber_M {
                when "../qsfp-link-length-OM1-62_5u-fiber_M != '0'";
                type uint32;
              }
              leaf qsfp-link-length-Copper-Cable-Assembly-fiber_M {
                when "../qsfp-link-length-Copper-Cable-Assembly-fiber_M  != '0'";
                type uint32;
              }
              leaf qsfp-device-tech {
                type string;
              }
              leaf qsfp-vendor-name {
                type string;
              }
              leaf qsfp-vendor-oui {
                type string;
              }
              leaf qsfp-vendor-part-num {
                type string;
              }
              leaf qsfp-laser-wavelength {
                when "../qsfp-laser-wavelength != '0'";
                type uint32;
              }
              leaf qsfp-wavelength_tolerance {
                type uint32;
              }
              leaf qsfp-max-case-temperature {
                type string;
              }
              leaf qsfp-option-value-Rx-amplitude {
                type bits {
                  bit RX-Output-Amplitude-Programming-Implemented {
                    position 0;
                  }
                }
                description
                  "Option value for Rx amplitude ";
              }
              leaf qsfp-option-values-Indicator {
                type bits {
                  bit TxSqlch {
                    position 0;
                  }
                  bit TxSqlchDisable {
                    position 1;
                  }
                  bit RxOutputDisable {
                    position 2;
                  }
                  bit RxSqlchDisable {
                    position 3;
                  }
                  bit TxLOS {
                    position 9;
                  }
                  bit TxSqlchReducePave {
                    position 10;
                  }
                  bit TxFaultSignal {
                    position 11;
                  }
                  bit TxDisable {
                    position 12;
                  }
                  bit RateSelect {
                    position 13;
                  }
                  bit MemPg01 {
                    position 14;
                  }
                  bit MemPg02 {
                    position 15;
                  }
                }
                description
                  "Options Implemented in the QSFP Module";
              }
              leaf qsfp-vendor-serial-num {
                type string;
              }
              leaf qsfp-date-code {
                type string;
              }
              leaf qsfp-diag-monitoring-type {
                type bits {
                  bit AvgPwrMon {
                    position 3;
                  }
                }
              }
            }
            container qsfp_page_A0_3_data {
              container qsfp-temperature {
                leaf qsfp-temp-alarm-high {
                  type string;
                }
                leaf qsfp-temp-warning-high {
                  type string;
                }
                leaf qsfp-temp-warning-low {
                  type string;
                }
                leaf qsfp-temp-alarm-low {
                  type string;
                }
              }
              container qsfp-voltage {
                leaf qsfp-volt-alarm-high {
                  type string;
                }
                leaf qsfp-volt-warning-high {
                  type string;
                }
                leaf qsfp-volt-warning-low {
                  type string;
                }
                leaf qsfp-volt-alarm-low {
                  type string;
                }
              }
              container qsfp-tx-bias {
                leaf qsfp-tx-bias-alarm-high {
                  type string;
                }
                leaf qsfp-tx-bias-warning-high {
                  type string;
                }
                leaf qsfp-tx-bias-warning-low {
                  type string;
                }
                leaf qsfp-tx-bias-alarm-low {
                  type string;
                }
              }
              container qsfp-tx-power {
                leaf qsfp-tx-power-alarm-high {
                  type string;
                }
                leaf qsfp-tx-power-warning-high {
                  type string;
                }
                leaf qsfp-tx-power-warning-low {
                  type string;
                }
                leaf qsfp-tx-power-alarm-low {
                  type string;
                }
              }
              container qsfp-rx-power {
                leaf qsfp-rx-power-alarm-high {
                  type string;
                }
                leaf qsfp-rx-power-warning-high {
                  type string;
                }
                leaf qsfp-rx-power-warning-low {
                  type string;
                }
                leaf qsfp-rx-power-alarm-low {
                  type string;
                }
              }
            }
          }
        }
      }
    }
  }

  grouping switch-sfp-group {
    container sfp {
      uses switch-sfp-summary-group;
      uses switch-sfp-detail-group;
    }
  }
}
