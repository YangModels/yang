module tailf-xsd-types {
  namespace "http://www.w3.org/2001/XMLSchema";
  prefix xs;

  description
    "This module contains useful XML Schema Datatypes that are not
     covered by YANG types directly.";

  revision 2009-03-17 {
    description
      "Initial revision.";
  }

  extension fraction-digits {
    argument num;
    description
      "To be used as a restriction with type xs:decimal.";
    reference "http://www.w3.org/TR/xmlschema-2/#rf-fractionDigits";
  }

  extension total-digits {
    argument num;
    description
      "To be used as a restriction with type xs:decimal.";
    reference "http://www.w3.org/TR/xmlschema-2/#rf-totalDigits";
  }

  typedef duration {
    type string;
    reference "http://www.w3.org/TR/xmlschema-2/#duration";
  }

  typedef date {
    type string;
    reference "http://www.w3.org/TR/xmlschema-2/#date";
  }

  typedef time {
    type string;
    reference "http://www.w3.org/TR/xmlschema-2/#time";
  }

  typedef token {
    type string;
    reference "http://www.w3.org/TR/xmlschema-2/#token";
  }

  typedef hexBinary {
    type string;
    reference "http://www.w3.org/TR/xmlschema-2/#hexBinary";
  }

  typedef QName {
    type string;
    reference "http://www.w3.org/TR/xmlschema-2/#QName";
  }

  typedef decimal {
    type string;
    reference "http://www.w3.org/TR/xmlschema-2/#decimal";
  }

  typedef float {
    type string;
    reference "http://www.w3.org/TR/xmlschema-2/#float";
  }

  typedef double {
    type string;
    reference "http://www.w3.org/TR/xmlschema-2/#double";
  }
}
