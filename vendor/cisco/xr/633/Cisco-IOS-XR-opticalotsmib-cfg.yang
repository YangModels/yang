module Cisco-IOS-XR-opticalotsmib-cfg {
  namespace "http://cisco.com/ns/yang/Cisco-IOS-XR-opticalotsmib-cfg";
  prefix opticalotsmib-cfg;

  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR opticalotsmib package configuration.
     
     This YANG module augments the
       Cisco-IOS-XR-snmp-agent-cfg
     module with configuration data.
     
     Copyright (c) 2013-2017 by Cisco Systems, Inc.
     All rights reserved.";

  revision 2015-11-09 {
    description
      "IOS XR 6.0 revision.";
  }

  augment "/a1:snmp/a1:notification" {
    description
      "This augment extends the configuration data of
       'Cisco-IOS-XR-snmp-agent-cfg'";
    container optical-ots {
      description
        "CISCO-OPTICAL-OTS-MIB notification configuration";
      leaf enable {
        type empty;
        description
          "Enable OpticalOtsmib notifications";
      }
    }
  }
}
