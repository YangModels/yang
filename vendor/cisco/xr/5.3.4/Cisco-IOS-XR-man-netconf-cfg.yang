module Cisco-IOS-XR-man-netconf-cfg {

  /*** NAMESPACE / PREFIX DEFINITION ***/

  namespace "http://cisco.com/ns/yang/Cisco-IOS-XR-man-netconf-cfg";


  prefix "man-netconf-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-netconf package configuration.

     This module contains definitions
     for the following management objects:
       netconf-yang: NETCONF YANG configuration commands

     Copyright (c) 2013-2015 by Cisco Systems, Inc.
     All rights reserved.";

  revision "2015-01-07" {
    description
      "IOS XR 5.3.1 revision.";
  }


  container netconf-yang {
    xr:xr-xml-map "cfg_netconf:NETCONF_YANG";
    description "NETCONF YANG configuration commands";

    container agent {
      xr:xr-xml-map "cfg_netconf:Agent";
      description "NETCONF YANG agent configuration commands";

      container ssh {
        xr:xr-xml-map "cfg_netconf:SSH";
        description "NETCONF YANG agent over SSH connection";
        leaf enable {
          xr:xr-xml-map "cfg_netconf:Enable";
          xr:xr-cli-map "netconf-yang agent ssh ";
          type empty;
          description
            "Enable NETCONF YANG agent over SSH connection";
        }
      }

      container session {
        xr:xr-xml-map "cfg_netconf:Session";
        description "Session settings";
        leaf limit {
          xr:xr-xml-map "cfg_netconf:Limit";
          xr:xr-cli-map "netconf-yang agent session limit <number> ";
          type uint32 {
            range "1..1024";
          }
          description
            "Count of allowable concurrent netconf-yang
            sessions";
        }
        leaf absolute-timeout {
          xr:xr-xml-map "cfg_netconf:AbsoluteTimeout";
          xr:xr-cli-map "netconf-yang agent session absolute-timeou"+
            "t <number> ";
          type uint32 {
            range "1..1440";
          }
          units "minute";
          description "Absolute timeout in minutes";
        }
        leaf idle-timeout {
          xr:xr-xml-map "cfg_netconf:IdleTimeout";
          xr:xr-cli-map "netconf-yang agent session idle-timeout <n"+
            "umber> ";
          type uint32 {
            range "1..1440";
          }
          units "minute";
          description "Idle timeout in minutes";
        }
      }
      leaf rate-limit {
        xr:xr-xml-map "cfg_netconf:RateLimit";
        xr:xr-cli-map "netconf-yang agent rate-limit <number> ";
        type uint32 {
          range "4096..4294967295";
        }
        units "byte";
        description "Number of bytes to process per sec";
      }
    }
  }
}
