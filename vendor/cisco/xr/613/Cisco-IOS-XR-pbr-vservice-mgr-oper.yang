module Cisco-IOS-XR-pbr-vservice-mgr-oper {

  /*** NAMESPACE / PREFIX DEFINITION ***/

  namespace "http://cisco.com/ns/yang"+
    "/Cisco-IOS-XR-pbr-vservice-mgr-oper";


  prefix "pbr-vservice-mgr-oper";

  /*** LINKAGE (IMPORTS / INCLUDES) ***/

  import Cisco-IOS-XR-types { prefix "xr"; }

  import Cisco-IOS-XR-pbr-datatypes { prefix "dt1"; }

  include Cisco-IOS-XR-pbr-vservice-mgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr-vservice-mgr package operational data.

     This module contains definitions
     for the following management objects:
       global-service-function-chaining: NSH Service Function
         Chaining global operational data

     Copyright (c) 2013-2016 by Cisco Systems, Inc.
     All rights reserved.";

  revision "2015-11-09" {
    description
      "IOS XR 6.0 revision.";
  }


  container global-service-function-chaining {
    config false;
    description
      "NSH Service Function Chaining global operational
      data";

    container service-function-path {
      description "Service Function Path operational data";

      container path-ids {
        description "Service Function Path Id ";

        list path-id {
          key "id";
          description "Specific Service-Function-Path identifier ";

          container stats {
            description "SFP Statistics";

            container detail {
              description "Detail statistics per service index ";
              uses VSERVICE-EDM-NSH-STATS-INFO;
            }

            container summarized {
              description
                "Combined statistics of all service index in
                service functionpath";
              uses VSERVICE-EDM-NSH-STATS-INFO;
            }
          }

          container service-indexes {
            description "Service Index Belonging to Path";

            list service-index {
              key "index";
              description
                "Service index operational data belonging to
                this path";
              leaf index {
                type dt1:Vservice-nsh-service-index-range;
                description "Service Index";
              }
              uses VSERVICE-EDM-NSH-STATS-INFO;
            }
          }
          leaf id {
            type dt1:Vservice-nsh-path-id-range;
            description "Specific Service-Function-Path identifier";
          }
        }
      }
    }

    container service-function {
      description "Service Function operational data";

      container sf-names {
        description "List of Service Function Names";

        list sf-name {
          key "name";
          description "Name of Service Function";
          leaf name {
            type xr:Cisco-ios-xr-string {
              length "0..32";
            }
            description "Name";
          }
          uses VSERVICE-EDM-NSH-STATS-INFO;
        }
      }
    }

    container service-function-forwarder {
      description "Service Function Forwarder operational data";

      container sff-names {
        description "List of Service Function Forwarder Names";

        list sff-name {
          key "name";
          description "Name of Service Function Forwarder";
          leaf name {
            type xr:Cisco-ios-xr-string {
              length "0..32";
            }
            description "Name";
          }
          uses VSERVICE-EDM-NSH-STATS-INFO;
        }
      }

      container local {
        description
          "Local Service Function Forwarder operational
          data";

        container error {
          description
            "Error Statistics for local service function
            forwarder";
          uses VSERVICE-EDM-NSH-STATS-INFO;
        }
      }
    }
  }
}
