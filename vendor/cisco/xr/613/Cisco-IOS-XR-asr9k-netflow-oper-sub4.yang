submodule Cisco-IOS-XR-asr9k-netflow-oper-sub4 {

  belongs-to Cisco-IOS-XR-asr9k-netflow-oper {
    prefix Cisco-IOS-XR-asr9k-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-netflow package operational data.

     Copyright (c) 2013-2016 by Cisco Systems, Inc.
     All rights reserved.";

  revision "2015-11-09" {
    description
      "IOS XR 6.0 revision.";
  }


  grouping NFMGR-EXPORTER-NAME {
    description "Exporter name";
    leaf name {
      type string;
      description "Exporter name";
    }
  }

  grouping NFMGR-FMM-EDM-INFO {
    description "Netflow flow monitor data";
    leaf id {
      type uint32;
      description "Unique ID in the global flow monitor ID space";
    }
    leaf name {
      type string;
      description "Name of the flow monitor map";
    }
    leaf record-map {
      type string;
      description "Name of the flow record map";
    }
    leaf cache-aging-mode {
      type string;
      description "Aging mode for flow cache";
    }
    leaf number-of-labels {
      type uint32;
      description "Number of MPLS labels in key";
    }
    leaf cache-max-entry {
      type uint32;
      description "Max num of entries in flow cache";
    }
    leaf cache-active-timeout {
      type uint32;
      units "second";
      description "Cache active flow timeout in seconds";
    }
    leaf cache-inactive-timeout {
      type uint32;
      units "second";
      description "Cache inactive flow timeout in seconds";
    }
    leaf cache-update-timeout {
      type uint32;
      units "second";
      description "Cache update timeout in seconds";
    }
    leaf cache-timeout-rate-limit {
      type uint32;
      description "Maximum number of entries to age each second";
    }
    leaf options {
      type uint32;
      description "Options applied to the flow monitor";
    }

    list exporter {
      max-elements "8";
      description
        "Name of the flow exporters used by the flow
        monitor";
      uses NFMGR-EXPORTER-NAME;
    }
  }
}
