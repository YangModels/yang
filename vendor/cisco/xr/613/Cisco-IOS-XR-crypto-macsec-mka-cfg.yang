module Cisco-IOS-XR-crypto-macsec-mka-cfg {

  /*** NAMESPACE / PREFIX DEFINITION ***/

  namespace "http://cisco.com/ns/yang"+
    "/Cisco-IOS-XR-crypto-macsec-mka-cfg";


  prefix "crypto-macsec-mka-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-mka package configuration.

     This module contains definitions
     for the following management objects:
       macsec: MACSec MKA

     Copyright (c) 2013-2016 by Cisco Systems, Inc.
     All rights reserved.";

  revision "2015-11-09" {
    description
      "IOS XR 6.0 revision.";
  }

  typedef Macsec-mka-window-size {
    type uint32 {
      range "0..1024";
    }
    description "Macsec mka window size";
  }
  typedef Macsec-mka-security-policy {
    type enumeration {
      enum should-secure {
        value 0;
        description "should secure";
      }
      enum must-secure {
        value 1;
        description "must secure";
      }
    }
    description "Macsec mka security policy";
  }
  typedef Macsec-mka-key-server-priority {
    type uint32 {
      range "0..255";
    }
    description "Macsec mka key server priority";
  }
  typedef Macsec-mka-policy-exception {
    type enumeration {
      enum lacp-in-clear {
        value 1;
        description "lacp in clear";
      }
    }
    description "Macsec mka policy exception";
  }
  typedef Macsec-mka-cipher-suite {
    type enumeration {
      enum gcm-aes-128 {
        value 1;
        description "GCM AES 128";
      }
      enum gcm-aes-256 {
        value 2;
        description "GCM AES 256";
      }
      enum gcm-aes-xpn-128 {
        value 3;
        description "GCM AES XPN 128";
      }
      enum gcm-aes-xpn-256 {
        value 4;
        description "GCM AES XPN 256";
      }
    }
    description "Macsec mka cipher suite";
  }
  typedef Macsec-mka-conf-offset {
    type enumeration {
      enum conf-off-set-0 {
        value 0;
        description "CONF OFFSET 0";
      }
      enum conf-off-set-30 {
        value 30;
        description "CONF OFFSET 30";
      }
      enum conf-off-set-50 {
        value 50;
        description "CONF OFFSET 50";
      }
    }
    description "Macsec mka conf offset";
  }
  typedef Macsec-mka-sak-rekey-interval {
    type uint32 {
      range "0..43200";
    }
    description "Macsec mka sak rekey interval";
  }
  typedef Macsec-mka-vlan-tags-in-clear {
    type uint32 {
      range "1..2";
    }
    description "Macsec mka vlan tags in clear";
  }

  container macsec {
    description "MACSec MKA";

    list policy {
      key "name";
      description "MACSec Policy";
      leaf security-policy {
        type Macsec-mka-security-policy;
        description "Security-Policy of Policy";
      }
      leaf key-server-priority {
        type Macsec-mka-key-server-priority;
        description "Key-Server-Priority of Policy";
      }
      leaf conf-offset {
        type Macsec-mka-conf-offset;
        description "Conf-Offset of Policy";
      }
      leaf sak-rekey-interval {
        type Macsec-mka-sak-rekey-interval;
        units "minute";
        description
          "Interval after which key-server generates new
          SAK for a Secured Session";
      }
      leaf policy-exception {
        type Macsec-mka-policy-exception;
        description
          "Macsec policy exception for packets to be in
          clear";
      }
      leaf window-size {
        type Macsec-mka-window-size;
        description "Window-Size of Policy";
      }
      leaf cipher-suite {
        type Macsec-mka-cipher-suite;
        description "Cipher-suite of Policy";
      }
      leaf include-icv-indicator {
        type boolean;
        description
          "TRUE enables Include ICV Indicator paramset in
          MKPDU";
      }
      leaf vlan-tags-in-clear {
        type Macsec-mka-vlan-tags-in-clear;
        description "VLAN-Tags-In-Clear of Policy";
      }
      leaf name {
        type xr:Cisco-ios-xr-string;
        description "Name of the Policy";
      }
    }
  }
}
