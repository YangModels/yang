module Cisco-IOS-XR-spirit-install-instmgr-oper {

  /*** NAMESPACE / PREFIX DEFINITION ***/

  namespace "http://cisco.com/ns/yang"+
    "/Cisco-IOS-XR-spirit-install-instmgr-oper";


  prefix "spirit-install-instmgr-oper";

  /*** LINKAGE (IMPORTS / INCLUDES) ***/

  import Cisco-IOS-XR-types { prefix "xr"; }

  include Cisco-IOS-XR-spirit-install-instmgr-oper-sub2 {
    revision-date 2015-11-09;
  }

  include Cisco-IOS-XR-spirit-install-instmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR spirit-install-instmgr package operational data.

     This module contains definitions
     for the following management objects:
       software-install: Install operations info

     Copyright (c) 2013-2016 by Cisco Systems, Inc.
     All rights reserved.";

  revision "2015-11-09" {
    description
      "IOS XR 6.0 revision.";
  }


  container software-install {
    config false;
    description "Install operations info";

    container files {
      description "Show information about an installed file";

      list file {
        key "file-name";
        description "Show information about an installed file";

        container brief {
          description "Show information about an installed file";
          uses INSTALL-LOG;
        }

        container detail {
          description
            "Show detail information about an installed
            file";
          uses INSTALL-LOG;
        }
        leaf file-name {
          type string;
          description "File name";
        }
      }
    }

    container last-n-operation-logs {
      description "Show log file for last n operations";

      list last-n-operation-log {
        key "last-n-logs";
        description "Show log file of last n operations";

        container summary {
          description "Show summary log file for last n operations";
          uses INSTALL-LOG;
        }

        container detail {
          description
            "Show detailed log file for last n operations";
          uses INSTALL-LOG;
        }
        leaf last-n-logs {
          type int32;
          description "Last N opeartion logs";
        }
      }
    }

    container prepare {
      description "Show prepared packages ready for activation";
      uses INSTALL-LOG;
    }

    container active {
      description "Show active packages installed";
      uses INSTMGR-CALV-SHOW-INST-ACT;
    }

    container version {
      description "Show install version";
      uses INSTALL-LOG;
    }

    container inactive {
      description "Show XR inactive packages";
      uses INSTALL-LOG;
    }

    container request {
      description "Show current request";
      uses INSTALL-LOG;
    }

    container issu {
      description "ISSU operation";

      container stage {
        description "Show XR install issu stage";
        uses ISD-STAGE-INFO;
      }

      container inventory {
        description "Show XR install issu inventory";
        uses ISD-INV-INFO-CONTAINER;
      }
    }

    container committed {
      description "Show Committed packages installed";
      uses INSTMGR-CALV-SHOW-INST-COMMIT;
    }

    container all-operations-log {
      description "Show log file for all operations";

      container summary {
        description "Show summary log file for all operations";
        uses INSTALL-LOG;
      }

      container detail {
        description "Show detailed log file for all operations";
        uses INSTALL-LOG;
      }
    }

    container packages {
      description "Show the list of installed packages";

      list package {
        key "package-name";
        description "Show the info for a installed package";

        container verbose {
          description
            "Show the verbose info for a installed package";
          uses INSTALL-LOG;
        }

        container brief {
          description "Show the info for a installed package";
          uses INSTALL-LOG;
        }

        container detail {
          description
            "Show the deatil info for a installed package";
          uses INSTALL-LOG;
        }
        leaf package-name {
          type string;
          description "Package name";
        }
      }
    }

    container operation-logs {
      description "Show log file";

      list operation-log {
        key "log-id";
        description "Show log file for the specified install ID";

        container summary {
          description
            "Show summary log file for the specified
            install ID";
          uses INSTALL-LOG;
        }

        container detail {
          description
            "Show detailed log file for the specified
            install ID";
          uses INSTALL-LOG;
        }
        leaf log-id {
          type int32;
          description "Log ID number";
        }
      }
    }

    container repository {
      description
        "Show packages stored in install software
        repositories";

      container xr {
        description "Show install software repository for XR";
        uses INSTALL-LOG;
      }

      container all {
        description
          "Show contents of all install software
          repositories";
        uses INSTALL-LOG;
      }
    }
  }
}
