module Cisco-IOS-XR-fretta-bcm-dpa-hw-resources-oper {

  /*** NAMESPACE / PREFIX DEFINITION ***/

  namespace "http://cisco.com/ns/yang"+
    "/Cisco-IOS-XR-fretta-bcm-dpa-hw-resources-oper";


  prefix "fretta-bcm-dpa-hw-resources-oper";

  /*** LINKAGE (IMPORTS / INCLUDES) ***/

  import Cisco-IOS-XR-types { prefix "xr"; }

  include Cisco-IOS-XR-fretta-bcm-dpa-hw-resources-oper-sub2 {
    revision-date 2015-11-09;
  }

  include Cisco-IOS-XR-fretta-bcm-dpa-hw-resources-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa-hw-resources package operational data.

     This module contains definitions
     for the following management objects:
       dpa: Stats Data

     Copyright (c) 2013-2016 by Cisco Systems, Inc.
     All rights reserved.";

  revision "2015-11-09" {
    description
      "IOS XR 6.0 revision.";
  }

  typedef Max-trap-s {
    type uint32 {
      range "0..4294967295";
    }
    description "Max trap s";
  }
  typedef Resource {
    type enumeration {
      enum lem {
        value 0;
        description "lem";
      }
      enum lpm {
        value 1;
        description "lpm";
      }
      enum encap {
        value 2;
        description "encap";
      }
      enum ext-tcam {
        value 3;
        description "ext tcam";
      }
      enum all {
        value 4;
        description "all hardware resources";
      }
    }
    description "Resource";
  }
  typedef Max-lc-intf-hand-les {
    type uint32 {
      range "0..4294967295";
    }
    description "Max lc intf hand les";
  }

  container dpa {
    config false;
    description "Stats Data";

    container stats {
      description "Voq or Trap Data";

      container nodes {
        description "DPA data for available nodes";

        list node {
          key "node-name";
          description "DPA operational data for a particular node";

          container hw-resources-datas {
            description "DPA hw resources stats ";

            list hw-resources-data {
              key "resource";
              description "Hardware resources table";
              leaf resource {
                type Resource;
                description "Resource type";
              }
              uses DPA-SYSDB-HW-RESOURCE;
            }
          }

          container asic-statistics {
            description "ASIC statistics table";

            container asic-statistics-for-npu-ids {
              description "ASIC statistics";

              list asic-statistics-for-npu-id {
                key "npu-id";
                description "ASIC statistics for a particular NPU";
                leaf npu-id {
                  type int32;
                  description "NPU number";
                }
                uses FIA-EDM-STATS-BRIEF-INFO;
              }
            }

            container asic-statistics-detail-for-npu-ids {
              description "Detailed ASIC statistics";

              list asic-statistics-detail-for-npu-id {
                key "npu-id";
                description
                  "Detailed ASIC statistics for a particular
                  NPU";
                leaf npu-id {
                  type int32;
                  description "NPU number";
                }
                uses FIA-EDM-STATS-INFO;
              }
            }
          }

          container npu-numbers {
            description "Ingress Stats";

            list npu-number {
              key "npu-id";
              description "Stats for a particular npu";

              container reset {
                description "clear npu specific voq or trap stats";

                container voq-base-data {
                  description "Reset voq stats by base number";
                  uses CLEAR-STATS;
                }

                container voq-interface-data {
                  description "Reset voq stats by interface";
                  uses CLEAR-STATS;
                }

                container trap-data {
                  description
                    "Reset trap stats for a particular npu";
                  uses CLEAR-STATS;
                }
              }

              container display {
                description "show npu specific voq or trap stats";

                container base-numbers {
                  description
                    "Voq stats grouped by voq base numbers";

                  list base-number {
                    key "base-number";
                    description
                      "Voq Base Number for a particular voq";
                    leaf base-number {
                      type Max-lc-intf-hand-les;
                      description "Interface handle";
                    }
                    uses DPA-VOQ-INTF-PORT;
                  }
                }

                container trap-ids {
                  description "Trap stats for a particular npu";

                  list trap-id {
                    key "trap-id";
                    description "Filter by specific trap id";
                    leaf trap-id {
                      type Max-trap-s;
                      description "Trap ID";
                    }
                    uses DPA-TRAP-STATS;
                  }
                }

                container interface-handles {
                  description
                    "Voq stats grouped by interface handle";

                  list interface-handle {
                    key "interface-handle";
                    description
                      "Voq stats for a particular interface
                      handle";
                    leaf interface-handle {
                      type Max-lc-intf-hand-les;
                      description "Interface Handle";
                    }
                    uses DPA-VOQ-INTF-PORT;
                  }
                }
              }
              leaf npu-id {
                type int32;
                description "Npu number";
              }
            }
          }

          container clear-asic-statistics-for-npu-ids {
            description "Clear ASIC statistics";

            list clear-asic-statistics-for-npu-id {
              key "npu-id";
              description
                "Clear ASIC statistics for a particular NPU";
              leaf npu-id {
                type int32;
                description "NPU number";
              }
              uses CLEAR-STATS;
            }
          }
          leaf node-name {
            type xr:Node-id;
            description "Node ID";
          }
        }
      }
    }
  }
}
