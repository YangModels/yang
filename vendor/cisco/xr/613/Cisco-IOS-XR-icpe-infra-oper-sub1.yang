submodule Cisco-IOS-XR-icpe-infra-oper-sub1 {

  belongs-to Cisco-IOS-XR-icpe-infra-oper {
    prefix Cisco-IOS-XR-icpe-infra-oper;
  }

  /*** LINKAGE (IMPORTS / INCLUDES) ***/

  import Cisco-IOS-XR-types { prefix "xr"; }

  include Cisco-IOS-XR-icpe-infra-oper-sub5 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2016 by Cisco Systems, Inc.
     All rights reserved.";

  revision "2015-11-09" {
    description
      "IOS XR 6.0 revision.";
  }


  grouping ICPE-INSTALL-OP-STATUS-DETAIL {
    description "Detailed breakdown of install status";
    leaf operation-id-xr {
      type uint32;
      description "Operation ID";
    }
    leaf satellite-range {
      type Xr-yang-string;
      description "Satellite range";
    }
    leaf-list sats-not-initiated {
      type uint16;
      description "Sats not initiated";
    }
    leaf-list sats-transferring {
      type uint16;
      description "Sats transferring";
    }
    leaf-list sats-activating {
      type uint16;
      description "Sats activating";
    }
    leaf-list sats-deactivating {
      type uint16;
      description "Sats deactivating";
    }
    leaf-list sats-removing {
      type uint16;
      description "Sats removing";
    }
    leaf-list sats-transfer-failed {
      type uint16;
      description "Sats transfer failed";
    }
    leaf-list sats-activate-failed {
      type uint16;
      description "Sats activate failed";
    }
    leaf-list sats-deactivate-failed {
      type uint16;
      description "Sats deactivate failed";
    }
    leaf-list sats-remove-failed {
      type uint16;
      description "Sats remove failed";
    }
    leaf-list sats-transfer-aborted {
      type uint16;
      description "Sats transfer aborted";
    }
    leaf-list sats-activate-aborted {
      type uint16;
      description "Sats activate aborted";
    }
    leaf-list sats-deactivate-aborted {
      type uint16;
      description "Sats deactivate aborted";
    }
    leaf-list sats-remove-aborted {
      type uint16;
      description "Sats remove aborted";
    }
    leaf-list sats-no-operation {
      type uint16;
      description "Sats no operation";
    }
    leaf-list sats-completed {
      type uint16;
      description "Sats completed";
    }
  }
}
