submodule Cisco-IOS-XR-lpts-pre-ifib-oper-sub1 {

  belongs-to Cisco-IOS-XR-lpts-pre-ifib-oper {
    prefix Cisco-IOS-XR-lpts-pre-ifib-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-pre-ifib package operational data.

     Copyright (c) 2013-2016 by Cisco Systems, Inc.
     All rights reserved.";

  revision "2016-02-22" {
    description
      "Initial revision for pre-ifib oper yang.";
  }

  revision "2015-11-09" {
    description
      "IOS XR 6.0 revision.";
  }


  grouping TIMESPEC-ENTRY {
    description "Creation or Update Time";
    leaf tv-sec {
      type uint32;
      description "Time Sec";
    }
    leaf tv-nsec {
      type uint32;
      description "Time Nanosec";
    }
  }

  grouping PIFIB-SHOW-ENTRY {
    description "LPTS Pre-IFIB Entry Information";

    container utime {
      description "Creation or Update Time";
      uses TIMESPEC-ENTRY;
    }
    leaf vid {
      type uint32;
      description "VRF ID";
    }
    leaf l3protocol {
      type uint32;
      description "Layer 3 Protocol";
    }
    leaf l4protocol {
      type uint32;
      description "Layer 4 Protocol";
    }
    leaf intf-handle {
      type uint32;
      description "Interface Handle";
    }
    leaf local-addr {
      type yang:hex-string;
      description "Local IP Address";
    }
    leaf local-prefix-len {
      type uint32;
      description "Local Prefix Length";
    }
    leaf remote-addr {
      type yang:hex-string;
      description "Remote IP Address";
    }
    leaf remote-prefix-len {
      type uint32;
      description "Remote Prefix Length";
    }
    leaf u-type {
      type uint8;
      description "Union Key Type";
    }
    leaf u-value {
      type uint32;
      description "Local Port/ICMP Type/IGMP Type";
    }
    leaf u-len {
      type uint32;
      description "Union Key Length";
    }
    leaf remote-port {
      type uint16;
      description "Remote port";
    }
    leaf is-frag {
      type uint8;
      description "Is Fragment";
    }
    leaf is-syn {
      type uint8;
      description "Is SYN";
    }
    leaf opcode {
      type uint8;
      description "Opcode";
    }
    leaf flow-type {
      type uint32;
      description "Flow type";
    }
    leaf listener-tag {
      type uint8;
      description "Listener Tag";
    }
    leaf local-flag {
      type uint8;
      description "Local Flag";
    }
    leaf is-fgid {
      type uint8;
      description "Is FGID or not";
    }
    leaf deliver-list {
      type uint32;
      description "Deliver List";
    }
    leaf deliver-list-str {
      type string {
        length "0..1024";
      }
      description "Deliver List String";
    }
    leaf min-ttl {
      type uint8;
      description "Minimum TTL";
    }
    leaf accepts {
      type uint64;
      description "Packets matched to accept";
    }
    leaf drops {
      type uint64;
      description "Packets matched for drop";
    }
    leaf stale {
      type uint8;
      description "Is Stale";
    }
    leaf pifib-type {
      type uint8;
      description "sub Pre-IFIB type";
    }
  }
}
