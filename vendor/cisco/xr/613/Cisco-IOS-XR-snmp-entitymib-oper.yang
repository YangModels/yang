module Cisco-IOS-XR-snmp-entitymib-oper {

  /*** NAMESPACE / PREFIX DEFINITION ***/

  namespace "http://cisco.com/ns/yang"+
    "/Cisco-IOS-XR-snmp-entitymib-oper";


  prefix "snmp-entitymib-oper";

  /*** LINKAGE (IMPORTS / INCLUDES) ***/

  import Cisco-IOS-XR-types { prefix "xr"; }

  import Cisco-IOS-XR-snmp-agent-oper { prefix "a1"; }

  include Cisco-IOS-XR-snmp-entitymib-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-entitymib package operational data.

     This YANG module augments the
       Cisco-IOS-XR-snmp-agent-oper
     module with state data.

     Copyright (c) 2013-2016 by Cisco Systems, Inc.
     All rights reserved.";

  revision "2015-11-09" {
    description
      "IOS XR 6.0 revision.";
  }


  augment "/a1:snmp" {

    container entity-mib {
      description "SNMP entity mib";

      container entity-physical-indexes {
        description "SNMP entity mib";

        list entity-physical-index {
          key "entity-phynum";
          description "SNMP entPhysical index number";
          leaf entity-phynum {
            type xr:Cisco-ios-xr-string;
            description "Entity physical index";
          }
          uses ENTMIB-NODE2PATH-INFO;
        }
      }
    }
    description
      "This augment extends the operational data of
      'Cisco-IOS-XR-snmp-agent-oper'";
  }
}
