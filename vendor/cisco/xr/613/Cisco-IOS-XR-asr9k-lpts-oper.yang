module Cisco-IOS-XR-asr9k-lpts-oper {

  /*** NAMESPACE / PREFIX DEFINITION ***/

  namespace "http://cisco.com/ns/yang/Cisco-IOS-XR-asr9k-lpts-oper";


  prefix "asr9k-lpts-oper";

  /*** LINKAGE (IMPORTS / INCLUDES) ***/

  import Cisco-IOS-XR-types { prefix "xr"; }

  include Cisco-IOS-XR-asr9k-lpts-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-lpts package operational data.

     This module contains definitions
     for the following management objects:
       platform-lptsp-ifib: ASR9K platform ifib operational data 

     Copyright (c) 2013-2016 by Cisco Systems, Inc.
     All rights reserved.";

  revision "2015-11-09" {
    description
      "IOS XR 6.0 revision.";
  }


  container platform-lptsp-ifib {
    config false;
    description "ASR9K platform ifib operational data ";

    container nodes {
      description
        "List of nodes with platform specific lpts
        operation data";

      list node {
        key "node-name";
        description "Node with platform specific lpts data";

        container police {
          description "pl_pifib police data";
          uses PL-PIFIB-SHOW-POLICE;
        }

        container stats {
          description "pl_pifib stats";
          uses PL-PIFIB-SHOW-STATS;
        }
        leaf node-name {
          type xr:Node-id;
          description "Node name";
        }
      }
    }
  }
}
