module Cisco-IOS-XR-crypto-macsec-mka-if-cfg {

  /*** NAMESPACE / PREFIX DEFINITION ***/

  namespace "http://cisco.com/ns/yang"+
    "/Cisco-IOS-XR-crypto-macsec-mka-if-cfg";


  prefix "crypto-macsec-mka-if-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-mka-if package configuration.

     This YANG module augments the
       Cisco-IOS-XR-ifmgr-cfg
     module with configuration data.

     Copyright (c) 2013-2016 by Cisco Systems, Inc.
     All rights reserved.";

  revision "2015-11-09" {
    description
      "IOS XR 6.0 revision.";
  }


  augment "/a1:interface-configurations/a1:interface-configuration" {

    container macsec {
      description "MACSec service for an interface";

      container macsec-service {
        presence "Indicates a macsec-service node is configured.";
        description "macsec-service configuration on interface";
        leaf decrypt-port {
          type xr:Interface-name;
          mandatory true;
          description "macsec service decryption port";
        }
        leaf key-chain {
          type string {
            length "0..32";
          }
          mandatory true;
          description "name of keychain";
        }
        leaf policy {
          type string;
          description "name of policy";
        }
      }

      container psk-key-chain {
        presence "Indicates a psk-key-chain node is configured.";
        description "MACSec MKA Configuration on Interface";
        leaf key-chain-name {
          type xr:Cisco-ios-xr-string {
            length "0..32";
          }
          mandatory true;
          description "Name of KeyChainName";
        }
        leaf policy-name {
          type string;
          description "Name of Policy";
        }
        leaf fallback-key-chain {
          type string {
            length "0..32";
          }
          description "name of fallback keychain";
        }
      }
    }
    description
      "This augment extends the configuration data of
      'Cisco-IOS-XR-ifmgr-cfg'";
  }
}
