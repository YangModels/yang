submodule Cisco-IOS-XR-ethernet-cfm-oper-sub4 {

  belongs-to Cisco-IOS-XR-ethernet-cfm-oper {
    prefix Cisco-IOS-XR-ethernet-cfm-oper;
  }

  /*** LINKAGE (IMPORTS / INCLUDES) ***/

  import Cisco-IOS-XR-types { prefix "xr"; }

  include Cisco-IOS-XR-ethernet-cfm-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-cfm package operational data.

     Copyright (c) 2013-2016 by Cisco Systems, Inc.
     All rights reserved.";

  revision "2015-11-09" {
    description
      "IOS XR 6.0 revision.";
  }


  grouping CGM-CFG-ERRORS {
    description "CFM Global Manager Service Error Information";

    container bridge-domain-id {
      description
        "BD/XC ID, or Service name if the Service is
        'down-only'";
      uses CFM-BAG-BDID;
    }
    leaf domain-name {
      type string;
      description "Domain name";
    }
    leaf level {
      type Cfm-bag-md-level;
      description "Level";
    }
    leaf service-name {
      type string;
      description "Service name";
    }
    leaf bridge-domain-is-configured {
      type boolean;
      description "The BD/XC is configured globally";
    }
    leaf l2-fib-download-error {
      type boolean;
      description "The BD/XC could not be downloaded to L2FIB";
    }
  }
}
