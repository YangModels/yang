submodule Cisco-IOS-XR-openconfig-terminal-device-oper-sub1 {

  belongs-to Cisco-IOS-XR-openconfig-terminal-device-oper {
    prefix Cisco-IOS-XR-openconfig-terminal-device-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR openconfig-terminal-device package operational data.

     Copyright (c) 2013-2016 by Cisco Systems, Inc.
     All rights reserved.";

  revision "2015-11-09" {
    description
      "IOS XR 6.0 revision.";
  }

  typedef Logical-protocol {
    type enumeration {
      enum proto-type-unknown {
        value 0;
        description "Unknown protocol framing";
      }
      enum proto-type-ethernet {
        value 1;
        description "Ethernet protocol framing";
      }
      enum proto-type-otn {
        value 2;
        description "OTN protocol framing";
      }
    }
    description "Logical protocol";
  }
  typedef Trib-protocol {
    type enumeration {
      enum trib-proto-type-unknown {
        value 0;
        description "Unknown protocol";
      }
      enum trib-proto-type1ge {
        value 1;
        description "1G Ethernet protocol";
      }
      enum trib-proto-type-oc48 {
        value 2;
        description "OC48 protocol";
      }
      enum trib-proto-type-stm16 {
        value 3;
        description "STM 16 protocol";
      }
      enum trib-proto-type10gelan {
        value 4;
        description "10G Ethernet LAN protocol";
      }
      enum trib-proto-type10gewan {
        value 5;
        description "10G Ethernet WAN protocol";
      }
      enum trib-proto-type-oc192 {
        value 6;
        description "OC 192 (9.6GB) port protocol";
      }
      enum trib-proto-type-stm64 {
        value 7;
        description "STM 64 protocol";
      }
      enum trib-proto-type-otu2 {
        value 8;
        description "OTU 2 protocol";
      }
      enum trib-proto-type-otu2e {
        value 9;
        description "OTU 2e protocol";
      }
      enum trib-proto-type-otu1e {
        value 10;
        description "OTU 1e protocol";
      }
      enum trib-proto-type-odu2 {
        value 11;
        description "ODU 2 protocol";
      }
      enum trib-proto-type-odu2e {
        value 12;
        description "ODU 2e protocol";
      }
      enum trib-proto-type40ge {
        value 13;
        description "40G Ethernet port protocol";
      }
      enum trib-proto-type-oc768 {
        value 14;
        description "OC 768 protocol";
      }
      enum trib-proto-type-stm256 {
        value 15;
        description "STM 256 protocol";
      }
      enum trib-proto-type-otu3 {
        value 16;
        description "OTU 3 protocol";
      }
      enum trib-proto-type-odu3 {
        value 17;
        description "ODU 3 protocol";
      }
      enum trib-proto-type100ge {
        value 18;
        description "100G Ethernet protocol";
      }
      enum trib-proto-type100g-mlg {
        value 19;
        description "100G MLG protocol";
      }
      enum trib-proto-type-otu4 {
        value 20;
        description
          "OTU4 signal protocol (112G) for transporting
          100GE signal";
      }
      enum trib-proto-type-otu-cn {
        value 21;
        description "OTU Cn protocol";
      }
      enum trib-proto-type-odu4 {
        value 22;
        description "ODU 4 protocol";
      }
    }
    description "Trib protocol";
  }
  typedef Trib-rate-class {
    type enumeration {
      enum trib-rate1g {
        value 0;
        description "1G tributary signal rate";
      }
      enum trib-rate25g {
        value 1;
        description "2.5G tributary signal rate";
      }
      enum trib-rate10g {
        value 2;
        description "10G tributary signal rate";
      }
      enum trib-rate40g {
        value 3;
        description "40G tributary signal rate";
      }
      enum trib-rate100g {
        value 4;
        description "100G tributary signal rate";
      }
      enum trib-rate-unknown {
        value 5;
        description "Unknown tributary signal rate";
      }
    }
    description "Trib rate class";
  }

  grouping LOGICAL-CHANNEL-ATTR {
    description "LOGICAL CHANNEL ATTR";
    leaf trib-rate-class {
      type Trib-rate-class;
      description "TribRateClass";
    }
    leaf trib-protocol {
      type Trib-protocol;
      description "TribProtocol";
    }
    leaf protocol-type {
      type Logical-protocol;
      description "ProtocolType";
    }
  }

  grouping OPERATIONAL-MODE-ATTRIBUTES {
    description "OPERATIONAL MODE ATTRIBUTES";
    leaf description {
      type string {
        length "0..128";
      }
      description "Description";
    }
    leaf vendor-id {
      type string {
        length "0..64";
      }
      description "VendorId";
    }
  }

  grouping LOGICAL-CHAN-ASSIGNMENT {
    description "LOGICAL CHAN ASSIGNMENT";
    leaf is-logical-link {
      type boolean;
      description "IsLogicalLink";
    }
    leaf logical-channel {
      type uint32;
      description "LogicalChannel";
    }
    leaf optical-channel {
      type string {
        length "0..128";
      }
      description "OpticalChannel";
    }
    leaf allocation {
      type uint32;
      description "Allocation";
    }
  }
}
