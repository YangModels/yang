submodule Cisco-IOS-XR-fib-common-oper-sub1 {

  belongs-to Cisco-IOS-XR-fib-common-oper {
    prefix Cisco-IOS-XR-fib-common-oper;
  }

  /*** LINKAGE (IMPORTS / INCLUDES) ***/

  import ietf-inet-types { prefix "inet"; }

  import ietf-yang-types { prefix "yang"; }

  import Cisco-IOS-XR-types { prefix "xr"; }

  include Cisco-IOS-XR-fib-common-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2016 by Cisco Systems, Inc.
     All rights reserved.";

  revision "2015-11-09" {
    description
      "IOS XR 6.0 revision.";
  }

  typedef Mgmt-fib-mpls-frr-state {
    type enumeration {
      enum partial {
        value 0;
        description "Partial";
      }
      enum active {
        value 1;
        description "Active";
      }
      enum ready {
        value 2;
        description "Ready";
      }
      enum complete {
        value 3;
        description "Complete";
      }
      enum any {
        value 4;
        description "Any";
      }
    }
    description "MPLS FRR entry state";
  }
  typedef Mgmt-fib-mpls-lsp-role {
    type enumeration {
      enum head {
        value 0;
        description "Head";
      }
      enum midpoint {
        value 1;
        description "Midpoint";
      }
    }
    description "MPLS FRR entry role";
  }

  grouping FIB-MPLS-TIMESPEC {
    description "FIB MPLS TIMESPEC";
    leaf seconds {
      type int32;
      units "second";
      description "Seconds part of time valueiin UTC";
    }
    leaf nanoseconds {
      type int32;
      units "nanosecond";
      description "Nanoseconds part of time value";
    }
  }

  grouping FIB-MPLS-FRR-EVENT {
    description "FIB MPLS FRR EVENT";

    container start-time {
      description
        "Time of FRR event processing start, Seconds in
        UTC, and Nano Seconds";
      uses FIB-MPLS-TIMESPEC;
    }
    leaf protected-frr-interface-name {
      type xr:Interface-name;
      description "Interface";
    }
    leaf next-hop {
      type uint32;
      description "Next Hop";
    }
    leaf number-of-rewrites-affected {
      type uint32;
      description "Number of rewrites affected";
    }
    leaf switching-time-nsecs {
      type uint32;
      units "nanosecond";
      description "Time to switch rewrites [nsecs]";
    }
    leaf main-processing {
      type uint32;
      description "Main Processing for FRR";
    }
    leaf fast-bundle-member-down-interface {
      type uint32;
      description "Fast Bundle Member Down Interface";
    }
    leaf frr-event-node-id {
      type xr:Node-id;
      description "Node on which the FRR event happened";
    }
  }

  grouping FIB-MPLS-FWDING-SUMMARY {
    description "FIB MPLS FWDING SUMMARY";
    leaf ipv4-imposition-entries {
      type uint32;
      description "Number of IPv4 imposition entries";
    }
    leaf reserved-label-entries {
      type uint32;
      description "Number of reserved label entries";
    }
    leaf label-switched-entries {
      type uint32;
      description "Number of label swap/disposition entries";
    }
    leaf protected-label-switched-entries {
      type uint32;
      description
        "Number of FRR protected label swap/disposition
        entries";
    }
    leaf deleted-stale-entries {
      type uint32;
      description "Number of delete stale label entries";
    }
    leaf te-head-entries {
      type uint32;
      description "Number of TE tunnel head imposition entries";
    }
    leaf te-frr-head-entries {
      type uint32;
      description "Number of TE FRR tunnel head imposition entries";
    }
    leaf te-frr-interface-entries {
      type uint32;
      description "Number of TE FRR protected interface entries";
    }
    leaf te-frr-next-hop-entries {
      type uint32;
      description "Number of TE FRR protected next-hop entries";
    }
    leaf te-mid-points-entries {
      type uint32;
      description "Number of TE MidPoints forwarding entries";
    }
    leaf te-frr-mid-points-entries {
      type uint32;
      description "Number of TE FRR MidPoints forwarding entries";
    }
    leaf te-internal-entries {
      type uint32;
      description "Number of TE internal forwarding entries";
    }
    leaf te-frr-internal-entries {
      type uint32;
      description "Number of TE internal forwarding entries";
    }
    leaf total-forwarding-updates {
      type uint32;
      description "Total forwarding updates from LSD to LFDs";
    }
    leaf total-forwarding-update-messages {
      type uint32;
      description
        "Total forwarding update messages from LSD to
        LFDs";
    }
    leaf total-p2mp-forwarding-updates {
      type uint32;
      description "Total forwarding updates from MRIB to LFDs";
    }
    leaf total-p2mp-forwarding-added-or-modify-messages {
      type uint32;
      description
        "Total p2mp forwarding add/modify messages from
        MRIB to LFDs";
    }
    leaf total-p2mp-forwarding-delete-messages {
      type uint32;
      description
        "Total p2mp forwarding del messages from MRIB to
        LFDs";
    }
    leaf total-p2mp-forwarding-drop-messages {
      type uint32;
      description
        "Total p2mp forwarding messages dropped from MRIB
        to LFDs";
    }
    leaf total-p2mp-iir-forwarding-drop-messages {
      type uint32;
      description
        "Total IIR triggered p2mp forwarding MRIB
        messages dropped";
    }
    leaf lowest-label {
      type uint32;
      description "Lowest label in use";
    }
    leaf highest-label {
      type uint32;
      description "Highest Label in use";
    }
    leaf ignore-protect {
      type uint32;
      description "Number of TE tunnels treated as non-protected";
    }
    leaf mte-head-entries {
      type uint32;
      description "Number of MTE tunnel head entries";
    }
    leaf mte-ll-entries {
      type uint32;
      description "Number of MTE local entries";
    }
    leaf mte-midpoint-entries {
      type uint32;
      description "Number of MTE midpoint entries";
    }
    leaf num-lsp {
      type uint32;
      description "Number of label switch paths";
    }
    leaf lrpf-entries {
      type uint32;
      description "Number of labels with RPF";
    }
  }

  grouping FIB-MPLS-FRR-DB-MCAST-LEGS {
    description "FIB MPLS FRR DB MCAST LEGS";

    container frr-entry-id {
      description "FRR entry ID";
      uses FIB-MPLS-FRR-DB-ENTRY-GEN-ID;
    }
    leaf tunnel-interface-name {
      type xr:Interface-name;
      description "Tunnel interface";
    }
    leaf input-label {
      type uint32;
      description "Input label";
    }
    leaf outgoing-interface {
      type xr:Interface-name;
      description "Outgoing interface";
    }
    leaf outgoing-label {
      type uint32;
      description "Outgoing label";
    }
    leaf frr-interface-name {
      type xr:Interface-name;
      description "FRR interface";
    }
    leaf frr-label {
      type uint32;
      description "FRR output label";
    }
    leaf entry-frr-state {
      type Mgmt-fib-mpls-frr-state;
      description "MPLS FRR entry state";
    }
    leaf frr-next-hop-ipv4-address {
      type inet:ipv4-address;
      description "Next hop IPv4 address";
    }
    leaf is-mldp-lsp {
      type boolean;
      description "MLDP or P2MP-TE";
    }
  }

  grouping FIB-MPLS-FRR-DB-ENTRY-MID-ID {
    description "FIB MPLS FRR DB ENTRY MID ID";
    leaf source-address {
      type inet:ipv4-address;
      description "Source IPv4 address";
    }
    leaf lspid {
      type uint32;
      description "LSP ID";
    }
    leaf tunnel-id {
      type uint32;
      description "Tunnel ID";
    }
  }

  grouping FIB-MPLS-FRR-DB-ENTRY-HEAD-ID {
    description "FIB MPLS FRR DB ENTRY HEAD ID";
    leaf destination-prefix {
      type inet:ipv4-address;
      description "Destination prefix";
    }
    leaf destination-prefix-length {
      type uint32;
      description "Destination prefix length";
    }
  }

  grouping FIB-MPLS-FRR-DB-ENTRY-GEN-ID {
    description "FIB MPLS FRR DB ENTRY GEN ID";

    container head {
      when "../role = 'head'" {
        description "../Role = 'Head'";
      }
      description "head";
      uses FIB-MPLS-FRR-DB-ENTRY-HEAD-ID;
    }

    container midpoint {
      when "../role = 'midpoint'" {
        description "../Role = 'Midpoint'";
      }
      description "midpoint";
      uses FIB-MPLS-FRR-DB-ENTRY-MID-ID;
    }
    leaf role {
      type Mgmt-fib-mpls-lsp-role;
      description "Role";
    }
  }

  grouping FIB-MPLS-FRR-DB-ENTRY {
    description "FIB MPLS FRR DB ENTRY";

    container frr-entry-id {
      description "FRR entry ID";
      uses FIB-MPLS-FRR-DB-ENTRY-GEN-ID;
    }
    leaf tunnel-interface-name {
      type xr:Interface-name;
      description "Tunnel interface";
    }
    leaf input-label {
      type uint32;
      description "Input label";
    }
    leaf outgoing-interface {
      type xr:Interface-name;
      description "Outgoing interface";
    }
    leaf outgoing-label {
      type uint32;
      description "Outgoing label";
    }
    leaf frr-interface-name {
      type xr:Interface-name;
      description "FRR interface";
    }
    leaf frr-label {
      type uint32;
      description "FRR output label";
    }
    leaf entry-frr-state {
      type Mgmt-fib-mpls-frr-state;
      description "MPLS FRR entry state";
    }
    leaf frr-next-hop-ipv4-address {
      type inet:ipv4-address;
      description "Next hop IPv4 address";
    }
    leaf is-mldp-lsp {
      type boolean;
      description "MLDP or P2MP-TE";
    }
    leaf is-multicast-tunnel {
      type boolean;
      description "Multicast tunnel";
    }
    leaf multicast-tunnel-legs {
      type uint32;
      description "Number of legs in MCAST tunnel";
    }

    list multicast-leg {
      description "MCAST legs";
      uses FIB-MPLS-FRR-DB-MCAST-LEGS;
    }
  }

  grouping FIB-MPLS-FRR-DB-SUM {
    description "FIB MPLS FRR DB SUM";
    leaf active {
      type uint32;
      description "Number of FRR rewrites in Active state";
    }
    leaf ready {
      type uint32;
      description "Number of FRR rewrites in Ready state";
    }
    leaf partial {
      type uint32;
      description "Number of FRR rewrites in Partial state";
    }
    leaf other {
      type uint32;
      description "Number of FRR rewrites in an unrecognized state";
    }
  }

  grouping FIB-MPLS-SH-TUN-INFO {
    description "Information about TE-head tunnel LI";
    leaf tunnel-interface-name {
      type xr:Interface-name;
      description "Tunnel interface";
    }
    leaf tunnel-local-label {
      type uint32;
      description "Tunnel Local label";
    }
    leaf tunnel-fwd-class {
      type uint8;
      description "Tunnel Forward Class";
    }
    leaf tunnel-load-metric {
      type uint8;
      description " Tunnel Load Metric";
    }
    leaf tunnel-is-srte {
      type boolean;
      description "Is Tunnel SRTE";
    }
    leaf tunnel-resolution-incomplete {
      type boolean;
      description "Tunnel head resolution is incomplete";
    }
    leaf tunnel-resolution-inconsistent {
      type boolean;
      description
        "Tunnel head resolition is inconsitent b/w TEhead
        and Local label";
    }
    leaf tunnel-is-programmed-to-drop {
      type boolean;
      description "Is Tunnel programmed as drop";
    }
    leaf tli-type {
      type uint32;
      description "Th tunnel LI type";
    }
    leaf tli-pointer {
      type uint32;
      description "The pointer to the Tun LI object";
    }
    leaf tli-reference-count {
      type uint32;
      description "The Tunnel LI object refcounter";
    }
    leaf tli-flags {
      type uint32;
      description "Tunnel LI flags";
    }
    leaf tli-flags-extended {
      type uint32;
      description "Tunnel LI extended flags";
    }
  }

  grouping FIB-MPLS-SH-TEHEAD {
    description "Information about TE tunnel head";

    container tunnel-info {
      description "Tunnel head information";
      uses FIB-MPLS-SH-TUN-INFO;
    }

    container fwdg {
      description "Tunnel forwarding information";
      uses FIB-MPLS-SH-LEAF;
    }
  }

  grouping FIB-MPLS-MCAST-INFO {
    description "Information for mpls multicast entries";
    leaf multicast-mol-base-flags {
      type uint32;
      description "MOL base flags";
    }
    leaf multicast-mol-flags {
      type uint16;
      description "MOL flags";
    }
    leaf multicast-mol-reference-count {
      type uint16;
      description "MOL reference count";
    }
    leaf multicast-tunnel-interface-name {
      type xr:Interface-name;
      description "multicast mpls tunnel ifh";
    }
    leaf multicast-tunnel-id {
      type uint32;
      description
        "multicast mpls P2MP-TE tunnel id or MLDP Tunnel
        LSMID on all nodes";
    }
    leaf multicast-tunnel-next-hop-information {
      type uint32;
      description "multicast nhinfo for p2mp TE Head";
    }
    leaf multicast-tunnel-lspvif {
      type uint32;
      description "multicast LSPVIF for MLDP Tunnels";
    }
    leaf multicast-mpls-output-paths {
      type uint16;
      description "num multicast mpls output paths ";
    }
    leaf multicast-mpls-protocol-output-paths {
      type uint16;
      description "num multicast mpls prot output paths ";
    }
    leaf multicast-mpls-local-output-paths {
      type uint16;
      description "num multicast mpls local output paths";
    }
    leaf multicast-rpf-id {
      type uint32;
      description "The multicast RPF-ID ";
    }
    leaf multicast-encap-id {
      type uint32;
      description "The multicast ENCAP-ID ";
    }
    leaf dependent-tunnel-local-label {
      type uint32;
      description "The Local Label of a dependant Tunnel ";
    }
    leaf dependent-tunnel-ifh {
      type uint32;
      description "The interface handle of a dependent tunnel ";
    }
    leaf multicast-v4-table-id {
      type uint32;
      description "The multicast IPv4 Table id";
    }
    leaf multicast-v6-table-id {
      type uint32;
      description "The multicast IPv6 Table id";
    }
    leaf label-bridge-domain-id {
      type uint32;
      description "Bridge domain-ID";
    }
    leaf label-xid {
      type uint32;
      description "The XID of PW";
    }
    leaf label-shg-id {
      type uint32;
      description "The SHG-ID of PW";
    }
    leaf multicast-platform-data-length {
      type uint8;
      description "The multicast platform data len";
    }
    leaf multicast-platform-data {
      type yang:hex-string;
      description "The multicast platform data";
    }
  }

  grouping FIB-MPLS-LDI-INFO {
    description
      "Detailed load sharing information for mpls table
      entries";
    leaf ldi-hardware-information {
      type yang:hex-string;
      description "Hardware info";
    }
  }

  grouping FIB-MPLS-MCAST-MPI-INFO {
    description "FIB MPLS MCAST MPI INFO";
    leaf my-node-id {
      type uint32;
      description "my node id";
    }
    leaf flags {
      type uint32;
      description "flags";
    }
    leaf via-label {
      type uint32;
      description "via label";
    }
    leaf mcast-id {
      type uint32;
      description "mcast id";
    }
    leaf pri-tos-mask {
      type uint32;
      description "pri tos mask";
    }
    leaf bk-tos-mask {
      type uint32;
      description "bk tos mask";
    }
    leaf pd-ts-ms {
      type uint64;
      description "pd ts ms";
    }
    leaf primary-is-local {
      type boolean;
      description "primary is local";
    }
    leaf backup-is-local {
      type boolean;
      description "backup is local";
    }
    leaf-list if-node-id {
      type uint32;
      max-elements "10";
      description "if node id";
    }
    leaf-list bkup-if-node-id {
      type uint32;
      max-elements "10";
      description "bkup if node id";
    }
    leaf-list if-hdl {
      type uint32;
      max-elements "10";
      description "if hdl";
    }
    leaf-list bkup-if-hdl {
      type uint32;
      max-elements "10";
      description "bkup if hdl";
    }
  }

  grouping FIB-MPLS-FWD-INFO {
    description "FIB MPLS FWD INFO";
    leaf l3-mtu {
      type uint32;
      description "L3 MTU";
    }
    leaf total-encapsulation-size {
      type uint32;
      description "Total encapsulation size: L2 + MPLS";
    }
    leaf mac-size {
      type uint32;
      description "Length of L2 encapsulation";
    }
    leaf transmit-number-of-packets-switched {
      type uint64;
      description "Number of packets switched";
    }
    leaf transmit-number-of-bytes-switched {
      type uint64;
      units "byte";
      description "Number of Bytes switched";
    }
    leaf transmit-number-of-tm-packets-switched {
      type uint64;
      description "Number of Traffic-Matrix packets switched";
    }
    leaf transmit-number-of-tm-bytes-switched {
      type uint64;
      units "byte";
      description "Number of Traffic-Matrix Bytes switched";
    }
    leaf status {
      type int32;
      description "Status";
    }
    leaf next-hop-interface-name {
      type xr:Interface-name;
      description "Next hop interface name";
    }
    leaf next-hop-protocol {
      type uint32;
      description "The address family (V4/V6) ";
    }
    leaf next-hop-string {
      type yang:hex-string;
      description "Next hop address in string format";
    }
    leaf nh-id {
      type uint32;
      description "Nexthop Id";
    }
    leaf version-priority-valid {
      type boolean;
      description
        "Indicates if the version/priority fields are
        valid";
    }
    leaf route-download-version {
      type uint64;
      description "Version of the route-download for the label";
    }
    leaf route-download-priority {
      type uint32;
      description "Priority at which the label was downloaded";
    }
    leaf-list label-stack {
      type uint32;
      description "Label stack";
    }
  }

  grouping FIB-MPLS-ADJ-INFO {
    description "FIB MPLS ADJ INFO";

    list fib-mpls-adj-info {
      description "fib mpls adj info";

      container label-information-detail {
        description "Detail label info";
        uses FIB-MPLS-FWD-INFO;
      }

      container mpi-info {
        description "The MPI info";
        uses FIB-MPLS-MCAST-MPI-INFO;
      }
      leaf label-information-type {
        type uint32;
        description "Label-Info type";
      }
      leaf local-label {
        type uint32;
        description "Local label";
      }
      leaf outgoing-label {
        type uint32;
        description "Outgoing label";
      }
      leaf frr-nh-ptr {
        type uint32;
        description "FRR next-hop object pointer";
      }
      leaf mpls-adjacency-flags {
        type uint32;
        description "MPLS Adjacency flags";
      }
      leaf path-flags {
        type uint32;
        description "PL path flags";
      }
      leaf path-index {
        type uint8;
        description "path index";
      }
      leaf backup-path-index {
        type uint8;
        description "backup path index";
      }
      leaf nhid {
        type uint32;
        description "Path's NH Id";
      }
      leaf weight {
        type uint32;
        description "Weight or load metric";
      }
      leaf app-id {
        type uint16;
        description "App ID";
      }
      leaf tunnel-id-present {
        type boolean;
        description "Tunnel id present?";
      }
      leaf outgoing-interface {
        type uint32;
        description "Outgoing interface";
      }
      leaf outgoing-physical-interface {
        type uint32;
        description "Outgoing Physical Interface";
      }
      leaf tunnel-interface-name {
        type xr:Interface-name;
        description "Tunnel Interface";
      }
      leaf label-information-path-index {
        type uint32;
        description "LabelInformationPathIndex";
      }
      leaf label-information-encap-id {
        type uint64;
        description "Encap ID";
      }
      leaf label-information-next-hop-type {
        type uint32;
        description "NHinfo Type";
      }
      leaf label-information-next-hop-table-id {
        type uint32;
        description "NHinfo Table ID";
      }
      leaf label-information-next-hop-protocol {
        type uint32;
        description "The address family (v4/v6) ";
      }
      leaf sli-from-ldi {
        type boolean;
        description "Path learnt the LDI/used for Forwarding?";
      }
      leaf label-information-next-hop-string {
        type yang:hex-string;
        description "Next hop address in string format";
      }
      leaf label-information-route-version {
        type uint64;
        description "The version of the route";
      }
      leaf label-information-time-in-milli-seconds {
        type uint64;
        description "The time of last update in msec";
      }
      leaf label-bridge-domain-id {
        type uint32;
        description "Bridge domain-ID";
      }
      leaf label-xid {
        type uint32;
        description "The XID of Xconnect";
      }
      leaf label-pw-xid {
        type uint32;
        description "The XID of PW";
      }
      leaf label-shg-id {
        type uint32;
        description "The SHG-ID of PW";
      }
      leaf pwhev-ctype {
        type uint32;
        description "PW-HE VC type";
      }
      leaf pwhecw-enabled {
        type boolean;
        description "PW-HE CW setting";
      }
      leaf pwhe-interface {
        type xr:Interface-name;
        description "PW-HE interface";
      }
      leaf pq-label {
        type uint32;
        description "PQ label";
      }
      leaf pq-flags {
        type uint32;
        description "PQ flags";
      }
      leaf li-pointer {
        type uint32;
        description "The pointer to the LI object";
      }
      leaf li-reference-count {
        type uint32;
        description "The LI object refcounter";
      }
      leaf is-srte {
        type boolean;
        description "Is SRTE?";
      }
      leaf is-pure-backup {
        type boolean;
        description "Is pure backup path?";
      }
      leaf is-frr-active {
        type boolean;
        description "Is FRR active?";
      }
    }
  }

  grouping FIB-MPLS-SH-LEAF {
    description "Information about label leaf";

    container label-information {
      description "Label-info in FIB leaf";
      uses FIB-MPLS-ADJ-INFO;
    }

    container ldi-information {
      description "LDI-info in FIB leaf";
      uses FIB-MPLS-LDI-INFO;
    }

    container multicast-information {
      description "The multicast info";
      uses FIB-MPLS-MCAST-INFO;
    }

    container rpf {
      description "RPF info";
      uses FIB-MPLS-LEAF-RPF;
    }
    leaf leaf-local-label {
      type uint32;
      description "Local label";
    }
    leaf eos-bit {
      type uint32;
      description "EOS bit";
    }
    leaf hardware-information {
      type yang:hex-string;
      description "Hardware info";
    }
    leaf leaf-reference-count {
      type uint32;
      description "Number of references to the leaf";
    }
    leaf leaf-ptr {
      type uint32;
      description "The Leaf pointer";
    }
    leaf leaf-flags {
      type uint32;
      description "The leaf flags";
    }
    leaf path-list-reference-count {
      type uint32;
      description "Number of references to the pathlist";
    }
    leaf path-list-ldi-mask {
      type uint32;
      description "The pathlist ldi mask";
    }
    leaf path-list-flags {
      type uint32;
      description "The pathlist flags";
    }
    leaf path-list-pointer {
      type uint32;
      description "The pointer to the pathlist";
    }
    leaf ldi-reference-count {
      type uint32;
      description "Number of references to the LDI";
    }
    leaf ldi-flags {
      type uint32;
      description "The LDI flags";
    }
    leaf ldi-type {
      type uint32;
      description "The LDI type";
    }
    leaf ldi-pointer {
      type uint32;
      description "The pointer to the LDI";
    }
    leaf lw-ldi-type {
      type uint32;
      description "The LW-LDI type";
    }
    leaf lw-ldi-pointer {
      type uint32;
      description "The pointer to the LW-LDI";
    }
    leaf lw-ldi-reference-count {
      type uint32;
      description "The LW-LDI refcounter";
    }
    leaf lw-shared-ldi-pointer {
      type uint32;
      description "The pointer to the shared LDI in LW-LDI";
    }
    leaf lspa-flags {
      type uint32;
      description "The LSPA flags";
    }
    leaf afi-table-id {
      type uint32;
      description "The AFI table ID";
    }
    leaf multicast-label {
      type boolean;
      description "The unicast or multicast label";
    }
    leaf leaf-time-in-milli-seconds {
      type uint64;
      description "The time of last update in msec";
    }
    leaf pwhe-interface-list-id {
      type uint16;
      description
        "Interface list associated with PW-HE VC
        imposition label";
    }
    leaf pwhe-interface-list-ptr {
      type uint32;
      description "Interface list ptr";
    }
    leaf pl-time-of-last-update-in-msec {
      type uint64;
      description "The time of last update for PL in msec";
    }
    leaf ldi-time-of-last-update-in-msec {
      type uint64;
      description "The time of last update for LDI in msec";
    }
    leaf lwldi-time-of-last-update-in-msec {
      type uint64;
      description "The time of last update for LW-LDI in msec";
    }
    leaf lspa-time-of-last-update-in-msec {
      type uint64;
      description "The time of last update for LSPA in msec";
    }
    leaf pl-time-stamp-type {
      type uint32;
      description "The type of time-stamp on PL";
    }
  }
}
