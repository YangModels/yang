module Cisco-IOS-XR-traceroute-act {
  namespace "http://cisco.com/ns/yang/Cisco-IOS-XR-traceroute-act";
  prefix traceroute-act;

  include Cisco-IOS-XR-ipv4-traceroute-act;
  include Cisco-IOS-XR-ipv6-traceroute-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ping action package configuration.
     
     Copyright (c) 2016, 2018 by Cisco Systems, Inc.
     All rights reserved.";

  revision 2018-10-01 {
    description
      "IOS XR 6.2.1 revision.";
  }

  rpc traceroute {
    description
      "Trace route to destination";
    input {
      container destination {
        presence "traceroute input";
        uses TRACEROUTE-OPTIONS;
        uses IPV6-SPECIFIC-OPTIONS;
      }
      container ipv4 {
        presence "ipv4 traceroute input";
        uses TRACEROUTE-OPTIONS;
      }
      container ipv6 {
        presence "ipv6 traceroute input";
        uses IPV6-TRACEROUTE-INPUT;
      }
    }
    output {
      container traceroute-response {
        container ipv4 {
          presence "ipv4 traceroute output";
          uses TRACEROUTE-OUTPUT;
        }
        container ipv6 {
          presence "ipv6 traceroute output";
          uses TRACEROUTE-OUTPUT;
        }
      }
    }
  }
}
