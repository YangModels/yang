module slice_control {
  namespace "http://www.cisco.com/calvados/calvados_controllers/slice_control";
  prefix slice_control;
  import cxp_driver {
    prefix cxp_driver;
  }
  import gearbox_driver {
    prefix gearbox_driver;
  }
  import gearbox2_driver {
    prefix gearbox2_driver;
  }
  import dual_gearbox_driver {
    prefix dual_gearbox_driver;
  }
  import cpak_driver {
    prefix cpak_driver;
  }
  import modena_driver {
    prefix modena_driver;
  }
  import slice_control_types {
    prefix slice-control-types;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2018-04-09 {
    description
      "Required changes for ConfD 6.4.5";
  }


  grouping clocking_device_info {
    list clocking_devices {
      key "pll_device_id";
      leaf pll_device_id {
        type slice-control-types:pll_device_id_type;
      }
      leaf is_data_available {
        type boolean;
        default "false";
      }
      list pll {
        key "pll_id";
        leaf pll_id {
          type slice-control-types:pll_id_type;
        }
        leaf clocking_bus {
          type string;
        }
        leaf clocking_mode {
          type string;
        }
        leaf clocking_dev_addr {
          type string;
        }
        leaf clocking_i2c_regs {
          type string;
        }
      }
    }
  }

  grouping current_sensor_info {
    list curr_sensor {
      key "sensor_id";
      leaf sensor_id {
        type slice-control-types:curr_sensor_id_type;
      }
      leaf curr_sensor_id {
        type string;
      }
      leaf curr_dev_addr {
        type uint32;
      }
      leaf curr_poll_intvl {
        type uint32;
      }
      leaf curr_delta {
        type uint32;
      }
      leaf curr_raw_data {
        type uint32;
      }
      leaf curr_sensor_value {
        type int32;
      }
      leaf curr_unit {
        type int32;
      }
      leaf curr_last_value {
        type uint32;
      }
      leaf curr_send_update {
        type boolean;
        default "false";
      }
      leaf curr_num_1sec_intervals {
        type int32;
      }
      leaf is_data_available {
        type boolean;
        default "false";
      }
    }
  }

  grouping eeprom_info {
    list eeprom {
      key "eeprom_id";
      leaf eeprom_id {
        type slice-control-types:eeprom_id_type;
      }
      leaf eeprom_type {
        type string;
      }
      leaf eeprom_bus {
        type string;
      }
      leaf eeprom_i2c_regs {
        type string;
      }
      leaf is_data_available {
        type boolean;
        default "false";
      }
    }
  }

  grouping optics_summary_info {
    list optics_summary {
      key "optics_id";
      leaf optics_id {
        type slice-control-types:optics_id_type;
      }
      leaf optics_type {
        type string;
      }
      leaf optics_bus {
        type string;
      }
      leaf optics_i2c_regs {
        type string;
      }
      leaf is_data_available {
        type boolean;
        default "false";
      }
    }
  }

  grouping optics_info {
    list optics {
      key "optics_id";
      leaf optics_id {
        type slice-control-types:optics_id_type;
      }
      uses cxp_driver:cxp_data_show;
      uses cxp_driver:status_error_tx_data_show;
      uses cxp_driver:status_error_rx_data_show;
      uses cxp_driver:equalization_tx_data_show;
      uses cxp_driver:coefficients_rx_data_show;
    }
  }

  grouping phy_info {
    list phy {
      key "phy_id";
      leaf phy_id {
        type slice-control-types:phy_id_type;
      }
      leaf phy_type {
        type string;
      }
      leaf phy_bus {
        type string;
      }
      leaf phy_i2c_regs {
        type string;
      }
      leaf is_data_available {
        type boolean;
        default "false";
      }
    }
  }

  grouping temp_sensor_info {
    list temp_sensor {
      key "sensor_id";
      leaf sensor_id {
        type slice-control-types:temp_sensor_id_type;
      }
      leaf temp_sensor_id {
        type string;
      }
      leaf temp_dev_addr {
        type uint32;
      }
      leaf temp_poll_intvl {
        type uint32;
      }
      leaf temp_delta {
        type uint32;
      }
      leaf temp_raw_data {
        type uint32;
      }
      leaf temp_sensor_value {
        type int32;
      }
      leaf temp_unit {
        type int32;
      }
      leaf temp_last_value {
        type uint32;
      }
      leaf temp_send_update {
        type boolean;
        default "false";
      }
      leaf temp_num_1sec_intervals {
        type int32;
      }
      leaf is_data_available {
        type boolean;
        default "false";
      }
    }
  }

  grouping volt_sensor_info {
    list volt_sensor {
      key "sensor_id";
      leaf sensor_id {
        type slice-control-types:volt_sensor_id_type;
      }
      leaf volt_sensor_id {
        type string;
      }
      leaf volt_dev_addr {
        type uint32;
      }
      leaf volt_poll_intvl {
        type uint32;
      }
      leaf volt_delta {
        type uint32;
      }
      leaf volt_raw_data {
        type uint32;
      }
      leaf volt_sensor_value {
        type int32;
      }
      leaf volt_unit {
        type int32;
      }
      leaf volt_last_value {
        type uint32;
      }
      leaf volt_send_update {
        type boolean;
        default "false";
      }
      leaf volt_num_1sec_intervals {
        type int32;
      }
      leaf is_data_available {
        type boolean;
        default "false";
      }
    }
  }

  grouping slice_summary_info {
    container summary {
      list slice_summary {
        key "slice_summ_id";
        leaf slice_summ_id {
          type slice-control-types:slice_id_type;
        }
        leaf slice_id {
          type slice-control-types:slice_id_type;
        }
        leaf num_phy {
          type uint8;
        }
        leaf num_optics {
          type uint8;
        }
        leaf num_eeprom {
          type uint8;
        }
        leaf num_temp_sensors {
          type uint8;
        }
        leaf num_volt_sensors {
          type uint8;
        }
        leaf num_curr_sensors {
          type uint8;
        }
        leaf is_data_available {
          type boolean;
          default "false";
        }
      }
    }
  }

  grouping slice_info {
    list slice {
      key "slice_id";
      leaf slice_id {
        type slice-control-types:slice_id_type;
      }
      uses slice_summary_info;
      uses current_sensor_info;
      uses eeprom_info;
      uses optics_summary_info;
      uses optics_info;
      uses phy_info;
      uses temp_sensor_info;
      uses volt_sensor_info;
      uses gearbox_driver:gearbox_summary_info;
      uses gearbox2_driver:gearbox2_summary_info;
      uses dual_gearbox_driver:dual_gearbox_summary_info;
      uses gearbox_driver:gearbox_data_show;
      uses gearbox2_driver:gearbox2_data_show;
      uses dual_gearbox_driver:dual_gearbox_data_show;
      uses cpak_driver:cpak_data_show;
      uses modena_driver:modena_summary_info;
      uses modena_driver:modena_data_show;
    }
  }

  grouping slice_controller_context_info {
    list slice_context_info {
      key "id";
      leaf id {
        type slice-control-types:slice_controller_id_type;
      }
      leaf slice_controller_id {
        type slice-control-types:slice_controller_id_type;
      }
      leaf slices {
        type uint8;
      }
      leaf oper_state {
        type int32;
      }
      leaf pci_status {
        type int32;
      }
      leaf bao_desc {
        type string;
      }
      leaf handle {
        type string;
      }
      leaf irq {
        type string;
      }
      leaf msi {
        type int32;
      }
      leaf regs {
        type string;
      }
      leaf num_pll {
        type uint8;
      }
      leaf c_hd {
        type string;
      }
      leaf d_hd {
        type string;
      }
      leaf i_hd {
        type string;
      }
      leaf fm_hdl {
        type string;
      }
      leaf trace {
        type string;
      }
      leaf levm {
        type string;
      }
      leaf hw_ver {
        type string;
      }
      leaf pca_ver {
        type string;
      }
      leaf tcam_vendor {
        type string;
      }
      leaf is_data_available {
        type boolean;
        default "false";
      }
    }
  }

  grouping slice_manager_context_info {
    list manager_context_info {
      key "id";
      leaf id {
        type string;
      }
      leaf num_controllers {
        type uint8;
      }
      leaf levm {
        type string;
      }
      leaf ccc_hdl {
        type string;
      }
      leaf trace {
        type string;
      }
      leaf xm_hdl {
        type string;
      }
      leaf fm_hdl {
        type string;
      }
      leaf sim {
        type boolean;
        default "false";
      }
      leaf debug {
        type boolean;
        default "false";
      }
      leaf card_type {
        type uint32;
      }
      leaf slot_num {
        type uint32;
      }
    }
  }

  grouping slice_control_oper {
    container slice_control {
      list location_list {
        key "loc_str";
        leaf loc_str {
          type slice-control-types:slice_location_type;
        }
        leaf description {
          type string;
        }
        uses slice_manager_context_info;
        list FPGA {
          key "slice_controller_id";
          leaf slice_controller_id {
            type slice-control-types:slice_controller_id_type;
          }
          uses slice_controller_context_info;
          uses clocking_device_info;
          uses slice_info;
        }
      }
    }
  }

  grouping slice_control {
    container oper {
      config false;
      uses slice_control_oper;
    }
  }
}
