submodule Cisco-IOS-XR-nto-misc-shprocmem-oper-sub1 {
  belongs-to Cisco-IOS-XR-nto-misc-shprocmem-oper {
    prefix Cisco-IOS-XR-nto-misc-shprocmem-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR nto-misc-shprocmem package operational data.
     
     Copyright (c) 2013-2018 by Cisco Systems, Inc.
     All rights reserved.";

  revision 2015-11-09 {
    description
      "IOS XR 6.0 revision.";
  }

  grouping PROCESSESMEMORY-ENTRY {
    description
      " Per Process Information";
    leaf name {
      type string;
      description
        "Process name";
    }
    leaf jid {
      type uint32;
      description
        "Job ID";
    }
    leaf text-seg-size {
      type uint32;
      description
        "Text Segment Size";
    }
    leaf data-seg-size {
      type uint32;
      description
        "Data Segment Size";
    }
    leaf stack-seg-size {
      type uint32;
      description
        "Stack Segment Size";
    }
    leaf malloc-size {
      type uint32;
      description
        "Malloced Memory Size";
    }
  }
}
