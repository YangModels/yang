module cxp_driver {
  namespace "http://www.cisco.com/panini/calvados/slice_control/optics";
  prefix cxp_driver;
  import cxp_driver_types {
    prefix cxp-driver-types;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2018-04-09 {
    description
      "Required changes for ConfD 6.4.5";
  }


  grouping coefficients_rx_data_show {
    list rx_coefficients {
      key "rx_channel_id";
      leaf rx_channel_id {
        type cxp-driver-types:channel_id_type;
      }
      leaf amplitude {
        type string;
      }
      leaf de_emphasis {
        type string;
      }
      leaf is_data_available {
        type boolean;
        default "false";
      }
    }
  }

  grouping equalization_tx_data_show {
    list tx_coefficients {
      key "tx_channel_id";
      leaf tx_channel_id {
        type cxp-driver-types:channel_id_type;
      }
      leaf equalization {
        type string;
      }
      leaf is_data_available {
        type boolean;
        default "false";
      }
    }
  }

  grouping status_error_rx_data_show {
    list rx_info {
      key "rx_channel_id";
      leaf rx_channel_id {
        type cxp-driver-types:channel_id_type;
      }
      leaf rx_status_flag {
        type string;
      }
      leaf rx_error_flag {
        type string;
      }
      leaf is_data_available {
        type boolean;
        default "false";
      }
    }
  }

  grouping status_error_tx_data_show {
    list tx_info {
      key "tx_channel_id";
      leaf tx_channel_id {
        type cxp-driver-types:channel_id_type;
      }
      leaf tx_status_flag {
        type string;
      }
      leaf tx_error_flag {
        type string;
      }
      leaf is_data_available {
        type boolean;
        default "false";
      }
    }
  }

  grouping cxp_data_show {
    list cxp {
      key "cxp_id";
      leaf cxp_id {
        type cxp-driver-types:cxp_id_type;
      }
      leaf signature {
        type string;
      }
      leaf cxp_port_ready {
        type boolean;
        default "false";
      }
      leaf opaque {
        type string;
      }
      leaf nodeid {
        type string;
      }
      leaf slice {
        type uint32;
      }
      leaf capabilities {
        type string;
      }
      leaf vendor_name {
        type string;
      }
      leaf vendor_part_num {
        type string;
      }
      leaf vendor_rev_num {
        type string;
      }
      leaf vendor_serial_num {
        type string;
      }
      leaf passive {
        type boolean;
        default "false";
      }
      leaf is_data_available {
        type boolean;
        default "false";
      }
    }
  }
}
