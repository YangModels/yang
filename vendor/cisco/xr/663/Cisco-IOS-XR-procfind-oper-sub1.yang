submodule Cisco-IOS-XR-procfind-oper-sub1 {
  belongs-to Cisco-IOS-XR-procfind-oper {
    prefix Cisco-IOS-XR-procfind-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR procfind package operational data.
     
     Copyright (c) 2013-2018 by Cisco Systems, Inc.
     All rights reserved.";

  revision 2015-11-09 {
    description
      "IOS XR 6.0 revision.";
  }

  grouping PROCFIND-PROC {
    description
      "Procfind information on a single running process";
    leaf nodeid {
      type uint32;
      description
        "Node ID";
    }
    leaf nodetype {
      type uint32;
      description
        "Node type";
    }
    leaf pid {
      type int32;
      description
        "Process ID";
    }
    leaf jid {
      type int32;
      description
        "Job ID";
    }
    leaf num-threads {
      type int32;
      description
        "Number of threads";
    }
    leaf name {
      type string;
      description
        "Process name";
    }
  }
}
