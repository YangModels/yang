module Cisco-IOS-XR-prm-hwmod-cfg {
  namespace "http://cisco.com/ns/yang/Cisco-IOS-XR-prm-hwmod-cfg";
  prefix prm-hwmod-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR prm-hwmod package configuration.
     
     This module contains definitions
     for the following management objects:
       hardware-module: HardwareModule
     
     Copyright (c) 2013-2018 by Cisco Systems, Inc.
     All rights reserved.";

  revision 2015-11-09 {
    description
      "IOS XR 6.0 revision.";
  }

  typedef Urpf-config {
    type enumeration {
      enum "disable" {
        value 0;
        description
          "Urpf Disable";
      }
      enum "enable" {
        value 1;
        description
          "Urpf Enable";
      }
    }
    description
      "Urpf config";
  }

  container hardware-module {
    description
      "HardwareModule";
    container loadbalancing {
      description
        "Loadbalance option";
      container bgp3107 {
        description
          "BGP LU";
        container ecmp {
          description
            "ECMP ";
          leaf enable {
            type empty;
            description
              "Enable Option";
          }
        }
      }
    }
    leaf urpf {
      type Urpf-config;
      description
        "Enabled Disabled";
    }
  }
}
