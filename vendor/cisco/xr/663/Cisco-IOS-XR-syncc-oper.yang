module Cisco-IOS-XR-syncc-oper {
  namespace "http://cisco.com/ns/yang/Cisco-IOS-XR-syncc-oper";
  prefix syncc-oper;

  import Cisco-IOS-XR-types {
    prefix xr;
  }
  include Cisco-IOS-XR-syncc-oper-sub1 {
    revision-date 2016-06-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR syncc package operational data.
     
     This module contains definitions
     for the following management objects:
       timing-controller: Timing controller operational data
     
     Copyright (c) 2013-2018 by Cisco Systems, Inc.
     All rights reserved.";

  revision 2016-06-08 {
    description
      "Schema added.";
  }
  revision 2015-11-09 {
    description
      "IOS XR 6.0 revision.";
  }

  container timing-controller {
    config false;
    description
      "Timing controller operational data";
    container nodes {
      description
        "List of nodes applicable to timing controller";
      list node {
        key "node-name";
        description
          "Syncc operational data for a single node";
        container state {
          description
            "Syncc state for a node";
          uses SYNCC-INTERNAL-STATE;
        }
        container clock {
          description
            "Syncc clock information for a node";
          uses SYNCC-CLOCK-SETTING-NEWTBL;
        }
        container timing-source {
          description
            "Syncc timing information for a node";
          uses SYNCC-TIMING-SRC-TBL;
        }
        leaf node-name {
          type xr:Node-id;
          description
            "Node Name";
        }
      }
    }
  }
}
