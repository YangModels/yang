module Cisco-IOS-XR-sysadmin-console {
  namespace "http://www.cisco.com/ns/yang/Cisco-IOS-XR-sysadmin-console";
  prefix calvados_console;

  import Cisco-IOS-XR-sysadmin-sdr-console {
    prefix sdr_mgr;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module defines the top level container for
     all 'console' commands for Sysadmin.
     
     Copyright(c) 2015-2016 by Cisco Systems, Inc.
     All rights reserved.
     
     Copyright (c) 2012-2018 by Cisco Systems, Inc.
     All rights reserved.";

  revision 2017-01-31 {
    description
      "Changed the namespace and module name";
  }

  container console {
    container config {
      config true;
      uses sdr_mgr:console-attach-config-group;
    }
  }
}
