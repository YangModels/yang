module Cisco-IOS-XR-nto-misc-shprocmem-oper {
  namespace "http://cisco.com/ns/yang/Cisco-IOS-XR-nto-misc-shprocmem-oper";
  prefix nto-misc-shprocmem-oper;

  import Cisco-IOS-XR-types {
    prefix xr;
  }
  include Cisco-IOS-XR-nto-misc-shprocmem-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR nto-misc-shprocmem package operational data.
     
     This module contains definitions
     for the following management objects:
       processes-memory: Process statistics
     
     Copyright (c) 2013-2018 by Cisco Systems, Inc.
     All rights reserved.";

  revision 2015-11-09 {
    description
      "IOS XR 6.0 revision.";
  }

  container processes-memory {
    config false;
    description
      "Process statistics";
    container nodes {
      description
        "List of nodes";
      list node {
        key "node-name";
        description
          "Node ID";
        container job-ids {
          description
            "List of jobs";
          list job-id {
            key "job-id";
            description
              "Job Id";
            leaf job-id {
              type uint32;
              description
                "Job Id";
            }
            uses PROCESSESMEMORY-ENTRY;
          }
        }
        leaf node-name {
          type xr:Node-id;
          description
            "Node name";
        }
      }
    }
  }
}
