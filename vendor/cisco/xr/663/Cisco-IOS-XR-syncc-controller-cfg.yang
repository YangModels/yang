module Cisco-IOS-XR-syncc-controller-cfg {
  namespace "http://cisco.com/ns/yang/Cisco-IOS-XR-syncc-controller-cfg";
  prefix syncc-controller-cfg;

  import Cisco-IOS-XR-config-mda-cfg {
    prefix node;
  }
  import Cisco-IOS-XR-freqsync-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR syncc-controller package configuration.
     
     This YANG module augments the
       Cisco-IOS-XR-freqsync-cfg
       Cisco-IOS-XR-config-mda-cfg
     modules with configuration data.
     
     Copyright (c) 2013-2018 by Cisco Systems, Inc.
     All rights reserved.";

  revision 2017-06-22 {
    description
      "Schema added.";
  }
  revision 2015-11-09 {
    description
      "IOS XR 6.0 revision.";
  }

  grouping SYNC-CONTROLLER {
    container sync-controller {
      description
        "sync-controller value";
      container transport-mode {
        description
          "Transport mode";
        container frequency-mode {
          description
            "Frequency Mode";
          container port-mode {
            presence "Indicates a port-mode node is configured.";
            description
              "clock-interface sync <value> location <value>
               port-parameters bits-input 2m -> Option1=0,
               Option2=2, Option3=0, Option4=0, Option5=0
               clock-interface sync <value> location <value>
               port-parameters bits-input 2m -> Option1=0,
               Option2=2, Option3=0, Option4=0, Option5=0
               clock-interface sync <value> location <value>
               port-parameters bits-input 64k-input-only ->
               Option1=0, Option2=3, Option3=0, Option4=0,
               Option5=0 clock-interface sync <value>
               location <value> port-parameters bits-input
               e1 crc-4 sa4 ami -> Option1=0, Option2=1,
               Option3=1, Option4=0, Option5=0
               clock-interface sync <value> location <value>
               port-parameters bits-input e1 crc-4 sa4 hdb3
               -> Option1=0, Option2=1, Option3=1, Option4=0
               , Option5=1 clock-interface sync <value>
               location <value> port-parameters bits-input
               e1 crc-4 sa5 ami -> Option1=0, Option2=1,
               Option3=1, Option4=0, Option5=1
               clock-interface sync <value> location <value>
               port-parameters bits-input e1 crc-4 sa5 hdb3
               -> Option1=0, Option2=1, Option3=1, Option4=1
               , Option5=1 clock-interface sync <value>
               location <value> port-parameters bits-input
               e1 crc-4 sa6 ami -> Option1=0, Option2=1,
               Option3=1, Option4=0, Option5=2
               clock-interface sync <value> location <value>
               port-parameters bits-input e1 crc-4 sa6 hdb3
               -> Option1=0, Option2=1, Option3=1, Option4=1
               , Option5=2 clock-interface sync <value>
               location <value> port-parameters bits-input
               e1 crc-4 sa7 ami -> Option1=0, Option2=1,
               Option3=1, Option4=0, Option5=3
               clock-interface sync <value> location <value>
               port-parameters bits-input e1 crc-4 sa7 hdb3
               -> Option1=0, Option2=1, Option3=1, Option4=1
               , Option5=3 clock-interface sync <value>
               location <value> port-parameters bits-input
               e1 crc-4 sa8 ami -> Option1=0, Option2=1,
               Option3=1, Option4=0, Option5=4
               clock-interface sync <value> location <value>
               port-parameters bits-input e1 crc-4 sa8 hdb3
               -> Option1=0, Option2=1, Option3=1, Option4=1
               , Option5=4 clock-interface sync <value>
               location <value> port-parameters bits-input
               e1 non-crc-4 ami -> Option1=0, Option2=1,
               Option3=0, Option4=0, Option5=0
               clock-interface sync <value> location <value>
               port-parameters bits-input e1 non-crc-4 hdb3
               -> Option1=0, Option2=1, Option3=0, Option4=1
               , Option5=0 clock-interface sync <value>
               location <value> port-parameters bits-input
               t1 d4 ami -> Option1=0, Option2=0, Option3=1,
               Option4=0, Option5=0 clock-interface sync
               <value> location <value> port-parameters
               bits-input t1 d4 b8zs -> Option1=0, Option2=0
               , Option3=1, Option4=1, Option5=0
               clock-interface sync <value> location <value>
               port-parameters bits-input t1 esf ami ->
               Option1=0, Option2=0, Option3=0, Option4=0,
               Option5=0 clock-interface sync <value>
               location <value> port-parameters bits-input
               t1 esf b8zs -> Option1=0, Option2=0,
               Option3=0, Option4=1, Option5=0
               clock-interface sync <value> location <value>
               port-parameters bits-output 2m -> Option1=1 ,
               Option2=2, Option3=0, Option4=0, Option5=0
               clock-interface sync <value> location <value>
               port-parameters bits-output 6m-output-only ->
               Option1=1 , Option2=4, Option3=0 , Option4=0,
               Option5=0 clock-interface sync <value>
               location <value> port-parameters bits-output
               e1 crc-4 sa4 ami -> Option1=1 , Option2=1,
               Option3=1 , Option4=0, Option5=0
               clock-interface sync <value> location <value>
               port-parameters bits-output e1 crc-4 sa4 hdb3
               -> Option1=1 , Option2=1, Option3=1 ,
               Option4=1, Option5=0 clock-interface sync
               <value> location <value> port-parameters
               bits-output e1 crc-4 sa5 ami -> Option1=1 ,
               Option2=1, Option3=1 , Option4=0, Option5=1
               clock-interface sync <value> location <value>
               port-parameters bits-output e1 crc-4 sa5 hdb3
               -> Option1=1 , Option2=1, Option3=1 ,
               Option4=1, Option5=1 clock-interface sync
               <value> location <value> port-parameters
               bits-output e1 crc-4 sa6 ami -> Option1=1 ,
               Option2=1, Option3=1 , Option4=0, Option5=2
               clock-interface sync <value> location <value>
               port-parameters bits-output e1 crc-4 sa6 hdb3
               -> Option1=1 , Option2=1, Option3=1 ,
               Option4=1, Option5=2 clock-interface sync
               <value> location <value> port-parameters
               bits-output e1 crc-4 sa7 ami -> Option1=1 ,
               Option2=1, Option3=1 , Option4=0, Option5=3
               clock-interface sync <value> location <value>
               port-parameters bits-output e1 crc-4 sa7 hdb3
               -> Option1=1 , Option2=1, Option3=1 ,
               Option4=1, Option5=3 clock-interface sync
               <value> location <value> port-parameters
               bits-output e1 crc-4 sa8 ami -> Option1=1 ,
               Option2=1, Option3=1 , Option4=0, Option5=4
               clock-interface sync <value> location <value>
               port-parameters bits-output e1 crc-4 sa8 hdb3
               -> Option1=1 , Option2=1, Option3=1 ,
               Option4=1, Option5=4 clock-interface sync
               <value> location <value> port-parameters
               bits-output e1 non-crc-4 ami -> Option1=1 ,
               Option2=1, Option3=0 , Option4=0, Option5=0
               clock-interface sync <value> location <value>
               port-parameters bits-output e1 non-crc-4 hdb3
               -> Option1=1 , Option2=1, Option3=0 ,
               Option4=1, Option5=0 clock-interface sync
               <value> location <value> port-parameters
               bits-output t1 d4 ami 0 -> Option1=1 ,
               Option2=0, Option3=1 , Option4=0, Option5=0
               clock-interface sync <value> location <value>
               port-parameters bits-output t1 d4 ami 1 ->
               Option1=1 , Option2=0, Option3=1 , Option4=0,
               Option5=1 clock-interface sync <value>
               location <value> port-parameters bits-output
               t1 d4 ami 2 -> Option1=1 , Option2=0,
               Option3=1 , Option4=0, Option5=2
               clock-interface sync <value> location <value>
               port-parameters bits-output t1 d4 ami 3 ->
               Option1=1 , Option2=0, Option3=1 , Option4=0,
               Option5=3 clock-interface sync <value>
               location <value> port-parameters bits-output
               t1 d4 ami 4 -> Option1=1 , Option2=0,
               Option3=1 , Option4=0, Option5=4
               clock-interface sync <value> location <value>
               port-parameters bits-output t1 d4 b8zs 0 ->
               Option1=1 , Option2=0, Option3=1 , Option4=1,
               Option5=0 clock-interface sync <value>
               location <value> port-parameters bits-output
               t1 d4 b8zs 1 -> Option1=1 , Option2=0,
               Option3=1 , Option4=1, Option5=1
               clock-interface sync <value> location <value>
               port-parameters bits-output t1 d4 b8zs 2 ->
               Option1=1 , Option2=0, Option3=1 , Option4=1,
               Option5=2 clock-interface sync <value>
               location <value> port-parameters bits-output
               t1 d4 b8zs 3 -> Option1=1 , Option2=0,
               Option3=1 , Option4=1, Option5=3
               clock-interface sync <value> location <value>
               port-parameters bits-output t1 d4 b8zs 4 ->
               Option1=1 , Option2=0, Option3=1 , Option4=1,
               Option5=4 clock-interface sync <value>
               location <value> port-parameters bits-output
               t1 esf ami 0 -> Option1=1 , Option2=0,
               Option3=0 , Option4=0, Option5=0
               clock-interface sync <value> location <value>
               port-parameters bits-output t1 esf ami 1 ->
               Option1=1 , Option2=0, Option3=0 , Option4=0,
               Option5=1 clock-interface sync <value>
               location <value> port-parameters bits-output
               t1 esf ami 2 -> Option1=1 , Option2=0,
               Option3=0 , Option4=0, Option5=2
               clock-interface sync <value> location <value>
               port-parameters bits-output t1 esf ami 3 ->
               Option1=1 , Option2=0, Option3=0 , Option4=0,
               Option5=3 clock-interface sync <value>
               location <value> port-parameters bits-output
               t1 esf ami 4 -> Option1=1 , Option2=0,
               Option3=0 , Option4=0, Option5=4
               clock-interface sync <value> location <value>
               port-parameters bits-output t1 esf b8zs 0 ->
               Option1=1 , Option2=0, Option3=0 , Option4=1,
               Option5=0 clock-interface sync <value>
               location <value> port-parameters bits-output
               t1 esf b8zs 1 -> Option1=1 , Option2=0,
               Option3=0 , Option4=1, Option5=1
               clock-interface sync <value> location <value>
               port-parameters bits-output t1 esf b8zs 2 ->
               Option1=1 , Option2=0, Option3=0 , Option4=1,
               Option5=2 clock-interface sync <value>
               location <value> port-parameters bits-output
               t1 esf b8zs 3 -> Option1=1 , Option2=0,
               Option3=0 , Option4=1, Option5=3
               clock-interface sync <value> location <value>
               port-parameters bits-output t1 esf b8zs 4 ->
               Option1=1 , Option2=0, Option3=0 , Option4=1,
               Option5=4 clock-interface sync <value>
               location <value> port-parameters
               port-parameters uti -> Option1=2 , Option2=0,
               Option3=0 , Option4=0, Option5=0
               clock-interface sync <value> location <value>
               port-parameters port-parameters gps-input ->
               Option1=3, Option2=0, Option3=0 , Option4=0,
               Option5=0 ";
            leaf option1 {
              type uint32 {
                range "0..3";
              }
              mandatory true;
              description
                "Option value #1";
            }
            leaf option2 {
              type uint32 {
                range "0..10";
              }
              mandatory true;
              description
                "Option value #2";
            }
            leaf option3 {
              type uint32 {
                range "0..10";
              }
              mandatory true;
              description
                "Option value #3";
            }
            leaf option4 {
              type uint32 {
                range "0..10";
              }
              mandatory true;
              description
                "Option value #4";
            }
            leaf option5 {
              type uint32 {
                range "0..4";
              }
              mandatory true;
              description
                "Option value #5";
            }
          }
          leaf shutdown {
            type empty;
            description
              "Disable the SyncE Port";
          }
        }
      }
    }
  }

  augment "/node:active-nodes/node:active-node/a1:clock-interface/a1:clocks/a1:clock" {
    description
      "This augment extends the configuration data of
       'Cisco-IOS-XR-freqsync-cfg'";
    uses SYNC-CONTROLLER;
  }
  augment "/node:preconfigured-nodes/node:preconfigured-node/a1:clock-interface/a1:clocks/a1:clock" {
    description
      "This augment extends the configuration data of
       'Cisco-IOS-XR-freqsync-cfg'";
    uses SYNC-CONTROLLER;
  }
}
