module Cisco-IOS-XR-prm-hwmod-profile-cfg {
  namespace "http://cisco.com/ns/yang/Cisco-IOS-XR-prm-hwmod-profile-cfg";
  prefix prm-hwmod-profile-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR prm-hwmod-profile package configuration.
     
     This module contains definitions
     for the following management objects:
       hardware-module: HardwareModule
     
     Copyright (c) 2013-2018 by Cisco Systems, Inc.
     All rights reserved.";

  revision 2017-12-05 {
    description
      "Implementing Conf Yang Model for profile selection";
  }
  revision 2015-11-09 {
    description
      "IOS XR 6.0 revision.";
  }

  typedef Profile-type-data {
    type enumeration {
      enum "sp" {
        value 1;
        description
          "SP Profile";
      }
      enum "dc" {
        value 2;
        description
          "DC Profile";
      }
    }
    description
      "Profile type data";
  }

  container hardware-module {
    description
      "HardwareModule";
    leaf profile {
      type Profile-type-data;
      description
        "Specify Profile type";
    }
  }
}
