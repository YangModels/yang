module Cisco-IOS-XR-reboot-history-oper {
  namespace "http://cisco.com/ns/yang/Cisco-IOS-XR-reboot-history-oper";
  prefix reboot-history-oper;

  import Cisco-IOS-XR-types {
    prefix xr;
  }
  include Cisco-IOS-XR-reboot-history-oper-sub1 {
    revision-date 2016-10-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR reboot-history package operational data.
     
     This module contains definitions
     for the following management objects:
       reboot-history: Reboot History information
     
     Copyright (c) 2013-2018 by Cisco Systems, Inc.
     All rights reserved.";

  revision 2016-10-04 {
    description
      "Added new schema file.";
  }
  revision 2015-11-09 {
    description
      "IOS XR 6.0 revision.";
  }

  container reboot-history {
    config false;
    description
      "Reboot History information";
    list node {
      key "node-name";
      description
        "Node ID";
      leaf node-name {
        type xr:Node-id;
        description
          "Node name";
      }
      uses HISTORY;
    }
  }
}
