module cpak_driver {
  namespace "http://www.cisco.com/calvados/calvados_controllers/slice_control/cpak";
  prefix cpak_driver;
  import cpak_driver_types {
    prefix cpak-driver-types;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2018-04-09 {
    description
      "Required changes for ConfD 6.4.5";
  }


  grouping cpak_data_show {
    list cpak {
      key "cpak_id";
      leaf cpak_id {
        type cpak-driver-types:cpak_id_type;
      }
      leaf is_data_available {
        type boolean;
        default "false";
      }
      leaf csignature {
        type string;
      }
      leaf cready {
        type boolean;
        default "false";
      }
      leaf cpassive {
        type boolean;
        default "false";
      }
      leaf chw_ver_major {
        type uint8;
      }
      leaf chw_ver_minor {
        type uint8;
      }
      leaf copaque {
        type string;
      }
      leaf cnodeid {
        type string;
      }
      leaf cslice {
        type uint32;
      }
      leaf cport {
        type uint32;
      }
      leaf cprt_addr {
        type uint8;
      }
      leaf cdev_addr {
        type uint8;
      }
      leaf cdev_sel {
        type uint8;
      }
      leaf cupgrade_inprogress {
        type uint8;
      }
      leaf coptics_type {
        type string;
      }
      leaf cctrace_err_hdl {
        type string;
      }
      leaf cctrace_evt_hdl {
        type string;
      }
      leaf cnext {
        type string;
      }
      leaf cparent {
        type string;
      }
      leaf crunning_image {
        type string;
      }
      leaf ccommitted_image {
        type string;
      }
    }
  }
}
