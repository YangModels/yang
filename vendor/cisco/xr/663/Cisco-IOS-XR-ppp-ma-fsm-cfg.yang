module Cisco-IOS-XR-ppp-ma-fsm-cfg {
  namespace "http://cisco.com/ns/yang/Cisco-IOS-XR-ppp-ma-fsm-cfg";
  prefix ppp-ma-fsm-cfg;

  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp-ma-fsm package configuration.
     
     This YANG module augments the
       Cisco-IOS-XR-ifmgr-cfg
     module with configuration data.
     
     Copyright (c) 2013-2018 by Cisco Systems, Inc.
     All rights reserved.";

  revision 2015-11-09 {
    description
      "IOS XR 6.0 revision.";
  }

  augment "/a1:interface-configurations/a1:interface-configuration" {
    description
      "This augment extends the configuration data of
       'Cisco-IOS-XR-ifmgr-cfg'";
    container ppp {
      description
        "Interface PPP configuration data";
      container fsm {
        description
          "PPP FSM configuration data";
        leaf retry-timeout {
          type uint32 {
            range "1..10";
          }
          default "3";
          description
            "This specifies the maximum time to wait for a
             response during PPP negotiation";
        }
        leaf max-unacknowledged-term-requests {
          type uint32 {
            range "2..10";
          }
          default "2";
          description
            "This specifies the maximum number of
             Term-Requests";
        }
        leaf max-consecutive-conf-naks {
          type uint32 {
            range "2..10";
          }
          default "5";
          description
            "This specifies the maximum number of
             consecutive Conf-Naks";
        }
        leaf max-unacknowledged-conf-requests {
          type uint32 {
            range "4..20";
          }
          default "10";
          description
            "This specifies the maximum number of
             unacknowledged Conf-Requests";
        }
      }
    }
  }
}
