submodule Cisco-IOS-XR-icpe-infra-oper-sub1 {
  belongs-to Cisco-IOS-XR-icpe-infra-oper {
    prefix Cisco-IOS-XR-icpe-infra-oper;
  }

  include Cisco-IOS-XR-icpe-infra-oper-sub4 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-infra package operational data.
     
     Copyright (c) 2013-2018 by Cisco Systems, Inc.
     All rights reserved.";

  revision 2015-11-09 {
    description
      "IOS XR 6.0 revision.";
  }

  grouping ICPE-OPER-INSTALL-IMAGE-REF-INFO-TYPE {
    description
      "Install Reference Information";
    leaf reference-name-xr {
      type Xr-yang-string;
      description
        "Reference name";
    }
    leaf-list reference-file {
      type Xr-yang-string;
      description
        "Reference files";
    }
  }
}
