submodule Cisco-IOS-XR-fretta-bcm-dpa-resources-oper-sub1 {
  belongs-to Cisco-IOS-XR-fretta-bcm-dpa-resources-oper {
    prefix Cisco-IOS-XR-fretta-bcm-dpa-resources-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fretta-bcm-dpa-resources package operational data.
     
     Copyright (c) 2013-2018 by Cisco Systems, Inc.
     All rights reserved.";

  revision 2015-11-09 {
    description
      "IOS XR 6.0 revision.";
  }

  grouping DPA-SYSDB-NPU-TABLE-RESOURCE {
    description
      "DPA SYSDB NPU TABLE RESOURCE";
    leaf npu-id {
      type uint32;
      description
        "npu id";
    }
    leaf num-objs {
      type uint32;
      description
        "num objs";
    }
    leaf create-req {
      type uint32;
      description
        "create req";
    }
    leaf create-ok {
      type uint32;
      description
        "create ok";
    }
    leaf delete-req {
      type uint32;
      description
        "delete req";
    }
    leaf delete-ok {
      type uint32;
      description
        "delete ok";
    }
    leaf update-req {
      type uint32;
      description
        "update req";
    }
    leaf update-ok {
      type uint32;
      description
        "update ok";
    }
    leaf get-req {
      type uint32;
      description
        "get req";
    }
    leaf eod-req {
      type uint32;
      description
        "eod req";
    }
    leaf eod-ok {
      type uint32;
      description
        "eod ok";
    }
    leaf err-hw-fail {
      type uint32;
      description
        "err hw fail";
    }
    leaf err-ref-resolve {
      type uint32;
      description
        "err ref resolve";
    }
    leaf err-db-notfound {
      type uint32;
      description
        "err db notfound";
    }
    leaf err-db-exists {
      type uint32;
      description
        "err db exists";
    }
    leaf err-db-nomem {
      type uint32;
      description
        "err db nomem";
    }
    leaf err-id-reserve {
      type uint32;
      description
        "err id reserve";
    }
    leaf err-id-release {
      type uint32;
      description
        "err id release";
    }
    leaf err-id-update {
      type uint32;
      description
        "err id update";
    }
  }

  grouping DPA-SYSDB-TABLE-RESOURCE {
    description
      "DPA SYSDB TABLE RESOURCE";
    leaf sysdb-avail-npu-mask {
      type uint64;
      description
        "sysdb avail npu mask";
    }
    leaf table-id {
      type uint32;
      description
        "table id";
    }
    leaf name {
      type string {
        length "0..64";
      }
      description
        "name";
    }
    leaf is-global {
      type boolean;
      description
        "is global";
    }
    leaf num-npus {
      type uint32;
      description
        "num npus";
    }
    leaf table-specific-list {
      type string;
      description
        "table specific list";
    }
    list npu-tblr {
      description
        "npu tblr";
      uses DPA-SYSDB-NPU-TABLE-RESOURCE;
    }
  }
}
